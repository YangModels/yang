submodule Cisco-IOS-XR-ipv6-ospfv3-oper-sub1 {

  belongs-to Cisco-IOS-XR-ipv6-ospfv3-oper {
    prefix Cisco-IOS-XR-ipv6-ospfv3-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-ospfv3 package operational data.

     Copyright (c) 2013-2015 by Cisco Systems, Inc.
     All rights reserved.";

  revision "2015-11-09" {
    description
      "IOS XR 6.0 revision.";
  }

  typedef Ospfv3-graceful-shutdown-state {
    type enumeration {
      enum init {
        value 0;
        description "Init";
      }
      enum normal {
        value 1;
        description "Normal";
      }
      enum flushing {
        value 2;
        description "Flushing";
      }
      enum empty-hellos {
        value 3;
        description "Empty Hellos";
      }
      enum quiet {
        value 4;
        description "Quiet";
      }
    }
    description "Graceful Shutdown state";
  }
  typedef Ipfrr-tbrkr {
    type enumeration {
      enum downstream {
        value 0;
        description "Downsteram";
      }
      enum line-card-disjoint {
        value 1;
        description "LC Disjoint";
      }
      enum backup-metric {
        value 2;
        description "Backup metric";
      }
      enum node-protect {
        value 3;
        description "Node protection";
      }
      enum primary-path {
        value 4;
        description "Primary path";
      }
      enum secondary-path {
        value 5;
        description "Secondary path";
      }
      enum srlg-disjoint {
        value 6;
        description "SRLG disjoint";
      }
      enum tunnel {
        value 7;
        description "Tunnel";
      }
    }
    description "FRR Tiebreakers";
  }
  typedef Stub-router-abr-off-reason {
    type enumeration {
      enum init-delay {
        value 2;
        description
          "Initial delay when stub router mode is
          activated";
      }
      enum no-neighbor {
        value 3;
        description "No neighbor present";
      }
      enum no-full-neighbor {
        value 4;
        description "No neighbor in FULL state present";
      }
      enum new-neighbor {
        value 5;
        description
          "A new neighbor discovered less than 60 seconds
          ago";
      }
      enum full-neighbor {
        value 6;
        description
          "A neighbor transitioned to FULL state less than
          60 seconds ago";
      }
    }
    description "Reason to exiting stub router mode";
  }
  typedef Stub-router-exit-reason {
    type enumeration {
      enum none {
        value 0;
        description "No reason";
      }
      enum bgp {
        value 1;
        description "BGP has converged";
      }
      enum timer {
        value 2;
        description "Stub Router timer has expired";
      }
      enum configuration {
        value 3;
        description "Configuration has changed";
      }
      enum cleared {
        value 4;
        description "Process has been cleared";
      }
      enum override {
        value 5;
        description "Preempted by always";
      }
    }
    description "Reason to exiting stub router mode";
  }
  typedef Stub-router-trigger {
    type enumeration {
      enum on-proc-migration {
        value 0;
        description "Process migration";
      }
      enum on-proc-restart {
        value 1;
        description "Process restart";
      }
      enum on-switchover {
        value 2;
        description "RP switchover";
      }
      enum on-startup {
        value 3;
        description "Router startup";
      }
      enum always {
        value 4;
        description "Always on";
      }
      enum none {
        value 5;
        description "No trigger";
      }
    }
    description "Trigger for entering stub router mode";
  }
  typedef Stub-router-mode {
    type enumeration {
      enum rbit {
        value 0;
        description "Stub Router mode r-bit";
      }
      enum v6bit {
        value 1;
        description "Stub Router mode v6-bit";
      }
      enum max-metric {
        value 2;
        description "Stub Router mode max-metric";
      }
      enum none {
        value 3;
        description "Stub Router not configured";
      }
    }
    description "Stub Router mode";
  }
  typedef Ospfv3-interface {
    type enumeration {
      enum none {
        description "None";
      }
      enum broadcast {
        description "Broadcast";
      }
      enum non-broadcast {
        description "Non broadcast";
      }
      enum point-to-point {
        description "Point To Point";
      }
      enum point-to-multipoint {
        description "Point To Multipoint";
      }
      enum point-to-multipoint-non-broadcast {
        description "Point-To-Multipoint Non broadcast";
      }
      enum virtual-link {
        description "Virtual link";
      }
      enum loopback-interface {
        description "Loopback";
      }
      enum mpls-traffic-engineering {
        description "MPLS traffic engineering";
      }
      enum sham-link {
        description "Sham link";
      }
    }
    description "OSPFv3 neighbor interface types";
  }
  typedef Im-state-enum {
    type enumeration {
      enum im-state-not-ready {
        description "im state not ready";
      }
      enum im-state-admin-down {
        description "im state admin down";
      }
      enum im-state-down {
        description "im state down";
      }
      enum im-state-up {
        description "im state up";
      }
      enum im-state-shutdown {
        description "im state shutdown";
      }
      enum im-state-err-disable {
        description "im state err disable";
      }
      enum im-state-down-immediate {
        description "im state down immediate";
      }
      enum im-state-down-immediate-admin {
        description "im state down immediate admin";
      }
      enum im-state-down-graceful {
        description "im state down graceful";
      }
      enum im-state-begin-shutdown {
        description "im state begin shutdown";
      }
      enum im-state-end-shutdown {
        description "im state end shutdown";
      }
      enum im-state-begin-error-disable {
        description "im state begin error disable";
      }
      enum im-state-end-error-disable {
        description "im state end error disable";
      }
      enum im-state-begin-down-graceful {
        description "im state begin down graceful";
      }
      enum im-state-reset {
        description "im state reset";
      }
      enum im-state-operational {
        description "im state operational";
      }
      enum im-state-not-operational {
        description "im state not operational";
      }
      enum im-state-unknown {
        description "im state unknown";
      }
      enum im-state-last {
        description "im state last";
      }
    }
    description "Im state enum";
  }
  typedef Ospfv3-graceful-restart-reason {
    type enumeration {
      enum grace-reason-unknown {
        description "Grace reason unknown";
      }
      enum grace-reason-software-restart {
        description "Grace reason software restart";
      }
      enum grace-reason-software-upgrade {
        description "Software reload/upgrade, RFC 3623";
      }
      enum grace-reason-switchover {
        description "Switch to redundant control processor";
      }
    }
    description "Reason for router restart";
  }
  typedef Ospfv3-lsa1 {
    type enumeration {
      enum link {
        value 8;
        description "Link LSA";
      }
      enum grace {
        value 11;
        description "Grace LSA";
      }
      enum router {
        value 8193;
        description "Router LSA";
      }
      enum network {
        value 8194;
        description "Network LSA";
      }
      enum inter-area-prefix {
        value 8195;
        description "Inter area prefix LSA";
      }
      enum inter-area-router {
        value 8196;
        description "Inter area router LSA";
      }
      enum mospf {
        value 8198;
        description "MOSPF LSA";
      }
      enum type7-external {
        value 8199;
        description "Type-7 External LSA";
      }
      enum lsa-prefix {
        value 8201;
        description "Prefix LSA";
      }
      enum as-external {
        value 16389;
        description "AS external LSA";
      }
      enum unknown-link {
        value 32768;
        description "Unknown link LSA";
      }
      enum unknown-area {
        value 40960;
        description "Unknown area LSA";
      }
      enum unknown-as {
        value 49152;
        description "Unknown AS LSA";
      }
      enum unknown-type {
        value 57344;
        description "Unknown type LSA";
      }
    }
    description "OSPFv3 LSA types";
  }
  typedef Prefix-priority {
    type enumeration {
      enum critical {
        value 0;
        description "Critical priority";
      }
      enum high {
        value 1;
        description "High priority";
      }
      enum medium {
        value 2;
        description "Medium priority";
      }
      enum low {
        value 3;
        description "Low priority";
      }
    }
    description "Prefix priority";
  }
  typedef Ospfv3-link {
    type enumeration {
      enum link-router {
        value 1;
        description "Router link";
      }
      enum link-trans-net {
        value 2;
        description "Transit network link";
      }
      enum link-virtual-link {
        value 4;
        description "Virutal link";
      }
    }
    description "OSPFV3 Link type";
  }
  typedef Ospf-lsa-sync-state {
    type enumeration {
      enum none {
        description "State not set";
      }
      enum out-of-sync {
        description "LSA out of sync with active";
      }
      enum in-sync {
        description "LSA in sync with active";
      }
      enum nsr-ack-pending {
        description "NSR ack pending for LSA sync";
      }
    }
    description "LSA synchronization states";
  }
  typedef Ospfv3-lsa-info-types {
    type enumeration {
      enum mgmt-lsa-lsasum-type {
        value 0;
        description "Summary information of LSAs";
      }
      enum mgmt-lsa-link-type {
        value 8;
        description "Link LSA";
      }
      enum mgmt-lsa-gr-type {
        value 11;
        description "Grace LSA";
      }
      enum mgmt-lsa-rtr-type {
        value 8193;
        description "Router LSA";
      }
      enum mgmt-lsa-net-type {
        value 8194;
        description "Network LSA";
      }
      enum mgmt-lsa-iapfx-type {
        value 8195;
        description "Inter Area Prefix Summary LSA";
      }
      enum mgmt-lsa-iartr-type {
        value 8196;
        description "Inter Area Router Summay LSA";
      }
      enum mgmt-lsa-nssaext-type {
        value 8199;
        description "NSSA external LSA";
      }
      enum mgmt-lsa-prefix-type {
        value 8201;
        description "Intra Area Prefix LSA";
      }
      enum mgmt-lsa-ext-type {
        value 16389;
        description "Type 5 External LSA";
      }
      enum mgmt-lsa-unk-link-type {
        value 32768;
        description "Opaque Link scope LSA";
      }
      enum mgmt-lsa-unk-area-type {
        value 40960;
        description "Opaque Area scope LSA";
      }
      enum mgmt-lsa-unk-as-type {
        value 49152;
        description "Opaque AS scope LSA";
      }
      enum mgmt-lsa-unk-type {
        value 57344;
        description "Opaque Reserved scope LSA";
      }
    }
    description "OSPFv3 LSA format types";
  }
  typedef Ospfv3-area-range-status {
    type enumeration {
      enum advertise {
        value 1;
        description "Advertise this range";
      }
      enum do-not-advertise {
        value 2;
        description "Do not advertise this range";
      }
    }
    description "Ospfv3 area range status";
  }
  typedef Ospfv3-neighbor-state {
    type enumeration {
      enum neigbhor-down {
        description "Down";
      }
      enum attempt {
        description "Attempting";
      }
      enum init {
        description "Initializing";
      }
      enum two-way {
        description "2 Way";
      }
      enum exstart {
        description "Exstart";
      }
      enum exchange {
        description "Exchange";
      }
      enum loading {
        description "Loading";
      }
      enum full {
        description "Full";
      }
      enum sc-virtual {
        description "SCVirtual";
      }
    }
    description "OSPFv3 neighbor states";
  }
  typedef Ospfv3-interface-state {
    type enumeration {
      enum down {
        description "Down";
      }
      enum loopback {
        description "Loopback";
      }
      enum waiting {
        description "Waiting";
      }
      enum point-to-multipoint {
        description "Point To Multipoint";
      }
      enum point-to-point {
        description "Point To Point";
      }
      enum designated-router {
        description "Designated router";
      }
      enum backup-designated-router {
        description "Backup designated router";
      }
      enum other-designated-router {
        description "Other designated router";
      }
    }
    description "OSPFv3 interface states";
  }
  typedef Ospfv3-border-route {
    type enumeration {
      enum abr {
        value 1;
        description "Area border router";
      }
      enum asbr {
        value 2;
        description "Area system boundary router";
      }
      enum abr-asbr {
        value 3;
        description
          "Area border router and area system boundary
          router";
      }
    }
    description "OSPFv3 border route destination types";
  }
  typedef Ospfv3-default-metric {
    type enumeration {
      enum type-none {
        description "OSPFv3 default metric type None ";
      }
      enum type1 {
        description "OSPFv3 default metric type 1 ";
      }
      enum type2 {
        description "OSPFv3 default metric type 2 ";
      }
    }
    description "OSPFv3 default metric types ";
  }

  grouping OSPF-SH-IPFRR-TOPO-ENTRY {
    description "OSPF_IPFRR Topology Entry";
    leaf node-id {
      xr:xr-xml-map "ospfv3_edm_show:NodeID";
      type inet:ipv4-address;
      description "IPFRR Topology Node ID";
    }
    leaf lsaid {
      xr:xr-xml-map "ospfv3_edm_show:LSAID";
      type uint32;
      description "IPFRR Topology LSA ID";
    }
    leaf distance {
      xr:xr-xml-map "ospfv3_edm_show:Distance";
      type uint32;
      description "IPFRR Topology Distance";
    }
    leaf type4 {
      xr:xr-xml-map "ospfv3_edm_show:Type4";
      type boolean;
      description "IPFRR Topoogy Type-4 entry";
    }
    leaf revision {
      xr:xr-xml-map "ospfv3_edm_show:Revision";
      type uint32;
      description "IPFRR Topology Revision";
    }
    leaf neighbor-sourced {
      xr:xr-xml-map "ospfv3_edm_show:NeighborSourced";
      type boolean;
      description "IPFRR Topology Neighbor Sourced";
    }
    leaf dr {
      xr:xr-xml-map "ospfv3_edm_show:DR";
      type boolean;
      description "IPFRR Topology DR entry";
    }
  }

  grouping OSPFV3-SH-IPFRR-TOPO {
    description "OSPF IPFRR Topology Information";
    leaf ipfrr-topo-area-id {
      xr:xr-xml-map "ospfv3_edm_show:IPFRRTopoAreaID";
      type string {
        length "0..16";
      }
      description
        "Area ID string in decimal or dotted decimal
        format";
    }
    leaf ipfrr-router-id {
      xr:xr-xml-map "ospfv3_edm_show:IPFRRRouterID";
      type inet:ipv4-address;
      description "OSPF Router ID";
    }
    leaf ipfrr-area-revision {
      xr:xr-xml-map "ospfv3_edm_show:IPFRRAreaRevision";
      type uint32;
      description "IPFRR Topology Revision";
    }

    list ipfrr-topo {
      description "IPFRR Topology entries";
      uses OSPF-SH-IPFRR-TOPO-ENTRY;
    }
  }

  grouping OSPFV3-SH-BAD-CHECKSUM {
    description "OSPFv3 Bad Checksum";

    container timestamp {
      description "Packet Timestamp (relative to 1970/1/1 00:00)";
      uses OSPFV3-EDM-TIME;
    }
    leaf received-checksum {
      xr:xr-xml-map "ospfv3_edm_show:ReceivedChecksum";
      type uint16;
      description "Received Checksum";
    }
    leaf computed-checksum {
      xr:xr-xml-map "ospfv3_edm_show:ComputedChecksum";
      type uint16;
      description "Computed Checksum";
    }
    leaf received-data {
      xr:xr-xml-map "ospfv3_edm_show:ReceivedData";
      type yang:hex-string;
      description "Received Hexadecimal Data";
    }
  }

  grouping OSPF-SH-IPFRR-TB {
    description "OSPF IPFRR Tiebreakers";
    leaf tiebreaker-type {
      xr:xr-xml-map "ospfv3_edm_show:TiebreakerType";
      type Ipfrr-tbrkr;
      description "Tiebreaker Type";
    }
    leaf tiebreaker-index {
      xr:xr-xml-map "ospfv3_edm_show:TiebreakerIndex";
      type uint32;
      description "Tiebreaker Index";
    }
  }

  grouping OSPFV3-SH-STUB-ROUTER-TRIGGER {
    description "OSPFv3 stub router trigger information";

    container unset-time {
      description
        "Timestamp (relative to 1970/1/1 00:00) when stub
        router condition was cleared";
      uses OSPFV3-EDM-TIME;
    }

    container start-time {
      description
        "Timestamp (relative to 1970/1/1 00:00) when stub
        router mode was activated";
      uses OSPFV3-EDM-TIME;
    }
    leaf trigger {
      xr:xr-xml-map "ospfv3_edm_show:Trigger";
      type Stub-router-trigger;
      description "Stub Router Trigger type";
    }
    leaf wait-for-bgp {
      xr:xr-xml-map "ospfv3_edm_show:WaitForBGP";
      type boolean;
      description
        "If true, stub router is terminated when BGP
        converges";
    }
    leaf unset-reason {
      xr:xr-xml-map "ospfv3_edm_show:UnsetReason";
      type Stub-router-exit-reason;
      description "Reason for clearing stub router condition";
    }
    leaf time {
      xr:xr-xml-map "ospfv3_edm_show:Time";
      type uint32;
      units "second";
      description "Time (in seconds) to stay in stub router mode";
    }
  }

  grouping OSPFV3-EDM-TIME {
    description "OSPFv3 time stamp";
    leaf second {
      xr:xr-xml-map "ospfv3_edm_show:Second";
      type uint32;
      units "second";
      description "Seconds ";
    }
    leaf nanosecond {
      xr:xr-xml-map "ospfv3_edm_show:Nanosecond";
      type uint32;
      units "nanosecond";
      description "Nano seconds ";
    }
  }

  grouping OSPFV3-SH-STUB-ROUTER {
    description "OSPFv3 Stub Router Information";

    container unset-time {
      description
        "Timestamp (relative to 1970/1/1 00:00) when stub
        router condition was cleared";
      uses OSPFV3-EDM-TIME;
    }

    container start-time {
      description
        "Timestamp (relative to 1970/1/1 00:00) when stub
        router mode was activated";
      uses OSPFV3-EDM-TIME;
    }

    container abr-resume-time {
      description
        "Timestamp (relative to 1970/1/1 00:00) when ABR
        duties were resumed";
      uses OSPFV3-EDM-TIME;
    }
    leaf mode {
      xr:xr-xml-map "ospfv3_edm_show:Mode";
      type Stub-router-mode;
      description "Stub router mode";
    }
    leaf active {
      xr:xr-xml-map "ospfv3_edm_show:Active";
      type boolean;
      description "If true, stub router mode is active";
    }
    leaf remaining-time {
      xr:xr-xml-map "ospfv3_edm_show:RemainingTime";
      type uint32;
      units "second";
      description "Remaining time (in seconds) in stub router mode";
    }
    leaf set-reason {
      xr:xr-xml-map "ospfv3_edm_show:SetReason";
      type Stub-router-trigger;
      description "Reason for entering stub router mode";
    }
    leaf unset-reason {
      xr:xr-xml-map "ospfv3_edm_show:UnsetReason";
      type Stub-router-exit-reason;
      description "Reason for clearing stub router condition";
    }
    leaf include-stub-links {
      xr:xr-xml-map "ospfv3_edm_show:IncludeStubLinks";
      type boolean;
      description
        "If true, advertise maximum metric for stub links";
    }
    leaf summary-lsa-metric {
      xr:xr-xml-map "ospfv3_edm_show:SummaryLSAMetric";
      type uint32;
      description "Metric for summary LSAs in max-metric mode";
    }
    leaf external-lsa-metric {
      xr:xr-xml-map "ospfv3_edm_show:ExternalLSAMetric";
      type uint32;
      description "Metric for external LSAs in max-metric mode";
    }
    leaf abr-off-reason {
      xr:xr-xml-map "ospfv3_edm_show:ABROffReason";
      type Stub-router-abr-off-reason;
      description "Reason for being in ABR off mode";
    }

    list trigger {
      description "Triggers for entering stub router mode";
      uses OSPFV3-SH-STUB-ROUTER-TRIGGER;
    }
  }

  grouping OSPFV3-SH-DOMAIN-ID-ENTRY {
    description "OSPF Domain ID";
    leaf domain-id-type {
      xr:xr-xml-map "ospfv3_edm_show:DomainIDType";
      type uint16;
      description "Domain ID Type";
    }
    leaf domain-id-value {
      xr:xr-xml-map "ospfv3_edm_show:DomainIDValue";
      type yang:hex-string;
      description "Domain ID value";
    }
  }

  grouping OSPFV3-SH-DOMAIN-ID {
    description "OSPF Domain ID entries";

    container primary-domain-id {
      description "Primary Domain ID";
      uses OSPFV3-SH-DOMAIN-ID-ENTRY;
    }

    list secondary-domain-id {
      description "List of secondary domain IDs";
      uses OSPFV3-SH-DOMAIN-ID-ENTRY;
    }
  }

  grouping OSPFV3-EDM-SUMMARY {
    description "OSPFv3 summary";

    container domain-id {
      description "Domain ID information";
      uses OSPFV3-SH-DOMAIN-ID;
    }
    leaf router-id {
      xr:xr-xml-map "ospfv3_edm_show:RouterID";
      type inet:ipv4-address;
      description "Router ID";
    }
    leaf is-role-standby {
      xr:xr-xml-map "ospfv3_edm_show:IsRoleStandby";
      type boolean;
      description "If true, the process is running as stanby role";
    }
    leaf role {
      xr:xr-xml-map "ospfv3_edm_show:Role";
      type uint32;
      description "Role, V1/V2 Active/Standby";
    }
    leaf is-nsr-enabled {
      xr:xr-xml-map "ospfv3_edm_show:IsNSREnabled";
      type boolean;
      description "If true, NSR is enabled";
    }
    leaf is-nsr-switchover-on-restart {
      xr:xr-xml-map "ospfv3_edm_show:IsNSRSwitchoverOnRestart";
      type boolean;
      description
        "Trigger RP Switchover on detectable process
        restart";
    }
    leaf is-router-id-stalled {
      xr:xr-xml-map "ospfv3_edm_show:IsRouterIDStalled";
      type boolean;
      description "Stalled Router ID ";
    }
    leaf is-opaque-capable {
      xr:xr-xml-map "ospfv3_edm_show:IsOpaqueCapable";
      type boolean;
      description "Opaque LSA capable ";
    }
    leaf is-area-border-router {
      xr:xr-xml-map "ospfv3_edm_show:IsAreaBorderRouter";
      type boolean;
      description "If true, is an area border router";
    }
    leaf is-as-border-router {
      xr:xr-xml-map "ospfv3_edm_show:IsASBorderRouter";
      type boolean;
      description "If true, is an AS border router";
    }
    leaf metric {
      xr:xr-xml-map "ospfv3_edm_show:Metric";
      type uint32;
      description "Redistribution metric ";
    }
    leaf is-default-originated {
      xr:xr-xml-map "ospfv3_edm_show:IsDefaultOriginated";
      type boolean;
      description "If true, origin is by default ";
    }
    leaf is-default-always {
      xr:xr-xml-map "ospfv3_edm_show:IsDefaultAlways";
      type boolean;
      description "If true, default always ";
    }
    leaf default-metric {
      xr:xr-xml-map "ospfv3_edm_show:DefaultMetric";
      type uint32;
      description "Default metric ";
    }
    leaf default-metric-type {
      xr:xr-xml-map "ospfv3_edm_show:DefaultMetricType";
      type Ospfv3-default-metric;
      description "Default metric type ";
    }
    leaf default-tag {
      xr:xr-xml-map "ospfv3_edm_show:DefaultTag";
      type uint32;
      description "Default tag ";
    }
    leaf is-default-policy {
      xr:xr-xml-map "ospfv3_edm_show:IsDefaultPolicy";
      type boolean;
      description "If true, is a default policy ";
    }
    leaf default-policy-name {
      xr:xr-xml-map "ospfv3_edm_show:DefaultPolicyName";
      type string;
      description "Default policy name ";
    }
    leaf spf-start-time {
      xr:xr-xml-map "ospfv3_edm_show:SPFStartTime";
      type uint32;
      description "Scheduling delay for SPF (ms)";
    }
    leaf spf-hold-time {
      xr:xr-xml-map "ospfv3_edm_show:SPFHoldTime";
      type uint32;
      description "Minimum delay time between SPF runs (ms)";
    }
    leaf spf-maximum-time {
      xr:xr-xml-map "ospfv3_edm_show:SPFMaximumTime";
      type uint32;
      description "Maximum delay time between SPF runs (ms)";
    }
    leaf lsa-start-time {
      xr:xr-xml-map "ospfv3_edm_show:LSAStartTime";
      type uint32;
      description "Initial LSA throttle delay (ms)";
    }
    leaf lsa-hold-time {
      xr:xr-xml-map "ospfv3_edm_show:LSAHoldTime";
      type uint32;
      description "Second delay before generating next LSA (ms)";
    }
    leaf lsa-maximum-time {
      xr:xr-xml-map "ospfv3_edm_show:LSAMaximumTime";
      type uint32;
      description "Maximum delay before generating an LSA (ms)";
    }
    leaf minimum-lsa-interval {
      xr:xr-xml-map "ospfv3_edm_show:MinimumLSAInterval";
      type uint32;
      description "Minimum time between LSA regeneration (ms)";
    }
    leaf lsa-group-interval {
      xr:xr-xml-map "ospfv3_edm_show:LSAGroupInterval";
      type uint32;
      description "LSA refresh interval (sec)";
    }
    leaf lsa-flood-pacing-interval {
      xr:xr-xml-map "ospfv3_edm_show:LSAFloodPacingInterval";
      type uint32;
      description "LSA flood pacing timer (ms)";
    }
    leaf lsa-retransmission-pacing-interval {
      xr:xr-xml-map "ospfv3_edm_show:LSARetransmissionPacingInterva"+
        "l";
      type uint32;
      description "LSA retransmission pacing timer (ms)";
    }
    leaf as-ls-as {
      xr:xr-xml-map "ospfv3_edm_show:AS_LSAs";
      type uint32;
      description "Number of AS scope LSAs";
    }
    leaf opaque-lsas {
      xr:xr-xml-map "ospfv3_edm_show:OpaqueLSAs";
      type uint32;
      description "Number of opaque LSAs";
    }
    leaf opaque-lsa-checksum {
      xr:xr-xml-map "ospfv3_edm_show:OpaqueLSAChecksum";
      type uint32;
      description "Sum of opaque LSA checksum";
    }
    leaf as-dc-bitless-ls-as {
      xr:xr-xml-map "ospfv3_edm_show:AS_DCBitlessLSAs";
      type uint32;
      description
        "Number of external and AS opaque LSAs with
        demand circut bit not set";
    }
    leaf as-do-not-age-ls-as {
      xr:xr-xml-map "ospfv3_edm_show:ASDoNotAgeLSAs";
      type uint32;
      description
        "Number of external and AS opaque LSAs with do
        not age set ";
    }
    leaf areas {
      xr:xr-xml-map "ospfv3_edm_show:Areas";
      type uint16;
      description "Number of areas";
    }
    leaf normal-areas {
      xr:xr-xml-map "ospfv3_edm_show:NormalAreas";
      type uint16;
      description "Number of normal areas";
    }
    leaf stub-areas {
      xr:xr-xml-map "ospfv3_edm_show:StubAreas";
      type uint16;
      description "Number of stub and total stub areas";
    }
    leaf nssa-areas {
      xr:xr-xml-map "ospfv3_edm_show:NSSAAreas";
      type uint16;
      description "Number of NSSA areas";
    }
    leaf as-lsa-flood-list-length {
      xr:xr-xml-map "ospfv3_edm_show:AS_LSAFloodListLength";
      type uint32;
      description "Length of AS LSAs flood list";
    }
    leaf is-grace-restart-enabled {
      xr:xr-xml-map "ospfv3_edm_show:IsGraceRestartEnabled";
      type boolean;
      description "If true, grace restart is enabled ";
    }
    leaf last-nsf-time {
      xr:xr-xml-map "ospfv3_edm_show:LastNSFTime";
      type uint32;
      description " Length of time since the last NSF (s)";
    }
    leaf grace-resync-time {
      xr:xr-xml-map "ospfv3_edm_show:GraceResyncTime";
      type uint32;
      description "Grace time to resync ";
    }
    leaf maximum-interfaces {
      xr:xr-xml-map "ospfv3_edm_show:MaximumInterfaces";
      type uint32;
      description "Maximum number of interfaces";
    }
    leaf maximum-paths {
      xr:xr-xml-map "ospfv3_edm_show:MaximumPaths";
      type uint32;
      description "Maximum number of paths";
    }
    leaf redistribution-limit {
      xr:xr-xml-map "ospfv3_edm_show:RedistributionLimit";
      type uint32;
      description "The number of redistributed prefixes allowed";
    }
    leaf redistribution-threshold {
      xr:xr-xml-map "ospfv3_edm_show:RedistributionThreshold";
      type uint32;
      description
        "When the number of redistributed prefixes
        reaches this threshold, a warning message is
        issued ";
    }
    leaf is-auto-cost {
      xr:xr-xml-map "ospfv3_edm_show:IsAutoCost";
      type boolean;
      description "If true, auto cost is enabled";
    }
    leaf reference-bandwidth {
      xr:xr-xml-map "ospfv3_edm_show:ReferenceBandwidth";
      type uint32;
      description "Reference Bandwdith";
    }
    leaf context-name {
      xr:xr-xml-map "ospfv3_edm_show:ContextName";
      type string {
        length "0..32";
      }
      description "Context name";
    }
    leaf snmp-trap-enabled {
      xr:xr-xml-map "ospfv3_edm_show:SNMPTrapEnabled";
      type boolean;
      description "If true, snmp trap is enabled";
    }
    leaf graceful-shutdown-state {
      xr:xr-xml-map "ospfv3_edm_show:GracefulShutdownState";
      type Ospfv3-graceful-shutdown-state;
      description "Graceful shutdown state";
    }

    list stub-router {
      description "Stub Router Information";
      uses OSPFV3-SH-STUB-ROUTER;
    }

    list ipfrr-tiebreakers {
      description "IPFRR-Tiebreakers list";
      uses OSPF-SH-IPFRR-TB;
    }
  }

  grouping OSPFV3-EDM-PROTOCOL {
    description "OSPFv3 Protocol Information";
    leaf protocol-router-id {
      xr:xr-xml-map "ospfv3_edm_show:ProtocolRouterID";
      type inet:ipv4-address;
      description "Protocol router ID";
    }
    leaf administrative-distance {
      xr:xr-xml-map "ospfv3_edm_show:AdministrativeDistance";
      type uint32;
      description "Administrative distance";
    }
    leaf administrative-distance-inter-area {
      xr:xr-xml-map "ospfv3_edm_show:AdministrativeDistanceInterAre"+
        "a";
      type uint32;
      description "Administrative Distance for Inter Area routes";
    }
    leaf administrative-distance-external {
      xr:xr-xml-map "ospfv3_edm_show:AdministrativeDistanceExternal";
      type uint32;
      description "Administrative Distance for External routes";
    }
    leaf is-graceful-restart {
      xr:xr-xml-map "ospfv3_edm_show:IsGracefulRestart";
      type boolean;
      description "If true, Graceful restart is enabled ";
    }
    leaf distribute-list-in {
      xr:xr-xml-map "ospfv3_edm_show:DistributeListIn";
      type string;
      description "Distribute List In";
    }
  }

  grouping OSPFV3-EDM-TOPOLOGY-CONNECTED {
    description "OSPFv3 Topology Connected Information";

    container route-topology {
      description "Common Route topology information";
      uses OSPFV3-EDM-TOPOLOGY;
    }

    list route-path {
      description "List of paths to this route";
      uses OSPFV3-EDM-TOP-PATH;
    }
  }

  grouping OSPFV3-EDM-PROTO-INTF {
    description "OSPFv3 Protocol Interface Information";
    leaf interface-name {
      xr:xr-xml-map "ospfv3_edm_show:InterfaceName";
      type xr:Interface-name;
      description "Protocol interface name ";
    }
    leaf distribute-list-in {
      xr:xr-xml-map "ospfv3_edm_show:DistributeListIn";
      type string;
      description "Distribute List In";
    }
  }

  grouping OSPFV3-EDM-PROTO-AREA {
    description "OSPFv3 Protocol Area Information";
    leaf protocol-area-id {
      xr:xr-xml-map "ospfv3_edm_show:ProtocolAreaID";
      type string {
        length "0..16";
      }
      description
        "Area ID string in decimal and dotted-decimal
        format";
    }
    leaf distribute-list-in {
      xr:xr-xml-map "ospfv3_edm_show:DistributeListIn";
      type string;
      description "Distribute List In";
    }

    list protocol-interface {
      description "Interface list";
      uses OSPFV3-EDM-PROTO-INTF;
    }
  }

  grouping OSPFV3-EDM-TOP-SOURCE {
    description "OSPFv3 topology source information";
    leaf route-source-adversting-router {
      xr:xr-xml-map "ospfv3_edm_show:RouteSourceAdverstingRouter";
      type inet:ipv4-address;
      description "Route source of the advertising router ";
    }
    leaf route-source-id {
      xr:xr-xml-map "ospfv3_edm_show:RouteSourceID";
      type inet:ipv4-address;
      description "Route source ID ";
    }
    leaf route-source-lsa-type {
      xr:xr-xml-map "ospfv3_edm_show:RouteSourceLsaType";
      type uint32;
      description "Type of LSA advertising the prefix, see RFC5340";
    }
  }

  grouping OSPFV3-EDM-TOPOLOGY-INTERNAL {
    description "OSPFv3 Topology Internal Information";

    container route-topology {
      description "Common Route topology information";
      uses OSPFV3-EDM-TOPOLOGY;
    }
    leaf route-area-id {
      xr:xr-xml-map "ospfv3_edm_show:RouteAreaID";
      type uint32;
      description "Route area ID ";
    }

    list route-source {
      description "List of topology source information";
      uses OSPFV3-EDM-TOP-SOURCE;
    }

    list route-path {
      description "List of paths to this route";
      uses OSPFV3-EDM-TOP-PATH;
    }
  }

  grouping OSPFV3-EDM-RETRANS {
    description "OSPFv3 retransmission list information";
    leaf retransmission-neighbor-address {
      xr:xr-xml-map "ospfv3_edm_show:RetransmissionNeighborAddress";
      type inet:ipv6-address;
      description "Neighbor IP address";
    }
    leaf is-retransmissionvirtual-link {
      xr:xr-xml-map "ospfv3_edm_show:IsRetransmissionVirtualLink";
      type boolean;
      description "If true, virtual link is retransmitted ";
    }
    leaf retransmissionvirtual-link-id {
      xr:xr-xml-map "ospfv3_edm_show:RetransmissionVirtualLinkID";
      type uint32;
      description "Retransmission virtual link ID ";
    }
    leaf is-retransmission-sham-link {
      xr:xr-xml-map "ospfv3_edm_show:IsRetransmissionShamLink";
      type boolean;
      description "If true, sham link is retransmitted ";
    }
    leaf retransmission-sham-link-id {
      xr:xr-xml-map "ospfv3_edm_show:RetransmissionShamLinkID";
      type uint32;
      description "Retransmission sham link ID ";
    }
    leaf retransmission-timer {
      xr:xr-xml-map "ospfv3_edm_show:RetransmissionTimer";
      type uint32;
      description
        "Amount of time remaining on retransmission timer
        (ms)";
    }
    leaf retransmission-length {
      xr:xr-xml-map "ospfv3_edm_show:RetransmissionLength";
      type uint32;
      description "Retransmission queue length";
    }

    list retransmissionvirtual-link-db {
      description "List of virtual link scope entries ";
      uses OSPFV3-EDM-LSA-SUM;
    }

    list retransmission-area-db {
      description "List of area scope entries";
      uses OSPFV3-EDM-LSA-SUM;
    }

    list retransmission-asdb {
      description "List of AS scope entries";
      uses OSPFV3-EDM-LSA-SUM;
    }
  }

  grouping OSPFV3-EDM-DB-SUMMARY-COUNTERS {
    description "OSPFv3 Database Summary Counters";
    leaf-list lsa {
      xr:xr-xml-map "ospfv3_edm_show:LSA";
      type uint32;
      max-elements "15";
      description "lsa";
    }
    leaf-list deleted-lsa {
      xr:xr-xml-map "ospfv3_edm_show:DeletedLSA";
      type uint32;
      max-elements "15";
      description "deleted lsa";
    }
    leaf-list max-age-lsa {
      xr:xr-xml-map "ospfv3_edm_show:MaxAgeLSA";
      type uint32;
      max-elements "15";
      description "max age lsa";
    }
    leaf-list lsa-checksum {
      xr:xr-xml-map "ospfv3_edm_show:LSAChecksum";
      type uint32;
      max-elements "15";
      description "lsa checksum";
    }
  }

  grouping OSPFV3-EDM-DB-SUMMARY-AREA {
    description "OSPFv3 Area Database Summary";

    container area-database-summary {
      description "Area database summary ";
      uses OSPFV3-EDM-DB-SUMMARY-COUNTERS;
    }
    leaf lsa-area-id {
      xr:xr-xml-map "ospfv3_edm_show:LSAAreaID";
      type string {
        length "0..16";
      }
      description "Area ID in decimal or dotted-decimal format";
    }
  }

  grouping OSPFV3-EDM-DB-SUMMARY {
    description "OSPFv3 Database Summary";

    container database-counters {
      description "OSPFv3 database counters ";
      uses OSPFV3-EDM-DB-SUMMARY-COUNTERS;
    }
    leaf database-router-id {
      xr:xr-xml-map "ospfv3_edm_show:DatabaseRouterID";
      type inet:ipv4-address;
      description "Database router ID ";
    }
    leaf is-opaque-database-capable {
      xr:xr-xml-map "ospfv3_edm_show:IsOpaqueDatabaseCapable";
      type boolean;
      description "If true, opaque database is capable ";
    }

    list area-database {
      description "OSPFv3 Area Database list ";
      uses OSPFV3-EDM-DB-SUMMARY-AREA;
    }
  }

  grouping OSPFV3-EDM-INTF-BRIEF {
    description "OSPFv3 brief interface information";
    leaf interface-address {
      xr:xr-xml-map "ospfv3_edm_show:InterfaceAddress";
      type inet:ipv6-address;
      description "Interface IP address";
    }
    leaf interface-link-cost {
      xr:xr-xml-map "ospfv3_edm_show:InterfaceLinkCost";
      type uint16;
      description "Interface link cost";
    }
    leaf ospf-interface-state {
      xr:xr-xml-map "ospfv3_edm_show:OSPFInterfaceState";
      type Ospfv3-interface-state;
      description "Interface OSPF state";
    }
    leaf interface-neighbors {
      xr:xr-xml-map "ospfv3_edm_show:InterfaceNeighbors";
      type uint16;
      description "Total number of neighbors ";
    }
    leaf interface-adjacent-neighbors {
      xr:xr-xml-map "ospfv3_edm_show:InterfaceAdjacentNeighbors";
      type uint16;
      description "Total number of adjacent neighbors";
    }
    leaf network-type {
      xr:xr-xml-map "ospfv3_edm_show:NetworkType";
      type Ospfv3-interface;
      description "Network type";
    }
  }

  grouping OSPFV3-EDM-NEIGHBOR-BFD {
    description "OSPFv3 Neighbor BFD information";
    leaf bfd-intf-enable-mode {
      xr:xr-xml-map "ospfv3_edm_show:BFDIntfEnableMode";
      type uint32;
      description "BFD enable mode - Default/Strict";
    }
    leaf bfd-status-flag {
      xr:xr-xml-map "ospfv3_edm_show:BFDStatusFlag";
      type uint8;
      description "Status of the BFD Session";
    }
  }

  grouping OSPFV3-EDM-NEIGHBOR-DETAIL {
    description "Detailed OSPFv3 neighbor information";

    container neighbor-retransmission {
      description "Retransmission information with this neighbor";
      uses OSPFV3-EDM-NEIGHBOR-RETRANS;
    }
    leaf state-changes {
      xr:xr-xml-map "ospfv3_edm_show:StateChanges";
      type uint16;
      description "Number of state changes ";
    }
    leaf neighbor-cost {
      xr:xr-xml-map "ospfv3_edm_show:NeighborCost";
      type uint16;
      description "Cost of path to this neighbor ";
    }
    leaf is-neighbor-filtered {
      xr:xr-xml-map "ospfv3_edm_show:IsNeighborFiltered";
      type boolean;
      description "If true, filter outgoing LSAs ";
    }
    leaf neighbor-designated-router-address {
      xr:xr-xml-map "ospfv3_edm_show:NeighborDesignatedRouterAddres"+
        "s";
      type inet:ipv4-address;
      description "Address of designated router";
    }
    leaf neighbor-backup-designated-router-address {
      xr:xr-xml-map "ospfv3_edm_show:NeighborBackupDesignatedRouter"+
        "Address";
      type inet:ipv4-address;
      description "Address of backup designated router";
    }
    leaf interface-type {
      xr:xr-xml-map "ospfv3_edm_show:InterfaceType";
      type Ospfv3-interface;
      description "Interface type";
    }
    leaf poll-interval {
      xr:xr-xml-map "ospfv3_edm_show:PollInterval";
      type uint32;
      description "Poll interval (s)";
    }
    leaf next-poll-interval {
      xr:xr-xml-map "ospfv3_edm_show:NextPollInterval";
      type uint32;
      units "second";
      description
        "For NBMA networks, amount of time remaining in
        seconds before the next poll interval expires
        and Hello is sent (s)";
    }
    leaf neighbor-ignore-timer {
      xr:xr-xml-map "ospfv3_edm_show:NeighborIgnoreTimer";
      type uint32;
      description "Remaining time when ignore timer is running ";
    }
    leaf neighbor-option {
      xr:xr-xml-map "ospfv3_edm_show:NeighborOption";
      type uint32;
      description
        " This is bitmask of neighbor's option field
        received ";
    }
    leaf pending-events {
      xr:xr-xml-map "ospfv3_edm_show:PendingEvents";
      type uint16;
      description "Number of pending events ";
    }
  }

  grouping OSPFV3-EDM-NEIGHBOR {
    description "OSPFv3 neighbor summary information";

    container neighbor-detail {
      description "Detailed OSPFv3 neighbor information ";
      uses OSPFV3-EDM-NEIGHBOR-DETAIL;
    }

    container neighbor-bfd-info {
      description "Neighbor BFD information";
      uses OSPFV3-EDM-NEIGHBOR-BFD;
    }
    leaf neighbor-address-xr {
      xr:xr-xml-map "ospfv3_edm_show:neighbor-address-xr";
      type inet:ipv6-address;
      description "Neighbor IP Address";
    }
    leaf neighbor-interface-id {
      xr:xr-xml-map "ospfv3_edm_show:NeighborInterfaceID";
      type uint32;
      description "Neighbor interface ID";
    }
    leaf neighbor-dr-priority {
      xr:xr-xml-map "ospfv3_edm_show:NeighborDRPriority";
      type uint8;
      description "Neighbor's DR priority";
    }
    leaf neighbor-state {
      xr:xr-xml-map "ospfv3_edm_show:NeighborState";
      type Ospfv3-neighbor-state;
      description "Neighbor's state";
    }
    leaf neighbor-designated-router {
      xr:xr-xml-map "ospfv3_edm_show:NeighborDesignatedRouter";
      type string {
        length "0..9";
      }
      description "Designated router ";
    }
    leaf neighbor-dead-timer {
      xr:xr-xml-map "ospfv3_edm_show:NeighborDeadTimer";
      type uint32;
      units "second";
      description
        "Time until neighbor's dead timer expires
        (seconds)";
    }
    leaf neighbor-up-time {
      xr:xr-xml-map "ospfv3_edm_show:NeighborUpTime";
      type uint32;
      units "second";
      description
        "Amount of time since the adjacency is up
        (seconds)";
    }
    leaf neighbor-virtual-link-id {
      xr:xr-xml-map "ospfv3_edm_show:NeighborVirtualLinkID";
      type uint32;
      description "Neighbor virtual link id ";
    }
    leaf is-neighbor-virtual-link {
      xr:xr-xml-map "ospfv3_edm_show:IsNeighborVirtualLink";
      type boolean;
      description "If true, neighbor is on a virtual link ";
    }
    leaf neighbor-sham-link-id {
      xr:xr-xml-map "ospfv3_edm_show:NeighborShamLinkID";
      type uint32;
      description "Neighbor sham link id ";
    }
    leaf is-neighbor-sham-link {
      xr:xr-xml-map "ospfv3_edm_show:IsNeighborShamLink";
      type boolean;
      description "If true, neighbor is on a sham link ";
    }
  }

  grouping OSPFV3-EDM-ROUTE-SUM {
    description "OSPFv3 route summary information";
    leaf route-id {
      xr:xr-xml-map "ospfv3_edm_show:RouteID";
      type inet:ipv4-address;
      description "Route summary of a route ID ";
    }
    leaf intra-area-route {
      xr:xr-xml-map "ospfv3_edm_show:IntraAreaRoute";
      type uint32;
      description "Intra route summary ";
    }
    leaf inter-area-route {
      xr:xr-xml-map "ospfv3_edm_show:InterAreaRoute";
      type uint32;
      description "Inter route summary ";
    }
    leaf extern-one-route {
      xr:xr-xml-map "ospfv3_edm_show:ExternOneRoute";
      type uint32;
      description "Extern 1 route summary ";
    }
    leaf extern-two-route {
      xr:xr-xml-map "ospfv3_edm_show:ExternTwoRoute";
      type uint32;
      description "Extern 2 route summary ";
    }
    leaf nssa-one-route {
      xr:xr-xml-map "ospfv3_edm_show:NSSAOneRoute";
      type uint32;
      description "NSSA 1 route summary ";
    }
    leaf nssa-two-route {
      xr:xr-xml-map "ospfv3_edm_show:NSSATwoRoute";
      type uint32;
      description "NSSA 2 route summary ";
    }
    leaf total-sent-route {
      xr:xr-xml-map "ospfv3_edm_show:TotalSentRoute";
      type uint32;
      description "Total route summary ";
    }
    leaf route-connected {
      xr:xr-xml-map "ospfv3_edm_show:RouteConnected";
      type uint32;
      description "Route connected ";
    }
    leaf redistribution-route {
      xr:xr-xml-map "ospfv3_edm_show:RedistributionRoute";
      type uint32;
      description "Redistribution route summary ";
    }
    leaf total-received-route {
      xr:xr-xml-map "ospfv3_edm_show:TotalReceivedRoute";
      type uint32;
      description "Total route received summary";
    }
  }

  grouping OSPFV3-EDM-FLOOD-LIST {
    description "OSPFv3 flood list information";
    leaf ls-transmission-timer {
      xr:xr-xml-map "ospfv3_edm_show:LSTransmissionTimer";
      type uint32;
      description "Time until next LS transmission (ms) ";
    }
    leaf queue-length {
      xr:xr-xml-map "ospfv3_edm_show:QueueLength";
      type uint32;
      description "Number of LSAs currently being flooded ";
    }

    list link-flood {
      description "Link floodlist";
      uses OSPFV3-EDM-LSA-SUM;
    }

    list area-flood {
      description "Area scope floodlist";
      uses OSPFV3-EDM-LSA-SUM;
    }

    list as-flood {
      description "AS scope floodlist";
      uses OSPFV3-EDM-LSA-SUM;
    }
  }

  grouping OSPFV3-EDM-VLINK-NEIGHBOR {
    description "OSPFv3 virtual link neighbor information";

    container virtual-link-retransmission {
      description "Virtual link retransmission information ";
      uses OSPFV3-EDM-NEIGHBOR-RETRANS;
    }
    leaf is-virtual-link-hello-suppressed {
      xr:xr-xml-map "ospfv3_edm_show:IsVirtualLinkHelloSuppressed";
      type boolean;
      description "If true, hello suppressed ";
    }
    leaf virtual-link-state {
      xr:xr-xml-map "ospfv3_edm_show:VirtualLinkState";
      type Ospfv3-interface-state;
      description "OSPF interface state for the virtual link";
    }
  }

  grouping OSPFV3-EDM-VIRTUAL-LINKS {
    description "OSPFv3 virtual link information";

    container virtual-link-neighbor {
      description "Neighbor information ";
      uses OSPFV3-EDM-VLINK-NEIGHBOR;
    }
    leaf virtual-link-neighbor-id {
      xr:xr-xml-map "ospfv3_edm_show:VirtualLinkNeighborID";
      type inet:ipv4-address;
      description "Neighbor on other end of this virtual link";
    }
    leaf virtual-link-interface-number {
      xr:xr-xml-map "ospfv3_edm_show:VirtualLinkInterfaceNumber";
      type uint32;
      description "Virtual link interface number ";
    }
    leaf virtual-link-state {
      xr:xr-xml-map "ospfv3_edm_show:VirtualLinkState";
      type Ospfv3-interface-state;
      description "OSPF interface state for the virtual link";
    }
    leaf is-virtual-link-ip-security-required {
      xr:xr-xml-map "ospfv3_edm_show:IsVirtualLinkIPSecurityRequire"+
        "d";
      type boolean;
      description "If true, virtual link IP security is required ";
    }
    leaf is-virtual-link-ip-security-active {
      xr:xr-xml-map "ospfv3_edm_show:IsVirtualLinkIPSecurityActive";
      type boolean;
      description "If true, Virtual link IP security is active ";
    }
    leaf virtual-link-neighbor-address {
      xr:xr-xml-map "ospfv3_edm_show:VirtualLinkNeighborAddress";
      type inet:ipv6-address;
      description "Virtual link neighbor addresss ";
    }
    leaf is-virtual-link-demand-circuit {
      xr:xr-xml-map "ospfv3_edm_show:IsVirtualLinkDemandCircuit";
      type boolean;
      description "If true, the link runs as demand circuit";
    }
    leaf virtual-link-dc-bitless-lsa {
      xr:xr-xml-map "ospfv3_edm_show:VirtualLinkDCBitlessLSA";
      type uint32;
      description
        "Number of LSA's with demand circuit bit not set ";
    }
    leaf transit-area-id {
      xr:xr-xml-map "ospfv3_edm_show:TransitAreaID";
      type string;
      description "Transit area id ";
    }
    leaf interface-name {
      xr:xr-xml-map "ospfv3_edm_show:InterfaceName";
      type xr:Interface-name;
      description "Interface on which this virtual link is formed";
    }
    leaf virtual-link-cost {
      xr:xr-xml-map "ospfv3_edm_show:VirtualLinkCost";
      type uint16;
      description "Cost of the virtual link";
    }
    leaf virual-link-transmission-delay {
      xr:xr-xml-map "ospfv3_edm_show:VirualLinkTransmissionDelay";
      type uint16;
      units "second";
      description "Transmission delay in seconds";
    }
    leaf virtual-link-hello-interval {
      xr:xr-xml-map "ospfv3_edm_show:VirtualLinkHelloInterval";
      type uint32;
      description "Hello interval (s)";
    }
    leaf virtual-link-dead-interval {
      xr:xr-xml-map "ospfv3_edm_show:VirtualLinkDeadInterval";
      type uint32;
      description "Dead interval (s)";
    }
    leaf virtual-link-wait-interval {
      xr:xr-xml-map "ospfv3_edm_show:VirtualLinkWaitInterval";
      type uint32;
      description "Wait interval (s)";
    }
    leaf virtual-link-retransmission-interval {
      xr:xr-xml-map "ospfv3_edm_show:VirtualLinkRetransmissionInter"+
        "val";
      type uint32;
      description "Retransmission interval (s)";
    }
    leaf virtual-link-next-hello {
      xr:xr-xml-map "ospfv3_edm_show:VirtualLinkNextHello";
      type uint32;
      description "Time until next hello (s)";
    }
    leaf is-virtual-link-passive {
      xr:xr-xml-map "ospfv3_edm_show:IsVirtualLinkPassive";
      type boolean;
      description "If true, interface is passive";
    }
    leaf is-virtual-link-authentication-enabled {
      xr:xr-xml-map "ospfv3_edm_show:IsVirtualLinkAuthenticationEna"+
        "bled";
      type boolean;
      description
        "If true, virtual link authentication is enabled ";
    }
    leaf virtual-link-authentication-spi {
      xr:xr-xml-map "ospfv3_edm_show:VirtualLinkAuthenticationSPI";
      type uint32;
      description "Virtual link authentication spi ";
    }
    leaf virtual-link-authentication-transmit {
      xr:xr-xml-map "ospfv3_edm_show:VirtualLinkAuthenticationTrans"+
        "mit";
      type uint32;
      description "Virtual link authentication transmit ";
    }
    leaf is-virtual-link-encryption-enabled {
      xr:xr-xml-map "ospfv3_edm_show:IsVirtualLinkEncryptionEnabled";
      type boolean;
      description "If true, virtual link encryption is enabled ";
    }
    leaf virtual-link-encryption-spi {
      xr:xr-xml-map "ospfv3_edm_show:VirtualLinkEncryptionSPI";
      type uint32;
      description "Virtual link encryption spi";
    }
    leaf virtual-link-encryption-transmitted {
      xr:xr-xml-map "ospfv3_edm_show:VirtualLinkEncryptionTransmitt"+
        "ed";
      type uint32;
      description "Virtual link encryption transmitted ";
    }
    leaf virtual-link-encrypted-authentication-transmitted {
      xr:xr-xml-map "ospfv3_edm_show:VirtualLinkEncryptedAuthentica"+
        "tionTransmitted";
      type uint32;
      description
        "Virtual link encrypted authentication
        transmitted ";
    }
  }

  grouping OSPFV3-EDM-LSA-SUM {
    description "LSA summary entry";
    leaf header-lsa-type {
      xr:xr-xml-map "ospfv3_edm_show:HeaderLSAType";
      type Ospfv3-lsa1;
      description "LSA type";
    }
    leaf header-lsa-age {
      xr:xr-xml-map "ospfv3_edm_show:HeaderLSAAge";
      type uint16;
      units "second";
      description "Age of the LSA (seconds)";
    }
    leaf header-lsa-id {
      xr:xr-xml-map "ospfv3_edm_show:HeaderLSA_ID";
      type inet:ipv4-address;
      description "LSA ID";
    }
    leaf header-advertising-router {
      xr:xr-xml-map "ospfv3_edm_show:HeaderAdvertisingRouter";
      type inet:ipv4-address;
      description "Router ID of the advertising router";
    }
    leaf header-sequence-number {
      xr:xr-xml-map "ospfv3_edm_show:HeaderSequenceNumber";
      type int32;
      description "Current LSA sequence number";
    }
  }

  grouping OSPFV3-EDM-REQUEST {
    description "OSPFv3 request list information";
    leaf request-neighbor-address {
      xr:xr-xml-map "ospfv3_edm_show:RequestNeighborAddress";
      type inet:ipv6-address;
      description "Neighbor IP address";
    }
    leaf is-request-virtual-link {
      xr:xr-xml-map "ospfv3_edm_show:IsRequestVirtualLink";
      type boolean;
      description "If true, virtual link is requested ";
    }
    leaf request-virtual-link-id {
      xr:xr-xml-map "ospfv3_edm_show:RequestVirtualLinkID";
      type uint32;
      description "Request virtual link ID ";
    }
    leaf is-request-sham-link {
      xr:xr-xml-map "ospfv3_edm_show:IsRequestShamLink";
      type boolean;
      description "If true, sham link is requested ";
    }
    leaf request-sham-link-id {
      xr:xr-xml-map "ospfv3_edm_show:RequestShamLinkID";
      type uint32;
      description "Request sham link ID ";
    }

    list request {
      description "List of request list entries";
      uses OSPFV3-EDM-LSA-SUM;
    }
  }

  grouping OSPFV3-SH-ROUTE-EXTENDED-COMM {
    description
      "OSPF External Route Extended Community
      Information";
    leaf extended-community-domain-id-value {
      xr:xr-xml-map "ospfv3_edm_show:ExtendedCommunityDomainIDValue";
      type yang:hex-string;
      description "Domain ID value";
    }
    leaf extended-communityl-domain-id-type {
      xr:xr-xml-map "ospfv3_edm_show:ExtendedCommunitylDomainIDType";
      type uint16;
      description "Domain ID type";
    }
    leaf extended-community-area-id {
      xr:xr-xml-map "ospfv3_edm_show:ExtendedCommunityAreaID";
      type uint32;
      description "Area id";
    }
    leaf extended-community-router-id {
      xr:xr-xml-map "ospfv3_edm_show:ExtendedCommunityRouterID";
      type inet:ipv4-address;
      description "Router id";
    }
    leaf extended-community-route-type {
      xr:xr-xml-map "ospfv3_edm_show:ExtendedCommunityRouteType";
      type uint8;
      description "Route type";
    }
    leaf extended-community-options {
      xr:xr-xml-map "ospfv3_edm_show:ExtendedCommunityOptions";
      type uint8;
      description "Route Options";
    }
  }

  grouping OSPFV3-SH-BACKUP-PATH {
    description "OSPFv3 Route Backup Path Information";
    leaf backup-route-interface-name {
      xr:xr-xml-map "ospfv3_edm_show:BackupRouteInterfaceName";
      type xr:Interface-name;
      description "Next hop Interface";
    }
    leaf backup-route-next-hop-address {
      xr:xr-xml-map "ospfv3_edm_show:BackupRouteNextHopAddress";
      type inet:ipv6-address;
      description "Nexthop IP address";
    }
    leaf backup-route-source {
      xr:xr-xml-map "ospfv3_edm_show:BackupRouteSource";
      type inet:ipv4-address;
      description "IP address of source of route";
    }
    leaf backup-metric {
      xr:xr-xml-map "ospfv3_edm_show:BackupMetric";
      type uint32;
      description "Metric";
    }
    leaf primary-path {
      xr:xr-xml-map "ospfv3_edm_show:PrimaryPath";
      type boolean;
      description "Primary Path";
    }
    leaf line-card-disjoint {
      xr:xr-xml-map "ospfv3_edm_show:LineCardDisjoint";
      type boolean;
      description "Line Card Disjoint";
    }
    leaf downstream {
      xr:xr-xml-map "ospfv3_edm_show:Downstream";
      type boolean;
      description "Downstream";
    }
    leaf node-protect {
      xr:xr-xml-map "ospfv3_edm_show:NodeProtect";
      type boolean;
      description "Node Protect";
    }
    leaf srlg-disjoint {
      xr:xr-xml-map "ospfv3_edm_show:SRLGDisjoint";
      type boolean;
      description "SRLG Disjoint";
    }
  }

  grouping OSPFV3-EDM-TOP-PATH {
    description "OSPFv3 topology path information";

    container route-backup-path {
      description "Backup Path Info";
      uses OSPFV3-SH-BACKUP-PATH;
    }
    leaf interface-name {
      xr:xr-xml-map "ospfv3_edm_show:InterfaceName";
      type xr:Interface-name;
      description "Route path interface name ";
    }
    leaf route-path-next-hop {
      xr:xr-xml-map "ospfv3_edm_show:RoutePathNextHop";
      type inet:ipv6-address;
      description "Route path next hop ";
    }
    leaf route-path-id {
      xr:xr-xml-map "ospfv3_edm_show:RoutePathID";
      type uint16;
      description "Path ID of path";
    }
  }

  grouping OSPFV3-EDM-TOPOLOGY {
    description "OSPFv3 Topology Information";
    leaf route-id {
      xr:xr-xml-map "ospfv3_edm_show:RouteID";
      type inet:ipv4-address;
      description "Route ID ";
    }
    leaf route-distance {
      xr:xr-xml-map "ospfv3_edm_show:RouteDistance";
      type uint32;
      description "Route distance ";
    }
    leaf route-cost {
      xr:xr-xml-map "ospfv3_edm_show:RouteCost";
      type uint32;
      description "Route cost ";
    }
    leaf route-type {
      xr:xr-xml-map "ospfv3_edm_show:RouteType";
      type uint32;
      description "Route type";
    }
  }

  grouping OSPFV3-EDM-TOPOLOGY-EXTERNAL {
    description "OSPFv3 Topology External Information";

    container route-topology {
      description "Common Route topology information";
      uses OSPFV3-EDM-TOPOLOGY;
    }

    container route-extended-community {
      description "Extended communities in the route";
      uses OSPFV3-SH-ROUTE-EXTENDED-COMM;
    }

    list route-path {
      description "List of paths to this route";
      uses OSPFV3-EDM-TOP-PATH;
    }
  }

  grouping OSPFV3-EDM-REDIST {
    description "OSPFv3 Redistribution Information";
    leaf protocol-name-xr {
      xr:xr-xml-map "ospfv3_edm_show:protocol-name-xr";
      type string {
        length "0..40";
      }
      description "Protocol name ";
    }
    leaf process-id {
      xr:xr-xml-map "ospfv3_edm_show:ProcessID";
      type string {
        length "0..40";
      }
      description "Process ID ";
    }
    leaf red-metric-flag {
      xr:xr-xml-map "ospfv3_edm_show:red_metric_flag";
      type boolean;
      description "red metric flag";
    }
    leaf red-metric {
      xr:xr-xml-map "ospfv3_edm_show:red_metric";
      type uint32;
      description "red metric";
    }
    leaf red-mtype-flag {
      xr:xr-xml-map "ospfv3_edm_show:red_mtype_flag";
      type boolean;
      description "red mtype flag";
    }
    leaf red-metric-type {
      xr:xr-xml-map "ospfv3_edm_show:red_metric_type";
      type uint8;
      description "red metric type";
    }
    leaf red-tag {
      xr:xr-xml-map "ospfv3_edm_show:red_tag";
      type uint32;
      description "red tag";
    }
    leaf policy-name {
      xr:xr-xml-map "ospfv3_edm_show:PolicyName";
      type string;
      description "Route policy name ";
    }
  }

  grouping OSPFV3-EDM-INTERFACE-BFD {
    description "Interface BFD information";
    leaf bfd-intf-enable-mode {
      xr:xr-xml-map "ospfv3_edm_show:BFDIntfEnableMode";
      type uint32;
      description
        "BFD Enable Mode on the interface -
        Default/Strict";
    }
    leaf bfd-interval {
      xr:xr-xml-map "ospfv3_edm_show:BFDInterval";
      type uint32;
      description "BFD interval (ms) ";
    }
    leaf bfd-detection-multiplier {
      xr:xr-xml-map "ospfv3_edm_show:BFDDetectionMultiplier";
      type uint32;
      description "BFD detection multiplier ";
    }
  }

  grouping OSPFV3-EDM-INTERFACE-UP {
    description "OSPFv3 interface up-only information";
    leaf wait-time {
      xr:xr-xml-map "ospfv3_edm_show:WaitTime";
      type uint32;
      description "Wait time for DR/BDR selection (s)";
    }
    leaf interface-area-flood-index {
      xr:xr-xml-map "ospfv3_edm_show:InterfaceAreaFloodIndex";
      type uint32;
      description "Area scope LSAs flood index";
    }
    leaf interface-as-flood-index {
      xr:xr-xml-map "ospfv3_edm_show:InterfaceASFloodIndex";
      type uint32;
      description "AS scope LSAs flood index ";
    }
    leaf interface-link-flood-index {
      xr:xr-xml-map "ospfv3_edm_show:InterfaceLinkFloodIndex";
      type uint32;
      description "Interface flood link index ";
    }
    leaf flood-queue-length {
      xr:xr-xml-map "ospfv3_edm_show:FloodQueueLength";
      type uint32;
      description "Flood queue length";
    }
    leaf interface-area-next-flood {
      xr:xr-xml-map "ospfv3_edm_show:InterfaceAreaNextFlood";
      type uint32;
      description "Next LSA to flood (Area scope)";
    }
    leaf interface-area-next-flood-index {
      xr:xr-xml-map "ospfv3_edm_show:InterfaceAreaNextFloodIndex";
      type uint32;
      description "Index of next LSA to flood (Area scope) ";
    }
    leaf interface-as-next-flood {
      xr:xr-xml-map "ospfv3_edm_show:InterfaceASNextFlood";
      type uint32;
      description "Next LSA to flood (AS scope)";
    }
    leaf interface-as-next-flood-index {
      xr:xr-xml-map "ospfv3_edm_show:InterfaceASNextFloodIndex";
      type uint32;
      description "Index of next LSA to flood (AS scope)";
    }
    leaf interface-link-next-flood {
      xr:xr-xml-map "ospfv3_edm_show:InterfaceLinkNextFlood";
      type uint32;
      description "Interface link next flood information ";
    }
    leaf interface-link-next-index {
      xr:xr-xml-map "ospfv3_edm_show:InterfaceLinkNextIndex";
      type uint32;
      description "Interface link next information index ";
    }
    leaf flood-scan-length {
      xr:xr-xml-map "ospfv3_edm_show:FloodScanLength";
      type uint32;
      description "Last flood scan length ";
    }
    leaf maximum-flood-length {
      xr:xr-xml-map "ospfv3_edm_show:MaximumFloodLength";
      type uint32;
      description "Maximum flood length ";
    }
    leaf last-flood-time {
      xr:xr-xml-map "ospfv3_edm_show:LastFloodTime";
      type uint32;
      description "Last flood scan time (ms)";
    }
    leaf maximum-flood-time {
      xr:xr-xml-map "ospfv3_edm_show:MaximumFloodTime";
      type uint32;
      description "Maximum flood time (ms) ";
    }
    leaf interface-flood-pacing-timer {
      xr:xr-xml-map "ospfv3_edm_show:InterfaceFloodPacingTimer";
      type uint32;
      description "Time until next flood pacing timer (ms) ";
    }
    leaf interface-neighbors {
      xr:xr-xml-map "ospfv3_edm_show:InterfaceNeighbors";
      type uint16;
      description "Total number of neighbors ";
    }
    leaf suppressed-hellos {
      xr:xr-xml-map "ospfv3_edm_show:SuppressedHellos";
      type uint16;
      description
        "Number of neighbors for which hellos are
        suppressed ";
    }
  }

  grouping OSPFV3-EDM-INTERFACE-NBR {
    description "OSPFv3 interface neighbor information";
    leaf interface-neighbor-id {
      xr:xr-xml-map "ospfv3_edm_show:InterfaceNeighborID";
      type inet:ipv4-address;
      description "Neighbor router ID ";
    }
    leaf interface-neighbor-cost {
      xr:xr-xml-map "ospfv3_edm_show:InterfaceNeighborCost";
      type uint32;
      description "Cost of link to neighbor";
    }
    leaf is-neighbor-dr {
      xr:xr-xml-map "ospfv3_edm_show:IsNeighborDR";
      type boolean;
      description "If true, designated router is found ";
    }
    leaf is-neighbor-bdr {
      xr:xr-xml-map "ospfv3_edm_show:IsNeighborBDR";
      type boolean;
      description "If true, backup designated router is found ";
    }
    leaf is-hello-suppressed {
      xr:xr-xml-map "ospfv3_edm_show:IsHelloSuppressed";
      type boolean;
      description "If true, hello is suppressed ";
    }
  }

  grouping OSPFV3-EDM-INTERFACE {
    description "OSPFv3 interface information";

    container active-interface {
      description "Active interface details ";
      uses OSPFV3-EDM-INTERFACE-UP;
    }

    container interface-bfd {
      description "BFD information ";
      uses OSPFV3-EDM-INTERFACE-BFD;
    }
    leaf interface-state {
      xr:xr-xml-map "ospfv3_edm_show:InterfaceState";
      type Im-state-enum;
      description "Interface state";
    }
    leaf is-interface-line-up {
      xr:xr-xml-map "ospfv3_edm_show:IsInterfaceLineUp";
      type boolean;
      description "If true, line protocol is up ";
    }
    leaf is-interface-ip-security-required {
      xr:xr-xml-map "ospfv3_edm_show:IsInterfaceIPSecurityRequired";
      type boolean;
      description "If true, interface IP security is required ";
    }
    leaf is-interface-ip-security-active {
      xr:xr-xml-map "ospfv3_edm_show:IsInterfaceIPSecurityActive";
      type boolean;
      description "If true, interface IP security is active ";
    }
    leaf interface-address {
      xr:xr-xml-map "ospfv3_edm_show:InterfaceAddress";
      type inet:ipv6-address;
      description "Interface IPv6 address";
    }
    leaf interface-number {
      xr:xr-xml-map "ospfv3_edm_show:InterfaceNumber";
      type uint32;
      description "Interface number ";
    }
    leaf interface-router-id {
      xr:xr-xml-map "ospfv3_edm_show:InterfaceRouterID";
      type inet:ipv4-address;
      description "Interface router ID ";
    }
    leaf network-type {
      xr:xr-xml-map "ospfv3_edm_show:NetworkType";
      type Ospfv3-interface;
      description "Network type";
    }
    leaf interface-link-cost {
      xr:xr-xml-map "ospfv3_edm_show:InterfaceLinkCost";
      type uint16;
      description "Interface link cost";
    }
    leaf is-interface-flood-reduction {
      xr:xr-xml-map "ospfv3_edm_show:IsInterfaceFloodReduction";
      type boolean;
      description "If true, interface flood reduction is active ";
    }
    leaf is-demand-circuit-configured {
      xr:xr-xml-map "ospfv3_edm_show:IsDemandCircuitConfigured";
      type boolean;
      description "If true, configured as demand circuit ";
    }
    leaf is-interface-demand-circuit {
      xr:xr-xml-map "ospfv3_edm_show:IsInterfaceDemandCircuit";
      type boolean;
      description "If true, interface running as demand circuit";
    }
    leaf interface-dc-bitless-ls-as {
      xr:xr-xml-map "ospfv3_edm_show:InterfaceDCBitlessLSAs";
      type uint32;
      description
        "Number of LSAs with demand circuit bit not set
        for the area in which the interface is running";
    }
    leaf transmission-delay {
      xr:xr-xml-map "ospfv3_edm_show:TransmissionDelay";
      type uint16;
      description "Interface transmission delay (sec)";
    }
    leaf ospf-interface-state {
      xr:xr-xml-map "ospfv3_edm_show:OSPFInterfaceState";
      type Ospfv3-interface-state;
      description "Interface state";
    }
    leaf interface-priority {
      xr:xr-xml-map "ospfv3_edm_show:InterfacePriority";
      type uint8;
      description "Interface priority";
    }
    leaf is-designated-router {
      xr:xr-xml-map "ospfv3_edm_show:IsDesignatedRouter";
      type boolean;
      description "If true, designated router";
    }
    leaf designated-router-id {
      xr:xr-xml-map "ospfv3_edm_show:DesignatedRouterID";
      type inet:ipv4-address;
      description "Designated router ID";
    }
    leaf designated-router-address {
      xr:xr-xml-map "ospfv3_edm_show:DesignatedRouterAddress";
      type inet:ipv6-address;
      description "Designated router interface address";
    }
    leaf backup-designated-router-id {
      xr:xr-xml-map "ospfv3_edm_show:BackupDesignatedRouterID";
      type inet:ipv4-address;
      description "Backup designated router ID";
    }
    leaf backup-designated-router-address {
      xr:xr-xml-map "ospfv3_edm_show:BackupDesignatedRouterAddress";
      type inet:ipv6-address;
      description "Backup designated router interface address";
    }
    leaf network-lsa-flush-timer {
      xr:xr-xml-map "ospfv3_edm_show:NetworkLSAFlushTimer";
      type uint32;
      units "second";
      description
        "The amount of time in seconds before flush timer
        for old network LSA expires ";
    }
    leaf is-interface-lsa-filtered {
      xr:xr-xml-map "ospfv3_edm_show:IsInterfaceLSAFiltered";
      type boolean;
      description "Filter is configured for out going LSAs ";
    }
    leaf hello-interval {
      xr:xr-xml-map "ospfv3_edm_show:HelloInterval";
      type uint32;
      description "Configured hello interval (s)";
    }
    leaf dead-interval {
      xr:xr-xml-map "ospfv3_edm_show:DeadInterval";
      type uint32;
      description "Configured dead interval (s) ";
    }
    leaf wait-interval {
      xr:xr-xml-map "ospfv3_edm_show:WaitInterval";
      type uint32;
      description "Configured wait interval (s) ";
    }
    leaf interface-retransmission-interval {
      xr:xr-xml-map "ospfv3_edm_show:InterfaceRetransmissionInterva"+
        "l";
      type uint32;
      description "Configured retransmit interval (s) ";
    }
    leaf next-hello-time {
      xr:xr-xml-map "ospfv3_edm_show:NextHelloTime";
      type uint32;
      description "Time until next Hello (s) ";
    }
    leaf interface-authentication-spi {
      xr:xr-xml-map "ospfv3_edm_show:InterfaceAuthenticationSPI";
      type uint32;
      description "Interface authentication spi ";
    }
    leaf interface-authentication-transmit {
      xr:xr-xml-map "ospfv3_edm_show:InterfaceAuthenticationTransmi"+
        "t";
      type uint32;
      description "Interface authentication transmit ";
    }
    leaf is-interface-encryption-enabled {
      xr:xr-xml-map "ospfv3_edm_show:IsInterfaceEncryptionEnabled";
      type boolean;
      description "If true, interface encryption is enabled ";
    }
    leaf interface-encryption-spi {
      xr:xr-xml-map "ospfv3_edm_show:InterfaceEncryptionSPI";
      type uint32;
      description "Interface encryption spi";
    }
    leaf interface-encryption-transmitted {
      xr:xr-xml-map "ospfv3_edm_show:InterfaceEncryptionTransmitted";
      type uint32;
      description "Interface encryption transmitted ";
    }
    leaf interface-encrypted-authentication-transmitted {
      xr:xr-xml-map "ospfv3_edm_show:InterfaceEncryptedAuthenticati"+
        "onTransmitted";
      type uint32;
      description "Interface encrypted authentication transmitted ";
    }
    leaf adjacent-neighbor {
      xr:xr-xml-map "ospfv3_edm_show:AdjacentNeighbor";
      type uint32;
      description "Number of adjacent neighbors";
    }
    leaf interface-references {
      xr:xr-xml-map "ospfv3_edm_show:InterfaceReferences";
      type uint32;
      description "Interface reference count ";
    }
    leaf configured-ldp-sync {
      xr:xr-xml-map "ospfv3_edm_show:ConfiguredLdpSync";
      type boolean;
      description "If true, configured as LDP sync";
    }
    leaf interface-ldp-sync {
      xr:xr-xml-map "ospfv3_edm_show:InterfaceLdpSync";
      type boolean;
      description "If true, interface LDP sync is achieved";
    }

    list interface-neighbor {
      description "Information for neighbors on the interface";
      uses OSPFV3-EDM-INTERFACE-NBR;
    }
  }

  grouping OSPFV3-EDM-LSA-UNKNOWN {
    description "OSPFv3 Unknown LSA Database Information";

    container lsa-header {
      description "Header information ";
      uses OSPFV3-EDM-DB-HEADER;
    }

    container lsa-detail {
      description "Detailed LSA information";
      uses OSPFV3-EDM-DB-DETAIL;
    }
    leaf interface-name {
      xr:xr-xml-map "ospfv3_edm_show:InterfaceName";
      type xr:Interface-name;
      description "LSA interface name ";
    }
    leaf is-virtual-link {
      xr:xr-xml-map "ospfv3_edm_show:IsVirtualLink";
      type boolean;
      description "If true, it is a virtual link ";
    }
    leaf virtual-link-id {
      xr:xr-xml-map "ospfv3_edm_show:VirtualLinkID";
      type uint32;
      description "Virtual link ID ";
    }
    leaf is-sham-link {
      xr:xr-xml-map "ospfv3_edm_show:IsShamLink";
      type boolean;
      description "If true, it is a sham link ";
    }
    leaf sham-link-id {
      xr:xr-xml-map "ospfv3_edm_show:ShamLinkID";
      type uint32;
      description "Shamlink ID ";
    }
  }

  grouping OSPFV3-EDM-LSA-GRACE {
    description "OSPFv3 Grace LSA";

    container lsa-header {
      description "Header information ";
      uses OSPFV3-EDM-DB-HEADER;
    }

    container lsa-detail {
      description "Detailed LSA information";
      uses OSPFV3-EDM-DB-DETAIL;
    }
    leaf grace-period {
      xr:xr-xml-map "ospfv3_edm_show:GracePeriod";
      type uint32;
      description
        "The grace periord where helper routers should
        wait before advertising it fully adjacent(s) ";
    }
    leaf grace-reason {
      xr:xr-xml-map "ospfv3_edm_show:GraceReason";
      type Ospfv3-graceful-restart-reason;
      description "Reason for router restart";
    }
  }

  grouping OSPFV3-EDM-LSA-PREFIX {
    description "OSPFv3 Prefix LSA";

    container lsa-header {
      description "Header information ";
      uses OSPFV3-EDM-DB-HEADER;
    }

    container lsa-detail {
      description "Detailed LSA information";
      uses OSPFV3-EDM-DB-DETAIL;
    }
    leaf reference-type {
      xr:xr-xml-map "ospfv3_edm_show:ReferenceType";
      type Ospfv3-lsa1;
      description "Reference type ";
    }
    leaf reference-lsa-id {
      xr:xr-xml-map "ospfv3_edm_show:ReferenceLSA_ID";
      type uint32;
      description "Reference LSA ID ";
    }
    leaf reference-advertised-router {
      xr:xr-xml-map "ospfv3_edm_show:ReferenceAdvertisedRouter";
      type inet:ipv4-address;
      description "Reference advertised router ";
    }

    list prefix {
      description "OSPFv3 prefix ";
      uses OSPFV3-EDM-PREFIX;
    }
  }

  grouping OSPFV3-EDM-PREFIX {
    description "OSPFv3 Prefix Type";
    leaf prefix {
      xr:xr-xml-map "ospfv3_edm_show:Prefix";
      type inet:ipv6-address;
      description "OSPFv3 prefix ";
    }
    leaf ospfv3-prefix-length {
      xr:xr-xml-map "ospfv3_edm_show:OSPFv3PrefixLength";
      type uint8;
      description "OSPFv3 prefix length ";
    }
    leaf ospfv3-prefix-options {
      xr:xr-xml-map "ospfv3_edm_show:OSPFv3PrefixOptions";
      type uint8;
      description "OSPFv3 prefix options ";
    }
    leaf ospfv3-prefix-metric {
      xr:xr-xml-map "ospfv3_edm_show:OSPFv3PrefixMetric";
      type uint16;
      description "OSPFv3 prefix metric ";
    }
    leaf priority {
      xr:xr-xml-map "ospfv3_edm_show:Priority";
      type Prefix-priority;
      description "Prefix priority";
    }
  }

  grouping OSPFV3-EDM-LSA-LINK {
    description "OSPFv3 Link LSA";

    container lsa-header {
      description "Header information ";
      uses OSPFV3-EDM-DB-HEADER;
    }

    container lsa-detail {
      description "Detailed LSA information";
      uses OSPFV3-EDM-DB-DETAIL;
    }
    leaf interface-name {
      xr:xr-xml-map "ospfv3_edm_show:InterfaceName";
      type xr:Interface-name;
      description "LSA interface handle";
    }
    leaf is-virtual-link {
      xr:xr-xml-map "ospfv3_edm_show:IsVirtualLink";
      type boolean;
      description "If true, it is a virtual link";
    }
    leaf virtual-link-id {
      xr:xr-xml-map "ospfv3_edm_show:VirtualLinkID";
      type uint32;
      description "Virtual link ID ";
    }
    leaf is-sham-link {
      xr:xr-xml-map "ospfv3_edm_show:IsShamLink";
      type boolean;
      description "If true, it is a sham link";
    }
    leaf sham-link-id {
      xr:xr-xml-map "ospfv3_edm_show:ShamLinkID";
      type uint32;
      description "Sham link ID ";
    }
    leaf lsa-link-local {
      xr:xr-xml-map "ospfv3_edm_show:LSALinkLocal";
      type inet:ipv6-address;
      description "LSA link local ";
    }
    leaf router-priority {
      xr:xr-xml-map "ospfv3_edm_show:RouterPriority";
      type uint8;
      description "Router priority ";
    }

    list prefix {
      description "OSPFv3 prefix ";
      uses OSPFV3-EDM-PREFIX;
    }
  }

  grouping OSPFV3-EDM-LSA-EXTERNAL {
    description "OSPFv3 External LSA";

    container lsa-header {
      description "Header information ";
      uses OSPFV3-EDM-DB-HEADER;
    }

    container lsa-detail {
      description "Detailed LSA Information";
      uses OSPFV3-EDM-DB-DETAIL;
    }
    leaf prefix {
      xr:xr-xml-map "ospfv3_edm_show:Prefix";
      type inet:ipv6-address;
      description "IPV6 address prefix ";
    }
    leaf prefix-length {
      xr:xr-xml-map "ospfv3_edm_show:PrefixLength";
      type uint8;
      description "Prefix length ";
    }
    leaf metric-type {
      xr:xr-xml-map "ospfv3_edm_show:MetricType";
      type Ospfv3-default-metric;
      description "Metric type ";
    }
    leaf tos-cost {
      xr:xr-xml-map "ospfv3_edm_show:TOSCost";
      type uint32;
      description "Type of service cost metric ";
    }
    leaf is-forwarding-address-set {
      xr:xr-xml-map "ospfv3_edm_show:IsForwardingAddressSet";
      type boolean;
      description "If true, forwarding address is set ";
    }
    leaf forwarding-address {
      xr:xr-xml-map "ospfv3_edm_show:ForwardingAddress";
      type inet:ipv6-address;
      description "Forwarding Address";
    }
    leaf external-tag {
      xr:xr-xml-map "ospfv3_edm_show:ExternalTag";
      type uint32;
      description "Route Tag";
    }
    leaf priority {
      xr:xr-xml-map "ospfv3_edm_show:Priority";
      type Prefix-priority;
      description "Prefix priority";
    }
  }

  grouping OSPFV3-EDM-LSA-IARTR {
    description "OSPFv3 Inter-area Router LSA";

    container lsa-header {
      description "Header information ";
      uses OSPFV3-EDM-DB-HEADER;
    }

    container lsa-detail {
      description "Detailed LSA information";
      uses OSPFV3-EDM-DB-DETAIL;
    }
    leaf lsa-router-id {
      xr:xr-xml-map "ospfv3_edm_show:LSARouterID";
      type uint32;
      description "LSA router ID ";
    }
  }

  grouping OSPFV3-EDM-LSA-IAPFX {
    description "OSPFv3 Inter-area Prefix LSA";

    container lsa-header {
      description "Header information ";
      uses OSPFV3-EDM-DB-HEADER;
    }

    container lsa-detail {
      description "Detailed LSA Information";
      uses OSPFV3-EDM-DB-DETAIL;
    }
    leaf prefix {
      xr:xr-xml-map "ospfv3_edm_show:Prefix";
      type inet:ipv6-address;
      description "LSA address prefix ";
    }
    leaf prefix-length {
      xr:xr-xml-map "ospfv3_edm_show:PrefixLength";
      type uint8;
      description "Prefix length ";
    }
    leaf priority {
      xr:xr-xml-map "ospfv3_edm_show:Priority";
      type Prefix-priority;
      description "Prefix priority";
    }
  }

  grouping OSPFV3-EDM-LSA-NETWORK {
    description "OSPFv3 Network LSA";

    container lsa-header {
      description "Header information ";
      uses OSPFV3-EDM-DB-HEADER;
    }

    container lsa-detail {
      description "Detailed LSA information";
      uses OSPFV3-EDM-DB-DETAIL;
    }
    leaf-list neighbor-router {
      xr:xr-xml-map "ospfv3_edm_show:NeighborRouterList";
      type inet:ipv4-address;
      description "Neighbor router list";
    }
  }

  grouping OSPFV3-EDM-RPF-PATH {
    description
      "OSPFv3 Router LSA Reverse-Path Forwarding
      Information";
    leaf rpf-multicast-next-hop {
      xr:xr-xml-map "ospfv3_edm_show:RPFMulticastNextHop";
      type uint32;
      description "RPF multicast next hop ";
    }
    leaf interface-name {
      xr:xr-xml-map "ospfv3_edm_show:InterfaceName";
      type xr:Interface-name;
      description "RPF multicast IDB ";
    }
  }

  grouping OSPFV3-EDM-LINK {
    description "OSPFv3 Router LSA Links";
    leaf link-type {
      xr:xr-xml-map "ospfv3_edm_show:LinkType";
      type Ospfv3-link;
      description "Type of link";
    }
    leaf link-metric {
      xr:xr-xml-map "ospfv3_edm_show:LinkMetric";
      type uint16;
      description "LSA link metric ";
    }
    leaf link-interface-id {
      xr:xr-xml-map "ospfv3_edm_show:LinkInterfaceID";
      type uint32;
      description "LSA link interface ID ";
    }
    leaf link-neighbor-interface-id {
      xr:xr-xml-map "ospfv3_edm_show:LinkNeighborInterfaceID";
      type uint32;
      description "LSA link neighbor interface ID ";
    }
    leaf link-neighbor-router-id {
      xr:xr-xml-map "ospfv3_edm_show:LinkNeighborRouterID";
      type uint32;
      description "LSA link neigbhor router id ";
    }
  }

  grouping OSPFV3-EDM-LSA-ROUTER {
    description "OSPFv3 Router LSA";

    container lsa-header {
      description "Header information ";
      uses OSPFV3-EDM-DB-HEADER;
    }

    container lsa-detail {
      description "Detailed LSA information";
      uses OSPFV3-EDM-DB-DETAIL;
    }

    container rpf-path {
      description "Router LSA Reverse-Path Forwarding information ";
      uses OSPFV3-EDM-RPF-PATH;
    }
    leaf router-la-bits {
      xr:xr-xml-map "ospfv3_edm_show:RouterLABits";
      type uint8;
      description "Router LA bits ";
    }

    list link {
      description "List of links in this LSA";
      uses OSPFV3-EDM-LINK;
    }
  }

  grouping OSPFV3-EDM-DB-DETAIL {
    description "OSPFv3 Detailed LSA Database Information";
    leaf second-table-index {
      xr:xr-xml-map "ospfv3_edm_show:SecondTableIndex";
      type uint8;
      description "Second table index";
    }
    leaf minute-table-index {
      xr:xr-xml-map "ospfv3_edm_show:MinuteTableIndex";
      type uint8;
      description "Minute table index";
    }
    leaf free-time {
      xr:xr-xml-map "ospfv3_edm_show:FreeTime";
      type uint32;
      description
        "The amount of time since the last check was made
        to free this LSA (s)";
    }
    leaf is-deleted {
      xr:xr-xml-map "ospfv3_edm_show:IsDeleted";
      type boolean;
      description "If true, flag is set to delete this LSA ";
    }
    leaf is-routing-bit {
      xr:xr-xml-map "ospfv3_edm_show:IsRoutingBit";
      type boolean;
      description "If true, Routing Bit set on the LSA";
    }
    leaf is-advertising-router-reachable {
      xr:xr-xml-map "ospfv3_edm_show:IsAdvertisingRouterReachable";
      type boolean;
      description "If true, Advertising Router is reachable";
    }
    leaf is-no-delete {
      xr:xr-xml-map "ospfv3_edm_show:IsNoDelete";
      type boolean;
      description
        "If true, the reason not to delete this LSA is
        because delete flag not set on this LSA";
    }
    leaf is-neighbor-exchange {
      xr:xr-xml-map "ospfv3_edm_show:IsNeighborExchange";
      type boolean;
      description
        "If true, the reason  not to delete this LSA is
        because neighbor is in exchange state";
    }
    leaf is-routing-table {
      xr:xr-xml-map "ospfv3_edm_show:IsRoutingTable";
      type boolean;
      description
        "If true, the reason  not to delete this LSA is
        because it has a contributing entry in the
        routing table ";
    }
    leaf is-acknowledged {
      xr:xr-xml-map "ospfv3_edm_show:IsAcknowledged";
      type boolean;
      description
        "If true, the reason not to delete this LSA is
        because it's Acknowledgement list is not empty ";
    }
    leaf is-maximum-aged {
      xr:xr-xml-map "ospfv3_edm_show:IsMaximumAged";
      type boolean;
      description
        "If true, the reason not to delete this LSA is
        because it is in Maxage Queue";
    }
    leaf is-partial-spf {
      xr:xr-xml-map "ospfv3_edm_show:IsPartialSPF";
      type boolean;
      description
        "If true, the reason not to delete this LSA is
        because it is in partial SPF queue";
    }
    leaf is-flood-pending {
      xr:xr-xml-map "ospfv3_edm_show:IsFloodPending";
      type boolean;
      description
        "If true, the reason not to delete this LSA is
        because waiting for flooding or retransmission";
    }
    leaf rate-limit {
      xr:xr-xml-map "ospfv3_edm_show:RateLimit";
      type boolean;
      description
        "If true, the reason not to delete this LSA is
        because waiting for next wait-interval to expire";
    }
    leaf is-nsr-ack-pending {
      xr:xr-xml-map "ospfv3_edm_show:IsNSRAckPending";
      type boolean;
      description
        "If true, the reason not to delete this LSA is
        because NSR ACK from standby is pending";
    }
    leaf nsr-flood-required {
      xr:xr-xml-map "ospfv3_edm_show:NSRFloodRequired";
      type boolean;
      description
        "If true, the reason not to delete this LSA is
        because it is pending flooding on switchover";
    }
    leaf lsa-flood-required-post-fail-over {
      xr:xr-xml-map "ospfv3_edm_show:LSAFloodRequiredPostFailOver";
      type boolean;
      description "LSA flood required after FO";
    }
    leaf lsa-length {
      xr:xr-xml-map "ospfv3_edm_show:LSALength";
      type uint16;
      description "Length of the LSA";
    }
    leaf lsa-sync-state {
      xr:xr-xml-map "ospfv3_edm_show:LSASyncState";
      type Ospf-lsa-sync-state;
      description "State of LSA sync with active";
    }
  }

  grouping OSPFV3-EDM-DB-HEADER {
    description "OSPFv3 LSA Database Header";
    leaf lsa-type {
      xr:xr-xml-map "ospfv3_edm_show:LSAType";
      type uint16;
      description "LSA type";
    }
    leaf lsa-area-id {
      xr:xr-xml-map "ospfv3_edm_show:LSAAreaID";
      type string {
        length "0..16";
      }
      description "Area ID in decimal or dotted-decimal format";
    }
    leaf lsa-age {
      xr:xr-xml-map "ospfv3_edm_show:LSAAge";
      type uint16;
      description "LSA's Age (s)";
    }
    leaf is-do-not-age-lsa {
      xr:xr-xml-map "ospfv3_edm_show:IsDoNotAgeLSA";
      type boolean;
      description "If true, Do Not Age this LSA";
    }
    leaf ls-id {
      xr:xr-xml-map "ospfv3_edm_show:LS_ID";
      type uint32;
      description "LS ID";
    }
    leaf advertising-router {
      xr:xr-xml-map "ospfv3_edm_show:AdvertisingRouter";
      type inet:ipv4-address;
      description "Router ID of Advertising Router";
    }
    leaf sequence-number {
      xr:xr-xml-map "ospfv3_edm_show:SequenceNumber";
      type uint32;
      description "Current Sequence number";
    }
    leaf checksum {
      xr:xr-xml-map "ospfv3_edm_show:Checksum";
      type uint16;
      description "Checksum value";
    }
    leaf is-graceful-restart-active {
      xr:xr-xml-map "ospfv3_edm_show:IsGracefulRestartActive";
      type boolean;
      description "If true, if grace restart is active ";
    }
  }

  grouping OSPFV3-EDM-DATABASE {
    description "OSPFv3 Database Information";

    container lsa-header {
      description "Header information ";
      uses OSPFV3-EDM-DB-HEADER;
    }

    container lsa-detail {
      description "Detailed LSA information";
      uses OSPFV3-EDM-DB-DETAIL;
    }
    leaf links {
      xr:xr-xml-map "ospfv3_edm_show:Links";
      type uint16;
      description "Number of links";
    }
    leaf router-la-bits {
      xr:xr-xml-map "ospfv3_edm_show:RouterLABits";
      type uint8;
      description "Router LA bits ";
    }
    leaf reference-type {
      xr:xr-xml-map "ospfv3_edm_show:ReferenceType";
      type uint16;
      description "Reference type ";
    }
    leaf reference-lsa-id {
      xr:xr-xml-map "ospfv3_edm_show:ReferenceLSA_ID";
      type uint32;
      description "Reference LSA ID ";
    }
    leaf lsa-router-id {
      xr:xr-xml-map "ospfv3_edm_show:LSARouterID";
      type uint32;
      description "LSA router ID ";
    }
    leaf prefix {
      xr:xr-xml-map "ospfv3_edm_show:Prefix";
      type inet:ipv6-address;
      description "OSPFv3 address Prefix ";
    }
    leaf prefix-length {
      xr:xr-xml-map "ospfv3_edm_show:PrefixLength";
      type uint8;
      description "Prefix length ";
    }
    leaf interface-name {
      xr:xr-xml-map "ospfv3_edm_show:InterfaceName";
      type xr:Interface-name;
      description "LSA interface name ";
    }
    leaf is-virtual-link {
      xr:xr-xml-map "ospfv3_edm_show:IsVirtualLink";
      type boolean;
      description "If true, it is a virtual link ";
    }
    leaf virtual-link-id {
      xr:xr-xml-map "ospfv3_edm_show:VirtualLinkID";
      type uint32;
      description "Virtual link ID ";
    }
    leaf is-sham-link {
      xr:xr-xml-map "ospfv3_edm_show:IsShamLink";
      type boolean;
      description "If true, it is a sham link ";
    }
    leaf sham-link-id {
      xr:xr-xml-map "ospfv3_edm_show:ShamLinkID";
      type uint32;
      description "Sham link ID ";
    }
  }

  grouping OSPFV3-LSA-INFO-UNION {
    description "Detail LSA information for an LSA";

    container lsa-summary-info {
      when "../lsa-info-type = 'mgmt-lsa-lsasum-type'" {
        description "../LSAInfoType = 'MGMT_LSA_LSASUM_TYPE'";
      }
      description "Summary information of LSAs";
      uses OSPFV3-EDM-DATABASE;
    }

    container router-lsa-type {
      when "../lsa-info-type = 'mgmt-lsa-rtr-type'" {
        description "../LSAInfoType = 'MGMT_LSA_RTR_TYPE'";
      }
      description "Router LSA";
      uses OSPFV3-EDM-LSA-ROUTER;
    }

    container network-lsa-type {
      when "../lsa-info-type = 'mgmt-lsa-net-type'" {
        description "../LSAInfoType = 'MGMT_LSA_NET_TYPE'";
      }
      description "Network LSA";
      uses OSPFV3-EDM-LSA-NETWORK;
    }

    container inter-area-prefix-lsa-type {
      when "../lsa-info-type = 'mgmt-lsa-iapfx-type'" {
        description "../LSAInfoType = 'MGMT_LSA_IAPFX_TYPE'";
      }
      description "Inter Area Prefix LSA";
      uses OSPFV3-EDM-LSA-IAPFX;
    }

    container inter-area-router-lsa-type {
      when "../lsa-info-type = 'mgmt-lsa-iartr-type'" {
        description "../LSAInfoType = 'MGMT_LSA_IARTR_TYPE'";
      }
      description "Inter Area Router LSA";
      uses OSPFV3-EDM-LSA-IARTR;
    }

    container external-lsa-type {
      when "../lsa-info-type = 'mgmt-lsa-ext-type'" {
        description "../LSAInfoType = 'MGMT_LSA_EXT_TYPE'";
      }
      description "External LSA";
      uses OSPFV3-EDM-LSA-EXTERNAL;
    }

    container nssalsa-type {
      when "../lsa-info-type = 'mgmt-lsa-nssaext-type'" {
        description "../LSAInfoType = 'MGMT_LSA_NSSAEXT_TYPE'";
      }
      description "NSSA External LSA";
      uses OSPFV3-EDM-LSA-EXTERNAL;
    }

    container link-lsa-type {
      when "../lsa-info-type = 'mgmt-lsa-link-type'" {
        description "../LSAInfoType = 'MGMT_LSA_LINK_TYPE'";
      }
      description "Link LSA";
      uses OSPFV3-EDM-LSA-LINK;
    }

    container intra-area-prefix-lsa-type {
      when "../lsa-info-type = 'mgmt-lsa-prefix-type'" {
        description "../LSAInfoType = 'MGMT_LSA_PREFIX_TYPE'";
      }
      description "Intra Area Prefix LSA";
      uses OSPFV3-EDM-LSA-PREFIX;
    }

    container grace-lsa {
      when "../lsa-info-type = 'mgmt-lsa-gr-type'" {
        description "../LSAInfoType = 'MGMT_LSA_GR_TYPE'";
      }
      description "Grace LSA";
      uses OSPFV3-EDM-LSA-GRACE;
    }

    container unknown-link-lsa-type {
      when "../lsa-info-type = 'mgmt-lsa-unk-link-type'" {
        description "../LSAInfoType = 'MGMT_LSA_UNK_LINK_TYPE'";
      }
      description "Unknown Link Scope LSA";
      uses OSPFV3-EDM-LSA-UNKNOWN;
    }

    container unknown-area-lsa-type {
      when "../lsa-info-type = 'mgmt-lsa-unk-area-type'" {
        description "../LSAInfoType = 'MGMT_LSA_UNK_AREA_TYPE'";
      }
      description "Unknown-Area scope LSA";
      uses OSPFV3-EDM-LSA-UNKNOWN;
    }

    container unknown-aslsa-type {
      when "../lsa-info-type = 'mgmt-lsa-unk-as-type'" {
        description "../LSAInfoType = 'MGMT_LSA_UNK_AS_TYPE'";
      }
      description "Unknown-AS scope LSA";
      uses OSPFV3-EDM-LSA-UNKNOWN;
    }

    container unknown-lsa-type {
      when "../lsa-info-type = 'mgmt-lsa-unk-type'" {
        description "../LSAInfoType = 'MGMT_LSA_UNK_TYPE'";
      }
      description "Unknown LSA";
      uses OSPFV3-EDM-LSA-UNKNOWN;
    }
    leaf lsa-info-type {
      xr:xr-xml-map "ospfv3_edm_show:LSAInfoType";
      type Ospfv3-lsa-info-types;
      description "LSAInfoType";
    }
  }

  grouping OSPFV3-EDM-DATABASE-LSAINFO {
    description "OSPFv3 LSA Information";

    container lsa-info {
      description
        "Summary of all LSAs or LSA specific information ";
      uses OSPFV3-LSA-INFO-UNION;
    }
  }

  grouping OSPFV3-EDM-AREA-RANGE {
    description "OSPFv3 area range information";
    leaf range-prefix {
      xr:xr-xml-map "ospfv3_edm_show:RangePrefix";
      type inet:ipv6-address;
      description "IP prefix for summarization";
    }
    leaf range-prefix-length {
      xr:xr-xml-map "ospfv3_edm_show:RangePrefixLength";
      type uint32;
      description "IP prefix length for summarization";
    }
    leaf net-cost {
      xr:xr-xml-map "ospfv3_edm_show:NetCost";
      type uint32;
      description "Net cost ";
    }
    leaf status {
      xr:xr-xml-map "ospfv3_edm_show:Status";
      type Ospfv3-area-range-status;
      description "Area range status ";
    }
    leaf is-cost-configured {
      xr:xr-xml-map "ospfv3_edm_show:IsCostConfigured";
      type boolean;
      description "If true, cost is configured ";
    }
  }

  grouping OSPFV3-EDM-AREA {
    description "OSPFv3 area summary information";
    leaf is-backbone-area-active {
      xr:xr-xml-map "ospfv3_edm_show:IsBackboneAreaActive";
      type boolean;
      description "If true, Backbone area is active";
    }
    leaf area-interfaces {
      xr:xr-xml-map "ospfv3_edm_show:AreaInterfaces";
      type uint16;
      description "Number of interfaces in the area";
    }
    leaf is-area-stubbed {
      xr:xr-xml-map "ospfv3_edm_show:IsAreaStubbed";
      type boolean;
      description "If true, stub area";
    }
    leaf is-area-total-stubbed {
      xr:xr-xml-map "ospfv3_edm_show:IsAreaTotalStubbed";
      type boolean;
      description "If true, totally stubby area";
    }
    leaf stub-default-cost {
      xr:xr-xml-map "ospfv3_edm_show:StubDefaultCost";
      type uint16;
      description "Default cost for Stub or NSSA area";
    }
    leaf is-area-nssa {
      xr:xr-xml-map "ospfv3_edm_show:IsAreaNSSA";
      type boolean;
      description "If true, area is a NSSA";
    }
    leaf nssa-no-redistribution {
      xr:xr-xml-map "ospfv3_edm_show:NSSANoRedistribution";
      type boolean;
      description "If true, No redistribution into this NSSA area";
    }
    leaf is-nssa-translated {
      xr:xr-xml-map "ospfv3_edm_show:IsNSSATranslated";
      type boolean;
      description "If true, perform 7/5 translation";
    }
    leaf is-nssa-default {
      xr:xr-xml-map "ospfv3_edm_show:IsNSSADefault";
      type boolean;
      description "If true, generate NSSA default route";
    }
    leaf is-rrr-enabled {
      xr:xr-xml-map "ospfv3_edm_show:IsRRREnabled";
      type boolean;
      description "If true, RRR is enabled";
    }
    leaf sp-fs {
      xr:xr-xml-map "ospfv3_edm_show:SPFs";
      type uint32;
      description "Number of SPF calculations run";
    }
    leaf area-opaque-lsas {
      xr:xr-xml-map "ospfv3_edm_show:AreaOpaqueLSAs";
      type uint32;
      description "Number of opaque LSAs in the area";
    }
    leaf area-opaque-lsa-checksum {
      xr:xr-xml-map "ospfv3_edm_show:AreaOpaqueLSAChecksum";
      type uint32;
      description "Sum of opaque LSA checksums";
    }
    leaf area-dc-bitless-ls-as {
      xr:xr-xml-map "ospfv3_edm_show:AreaDCBitlessLSAs";
      type uint32;
      description "Number of LSA with demand circuit bit not set";
    }
    leaf indication-ls-as {
      xr:xr-xml-map "ospfv3_edm_show:IndicationLSAs";
      type uint32;
      description "Number of indication LSAs";
    }
    leaf do-not-age-ls-as {
      xr:xr-xml-map "ospfv3_edm_show:DoNotAgeLSAs";
      type uint32;
      description "Number of do not age LSAs";
    }
    leaf flood-list-length {
      xr:xr-xml-map "ospfv3_edm_show:FloodListLength";
      type uint32;
      description "Number of LSAs which need to be flooded";
    }
    leaf area-lfa-interface-count {
      xr:xr-xml-map "ospfv3_edm_show:AreaLFAInterfaceCount";
      type uint32;
      description "Number of LFA enabled interfaces";
    }
    leaf area-per-prefix-lfa-interface-count {
      xr:xr-xml-map "ospfv3_edm_show:AreaPerPrefixLFAInterfaceCount";
      type uint32;
      description "Number of Per Prefix LFA enabled interfaces";
    }
    leaf area-lfa-revision {
      xr:xr-xml-map "ospfv3_edm_show:AreaLFARevision";
      type uint32;
      description "Area LFA revision";
    }

    list area-range {
      description "List of ranges to summarize";
      uses OSPFV3-EDM-AREA-RANGE;
    }
  }

  grouping OSPFV3-EDM-NEIGHBOR-RETRANS {
    description "OSPFv3 neighbor retransmission information";
    leaf database-descriptor-retransmissions {
      xr:xr-xml-map "ospfv3_edm_show:DatabaseDescriptorRetransmissi"+
        "ons";
      type uint32;
      description
        "Number of database descriptor retransmissions
        during last exchange";
    }
    leaf area-flood-index {
      xr:xr-xml-map "ospfv3_edm_show:AreaFloodIndex";
      type uint32;
      description "Area scope LSA's flood index";
    }
    leaf as-flood-index {
      xr:xr-xml-map "ospfv3_edm_show:ASFloodIndex";
      type uint32;
      description "AS scope LSA's flood index";
    }
    leaf link-flood-index {
      xr:xr-xml-map "ospfv3_edm_show:LinkFloodIndex";
      type uint32;
      description "Link flood index";
    }
    leaf neighbor-retransmissions {
      xr:xr-xml-map "ospfv3_edm_show:NeighborRetransmissions";
      type uint32;
      description "Number of neighbor retransmissions ";
    }
    leaf retransmissions {
      xr:xr-xml-map "ospfv3_edm_show:Retransmissions";
      type uint32;
      description "Number of retransmissions for this neighbor";
    }
    leaf area-first-flood {
      xr:xr-xml-map "ospfv3_edm_show:AreaFirstFlood";
      type uint32;
      description "First flood item for area scope LSAs";
    }
    leaf area-first-flood-index {
      xr:xr-xml-map "ospfv3_edm_show:AreaFirstFloodIndex";
      type uint32;
      description
        "Index of the first flood item for area scope
        LSAs";
    }
    leaf as-first-flood {
      xr:xr-xml-map "ospfv3_edm_show:ASFirstFlood";
      type uint32;
      description "First flood item for AS scope LSAs";
    }
    leaf as-first-flood-index {
      xr:xr-xml-map "ospfv3_edm_show:ASFirstFloodIndex";
      type uint32;
      description "Index for first flood item for AS scope LSAs";
    }
    leaf link-first-flood {
      xr:xr-xml-map "ospfv3_edm_show:LinkFirstFlood";
      type uint32;
      description "Link first flood information ";
    }
    leaf link-first-flood-index {
      xr:xr-xml-map "ospfv3_edm_show:LinkFirstFloodIndex";
      type uint32;
      description "Link first flood information index";
    }
    leaf area-next-flood {
      xr:xr-xml-map "ospfv3_edm_show:AreaNextFlood";
      type uint32;
      description "Next flood item for area scope LSAs";
    }
    leaf area-next-flood-index {
      xr:xr-xml-map "ospfv3_edm_show:AreaNextFloodIndex";
      type uint32;
      description "Index of next flood item for Area scope LSAs";
    }
    leaf as-next-flood {
      xr:xr-xml-map "ospfv3_edm_show:ASNextFlood";
      type uint32;
      description "Next flood item for AS scope LSAs";
    }
    leaf as-next-flood-index {
      xr:xr-xml-map "ospfv3_edm_show:ASNextFloodIndex";
      type uint32;
      description "Index of next flood item for AS scope LSAs";
    }
    leaf link-next-flood {
      xr:xr-xml-map "ospfv3_edm_show:LinkNextFlood";
      type uint32;
      description "Link next flood information ";
    }
    leaf link-next-flood-index {
      xr:xr-xml-map "ospfv3_edm_show:LinkNextFloodIndex";
      type uint32;
      description "Link next flood information index ";
    }
    leaf last-retransmission-length {
      xr:xr-xml-map "ospfv3_edm_show:LastRetransmissionLength";
      type uint32;
      description "Number of LSAs sent in last retransmission";
    }
    leaf maximum-retransmission-length {
      xr:xr-xml-map "ospfv3_edm_show:MaximumRetransmissionLength";
      type uint32;
      description "Maximum number of LSAs sent in a retransmission";
    }
    leaf last-retransmission-time {
      xr:xr-xml-map "ospfv3_edm_show:LastRetransmissionTime";
      type uint32;
      description "Last retransmission scan time (ms)";
    }
    leaf maximum-retransmission-time {
      xr:xr-xml-map "ospfv3_edm_show:MaximumRetransmissionTime";
      type uint32;
      description "Maximum retransmission scan time (ms)";
    }
    leaf lsa-retransmission-timer {
      xr:xr-xml-map "ospfv3_edm_show:LSARetransmissionTimer";
      type uint32;
      description "Time until next LSA retransmission (ms)";
    }
  }

  grouping OSPFV3-SH-SLINK-NEIGHBOR {
    description "Sham Link Neighbor Information";

    container sham-link-retransmission {
      description "Neighbor retransmission info";
      uses OSPFV3-EDM-NEIGHBOR-RETRANS;
    }
    leaf sham-link-suppress-hello {
      xr:xr-xml-map "ospfv3_edm_show:ShamLinkSuppressHello";
      type boolean;
      description "If true Hellos suppressed";
    }
    leaf sham-link-state {
      xr:xr-xml-map "ospfv3_edm_show:ShamLinkState";
      type Ospfv3-neighbor-state;
      description "Adjacency state";
    }
  }

  grouping OSPFV3-SH-SHAM-LINKS {
    description "OSPFv3 Sham Link";

    container sham-link-neighbor {
      description "Neighbor information";
      uses OSPFV3-SH-SLINK-NEIGHBOR;
    }
    leaf sham-link-neighbor-id {
      xr:xr-xml-map "ospfv3_edm_show:ShamLinkNeighborID";
      type inet:ipv4-address;
      description "Neighbor on other end of this sham link";
    }
    leaf sham-link-source-address {
      xr:xr-xml-map "ospfv3_edm_show:ShamLinkSourceAddress";
      type inet:ipv6-address;
      description "Sham-link source";
    }
    leaf sham-link-dest-address {
      xr:xr-xml-map "ospfv3_edm_show:ShamLinkDestAddress";
      type inet:ipv6-address;
      description "Sham-link dest";
    }
    leaf sham-link-state {
      xr:xr-xml-map "ospfv3_edm_show:ShamLinkState";
      type Ospfv3-interface-state;
      description "OSPF interface state for the sham link";
    }
    leaf sham-link-demand-circuit {
      xr:xr-xml-map "ospfv3_edm_show:ShamLinkDemandCircuit";
      type boolean;
      description "If true, the link runs as demand circuit";
    }
    leaf sham-link-dc-bitless-lsa {
      xr:xr-xml-map "ospfv3_edm_show:ShamLinkDCBitlessLSA";
      type uint32;
      description "Number of LSA's with demand circuit bit not set";
    }
    leaf sham-link-ifindex {
      xr:xr-xml-map "ospfv3_edm_show:ShamLinkIfindex";
      type uint32;
      description "Sham-link ifindex";
    }
    leaf sham-link-area {
      xr:xr-xml-map "ospfv3_edm_show:ShamLinkArea";
      type string;
      description "Area id";
    }
    leaf sham-link-cost {
      xr:xr-xml-map "ospfv3_edm_show:ShamLinkCost";
      type uint16;
      description "Cost of the sham link";
    }
    leaf sham-link-transmission-delay {
      xr:xr-xml-map "ospfv3_edm_show:ShamLinkTransmissionDelay";
      type uint16;
      units "second";
      description "Transmission delay in seconds";
    }
    leaf sham-link-hello-interval {
      xr:xr-xml-map "ospfv3_edm_show:ShamLinkHelloInterval";
      type uint32;
      description "Hello interval (s)";
    }
    leaf sham-link-dead-interval {
      xr:xr-xml-map "ospfv3_edm_show:ShamLinkDeadInterval";
      type uint32;
      description "Dead interval (s)";
    }
    leaf sham-link-wait-interval {
      xr:xr-xml-map "ospfv3_edm_show:ShamLinkWaitInterval";
      type uint32;
      description "Wait interval (s)";
    }
    leaf sham-link-retransmission-interval {
      xr:xr-xml-map "ospfv3_edm_show:ShamLinkRetransmissionInterval";
      type uint32;
      description "Retransmission interval (s)";
    }
    leaf sham-link-next-hello {
      xr:xr-xml-map "ospfv3_edm_show:ShamLinkNextHello";
      type uint32;
      description "Time until next hello (s)";
    }
    leaf sham-link-passive {
      xr:xr-xml-map "ospfv3_edm_show:ShamLinkPassive";
      type boolean;
      description "If true, interface is passive";
    }
    leaf is-sham-link-ip-security-required {
      xr:xr-xml-map "ospfv3_edm_show:IsShamLinkIPSecurityRequired";
      type boolean;
      description "If true, sham link IP security is required ";
    }
    leaf is-sham-link-ip-security-active {
      xr:xr-xml-map "ospfv3_edm_show:IsShamLinkIPSecurityActive";
      type boolean;
      description "If true, Sham link IP security is active ";
    }
    leaf is-sham-link-authentication-enabled {
      xr:xr-xml-map "ospfv3_edm_show:IsShamLinkAuthenticationEnable"+
        "d";
      type boolean;
      description "If true, sham link authentication is enabled ";
    }
    leaf virtual-link-authentication-spi {
      xr:xr-xml-map "ospfv3_edm_show:VirtualLinkAuthenticationSPI";
      type uint32;
      description "Sham link authentication spi ";
    }
    leaf sham-link-authentication-transmit {
      xr:xr-xml-map "ospfv3_edm_show:ShamLinkAuthenticationTransmit";
      type uint32;
      description "Sham link authentication transmit ";
    }
    leaf is-sham-link-encryption-enabled {
      xr:xr-xml-map "ospfv3_edm_show:IsShamLinkEncryptionEnabled";
      type boolean;
      description "If true, sham link encryption is enabled ";
    }
    leaf sham-link-encryption-spi {
      xr:xr-xml-map "ospfv3_edm_show:ShamLinkEncryptionSPI";
      type uint32;
      description "Sham link encryption spi";
    }
    leaf sham-link-encryption-transmitted {
      xr:xr-xml-map "ospfv3_edm_show:ShamLinkEncryptionTransmitted";
      type uint32;
      description "Sham link encryption transmitted ";
    }
    leaf sham-link-encrypted-authentication-transmitted {
      xr:xr-xml-map "ospfv3_edm_show:ShamLinkEncryptedAuthenticatio"+
        "nTransmitted";
      type uint32;
      description "Sham link encrypted authentication transmitted ";
    }
    leaf sham-link-gr-enabled {
      xr:xr-xml-map "ospfv3_edm_show:ShamLinkGREnabled";
      type boolean;
      description "If true,  enabled";
    }
    leaf sham-link-gr {
      xr:xr-xml-map "ospfv3_edm_show:ShamLinkGR";
      type boolean;
      description "If true, Gracefule restart in progress";
    }
    leaf sham-link-last-gr {
      xr:xr-xml-map "ospfv3_edm_show:ShamLinkLastGR";
      type uint32;
      units "second";
      description "Time in seconds since last GR";
    }
  }

  grouping OSPFV3-EDM-BR-PATH {
    description "OSPFv3 border router path";
    leaf is-intra-area-router {
      xr:xr-xml-map "ospfv3_edm_show:IsIntraAreaRouter";
      type boolean;
      description
        "If true, intra-area router else inter-area
        router";
    }
    leaf border-router-route-metric {
      xr:xr-xml-map "ospfv3_edm_show:BorderRouterRouteMetric";
      type uint32;
      description "Metric";
    }
    leaf border-router-next-hop {
      xr:xr-xml-map "ospfv3_edm_show:BorderRouterNextHop";
      type inet:ipv6-address;
      description "Next hop address ";
    }
    leaf interface-name {
      xr:xr-xml-map "ospfv3_edm_show:InterfaceName";
      type xr:Interface-name;
      description "Next hop interface name";
    }
    leaf border-router-type {
      xr:xr-xml-map "ospfv3_edm_show:BorderRouterType";
      type Ospfv3-border-route;
      description "Border router type ";
    }
    leaf border-router-area-id {
      xr:xr-xml-map "ospfv3_edm_show:BorderRouterAreaID";
      type string {
        length "0..16";
      }
      description
        "Area string in decimal or dotted-decimal format ";
    }
    leaf spf-version {
      xr:xr-xml-map "ospfv3_edm_show:SPFVersion";
      type uint32;
      description "SPF version";
    }
  }

  grouping OSPFV3-EDM-BORDER-ROUTER {
    description "OSPFv3 border router information";

    list border-router-path {
      description "List of border router paths";
      uses OSPFV3-EDM-BR-PATH;
    }
  }

  grouping OSPFV3-EDM-SUMMARY-PREFIX {
    description "OSPFv3 summary prefix information";
    leaf prefix-metric {
      xr:xr-xml-map "ospfv3_edm_show:PrefixMetric";
      type uint32;
      description "Prefix metric";
    }
    leaf prefix-metric-type {
      xr:xr-xml-map "ospfv3_edm_show:PrefixMetricType";
      type Ospfv3-default-metric;
      description "Prefix metric type";
    }
    leaf tag {
      xr:xr-xml-map "ospfv3_edm_show:Tag";
      type uint32;
      description "Tag";
    }
  }
}
