//*************  DO-NOT EDIT  **************
//*********** Auto-generated file ********** 

 module cisco-openconfig-if-ethernet-devs {

  prefix  "ethdevs";

  namespace "http://cisco.com/ns/yang/openconfig-if-ethernet-devs";

  import openconfig-interfaces { prefix ocif; }
  import openconfig-if-ethernet { prefix eth; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-if-ethernet.yang@2015-11-20 

     on Cisco IOS-XR devices.

     Copyright (c) 2015-2016 by Cisco Systems, Inc.
     All rights reserved.";

  revision "2016-05-16" {
    description
      "Initial revision applicable to IOS-XR 6.0.1";
  }

  deviation /ocif:interfaces/ocif:interface/eth:ethernet/eth:config/eth:auto-negotiate {
    deviate delete {
      default true;
    }
  }

  deviation /ocif:interfaces/ocif:interface/eth:ethernet/eth:state/eth:auto-negotiate {
    deviate delete {
      default true;
    }
  }

  deviation /ocif:interfaces/ocif:interface/eth:ethernet/eth:state/eth:counters/eth:in-mac-control-frames {
    deviate not-supported;
  }

  deviation /ocif:interfaces/ocif:interface/eth:ethernet/eth:state/eth:counters/eth:out-mac-control-frames {
    deviate not-supported;
  }


}
//total deviations:4
