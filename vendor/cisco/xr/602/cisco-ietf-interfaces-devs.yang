//*************  DO-NOT EDIT  **************
//*********** Auto-generated file ********** 

 module cisco-ietf-interfaces-devs {

  prefix  "ifdevs";

  namespace "http://cisco.com/ns/yang/ietf-interfaces-devs";

  import ietf-interfaces { prefix if; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     ietf-interfaces.yang@2013-12-23 

     on Cisco IOS-XR devices.

     Copyright (c) 2015-2016 by Cisco Systems, Inc.
     All rights reserved.";

  revision "2016-05-16" {
    description
      "Initial revision applicable to IOS-XR 6.0.1";
  }


  deviation /if:interfaces/if:interface {
    deviate not-supported;
  }

  deviation /if:interfaces-state/if:interface {
    deviate not-supported;
  }


}
//total deviations:2
