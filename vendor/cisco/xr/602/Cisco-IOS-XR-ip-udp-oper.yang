module Cisco-IOS-XR-ip-udp-oper {

  /*** NAMESPACE / PREFIX DEFINITION ***/

  namespace "http://cisco.com/ns/yang/Cisco-IOS-XR-ip-udp-oper";


  prefix "ip-udp-oper";

  /*** LINKAGE (IMPORTS / INCLUDES) ***/

  import Cisco-IOS-XR-types { prefix "xr"; }

  include Cisco-IOS-XR-ip-udp-oper-sub4 {
    revision-date 2015-11-09;
  }

  include Cisco-IOS-XR-ip-udp-oper-sub3 {
    revision-date 2015-11-09;
  }

  include Cisco-IOS-XR-ip-udp-oper-sub2 {
    revision-date 2015-11-09;
  }

  include Cisco-IOS-XR-ip-udp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-udp package operational data.

     This module contains definitions
     for the following management objects:
       udp: IP UDP Operational Data
       udp-connection: udp connection

     Copyright (c) 2013-2015 by Cisco Systems, Inc.
     All rights reserved.";

  revision "2015-11-09" {
    description
      "IOS XR 6.0 revision.";
  }

  typedef Lpts-pcb-query {
    type enumeration {
      enum all {
        value 0;
        description "No filter";
      }
      enum static-policy {
        value 1;
        description "Static policy filter";
      }
      enum interface {
        value 2;
        description "Interface filter";
      }
      enum packet {
        value 3;
        description "Packet type filter";
      }
    }
    description "Lpts pcb query";
  }

  container udp {
    xr:xr-xml-map "ip_udp_traffic_oper:UDP";
    config false;
    description "IP UDP Operational Data";

    container nodes {
      xr:xr-xml-map "ip_udp_traffic_oper:NodeTable";
      description "Node-specific UDP operational data";

      list node {
        xr:xr-xml-map "ip_udp_traffic_oper:Node";
        key "node-name";
        description "UDP operational data for a particular node";

        container statistics {
          xr:xr-xml-map "ip_udp_traffic_oper:Statistics";
          description "Statistical UDP operational data for a node";

          container ipv4-traffic {
            xr:xr-xml-map "ip_udp_traffic_oper:IPv4Traffic";
            description "UDP Traffic statistics for IPv4";
            uses IP-UDP;
          }

          container ipv6-traffic {
            xr:xr-xml-map "ip_udp_traffic_oper:IPv6Traffic";
            description "UDP Traffic statistics for IPv6";
            uses IP-UDP;
          }
        }
        leaf node-name {
          xr:xr-xml-map "ip_udp_traffic_oper:NodeName";
          type xr:Node-id;
          description "Node name";
        }
      }
    }
  }

  container udp-connection {
    xr:xr-xml-map "ip_udp_oper:UDPConnection";
    config false;
    description "udp connection";

    container nodes {
      xr:xr-xml-map "ip_udp_oper:NodeTable";
      description "List of UDP connections nodes";

      list node {
        xr:xr-xml-map "ip_udp_oper:Node";
        key "node-name";
        description "Information about a particular node";

        container statistics {
          xr:xr-xml-map "ip_udp_oper:Statistics";
          description "Statistics of UDP connections";

          container clients {
            xr:xr-xml-map "ip_udp_oper:ClientTable";
            description "Table listing clients";

            list client {
              xr:xr-xml-map "ip_udp_oper:Client";
              key "client-id";
              description "Describing Client ID";
              leaf client-id {
                xr:xr-xml-map "ip_udp_oper:ClientID";
                type uint32 {
                  range "0..4294967295";
                }
                description
                  "Displaying client's aggregated statistics";
              }
              uses TRANSP-CLIENT-STATS-BAG;
            }
          }

          container summary {
            xr:xr-xml-map "ip_udp_oper:Summary";
            description
              "Summary statistics across all UDP connections";
            uses UDP-SH-STATS-BAG;
          }

          container pcb-statistics {
            xr:xr-xml-map "ip_udp_oper:PCBStatisticsTable";
            description
              "Table listing the UDP connections for which
              statistics are provided";

            list pcb-statistic {
              xr:xr-xml-map "ip_udp_oper:PCBStatistics";
              key "pcb-address";
              description
                "Satistics associated with a particular PCB";
              leaf pcb-address {
                xr:xr-xml-map "ip_udp_oper:PCBAddress";
                type int32;
                description "Protocol Control Block address";
              }
              uses UDP-SH-PCB-STATS-BAG;
            }
          }
        }

        container lpts {
          xr:xr-xml-map "ip_udp_oper:LPTS";
          description "LPTS statistical data";

          container queries {
            xr:xr-xml-map "ip_udp_oper:QueryTable";
            description "List of query options";

            list query {
              xr:xr-xml-map "ip_udp_oper:Query";
              key "query-name";
              description "Query option";

              container pcbs {
                xr:xr-xml-map "ip_udp_oper:PCBTable";
                description "List of PCBs";

                list pcb {
                  xr:xr-xml-map "ip_udp_oper:PCB";
                  key "pcb-address";
                  description "A PCB information";
                  leaf pcb-address {
                    xr:xr-xml-map "ip_udp_oper:PCBAddress";
                    type int32;
                    description "PCB address";
                  }
                  uses SHOW-PCB-INFO;
                }
              }
              leaf query-name {
                xr:xr-xml-map "ip_udp_oper:QueryName";
                type Lpts-pcb-query;
                description "Query option";
              }
            }
          }
        }

        container pcb-details {
          xr:xr-xml-map "ip_udp_oper:PCBDetailTable";
          description
            "Detail information for list of UDP connections
            .";

          list pcb-detail {
            xr:xr-xml-map "ip_udp_oper:PCBDetail";
            key "pcb-address";
            description "Detail information about a UDP connection";
            leaf pcb-address {
              xr:xr-xml-map "ip_udp_oper:PCBAddress";
              type int32;
              description "Protocol Control Block address";
            }
            uses UDP-SH-TABLE-BAG;
          }
        }

        container pcb-briefs {
          xr:xr-xml-map "ip_udp_oper:PCBBriefTable";
          description
            "Brief information for list of UDP connections.";

          list pcb-brief {
            xr:xr-xml-map "ip_udp_oper:PCBBrief";
            key "pcb-address";
            description "Brief information about a UDP connection";
            leaf pcb-address {
              xr:xr-xml-map "ip_udp_oper:PCBAddress";
              type int32;
              description "Protocol Control Block address";
            }
            uses UDP-SH-BRIEF-BAG;
          }
        }
        leaf node-name {
          xr:xr-xml-map "ip_udp_oper:NodeName";
          type xr:Node-id;
          description "Node name";
        }
      }
    }
  }
}
