submodule Cisco-IOS-XR-l2vpn-oper-sub1 {

  belongs-to Cisco-IOS-XR-l2vpn-oper {
    prefix Cisco-IOS-XR-l2vpn-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR l2vpn package operational data.

     Copyright (c) 2013-2015 by Cisco Systems, Inc.
     All rights reserved.";

  revision "2015-11-09" {
    description
      "IOS XR 6.0 revision.";
  }

  typedef Iflist-rep-status {
    type enumeration {
      enum invalid {
        value 0;
        description "Invalid";
      }
      enum pending {
        value 1;
        description "Pending";
      }
      enum done {
        value 2;
        description "Done";
      }
      enum not-supported {
        value 3;
        description "Not supported";
      }
      enum failed {
        value 4;
        description "Failed";
      }
    }
    description "Interface list replication status";
  }

  grouping IFLIST-IFL {
    description "Generic interface list info";
    leaf interface-list-name {
      xr:xr-xml-map "iflist:InterfaceListName";
      type string {
        length "0..33";
      }
      description "Interface-list name";
    }
    leaf interface-list-id {
      xr:xr-xml-map "iflist:InterfaceListID";
      type uint32;
      description "Interface internal ID";
    }
    leaf items {
      xr:xr-xml-map "iflist:Items";
      type uint32;
      description
        "Number of items on which interface list is
        replicated";
    }
    leaf is-provisioned {
      xr:xr-xml-map "iflist:IsProvisioned";
      type boolean;
      description "Is Provisioned";
    }
    leaf is-fib-downloaded {
      xr:xr-xml-map "iflist:IsFIBDownloaded";
      type boolean;
      description "Is Interface list downloaded to FIB";
    }

    list interface {
      description "Interfaces";
      uses IFLIST-IF;
    }
  }

  grouping IFLIST-IF {
    description "Interface info for Generic interface list";
    leaf interface-name {
      xr:xr-xml-map "iflist:InterfaceName";
      type string;
      description "Interface name";
    }
    leaf pending-replications {
      xr:xr-xml-map "iflist:PendingReplications";
      type uint32;
      description "Number of pending replications";
    }
    leaf not-supported-replications {
      xr:xr-xml-map "iflist:NotSupportedReplications";
      type uint32;
      description
        "Number of replications failed because
        unsupported";
    }
    leaf is-fib-downloaded {
      xr:xr-xml-map "iflist:IsFIBDownloaded";
      type boolean;
      description "Is interface downloaded to FIB";
    }
  }

  grouping ITEM-IFLIST-IF {
    description "Interface info for Generic interface list";
    leaf interface-name {
      xr:xr-xml-map "iflist:InterfaceName";
      type string;
      description "Interface name";
    }
    leaf replicate-status {
      xr:xr-xml-map "iflist:ReplicateStatus";
      type Iflist-rep-status;
      description "Replicate status";
    }
  }

  grouping ITEM-IFLIST-IFL {
    description "Generic interface list info";
    leaf interface-list-name {
      xr:xr-xml-map "iflist:InterfaceListName";
      type string {
        length "0..33";
      }
      description "Interface-list name";
    }
    leaf interface-list-id {
      xr:xr-xml-map "iflist:InterfaceListID";
      type uint32;
      description "Interface internal ID";
    }

    list interface {
      max-elements "8";
      description "Interfaces";
      uses ITEM-IFLIST-IF;
    }
  }
}
