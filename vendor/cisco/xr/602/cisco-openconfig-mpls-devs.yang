//*************  DO-NOT EDIT  **************
//*********** Auto-generated file ********** 

 module cisco-openconfig-mpls-devs {

  prefix  "mplsdevs";

  namespace "http://cisco.com/ns/yang/openconfig-mpls-devs";

  import openconfig-mpls { prefix mpls; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-mpls.yang@2015-11-05 

     on Cisco IOS-XR devices.

     Copyright (c) 2015-2016 by Cisco Systems, Inc.
     All rights reserved.";

  revision "2016-05-16" {
    description
      "Initial revision applicable to IOS-XR 6.0.1";
  }


  deviation /mpls:mpls/mpls:global/mpls:config/mpls:null-label {
    deviate not-supported;
  }

  deviation /mpls:mpls/mpls:global/mpls:state/mpls:null-label {
    deviate not-supported;
  }

  deviation /mpls:mpls/mpls:global/mpls:mpls-interface-attributes/mpls:interface {
    deviate not-supported;
  }

  deviation /mpls:mpls/mpls:te-global-attributes/mpls:srlg/mpls:srlg/mpls:config/mpls:flooding-type {
    deviate not-supported;
  }

  deviation /mpls:mpls/mpls:te-global-attributes/mpls:srlg/mpls:srlg/mpls:state/mpls:name {
    deviate not-supported;
  }

  deviation /mpls:mpls/mpls:te-global-attributes/mpls:srlg/mpls:srlg/mpls:state/mpls:value {
    deviate not-supported;
  }

  deviation /mpls:mpls/mpls:te-global-attributes/mpls:srlg/mpls:srlg/mpls:state/mpls:cost {
    deviate not-supported;
  }

  deviation /mpls:mpls/mpls:te-global-attributes/mpls:srlg/mpls:srlg/mpls:state/mpls:flooding-type {
    deviate not-supported;
  }

  deviation /mpls:mpls/mpls:te-global-attributes/mpls:srlg/mpls:srlg/mpls:static-srlg-members/mpls:members-list/mpls:state/mpls:from-address {
    deviate not-supported;
  }

  deviation /mpls:mpls/mpls:te-global-attributes/mpls:srlg/mpls:srlg/mpls:static-srlg-members/mpls:members-list/mpls:state/mpls:to-address {
    deviate not-supported;
  }

  deviation /mpls:mpls/mpls:te-global-attributes/mpls:igp-flooding-bandwidth/mpls:config/mpls:threshold-type {
    deviate not-supported;
  }

  deviation /mpls:mpls/mpls:te-global-attributes/mpls:igp-flooding-bandwidth/mpls:config/mpls:threshold-specification {
    deviate not-supported;
  }

  deviation /mpls:mpls/mpls:te-global-attributes/mpls:igp-flooding-bandwidth/mpls:config/mpls:up-thresholds {
    deviate not-supported;
  }

  deviation /mpls:mpls/mpls:te-global-attributes/mpls:igp-flooding-bandwidth/mpls:config/mpls:down-thresholds {
    deviate not-supported;
  }

  deviation /mpls:mpls/mpls:te-global-attributes/mpls:igp-flooding-bandwidth/mpls:config/mpls:up-down-thresholds {
    deviate not-supported;
  }

  deviation /mpls:mpls/mpls:te-global-attributes/mpls:igp-flooding-bandwidth/mpls:state/mpls:threshold-type {
    deviate not-supported;
  }

  deviation /mpls:mpls/mpls:te-global-attributes/mpls:igp-flooding-bandwidth/mpls:state/mpls:delta-percentage {
    deviate not-supported;
  }

  deviation /mpls:mpls/mpls:te-global-attributes/mpls:igp-flooding-bandwidth/mpls:state/mpls:threshold-specification {
    deviate not-supported;
  }

  deviation /mpls:mpls/mpls:te-global-attributes/mpls:igp-flooding-bandwidth/mpls:state/mpls:up-thresholds {
    deviate not-supported;
  }

  deviation /mpls:mpls/mpls:te-global-attributes/mpls:igp-flooding-bandwidth/mpls:state/mpls:down-thresholds {
    deviate not-supported;
  }

  deviation /mpls:mpls/mpls:te-global-attributes/mpls:igp-flooding-bandwidth/mpls:state/mpls:up-down-thresholds {
    deviate not-supported;
  }

  deviation /mpls:mpls/mpls:te-global-attributes/mpls:mpls-admin-groups/mpls:admin-group/mpls:state/mpls:admin-group-name {
    deviate not-supported;
  }

  deviation /mpls:mpls/mpls:te-global-attributes/mpls:mpls-admin-groups/mpls:admin-group/mpls:state/mpls:bit-position {
    deviate not-supported;
  }

  deviation /mpls:mpls/mpls:te-global-attributes/mpls:te-lsp-timers/mpls:state/mpls:cleanup-delay {
    deviate not-supported;
  }

  deviation /mpls:mpls/mpls:te-global-attributes/mpls:te-lsp-timers/mpls:state/mpls:reoptimize-timer {
    deviate not-supported;
  }

  deviation /mpls:mpls/mpls:te-interface-attributes/mpls:interface/mpls:state/mpls:name {
    deviate not-supported;
  }

  deviation /mpls:mpls/mpls:te-interface-attributes/mpls:interface/mpls:state/mpls:te-metric {
    deviate not-supported;
  }

  deviation /mpls:mpls/mpls:te-interface-attributes/mpls:interface/mpls:state/mpls:srlg-membership {
    deviate not-supported;
  }

  deviation /mpls:mpls/mpls:te-interface-attributes/mpls:interface/mpls:state/mpls:admin-group {
    deviate not-supported;
  }

  deviation /mpls:mpls/mpls:te-interface-attributes/mpls:interface/mpls:igp-flooding-bandwidth/mpls:config/mpls:threshold-type {
    deviate not-supported;
  }

  deviation /mpls:mpls/mpls:te-interface-attributes/mpls:interface/mpls:igp-flooding-bandwidth/mpls:config/mpls:delta-percentage {
    deviate not-supported;
  }

  deviation /mpls:mpls/mpls:te-interface-attributes/mpls:interface/mpls:igp-flooding-bandwidth/mpls:config/mpls:threshold-specification {
    deviate not-supported;
  }

  deviation /mpls:mpls/mpls:te-interface-attributes/mpls:interface/mpls:igp-flooding-bandwidth/mpls:config/mpls:up-down-thresholds {
    deviate not-supported;
  }

  deviation /mpls:mpls/mpls:te-interface-attributes/mpls:interface/mpls:igp-flooding-bandwidth/mpls:state/mpls:threshold-type {
    deviate not-supported;
  }

  deviation /mpls:mpls/mpls:te-interface-attributes/mpls:interface/mpls:igp-flooding-bandwidth/mpls:state/mpls:delta-percentage {
    deviate not-supported;
  }

  deviation /mpls:mpls/mpls:te-interface-attributes/mpls:interface/mpls:igp-flooding-bandwidth/mpls:state/mpls:threshold-specification {
    deviate not-supported;
  }

  deviation /mpls:mpls/mpls:te-interface-attributes/mpls:interface/mpls:igp-flooding-bandwidth/mpls:state/mpls:up-thresholds {
    deviate not-supported;
  }

  deviation /mpls:mpls/mpls:te-interface-attributes/mpls:interface/mpls:igp-flooding-bandwidth/mpls:state/mpls:down-thresholds {
    deviate not-supported;
  }

  deviation /mpls:mpls/mpls:te-interface-attributes/mpls:interface/mpls:igp-flooding-bandwidth/mpls:state/mpls:up-down-thresholds {
    deviate not-supported;
  }

  deviation /mpls:mpls/mpls:signaling-protocols/mpls:rsvp-te/mpls:sessions/mpls:state/mpls:session {
    deviate not-supported;
  }

  deviation /mpls:mpls/mpls:signaling-protocols/mpls:rsvp-te/mpls:neighbors/mpls:state/mpls:neighbor {
    deviate not-supported;
  }

  deviation /mpls:mpls/mpls:signaling-protocols/mpls:rsvp-te/mpls:global/mpls:graceful-restart/mpls:state/mpls:enable {
    deviate not-supported;
  }

  deviation /mpls:mpls/mpls:signaling-protocols/mpls:rsvp-te/mpls:global/mpls:graceful-restart/mpls:state/mpls:restart-time {
    deviate not-supported;
  }

  deviation /mpls:mpls/mpls:signaling-protocols/mpls:rsvp-te/mpls:global/mpls:graceful-restart/mpls:state/mpls:recovery-time {
    deviate not-supported;
  }

  deviation /mpls:mpls/mpls:signaling-protocols/mpls:rsvp-te/mpls:global/mpls:soft-preemption/mpls:state/mpls:enable {
    deviate not-supported;
  }

  deviation /mpls:mpls/mpls:signaling-protocols/mpls:rsvp-te/mpls:global/mpls:soft-preemption/mpls:state/mpls:soft-preemption-timeout {
    deviate not-supported;
  }

  deviation /mpls:mpls/mpls:signaling-protocols/mpls:rsvp-te/mpls:global/mpls:hellos/mpls:config/mpls:refresh-reduction {
    deviate not-supported;
  }

  deviation /mpls:mpls/mpls:signaling-protocols/mpls:rsvp-te/mpls:global/mpls:hellos/mpls:state/mpls:hello-interval {
    deviate not-supported;
  }

  deviation /mpls:mpls/mpls:signaling-protocols/mpls:rsvp-te/mpls:global/mpls:hellos/mpls:state/mpls:refresh-reduction {
    deviate not-supported;
  }

  deviation /mpls:mpls/mpls:signaling-protocols/mpls:rsvp-te/mpls:global/mpls:state/mpls:counters/mpls:path-timeouts {
    deviate not-supported;
  }

  deviation /mpls:mpls/mpls:signaling-protocols/mpls:rsvp-te/mpls:global/mpls:state/mpls:counters/mpls:reservation-timeouts {
    deviate not-supported;
  }

  deviation /mpls:mpls/mpls:signaling-protocols/mpls:rsvp-te/mpls:interface-attributes/mpls:interface/mpls:state/mpls:bandwidth {
    deviate not-supported;
  }

  deviation /mpls:mpls/mpls:signaling-protocols/mpls:rsvp-te/mpls:interface-attributes/mpls:interface/mpls:state/mpls:highwater-mark {
    deviate not-supported;
  }

  deviation /mpls:mpls/mpls:signaling-protocols/mpls:rsvp-te/mpls:interface-attributes/mpls:interface/mpls:state/mpls:active-reservation-count {
    deviate not-supported;
  }

  deviation /mpls:mpls/mpls:signaling-protocols/mpls:rsvp-te/mpls:interface-attributes/mpls:interface/mpls:hellos/mpls:config/mpls:hello-interval {
    deviate not-supported;
  }

  deviation /mpls:mpls/mpls:signaling-protocols/mpls:rsvp-te/mpls:interface-attributes/mpls:interface/mpls:hellos/mpls:state/mpls:hello-interval {
    deviate not-supported;
  }

  deviation /mpls:mpls/mpls:signaling-protocols/mpls:rsvp-te/mpls:interface-attributes/mpls:interface/mpls:hellos/mpls:state/mpls:refresh-reduction {
    deviate not-supported;
  }

  deviation /mpls:mpls/mpls:signaling-protocols/mpls:rsvp-te/mpls:interface-attributes/mpls:interface/mpls:authentication/mpls:state/mpls:enable {
    deviate not-supported;
  }

  deviation /mpls:mpls/mpls:signaling-protocols/mpls:rsvp-te/mpls:interface-attributes/mpls:interface/mpls:authentication/mpls:state/mpls:authentication-key {
    deviate not-supported;
  }

  deviation /mpls:mpls/mpls:signaling-protocols/mpls:rsvp-te/mpls:interface-attributes/mpls:interface/mpls:subscription/mpls:state/mpls:subscription {
    deviate not-supported;
  }

  deviation /mpls:mpls/mpls:signaling-protocols/mpls:rsvp-te/mpls:interface-attributes/mpls:interface/mpls:protection/mpls:config/mpls:bypass-optimize-interval {
    deviate not-supported;
  }

  deviation /mpls:mpls/mpls:signaling-protocols/mpls:rsvp-te/mpls:interface-attributes/mpls:interface/mpls:protection/mpls:state/mpls:link-protection-style-requested {
    deviate not-supported;
  }

  deviation /mpls:mpls/mpls:signaling-protocols/mpls:rsvp-te/mpls:interface-attributes/mpls:interface/mpls:protection/mpls:state/mpls:bypass-optimize-interval {
    deviate not-supported;
  }

  deviation /mpls:mpls/mpls:signaling-protocols/mpls:segment-routing/mpls:srgb {
    deviate not-supported;
  }

  deviation /mpls:mpls/mpls:signaling-protocols/mpls:segment-routing/mpls:interfaces {
    deviate not-supported;
  }

  deviation /mpls:mpls/mpls:lsps/mpls:constrained-path/mpls:named-explicit-paths/mpls:state/mpls:name {
    deviate not-supported;
  }

  deviation /mpls:mpls/mpls:lsps/mpls:constrained-path/mpls:named-explicit-paths/mpls:explicit-route-objects/mpls:state/mpls:address {
    deviate not-supported;
  }

  deviation /mpls:mpls/mpls:lsps/mpls:constrained-path/mpls:named-explicit-paths/mpls:explicit-route-objects/mpls:state/mpls:hop-type {
    deviate not-supported;
  }

  deviation /mpls:mpls/mpls:lsps/mpls:constrained-path/mpls:named-explicit-paths/mpls:explicit-route-objects/mpls:state/mpls:index {
    deviate not-supported;
  }

  deviation /mpls:mpls/mpls:lsps/mpls:constrained-path/mpls:tunnel/mpls:config/mpls:signaling-protocol {
    deviate not-supported;
  }

  deviation /mpls:mpls/mpls:lsps/mpls:constrained-path/mpls:tunnel/mpls:config/mpls:description {
    deviate not-supported;
  }

  deviation /mpls:mpls/mpls:lsps/mpls:constrained-path/mpls:tunnel/mpls:config/mpls:admin-status {
    deviate not-supported;
  }

  deviation /mpls:mpls/mpls:lsps/mpls:constrained-path/mpls:tunnel/mpls:config/mpls:preference {
    deviate not-supported;
  }

  deviation /mpls:mpls/mpls:lsps/mpls:constrained-path/mpls:tunnel/mpls:config/mpls:reoptimize-timer {
    deviate not-supported;
  }

  deviation /mpls:mpls/mpls:lsps/mpls:constrained-path/mpls:tunnel/mpls:config/mpls:source {
    deviate not-supported;
  }

  deviation /mpls:mpls/mpls:lsps/mpls:constrained-path/mpls:tunnel/mpls:state/mpls:name {
    deviate not-supported;
  }

  deviation /mpls:mpls/mpls:lsps/mpls:constrained-path/mpls:tunnel/mpls:state/mpls:type {
    deviate not-supported;
  }

  deviation /mpls:mpls/mpls:lsps/mpls:constrained-path/mpls:tunnel/mpls:state/mpls:signaling-protocol {
    deviate not-supported;
  }

  deviation /mpls:mpls/mpls:lsps/mpls:constrained-path/mpls:tunnel/mpls:state/mpls:local-id {
    deviate not-supported;
  }

  deviation /mpls:mpls/mpls:lsps/mpls:constrained-path/mpls:tunnel/mpls:state/mpls:description {
    deviate not-supported;
  }

  deviation /mpls:mpls/mpls:lsps/mpls:constrained-path/mpls:tunnel/mpls:state/mpls:admin-status {
    deviate not-supported;
  }

  deviation /mpls:mpls/mpls:lsps/mpls:constrained-path/mpls:tunnel/mpls:state/mpls:preference {
    deviate not-supported;
  }

  deviation /mpls:mpls/mpls:lsps/mpls:constrained-path/mpls:tunnel/mpls:state/mpls:metric {
    deviate not-supported;
  }

  deviation /mpls:mpls/mpls:lsps/mpls:constrained-path/mpls:tunnel/mpls:state/mpls:protection-style-requested {
    deviate not-supported;
  }

  deviation /mpls:mpls/mpls:lsps/mpls:constrained-path/mpls:tunnel/mpls:state/mpls:reoptimize-timer {
    deviate not-supported;
  }

  deviation /mpls:mpls/mpls:lsps/mpls:constrained-path/mpls:tunnel/mpls:state/mpls:source {
    deviate not-supported;
  }

  deviation /mpls:mpls/mpls:lsps/mpls:constrained-path/mpls:tunnel/mpls:state/mpls:soft-preemption {
    deviate not-supported;
  }

  deviation /mpls:mpls/mpls:lsps/mpls:constrained-path/mpls:tunnel/mpls:state/mpls:setup-priority {
    deviate not-supported;
  }

  deviation /mpls:mpls/mpls:lsps/mpls:constrained-path/mpls:tunnel/mpls:state/mpls:hold-priority {
    deviate not-supported;
  }

  deviation /mpls:mpls/mpls:lsps/mpls:constrained-path/mpls:tunnel/mpls:state/mpls:oper-status {
    deviate not-supported;
  }

  deviation /mpls:mpls/mpls:lsps/mpls:constrained-path/mpls:tunnel/mpls:state/mpls:role {
    deviate not-supported;
  }

  deviation /mpls:mpls/mpls:lsps/mpls:constrained-path/mpls:tunnel/mpls:state/mpls:counters/mpls:bytes {
    deviate not-supported;
  }

  deviation /mpls:mpls/mpls:lsps/mpls:constrained-path/mpls:tunnel/mpls:state/mpls:counters/mpls:packets {
    deviate not-supported;
  }

  deviation /mpls:mpls/mpls:lsps/mpls:constrained-path/mpls:tunnel/mpls:state/mpls:counters/mpls:path-changes {
    deviate not-supported;
  }

  deviation /mpls:mpls/mpls:lsps/mpls:constrained-path/mpls:tunnel/mpls:state/mpls:counters/mpls:state-changes {
    deviate not-supported;
  }

  deviation /mpls:mpls/mpls:lsps/mpls:constrained-path/mpls:tunnel/mpls:state/mpls:counters/mpls:online-time {
    deviate not-supported;
  }

  deviation /mpls:mpls/mpls:lsps/mpls:constrained-path/mpls:tunnel/mpls:state/mpls:counters/mpls:current-path-time {
    deviate not-supported;
  }

  deviation /mpls:mpls/mpls:lsps/mpls:constrained-path/mpls:tunnel/mpls:state/mpls:counters/mpls:next-reoptimization-time {
    deviate not-supported;
  }

  deviation /mpls:mpls/mpls:lsps/mpls:constrained-path/mpls:tunnel/mpls:bandwidth/mpls:config/mpls:specification-type {
    deviate not-supported;
  }

  deviation /mpls:mpls/mpls:lsps/mpls:constrained-path/mpls:tunnel/mpls:bandwidth/mpls:state/mpls:specification-type {
    deviate not-supported;
  }

  deviation /mpls:mpls/mpls:lsps/mpls:constrained-path/mpls:tunnel/mpls:bandwidth/mpls:state/mpls:set-bandwidth {
    deviate not-supported;
  }

  deviation /mpls:mpls/mpls:lsps/mpls:constrained-path/mpls:tunnel/mpls:bandwidth/mpls:auto-bandwidth/mpls:state/mpls:enabled {
    deviate not-supported;
  }

  deviation /mpls:mpls/mpls:lsps/mpls:constrained-path/mpls:tunnel/mpls:bandwidth/mpls:auto-bandwidth/mpls:state/mpls:min-bw {
    deviate not-supported;
  }

  deviation /mpls:mpls/mpls:lsps/mpls:constrained-path/mpls:tunnel/mpls:bandwidth/mpls:auto-bandwidth/mpls:state/mpls:max-bw {
    deviate not-supported;
  }

  deviation /mpls:mpls/mpls:lsps/mpls:constrained-path/mpls:tunnel/mpls:bandwidth/mpls:auto-bandwidth/mpls:state/mpls:adjust-interval {
    deviate not-supported;
  }

  deviation /mpls:mpls/mpls:lsps/mpls:constrained-path/mpls:tunnel/mpls:bandwidth/mpls:auto-bandwidth/mpls:state/mpls:adjust-threshold {
    deviate not-supported;
  }

  deviation /mpls:mpls/mpls:lsps/mpls:constrained-path/mpls:tunnel/mpls:bandwidth/mpls:auto-bandwidth/mpls:overflow/mpls:state/mpls:enabled {
    deviate not-supported;
  }

  deviation /mpls:mpls/mpls:lsps/mpls:constrained-path/mpls:tunnel/mpls:bandwidth/mpls:auto-bandwidth/mpls:overflow/mpls:state/mpls:overflow-threshold {
    deviate not-supported;
  }

  deviation /mpls:mpls/mpls:lsps/mpls:constrained-path/mpls:tunnel/mpls:bandwidth/mpls:auto-bandwidth/mpls:overflow/mpls:state/mpls:trigger-event-count {
    deviate not-supported;
  }

  deviation /mpls:mpls/mpls:lsps/mpls:constrained-path/mpls:tunnel/mpls:bandwidth/mpls:auto-bandwidth/mpls:underflow/mpls:state/mpls:enabled {
    deviate not-supported;
  }

  deviation /mpls:mpls/mpls:lsps/mpls:constrained-path/mpls:tunnel/mpls:bandwidth/mpls:auto-bandwidth/mpls:underflow/mpls:state/mpls:underflow-threshold {
    deviate not-supported;
  }

  deviation /mpls:mpls/mpls:lsps/mpls:constrained-path/mpls:tunnel/mpls:bandwidth/mpls:auto-bandwidth/mpls:underflow/mpls:state/mpls:trigger-event-count {
    deviate not-supported;
  }

  deviation /mpls:mpls/mpls:lsps/mpls:constrained-path/mpls:tunnel/mpls:p2p-tunnel-attributes/mpls:state/mpls:destination {
    deviate not-supported;
  }

  deviation /mpls:mpls/mpls:lsps/mpls:constrained-path/mpls:tunnel/mpls:p2p-tunnel-attributes/mpls:p2p-primary-paths/mpls:config/mpls:use-cspf {
    deviate not-supported;
  }

  deviation /mpls:mpls/mpls:lsps/mpls:constrained-path/mpls:tunnel/mpls:p2p-tunnel-attributes/mpls:p2p-primary-paths/mpls:config/mpls:cspf-tiebreaker {
    deviate not-supported;
  }

  deviation /mpls:mpls/mpls:lsps/mpls:constrained-path/mpls:tunnel/mpls:p2p-tunnel-attributes/mpls:p2p-primary-paths/mpls:config/mpls:setup-priority {
    deviate not-supported;
  }

  deviation /mpls:mpls/mpls:lsps/mpls:constrained-path/mpls:tunnel/mpls:p2p-tunnel-attributes/mpls:p2p-primary-paths/mpls:config/mpls:hold-priority {
    deviate not-supported;
  }

  deviation /mpls:mpls/mpls:lsps/mpls:constrained-path/mpls:tunnel/mpls:p2p-tunnel-attributes/mpls:p2p-primary-paths/mpls:config/mpls:retry-timer {
    deviate not-supported;
  }

  deviation /mpls:mpls/mpls:lsps/mpls:constrained-path/mpls:tunnel/mpls:p2p-tunnel-attributes/mpls:p2p-primary-paths/mpls:state/mpls:name {
    deviate not-supported;
  }

  deviation /mpls:mpls/mpls:lsps/mpls:constrained-path/mpls:tunnel/mpls:p2p-tunnel-attributes/mpls:p2p-primary-paths/mpls:state/mpls:path-computation-method {
    deviate not-supported;
  }

  deviation /mpls:mpls/mpls:lsps/mpls:constrained-path/mpls:tunnel/mpls:p2p-tunnel-attributes/mpls:p2p-primary-paths/mpls:state/mpls:use-cspf {
    deviate not-supported;
  }

  deviation /mpls:mpls/mpls:lsps/mpls:constrained-path/mpls:tunnel/mpls:p2p-tunnel-attributes/mpls:p2p-primary-paths/mpls:state/mpls:cspf-tiebreaker {
    deviate not-supported;
  }

  deviation /mpls:mpls/mpls:lsps/mpls:constrained-path/mpls:tunnel/mpls:p2p-tunnel-attributes/mpls:p2p-primary-paths/mpls:state/mpls:path-computation-server {
    deviate not-supported;
  }

  deviation /mpls:mpls/mpls:lsps/mpls:constrained-path/mpls:tunnel/mpls:p2p-tunnel-attributes/mpls:p2p-primary-paths/mpls:state/mpls:explicit-path-name {
    deviate not-supported;
  }

  deviation /mpls:mpls/mpls:lsps/mpls:constrained-path/mpls:tunnel/mpls:p2p-tunnel-attributes/mpls:p2p-primary-paths/mpls:state/mpls:preference {
    deviate not-supported;
  }

  deviation /mpls:mpls/mpls:lsps/mpls:constrained-path/mpls:tunnel/mpls:p2p-tunnel-attributes/mpls:p2p-primary-paths/mpls:state/mpls:setup-priority {
    deviate not-supported;
  }

  deviation /mpls:mpls/mpls:lsps/mpls:constrained-path/mpls:tunnel/mpls:p2p-tunnel-attributes/mpls:p2p-primary-paths/mpls:state/mpls:hold-priority {
    deviate not-supported;
  }

  deviation /mpls:mpls/mpls:lsps/mpls:constrained-path/mpls:tunnel/mpls:p2p-tunnel-attributes/mpls:p2p-primary-paths/mpls:state/mpls:retry-timer {
    deviate not-supported;
  }

  deviation /mpls:mpls/mpls:lsps/mpls:constrained-path/mpls:tunnel/mpls:p2p-tunnel-attributes/mpls:p2p-primary-paths/mpls:candidate-secondary-paths/mpls:candidate-secondary-path {
    deviate not-supported;
  }

  deviation /mpls:mpls/mpls:lsps/mpls:constrained-path/mpls:tunnel/mpls:p2p-tunnel-attributes/mpls:p2p-primary-paths/mpls:admin-groups/mpls:state/mpls:exclude-group {
    deviate not-supported;
  }

  deviation /mpls:mpls/mpls:lsps/mpls:constrained-path/mpls:tunnel/mpls:p2p-tunnel-attributes/mpls:p2p-primary-paths/mpls:admin-groups/mpls:state/mpls:include-all-group {
    deviate not-supported;
  }

  deviation /mpls:mpls/mpls:lsps/mpls:constrained-path/mpls:tunnel/mpls:p2p-tunnel-attributes/mpls:p2p-primary-paths/mpls:admin-groups/mpls:state/mpls:include-any-group {
    deviate not-supported;
  }

  deviation /mpls:mpls/mpls:lsps/mpls:constrained-path/mpls:tunnel/mpls:p2p-tunnel-attributes/mpls:p2p-secondary-paths {
    deviate not-supported;
  }

  deviation /mpls:mpls/mpls:lsps/mpls:unconstrained-path/mpls:path-setup-protocol/mpls:ldp/mpls:tunnel/mpls:tunnel-type {
    deviate not-supported;
  }

  deviation /mpls:mpls/mpls:lsps/mpls:unconstrained-path/mpls:path-setup-protocol/mpls:ldp/mpls:tunnel/mpls:ldp-type {
    deviate not-supported;
  }

  deviation /mpls:mpls/mpls:lsps/mpls:unconstrained-path/mpls:path-setup-protocol/mpls:ldp/mpls:tunnel/mpls:p2p-lsp/mpls:fec-address {
    deviate not-supported;
  }

  deviation /mpls:mpls/mpls:lsps/mpls:unconstrained-path/mpls:path-setup-protocol/mpls:segment-routing/mpls:tunnel/mpls:tunnel-type {
    deviate not-supported;
  }

  deviation /mpls:mpls/mpls:lsps/mpls:unconstrained-path/mpls:path-setup-protocol/mpls:segment-routing/mpls:tunnel/mpls:p2p-lsp/mpls:fec {
    deviate not-supported;
  }


}
//total deviations:138
