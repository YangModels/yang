submodule Cisco-IOS-XR-fretta-bcm-dpa-npu-stats-oper-sub1 {

  belongs-to Cisco-IOS-XR-fretta-bcm-dpa-npu-stats-oper {
    prefix Cisco-IOS-XR-fretta-bcm-dpa-npu-stats-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-bcm-dpa-npu-stats package operational data.

     Copyright (c) 2013-2015 by Cisco Systems, Inc.
     All rights reserved.";

  revision "2015-11-09" {
    description
      "IOS XR 6.0 revision.";
  }


  grouping DPA-VOQ-INGRESS-PACKET-STATISTICS {
    description "DPA VOQ INGRESS PACKET STATISTICS";
    leaf gport-received-bytes {
      xr:xr-xml-map "dpa_npu_stats:GportReceivedBytes";
      type uint64;
      description "GportReceivedBytes";
    }
    leaf gport-received-pkts {
      xr:xr-xml-map "dpa_npu_stats:GportReceivedPkts";
      type uint64;
      description "GportReceivedPkts";
    }
    leaf gport-dropped-bytes {
      xr:xr-xml-map "dpa_npu_stats:GportDroppedBytes";
      type uint64;
      description "GportDroppedBytes";
    }
    leaf gport-dropped-pkts {
      xr:xr-xml-map "dpa_npu_stats:GportDroppedPkts";
      type uint64;
      description "GportDroppedPkts";
    }
  }

  grouping DPA-VOQ-INTF-PORT {
    description "DPA VOQ INTF PORT";
    leaf is-inuse {
      xr:xr-xml-map "dpa_npu_stats:is_inuse";
      type boolean;
      description "is inuse";
    }
    leaf rack-num {
      xr:xr-xml-map "dpa_npu_stats:rack_num";
      type uint8;
      description "rack num";
    }
    leaf slot-num {
      xr:xr-xml-map "dpa_npu_stats:slot_num";
      type uint8;
      description "slot num";
    }
    leaf npu-num {
      xr:xr-xml-map "dpa_npu_stats:npu_num";
      type uint8;
      description "npu num";
    }
    leaf npu-core {
      xr:xr-xml-map "dpa_npu_stats:npu_core";
      type uint8;
      description "npu core";
    }
    leaf port-num {
      xr:xr-xml-map "dpa_npu_stats:port_num";
      type uint8;
      description "port num";
    }
    leaf ifhandle {
      xr:xr-xml-map "dpa_npu_stats:ifhandle";
      type uint32;
      description "ifhandle";
    }
    leaf sysport {
      xr:xr-xml-map "dpa_npu_stats:sysport";
      type uint32;
      description "sysport";
    }
    leaf pp-port {
      xr:xr-xml-map "dpa_npu_stats:pp_port";
      type uint32;
      description "pp port";
    }
    leaf port-speed {
      xr:xr-xml-map "dpa_npu_stats:port_speed";
      type uint32;
      description "port speed";
    }
    leaf voq-base {
      xr:xr-xml-map "dpa_npu_stats:voq_base";
      type uint32;
      description "voq base";
    }
    leaf connector-id {
      xr:xr-xml-map "dpa_npu_stats:connector_id";
      type uint32;
      description "connector id";
    }
    leaf is-local-port {
      xr:xr-xml-map "dpa_npu_stats:is_local_port";
      type boolean;
      description "is local port";
    }

    list voq-stat {
      max-elements "8";
      description "voq stat";
      uses DPA-VOQ-INGRESS-PACKET-STATISTICS;
    }
  }

  grouping DPA-TRAP-STATS {
    description "DPA TRAP STATS";
    leaf trap-strength {
      xr:xr-xml-map "dpa_npu_stats:trap_strength";
      type uint32;
      description "trap strength";
    }
    leaf priority {
      xr:xr-xml-map "dpa_npu_stats:priority";
      type uint32;
      description "priority";
    }
    leaf trap-id {
      xr:xr-xml-map "dpa_npu_stats:trap_id";
      type uint32;
      description "trap id";
    }
    leaf gport {
      xr:xr-xml-map "dpa_npu_stats:gport";
      type uint32;
      description "gport";
    }
    leaf fec-id {
      xr:xr-xml-map "dpa_npu_stats:fec_id";
      type uint32;
      description "fec id";
    }
    leaf policer-id {
      xr:xr-xml-map "dpa_npu_stats:policer_id";
      type uint32;
      description "policer id";
    }
    leaf stats-id {
      xr:xr-xml-map "dpa_npu_stats:stats_id";
      type uint32;
      description "stats id";
    }
    leaf encap-id {
      xr:xr-xml-map "dpa_npu_stats:encap_id";
      type uint32;
      description "encap id";
    }
    leaf mc-group {
      xr:xr-xml-map "dpa_npu_stats:mc_group";
      type uint32;
      description "mc group";
    }
    leaf trap-string {
      xr:xr-xml-map "dpa_npu_stats:trap_string";
      type string;
      description "trap string";
    }
    leaf id {
      xr:xr-xml-map "dpa_npu_stats:id";
      type uint32;
      description "id";
    }
    leaf offset {
      xr:xr-xml-map "dpa_npu_stats:offset";
      type uint64;
      description "offset";
    }
    leaf npu-id {
      xr:xr-xml-map "dpa_npu_stats:npu_id";
      type uint64;
      description "npu id";
    }
    leaf packet-dropped {
      xr:xr-xml-map "dpa_npu_stats:packet_dropped";
      type uint64;
      description "packet dropped";
    }
    leaf packet-accepted {
      xr:xr-xml-map "dpa_npu_stats:packet_accepted";
      type uint64;
      description "packet accepted";
    }
  }

  grouping CLEAR-STATS {
    description "CLEAR STATS";
    leaf clear-status {
      xr:xr-xml-map "dpa_npu_stats:clear_status";
      type uint8;
      description "clear status";
    }
  }
}
