submodule Cisco-IOS-XR-fib-common-oper-sub1 {

  belongs-to Cisco-IOS-XR-fib-common-oper {
    prefix Cisco-IOS-XR-fib-common-oper;
  }

  /*** LINKAGE (IMPORTS / INCLUDES) ***/

  import ietf-inet-types { prefix "inet"; }

  import ietf-yang-types { prefix "yang"; }

  import Cisco-IOS-XR-types { prefix "xr"; }

  include Cisco-IOS-XR-fib-common-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2015 by Cisco Systems, Inc.
     All rights reserved.";

  revision "2015-11-09" {
    description
      "IOS XR 6.0 revision.";
  }

  typedef Mgmt-fib-mpls-frr-state {
    type enumeration {
      enum partial {
        value 0;
        description "Partial";
      }
      enum active {
        value 1;
        description "Active";
      }
      enum ready {
        value 2;
        description "Ready";
      }
      enum complete {
        value 3;
        description "Complete";
      }
      enum any {
        value 4;
        description "Any";
      }
    }
    description "MPLS FRR entry state";
  }
  typedef Mgmt-fib-mpls-lsp-role {
    type enumeration {
      enum head {
        value 0;
        description "Head";
      }
      enum midpoint {
        value 1;
        description "Midpoint";
      }
    }
    description "MPLS FRR entry role";
  }

  grouping FIB-MPLS-TIMESPEC {
    description "FIB MPLS TIMESPEC";
    leaf seconds {
      xr:xr-xml-map "fib_mpls:Seconds";
      type int32;
      units "second";
      description "Seconds part of time valueiin UTC";
    }
    leaf nanoseconds {
      xr:xr-xml-map "fib_mpls:Nanoseconds";
      type int32;
      units "nanosecond";
      description "Nanoseconds part of time value";
    }
  }

  grouping FIB-MPLS-FRR-EVENT {
    description "FIB MPLS FRR EVENT";

    container start-time {
      description
        "Time of FRR event processing start, Seconds in
        UTC, and Nano Seconds";
      uses FIB-MPLS-TIMESPEC;
    }
    leaf protected-frr-interface-name {
      xr:xr-xml-map "fib_mpls:ProtectedFRRInterfaceName";
      type xr:Interface-name;
      description "Interface";
    }
    leaf next-hop {
      xr:xr-xml-map "fib_mpls:NextHop";
      type uint32;
      description "Next Hop";
    }
    leaf number-of-rewrites-affected {
      xr:xr-xml-map "fib_mpls:NumberOfRewritesAffected";
      type uint32;
      description "Number of rewrites affected";
    }
    leaf switching-time-nsecs {
      xr:xr-xml-map "fib_mpls:SwitchingTimeNsecs";
      type uint32;
      units "nanosecond";
      description "Time to switch rewrites [nsecs]";
    }
    leaf main-processing {
      xr:xr-xml-map "fib_mpls:MainProcessing";
      type uint32;
      description "Main Processing for FRR";
    }
    leaf fast-bundle-member-down-interface {
      xr:xr-xml-map "fib_mpls:FastBundleMemberDownInterface";
      type uint32;
      description "Fast Bundle Member Down Interface";
    }
    leaf frr-event-node-id {
      xr:xr-xml-map "fib_mpls:FRREventNodeID";
      type xr:Node-id;
      description "Node on which the FRR event happened";
    }
  }

  grouping FIB-MPLS-FWDING-SUMMARY {
    description "FIB MPLS FWDING SUMMARY";
    leaf ipv4-imposition-entries {
      xr:xr-xml-map "fib_mpls:IPv4ImpositionEntries";
      type uint32;
      description "Number of IPv4 imposition entries";
    }
    leaf reserved-label-entries {
      xr:xr-xml-map "fib_mpls:ReservedLabelEntries";
      type uint32;
      description "Number of reserved label entries";
    }
    leaf label-switched-entries {
      xr:xr-xml-map "fib_mpls:LabelSwitchedEntries";
      type uint32;
      description "Number of label swap/disposition entries";
    }
    leaf protected-label-switched-entries {
      xr:xr-xml-map "fib_mpls:ProtectedLabelSwitchedEntries";
      type uint32;
      description
        "Number of FRR protected label swap/disposition
        entries";
    }
    leaf deleted-stale-entries {
      xr:xr-xml-map "fib_mpls:DeletedStaleEntries";
      type uint32;
      description "Number of delete stale label entries";
    }
    leaf te-head-entries {
      xr:xr-xml-map "fib_mpls:TEHeadEntries";
      type uint32;
      description "Number of TE tunnel head imposition entries";
    }
    leaf te-frr-head-entries {
      xr:xr-xml-map "fib_mpls:TE_FRRHeadEntries";
      type uint32;
      description "Number of TE FRR tunnel head imposition entries";
    }
    leaf te-frr-interface-entries {
      xr:xr-xml-map "fib_mpls:TE_FRRInterfaceEntries";
      type uint32;
      description "Number of TE FRR protected interface entries";
    }
    leaf te-frr-next-hop-entries {
      xr:xr-xml-map "fib_mpls:TE_FRRNextHopEntries";
      type uint32;
      description "Number of TE FRR protected next-hop entries";
    }
    leaf te-mid-points-entries {
      xr:xr-xml-map "fib_mpls:TEMidPointsEntries";
      type uint32;
      description "Number of TE MidPoints forwarding entries";
    }
    leaf te-frr-mid-points-entries {
      xr:xr-xml-map "fib_mpls:TE_FRRMidPointsEntries";
      type uint32;
      description "Number of TE FRR MidPoints forwarding entries";
    }
    leaf te-internal-entries {
      xr:xr-xml-map "fib_mpls:TEInternalEntries";
      type uint32;
      description "Number of TE internal forwarding entries";
    }
    leaf te-frr-internal-entries {
      xr:xr-xml-map "fib_mpls:TE_FRRInternalEntries";
      type uint32;
      description "Number of TE internal forwarding entries";
    }
    leaf total-forwarding-updates {
      xr:xr-xml-map "fib_mpls:TotalForwardingUpdates";
      type uint32;
      description "Total forwarding updates from LSD to LFDs";
    }
    leaf total-forwarding-update-messages {
      xr:xr-xml-map "fib_mpls:TotalForwardingUpdateMessages";
      type uint32;
      description
        "Total forwarding update messages from LSD to
        LFDs";
    }
    leaf total-p2mp-forwarding-updates {
      xr:xr-xml-map "fib_mpls:TotalP2MPForwardingUpdates";
      type uint32;
      description "Total forwarding updates from MRIB to LFDs";
    }
    leaf total-p2mp-forwarding-added-or-modify-messages {
      xr:xr-xml-map "fib_mpls:TotalP2MPForwardingAddedOrModifyMessa"+
        "ges";
      type uint32;
      description
        "Total p2mp forwarding add/modify messages from
        MRIB to LFDs";
    }
    leaf total-p2mp-forwarding-delete-messages {
      xr:xr-xml-map "fib_mpls:TotalP2MPForwardingDeleteMessages";
      type uint32;
      description
        "Total p2mp forwarding del messages from MRIB to
        LFDs";
    }
    leaf total-p2mp-forwarding-drop-messages {
      xr:xr-xml-map "fib_mpls:TotalP2MPForwardingDropMessages";
      type uint32;
      description
        "Total p2mp forwarding messages dropped from MRIB
        to LFDs";
    }
    leaf total-p2mp-iir-forwarding-drop-messages {
      xr:xr-xml-map "fib_mpls:TotalP2MP_IIRForwardingDropMessages";
      type uint32;
      description
        "Total IIR triggered p2mp forwarding MRIB
        messages dropped";
    }
    leaf lowest-label {
      xr:xr-xml-map "fib_mpls:LowestLabel";
      type uint32;
      description "Lowest label in use";
    }
    leaf highest-label {
      xr:xr-xml-map "fib_mpls:HighestLabel";
      type uint32;
      description "Highest Label in use";
    }
    leaf ignore-protect {
      xr:xr-xml-map "fib_mpls:IgnoreProtect";
      type uint32;
      description "Number of TE tunnels treated as non-protected";
    }
    leaf mte-head-entries {
      xr:xr-xml-map "fib_mpls:MTEHeadEntries";
      type uint32;
      description "Number of MTE tunnel head entries";
    }
    leaf mte-ll-entries {
      xr:xr-xml-map "fib_mpls:MTE_LLEntries";
      type uint32;
      description "Number of MTE local entries";
    }
    leaf mte-midpoint-entries {
      xr:xr-xml-map "fib_mpls:MTEMidpointEntries";
      type uint32;
      description "Number of MTE midpoint entries";
    }
    leaf num-lsp {
      xr:xr-xml-map "fib_mpls:NumLSP";
      type uint32;
      description "Number of label switch paths";
    }
    leaf lrpf-entries {
      xr:xr-xml-map "fib_mpls:LRPFEntries";
      type uint32;
      description "Number of labels with RPF";
    }
  }

  grouping FIB-MPLS-FRR-DB-MCAST-LEGS {
    description "FIB MPLS FRR DB MCAST LEGS";

    container frr-entry-id {
      description "FRR entry ID";
      uses FIB-MPLS-FRR-DB-ENTRY-GEN-ID;
    }
    leaf tunnel-interface-name {
      xr:xr-xml-map "fib_mpls:TunnelInterfaceName";
      type xr:Interface-name;
      description "Tunnel interface";
    }
    leaf input-label {
      xr:xr-xml-map "fib_mpls:InputLabel";
      type uint32;
      description "Input label";
    }
    leaf outgoing-interface {
      xr:xr-xml-map "fib_mpls:OutgoingInterface";
      type xr:Interface-name;
      description "Outgoing interface";
    }
    leaf outgoing-label {
      xr:xr-xml-map "fib_mpls:OutgoingLabel";
      type uint32;
      description "Outgoing label";
    }
    leaf frr-interface-name {
      xr:xr-xml-map "fib_mpls:FRRInterfaceName";
      type xr:Interface-name;
      description "FRR interface";
    }
    leaf frr-label {
      xr:xr-xml-map "fib_mpls:FRRLabel";
      type uint32;
      description "FRR output label";
    }
    leaf entry-frr-state {
      xr:xr-xml-map "fib_mpls:EntryFRRState";
      type Mgmt-fib-mpls-frr-state;
      description "MPLS FRR entry state";
    }
    leaf frr-next-hop-ipv4-address {
      xr:xr-xml-map "fib_mpls:FRRNextHopIPv4Address";
      type inet:ipv4-address;
      description "Next hop IPv4 address";
    }
    leaf is-mldp-lsp {
      xr:xr-xml-map "fib_mpls:IsMLDP_LSP";
      type boolean;
      description "MLDP or P2MP-TE";
    }
  }

  grouping FIB-MPLS-FRR-DB-ENTRY-MID-ID {
    description "FIB MPLS FRR DB ENTRY MID ID";
    leaf source-address {
      xr:xr-xml-map "fib_mpls:SourceAddress";
      type inet:ipv4-address;
      description "Source IPv4 address";
    }
    leaf lspid {
      xr:xr-xml-map "fib_mpls:LSPID";
      type uint32;
      description "LSP ID";
    }
    leaf tunnel-id {
      xr:xr-xml-map "fib_mpls:TunnelID";
      type uint32;
      description "Tunnel ID";
    }
  }

  grouping FIB-MPLS-FRR-DB-ENTRY-HEAD-ID {
    description "FIB MPLS FRR DB ENTRY HEAD ID";
    leaf destination-prefix {
      xr:xr-xml-map "fib_mpls:DestinationPrefix";
      type inet:ipv4-address;
      description "Destination prefix";
    }
    leaf destination-prefix-length {
      xr:xr-xml-map "fib_mpls:DestinationPrefixLength";
      type uint32;
      description "Destination prefix length";
    }
  }

  grouping FIB-MPLS-FRR-DB-ENTRY-GEN-ID {
    description "FIB MPLS FRR DB ENTRY GEN ID";

    container head {
      when "../role = 'head'" {
        description "../Role = 'Head'";
      }
      description "head";
      uses FIB-MPLS-FRR-DB-ENTRY-HEAD-ID;
    }

    container midpoint {
      when "../role = 'midpoint'" {
        description "../Role = 'Midpoint'";
      }
      description "midpoint";
      uses FIB-MPLS-FRR-DB-ENTRY-MID-ID;
    }
    leaf role {
      xr:xr-xml-map "fib_mpls:Role";
      type Mgmt-fib-mpls-lsp-role;
      description "Role";
    }
  }

  grouping FIB-MPLS-FRR-DB-ENTRY {
    description "FIB MPLS FRR DB ENTRY";

    container frr-entry-id {
      description "FRR entry ID";
      uses FIB-MPLS-FRR-DB-ENTRY-GEN-ID;
    }
    leaf tunnel-interface-name {
      xr:xr-xml-map "fib_mpls:TunnelInterfaceName";
      type xr:Interface-name;
      description "Tunnel interface";
    }
    leaf input-label {
      xr:xr-xml-map "fib_mpls:InputLabel";
      type uint32;
      description "Input label";
    }
    leaf outgoing-interface {
      xr:xr-xml-map "fib_mpls:OutgoingInterface";
      type xr:Interface-name;
      description "Outgoing interface";
    }
    leaf outgoing-label {
      xr:xr-xml-map "fib_mpls:OutgoingLabel";
      type uint32;
      description "Outgoing label";
    }
    leaf frr-interface-name {
      xr:xr-xml-map "fib_mpls:FRRInterfaceName";
      type xr:Interface-name;
      description "FRR interface";
    }
    leaf frr-label {
      xr:xr-xml-map "fib_mpls:FRRLabel";
      type uint32;
      description "FRR output label";
    }
    leaf entry-frr-state {
      xr:xr-xml-map "fib_mpls:EntryFRRState";
      type Mgmt-fib-mpls-frr-state;
      description "MPLS FRR entry state";
    }
    leaf frr-next-hop-ipv4-address {
      xr:xr-xml-map "fib_mpls:FRRNextHopIPv4Address";
      type inet:ipv4-address;
      description "Next hop IPv4 address";
    }
    leaf is-mldp-lsp {
      xr:xr-xml-map "fib_mpls:IsMLDP_LSP";
      type boolean;
      description "MLDP or P2MP-TE";
    }
    leaf is-multicast-tunnel {
      xr:xr-xml-map "fib_mpls:IsMulticastTunnel";
      type boolean;
      description "Multicast tunnel";
    }
    leaf multicast-tunnel-legs {
      xr:xr-xml-map "fib_mpls:MulticastTunnelLegs";
      type uint32;
      description "Number of legs in MCAST tunnel";
    }

    list multicast-leg {
      description "MCAST legs";
      uses FIB-MPLS-FRR-DB-MCAST-LEGS;
    }
  }

  grouping FIB-MPLS-FRR-DB-SUM {
    description "FIB MPLS FRR DB SUM";
    leaf active {
      xr:xr-xml-map "fib_mpls:Active";
      type uint32;
      description "Number of FRR rewrites in Active state";
    }
    leaf ready {
      xr:xr-xml-map "fib_mpls:Ready";
      type uint32;
      description "Number of FRR rewrites in Ready state";
    }
    leaf partial {
      xr:xr-xml-map "fib_mpls:Partial";
      type uint32;
      description "Number of FRR rewrites in Partial state";
    }
    leaf other {
      xr:xr-xml-map "fib_mpls:Other";
      type uint32;
      description "Number of FRR rewrites in an unrecognized state";
    }
  }

  grouping FIB-MPLS-SH-TUN-INFO {
    description "Information about TE-head tunnel LI";
    leaf tunnel-interface-name {
      xr:xr-xml-map "fib_mpls:TunnelInterfaceName";
      type xr:Interface-name;
      description "Tunnel interface";
    }
    leaf tunnel-local-label {
      xr:xr-xml-map "fib_mpls:TunnelLocalLabel";
      type uint32;
      description "Tunnel Local label";
    }
    leaf tunnel-fwd-class {
      xr:xr-xml-map "fib_mpls:TunnelFwdClass";
      type uint8;
      description "Tunnel Forward Class";
    }
    leaf tunnel-load-metric {
      xr:xr-xml-map "fib_mpls:TunnelLoadMetric";
      type uint8;
      description " Tunnel Load Metric";
    }
    leaf tunnel-is-srte {
      xr:xr-xml-map "fib_mpls:TunnelIsSRTE";
      type boolean;
      description "Is Tunnel SRTE";
    }
    leaf tunnel-resolution-incomplete {
      xr:xr-xml-map "fib_mpls:TunnelResolutionIncomplete";
      type boolean;
      description "Tunnel head resolution is incomplete";
    }
    leaf tunnel-resolution-inconsistent {
      xr:xr-xml-map "fib_mpls:TunnelResolutionInconsistent";
      type boolean;
      description
        "Tunnel head resolition is inconsitent b/w TEhead
        and Local label";
    }
    leaf tunnel-is-programmed-to-drop {
      xr:xr-xml-map "fib_mpls:TunnelIsProgrammedToDrop";
      type boolean;
      description "Is Tunnel programmed as drop";
    }
    leaf tli-type {
      xr:xr-xml-map "fib_mpls:TLIType";
      type uint32;
      description "Th tunnel LI type";
    }
    leaf tli-pointer {
      xr:xr-xml-map "fib_mpls:TLIPointer";
      type uint32;
      description "The pointer to the Tun LI object";
    }
    leaf tli-reference-count {
      xr:xr-xml-map "fib_mpls:TLIReferenceCount";
      type uint32;
      description "The Tunnel LI object refcounter";
    }
    leaf tli-flags {
      xr:xr-xml-map "fib_mpls:TLIFlags";
      type uint32;
      description "Tunnel LI flags";
    }
    leaf tli-flags-extended {
      xr:xr-xml-map "fib_mpls:TLIFlagsExtended";
      type uint32;
      description "Tunnel LI extended flags";
    }
  }

  grouping FIB-MPLS-SH-TEHEAD {
    description "Information about TE tunnel head";

    container tunnel-info {
      description "Tunnel head information";
      uses FIB-MPLS-SH-TUN-INFO;
    }

    container fwdg {
      description "Tunnel forwarding information";
      uses FIB-MPLS-SH-LEAF;
    }
  }

  grouping FIB-MPLS-MCAST-INFO {
    description "Information for mpls multicast entries";
    leaf multicast-mol-base-flags {
      xr:xr-xml-map "fib_mpls:MulticastMOLBaseFlags";
      type uint32;
      description "MOL base flags";
    }
    leaf multicast-mol-flags {
      xr:xr-xml-map "fib_mpls:MulticastMOLFlags";
      type uint16;
      description "MOL flags";
    }
    leaf multicast-mol-reference-count {
      xr:xr-xml-map "fib_mpls:MulticastMOLReferenceCount";
      type uint16;
      description "MOL reference count";
    }
    leaf multicast-tunnel-interface-name {
      xr:xr-xml-map "fib_mpls:MulticastTunnelInterfaceName";
      type xr:Interface-name;
      description "multicast mpls tunnel ifh";
    }
    leaf multicast-tunnel-id {
      xr:xr-xml-map "fib_mpls:MulticastTunnelID";
      type uint32;
      description
        "multicast mpls P2MP-TE tunnel id or MLDP Tunnel
        LSMID on all nodes";
    }
    leaf multicast-tunnel-next-hop-information {
      xr:xr-xml-map "fib_mpls:MulticastTunnelNextHopInformation";
      type uint32;
      description "multicast nhinfo for p2mp TE Head";
    }
    leaf multicast-tunnel-lspvif {
      xr:xr-xml-map "fib_mpls:MulticastTunnelLSPVIF";
      type uint32;
      description "multicast LSPVIF for MLDP Tunnels";
    }
    leaf multicast-mpls-output-paths {
      xr:xr-xml-map "fib_mpls:MulticastMPLSOutputPaths";
      type uint16;
      description "num multicast mpls output paths ";
    }
    leaf multicast-mpls-protocol-output-paths {
      xr:xr-xml-map "fib_mpls:MulticastMPLSProtocolOutputPaths";
      type uint16;
      description "num multicast mpls prot output paths ";
    }
    leaf multicast-mpls-local-output-paths {
      xr:xr-xml-map "fib_mpls:MulticastMPLSLocalOutputPaths";
      type uint16;
      description "num multicast mpls local output paths";
    }
    leaf multicast-rpf-id {
      xr:xr-xml-map "fib_mpls:MulticastRPF_ID";
      type uint32;
      description "The multicast RPF-ID ";
    }
    leaf multicast-encap-id {
      xr:xr-xml-map "fib_mpls:MulticastEncap_ID";
      type uint32;
      description "The multicast ENCAP-ID ";
    }
    leaf dependent-tunnel-local-label {
      xr:xr-xml-map "fib_mpls:DependentTunnelLocalLabel";
      type uint32;
      description "The Local Label of a dependant Tunnel ";
    }
    leaf dependent-tunnel-ifh {
      xr:xr-xml-map "fib_mpls:DependentTunnel_ifh";
      type uint32;
      description "The interface handle of a dependent tunnel ";
    }
    leaf multicast-v4-table-id {
      xr:xr-xml-map "fib_mpls:MulticastV4TableID";
      type uint32;
      description "The multicast IPv4 Table id";
    }
    leaf multicast-v6-table-id {
      xr:xr-xml-map "fib_mpls:MulticastV6TableID";
      type uint32;
      description "The multicast IPv6 Table id";
    }
    leaf label-bridge-domain-id {
      xr:xr-xml-map "fib_mpls:LabelBridgeDomainId";
      type uint32;
      description "Bridge domain-ID";
    }
    leaf label-xid {
      xr:xr-xml-map "fib_mpls:LabelXid";
      type uint32;
      description "The XID of PW";
    }
    leaf label-shg-id {
      xr:xr-xml-map "fib_mpls:LabelShgId";
      type uint32;
      description "The SHG-ID of PW";
    }
    leaf multicast-platform-data-length {
      xr:xr-xml-map "fib_mpls:MulticastPlatformDataLength";
      type uint8;
      description "The multicast platform data len";
    }
    leaf multicast-platform-data {
      xr:xr-xml-map "fib_mpls:MulticastPlatformData";
      type yang:hex-string;
      description "The multicast platform data";
    }
  }

  grouping FIB-MPLS-LDI-INFO {
    description
      "Detailed load sharing information for mpls table
      entries";
    leaf ldi-hardware-information {
      xr:xr-xml-map "fib_mpls:LDIHardwareInformation";
      type yang:hex-string;
      description "Hardware info";
    }
  }

  grouping FIB-MPLS-MCAST-MPI-INFO {
    description "FIB MPLS MCAST MPI INFO";
    leaf my-node-id {
      xr:xr-xml-map "fib_mpls:my_node_id";
      type uint32;
      description "my node id";
    }
    leaf flags {
      xr:xr-xml-map "fib_mpls:flags";
      type uint32;
      description "flags";
    }
    leaf via-label {
      xr:xr-xml-map "fib_mpls:via_label";
      type uint32;
      description "via label";
    }
    leaf mcast-id {
      xr:xr-xml-map "fib_mpls:mcast_id";
      type uint32;
      description "mcast id";
    }
    leaf pri-tos-mask {
      xr:xr-xml-map "fib_mpls:pri_tos_mask";
      type uint32;
      description "pri tos mask";
    }
    leaf bk-tos-mask {
      xr:xr-xml-map "fib_mpls:bk_tos_mask";
      type uint32;
      description "bk tos mask";
    }
    leaf pd-ts-ms {
      xr:xr-xml-map "fib_mpls:pd_ts_ms";
      type uint64;
      description "pd ts ms";
    }
    leaf primary-is-local {
      xr:xr-xml-map "fib_mpls:primary_is_local";
      type boolean;
      description "primary is local";
    }
    leaf backup-is-local {
      xr:xr-xml-map "fib_mpls:backup_is_local";
      type boolean;
      description "backup is local";
    }
    leaf-list if-node-id {
      xr:xr-xml-map "fib_mpls:if_node_id";
      type uint32;
      max-elements "10";
      description "if node id";
    }
    leaf-list bkup-if-node-id {
      xr:xr-xml-map "fib_mpls:bkup_if_node_id";
      type uint32;
      max-elements "10";
      description "bkup if node id";
    }
    leaf-list if-hdl {
      xr:xr-xml-map "fib_mpls:if_hdl";
      type uint32;
      max-elements "10";
      description "if hdl";
    }
    leaf-list bkup-if-hdl {
      xr:xr-xml-map "fib_mpls:bkup_if_hdl";
      type uint32;
      max-elements "10";
      description "bkup if hdl";
    }
  }

  grouping FIB-MPLS-FWD-INFO {
    description "FIB MPLS FWD INFO";
    leaf l3-mtu {
      xr:xr-xml-map "fib_mpls:L3_MTU";
      type uint32;
      description "L3 MTU";
    }
    leaf total-encapsulation-size {
      xr:xr-xml-map "fib_mpls:TotalEncapsulationSize";
      type uint32;
      description "Total encapsulation size: L2 + MPLS";
    }
    leaf mac-size {
      xr:xr-xml-map "fib_mpls:MACSize";
      type uint32;
      description "Length of L2 encapsulation";
    }
    leaf transmit-number-of-packets-switched {
      xr:xr-xml-map "fib_mpls:TransmitNumberOfPacketsSwitched";
      type uint64;
      description "Number of packets switched";
    }
    leaf transmit-number-of-bytes-switched {
      xr:xr-xml-map "fib_mpls:TransmitNumberOfBytesSwitched";
      type uint64;
      units "byte";
      description "Number of Bytes switched";
    }
    leaf transmit-number-of-tm-packets-switched {
      xr:xr-xml-map "fib_mpls:TransmitNumberOfTmPacketsSwitched";
      type uint64;
      description "Number of Traffic-Matrix packets switched";
    }
    leaf transmit-number-of-tm-bytes-switched {
      xr:xr-xml-map "fib_mpls:TransmitNumberOfTmBytesSwitched";
      type uint64;
      units "byte";
      description "Number of Traffic-Matrix Bytes switched";
    }
    leaf status {
      xr:xr-xml-map "fib_mpls:Status";
      type int32;
      description "Status";
    }
    leaf next-hop-interface-name {
      xr:xr-xml-map "fib_mpls:NextHopInterfaceName";
      type xr:Interface-name;
      description "Next hop interface name";
    }
    leaf next-hop-protocol {
      xr:xr-xml-map "fib_mpls:NextHopProtocol";
      type uint32;
      description "The address family (V4/V6) ";
    }
    leaf next-hop-string {
      xr:xr-xml-map "fib_mpls:NextHopString";
      type yang:hex-string;
      description "Next hop address in string format";
    }
    leaf nh-id {
      xr:xr-xml-map "fib_mpls:NHId";
      type uint32;
      description "Nexthop Id";
    }
    leaf version-priority-valid {
      xr:xr-xml-map "fib_mpls:VersionPriorityValid";
      type boolean;
      description
        "Indicates if the version/priority fields are
        valid";
    }
    leaf route-download-version {
      xr:xr-xml-map "fib_mpls:RouteDownloadVersion";
      type uint64;
      description "Version of the route-download for the label";
    }
    leaf route-download-priority {
      xr:xr-xml-map "fib_mpls:RouteDownloadPriority";
      type uint32;
      description "Priority at which the label was downloaded";
    }
    leaf-list label-stack {
      xr:xr-xml-map "fib_mpls:LabelStack";
      type uint32;
      description "Label stack";
    }
  }

  grouping FIB-MPLS-ADJ-INFO {
    description "FIB MPLS ADJ INFO";

    list fib-mpls-adj-info {
      description "fib mpls adj info";

      container label-information-detail {
        description "Detail label info";
        uses FIB-MPLS-FWD-INFO;
      }

      container mpi-info {
        description "The MPI info";
        uses FIB-MPLS-MCAST-MPI-INFO;
      }
      leaf label-information-type {
        type uint32;
        description "Label-Info type";
      }
      leaf local-label {
        type uint32;
        description "Local label";
      }
      leaf outgoing-label {
        type uint32;
        description "Outgoing label";
      }
      leaf frr-nh-ptr {
        type uint32;
        description "FRR next-hop object pointer";
      }
      leaf mpls-adjacency-flags {
        type uint32;
        description "MPLS Adjacency flags";
      }
      leaf path-flags {
        type uint32;
        description "PL path flags";
      }
      leaf path-index {
        type uint8;
        description "path index";
      }
      leaf backup-path-index {
        type uint8;
        description "backup path index";
      }
      leaf nhid {
        type uint32;
        description "Path's NH Id";
      }
      leaf weight {
        type uint32;
        description "Weight or load metric";
      }
      leaf app-id {
        type uint16;
        description "App ID";
      }
      leaf tunnel-id-present {
        type boolean;
        description "Tunnel id present?";
      }
      leaf outgoing-interface {
        type uint32;
        description "Outgoing interface";
      }
      leaf outgoing-physical-interface {
        type uint32;
        description "Outgoing Physical Interface";
      }
      leaf tunnel-interface-name {
        type xr:Interface-name;
        description "Tunnel Interface";
      }
      leaf label-information-path-index {
        type uint32;
        description "LabelInformationPathIndex";
      }
      leaf label-information-encap-id {
        type uint64;
        description "Encap ID";
      }
      leaf label-information-next-hop-type {
        type uint32;
        description "NHinfo Type";
      }
      leaf label-information-next-hop-table-id {
        type uint32;
        description "NHinfo Table ID";
      }
      leaf label-information-next-hop-protocol {
        type uint32;
        description "The address family (v4/v6) ";
      }
      leaf sli-from-ldi {
        type boolean;
        description "Path learnt the LDI/used for Forwarding?";
      }
      leaf label-information-next-hop-string {
        type yang:hex-string;
        description "Next hop address in string format";
      }
      leaf label-information-route-version {
        type uint64;
        description "The version of the route";
      }
      leaf label-information-time-in-milli-seconds {
        type uint64;
        description "The time of last update in msec";
      }
      leaf label-bridge-domain-id {
        type uint32;
        description "Bridge domain-ID";
      }
      leaf label-xid {
        type uint32;
        description "The XID of Xconnect";
      }
      leaf label-pw-xid {
        type uint32;
        description "The XID of PW";
      }
      leaf label-shg-id {
        type uint32;
        description "The SHG-ID of PW";
      }
      leaf pwhev-ctype {
        type uint32;
        description "PW-HE VC type";
      }
      leaf pwhecw-enabled {
        type boolean;
        description "PW-HE CW setting";
      }
      leaf pwhe-interface {
        type xr:Interface-name;
        description "PW-HE interface";
      }
      leaf pq-label {
        type uint32;
        description "PQ label";
      }
      leaf pq-flags {
        type uint32;
        description "PQ flags";
      }
      leaf li-pointer {
        type uint32;
        description "The pointer to the LI object";
      }
      leaf li-reference-count {
        type uint32;
        description "The LI object refcounter";
      }
      leaf is-srte {
        type boolean;
        description "Is SRTE?";
      }
      leaf is-pure-backup {
        type boolean;
        description "Is pure backup path?";
      }
      leaf is-frr-active {
        type boolean;
        description "Is FRR active?";
      }
    }
  }

  grouping FIB-MPLS-SH-LEAF {
    description "Information about label leaf";

    container label-information {
      description "Label-info in FIB leaf";
      uses FIB-MPLS-ADJ-INFO;
    }

    container ldi-information {
      description "LDI-info in FIB leaf";
      uses FIB-MPLS-LDI-INFO;
    }

    container multicast-information {
      description "The multicast info";
      uses FIB-MPLS-MCAST-INFO;
    }

    container rpf {
      description "RPF info";
      uses FIB-MPLS-LEAF-RPF;
    }
    leaf leaf-local-label {
      xr:xr-xml-map "fib_mpls:LeafLocalLabel";
      type uint32;
      description "Local label";
    }
    leaf eos-bit {
      xr:xr-xml-map "fib_mpls:EOSBit";
      type uint32;
      description "EOS bit";
    }
    leaf hardware-information {
      xr:xr-xml-map "fib_mpls:HardwareInformation";
      type yang:hex-string;
      description "Hardware info";
    }
    leaf leaf-reference-count {
      xr:xr-xml-map "fib_mpls:LeafReferenceCount";
      type uint32;
      description "Number of references to the leaf";
    }
    leaf leaf-ptr {
      xr:xr-xml-map "fib_mpls:LeafPtr";
      type uint32;
      description "The Leaf pointer";
    }
    leaf leaf-flags {
      xr:xr-xml-map "fib_mpls:LeafFlags";
      type uint32;
      description "The leaf flags";
    }
    leaf path-list-reference-count {
      xr:xr-xml-map "fib_mpls:PathListReferenceCount";
      type uint32;
      description "Number of references to the pathlist";
    }
    leaf path-list-ldi-mask {
      xr:xr-xml-map "fib_mpls:PathListLDIMask";
      type uint32;
      description "The pathlist ldi mask";
    }
    leaf path-list-flags {
      xr:xr-xml-map "fib_mpls:PathListFlags";
      type uint32;
      description "The pathlist flags";
    }
    leaf path-list-pointer {
      xr:xr-xml-map "fib_mpls:PathListPointer";
      type uint32;
      description "The pointer to the pathlist";
    }
    leaf ldi-reference-count {
      xr:xr-xml-map "fib_mpls:LDIReferenceCount";
      type uint32;
      description "Number of references to the LDI";
    }
    leaf ldi-flags {
      xr:xr-xml-map "fib_mpls:LDIFlags";
      type uint32;
      description "The LDI flags";
    }
    leaf ldi-type {
      xr:xr-xml-map "fib_mpls:LDIType";
      type uint32;
      description "The LDI type";
    }
    leaf ldi-pointer {
      xr:xr-xml-map "fib_mpls:LDIPointer";
      type uint32;
      description "The pointer to the LDI";
    }
    leaf lw-ldi-type {
      xr:xr-xml-map "fib_mpls:LW_LDIType";
      type uint32;
      description "The LW-LDI type";
    }
    leaf lw-ldi-pointer {
      xr:xr-xml-map "fib_mpls:LW_LDIPointer";
      type uint32;
      description "The pointer to the LW-LDI";
    }
    leaf lw-ldi-reference-count {
      xr:xr-xml-map "fib_mpls:LW_LDIReferenceCount";
      type uint32;
      description "The LW-LDI refcounter";
    }
    leaf lw-shared-ldi-pointer {
      xr:xr-xml-map "fib_mpls:LWSharedLDIPointer";
      type uint32;
      description "The pointer to the shared LDI in LW-LDI";
    }
    leaf lspa-flags {
      xr:xr-xml-map "fib_mpls:LSPAFlags";
      type uint32;
      description "The LSPA flags";
    }
    leaf afi-table-id {
      xr:xr-xml-map "fib_mpls:AFITableID";
      type uint32;
      description "The AFI table ID";
    }
    leaf multicast-label {
      xr:xr-xml-map "fib_mpls:MulticastLabel";
      type boolean;
      description "The unicast or multicast label";
    }
    leaf leaf-time-in-milli-seconds {
      xr:xr-xml-map "fib_mpls:LeafTimeInMilliSeconds";
      type uint64;
      description "The time of last update in msec";
    }
    leaf pwhe-interface-list-id {
      xr:xr-xml-map "fib_mpls:PWHEInterfaceListId";
      type uint16;
      description
        "Interface list associated with PW-HE VC
        imposition label";
    }
    leaf pwhe-interface-list-ptr {
      xr:xr-xml-map "fib_mpls:PWHEInterfaceListPtr";
      type uint32;
      description "Interface list ptr";
    }
    leaf pl-time-of-last-update-in-msec {
      xr:xr-xml-map "fib_mpls:PLTimeOfLastUpdateInMsec";
      type uint64;
      description "The time of last update for PL in msec";
    }
    leaf ldi-time-of-last-update-in-msec {
      xr:xr-xml-map "fib_mpls:LDITimeOfLastUpdateInMsec";
      type uint64;
      description "The time of last update for LDI in msec";
    }
    leaf lwldi-time-of-last-update-in-msec {
      xr:xr-xml-map "fib_mpls:LWLDITimeOfLastUpdateInMsec";
      type uint64;
      description "The time of last update for LW-LDI in msec";
    }
    leaf lspa-time-of-last-update-in-msec {
      xr:xr-xml-map "fib_mpls:LSPATimeOfLastUpdateInMsec";
      type uint64;
      description "The time of last update for LSPA in msec";
    }
    leaf pl-time-stamp-type {
      xr:xr-xml-map "fib_mpls:PLTimeStampType";
      type uint32;
      description "The type of time-stamp on PL";
    }
  }
}
