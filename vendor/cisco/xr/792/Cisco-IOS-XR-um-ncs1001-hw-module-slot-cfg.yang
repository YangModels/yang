module Cisco-IOS-XR-um-ncs1001-hw-module-slot-cfg {
  namespace "http://cisco.com/ns/yang/Cisco-IOS-XR-um-ncs1001-hw-module-slot-cfg";
  prefix um-ncs1001-hw-module-slot-cfg;

  import ietf-inet-types {
    prefix inet;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-hw-module-slot package configuration.
     
     This YANG module augments the
     modules with configuration data.
     
     Copyright (c) 2020, 2022 by Cisco Systems, Inc.
     All rights reserved.";

  revision 2022-07-11 {
    description
      "Added missing description statement to nodes
       2022-04-01
         Added mandatory keyword under leaf channel-width";
    semver:module-version "2.0.0";
  }
  revision 2020-12-07 {
    description
      "Initial release";
    semver:module-version "1.0.0";
  }

  grouping LOCATION-BODY {
    description
      "Grouping for location";
    container location {
      description
        "Fully qualified location specification";
      container slot {
        description
          "Slot Id";
        container give-the-slot-number-in-ranges {
          description
            "Give the Slot Number in Range <1-3>";
          list give-the-slot-number-in-range {
            key "give-the-slot-number-in-range-id";
            description
              "Give the Slot Number in Range <1-3>";
            leaf give-the-slot-number-in-range-id {
              type uint32 {
                range "1..3" {
                  description
                    "Give the Slot Number in Range <1-3>";
                }
              }
              description
                "Give the Slot Number in Range <1-3>";
            }
            container ampli {
              description
                "ampli commands";
              leaf node-type {
                type enumeration {
                  enum "TERM" {
                    value 0;
                    description
                      "";
                  }
                  enum "ILA" {
                    value 1;
                    description
                      "";
                  }
                }
                description
                  "Define the type of node in which the amplifier is set to work";
              }
              leaf grid-mode {
                type enumeration {
                  enum "100GHz" {
                    value 0;
                    description
                      "configure the amplifier with a 100GHz grid of channels";
                  }
                  enum "50GHz" {
                    value 1;
                    description
                      "configure the amplifier with a 50GHz grid of channels";
                  }
                  enum "gridless" {
                    value 2;
                    description
                      "";
                  }
                  enum "75GHz" {
                    value 3;
                    description
                      "configure the amplifier with a 75GHz grid of channels";
                  }
                }
                description
                  "Define the working mode for the optical module";
              }
              leaf udc-vlan {
                type uint32 {
                  range "2..4080" {
                    description
                      "Define the VLAN ID in range <2-4080>";
                  }
                }
                description
                  "Define the VLAN associated to selected slot and its UDC port";
              }
              container span-loss {
                presence "Indicates a span-loss node is configured.";
                description
                  "Enable Span Loss";
                leaf span-loss-delta {
                  type uint32 {
                    range "0..500" {
                      description
                        "Span Loss change delta value";
                    }
                  }
                  description
                    "Span Loss change delta value";
                }
              }
              container flex-mode {
                presence "Indicates a flex-mode node is configured.";
                description
                  "Enable Flex Mode";
                container flex-spectrum {
                  presence "Indicates a flex-spectrum node is configured.";
                  description
                    "Enable Gridless Flex Spectrum Mode";
                }
              }
              container remote-node {
                description
                  "Remote node connected to this slot";
                leaf local-ipv4 {
                  type inet:ipv4-address-no-zone;
                  must "../remote-ipv4";
                  description
                    "Specify local host";
                }
                leaf remote-ipv4 {
                  type inet:ipv4-address-no-zone;
                  must "../local-ipv4 and ../remote-slot-id";
                  description
                    "Specify remote host";
                }
                leaf remote-slot-id {
                  type uint32 {
                    range "1..3" {
                      description
                        "Give the Slot Number in Range <1-3>";
                    }
                  }
                  must "../remote-ipv4";
                  description
                    "Specify remote slot";
                }
              }
              container auto-threshold {
                presence "Indicates a auto-threshold node is configured.";
                description
                  "Enable amplifier automatic rx-low threshold set";
              }
              container otdr-autoscan {
                description
                  "Enable OTDR auto-scan on OTDR module connected to this amplifier";
                leaf otdr-module-ipv4-addr {
                  type inet:ipv4-address-no-zone;
                  must "../otdr-slot-id";
                  description
                    "Specify OTDR module host address";
                }
                leaf otdr-slot-id {
                  type uint32 {
                    range "1..3" {
                      description
                        "Specify OTDR slot number in range <1-3>";
                    }
                  }
                  must "../otdr-module-ipv4-addr and ../otdr-port-id";
                  description
                    "Specify OTDR slot number";
                }
                leaf otdr-port-id {
                  type uint32 {
                    range "1..2" {
                      description
                        "Specify OTDR port number in range <1-2>";
                    }
                  }
                  must "../otdr-slot-id and ../ampli-far-end-ipv4-addr";
                  description
                    "Specify OTDR port number";
                }
                leaf ampli-far-end-ipv4-addr {
                  type inet:ipv4-address-no-zone;
                  must "../otdr-port-id and ../ampli-far-end-slot-id";
                  description
                    "Specify amplifier far-end host address";
                }
                leaf ampli-far-end-slot-id {
                  type uint32 {
                    range "1..3" {
                      description
                        "Specify amplifier far-end slot number in Range <1-3>";
                    }
                  }
                  must "../ampli-far-end-ipv4-addr and ../scan-type";
                  description
                    "Specify amplifier far-end slot number";
                }
                leaf scan-type {
                  type enumeration {
                    enum "AUTO" {
                      value 0;
                      description
                        "OTDR scan type Automatic";
                    }
                  }
                  must "../ampli-far-end-slot-id";
                  description
                    "Specify OTDR scan type";
                }
              }
              container channel-ids {
                description
                  "Channel Id";
                list channel-id {
                  key "channel-id";
                  description
                    "Channel Id";
                  leaf channel-id {
                    type uint32 {
                      range "1..96" {
                        description
                          "Give the Channel ID in Range <1-96>";
                      }
                    }
                    description
                      "Channel Id";
                  }
                  leaf channel-width {
                    type uint32 {
                      range "1000..8000" {
                        description
                          "values in step of 250";
                      }
                    }
                    mandatory true;
                    description
                      "Set Channel Width (in units of 0.1Ghz)";
                  }
                }
              }
              container flex-channel-ids {
                description
                  "Flex Channel Id";
                list flex-channel-id {
                  key "flex-channel-id chan-central-freq-id";
                  description
                    "Flex Channel Id";
                  leaf flex-channel-id {
                    type uint32 {
                      range "1..96" {
                        description
                          "Specify Flex Channel ID in Range <1-96>";
                      }
                    }
                    description
                      "Flex Channel Id";
                  }
                  leaf chan-central-freq-id {
                    type uint32 {
                      range "1913500..1961000" {
                        description
                          "values in steps of 125";
                      }
                    }
                    description
                      "Set Channel Central Frequency (in units of 0.1Ghz)";
                  }
                  leaf chan-width {
                    type uint32 {
                      range "500..8000" {
                        description
                          "values in step of 125";
                      }
                    }
                    description
                      "Set Channel Width (in units of 0.1Ghz)";
                  }
                }
              }
            }
            container psm {
              description
                "psm commands";
              leaf primary-path {
                type enumeration {
                  enum "WORKING" {
                    value 1;
                    description
                      "";
                  }
                  enum "PROTECTED" {
                    value 2;
                    description
                      "";
                  }
                }
                description
                  "Select Psm primary path";
              }
              leaf lockout-from {
                type enumeration {
                  enum "WORKING" {
                    value 1;
                    description
                      "";
                  }
                  enum "PROTECTED" {
                    value 2;
                    description
                      "";
                  }
                }
                description
                  "Exclude selected port from protection";
              }
              container path-protection {
                presence "Indicates a path-protection node is configured.";
                description
                  "Enable PSM path protection";
              }
              container uni-dir {
                presence "Indicates a uni-dir node is configured.";
                description
                  "Enable PSM uni directional (use switch only)";
              }
              container section-protection {
                presence "Indicates a section-protection node is configured.";
                description
                  "Enable PSM section protection";
              }
              container revertive {
                presence "Indicates a revertive node is configured.";
                description
                  "Enable revertive mode";
                leaf wtr {
                  type uint32 {
                    range "0..4294967295" {
                      description
                        "wait time to restore in seconds";
                    }
                  }
                  description
                    "wait time to restore";
                }
              }
              container auto-threshold {
                presence "Indicates a auto-threshold node is configured.";
                description
                  "Enable PSM auto threshold setting";
                leaf auto-threshold-offset {
                  type uint32 {
                    range "0..800" {
                      description
                        "PSM auto threshold offset value";
                    }
                  }
                  description
                    "PSM auto threshold offset value";
                }
              }
              leaf relative-switch-threshold {
                type uint32 {
                  range "0..800" {
                    description
                      "Set Psm Relative Switch Threshold (in units of 0.1 dB)";
                  }
                }
                must "../relative-switch-threshold-offset";
                description
                  "Set Psm Relative Threshold";
              }
              leaf relative-switch-threshold-offset {
                type int32 {
                  range "-300..300" {
                    description
                      "Set Psm Relative Switch Threshold Offset (in units of 0.1 dB)";
                  }
                }
                must "../relative-switch-threshold";
                description
                  "Set Psm Relative Threshold Offset";
              }
            }
            container otdr {
              description
                "otdr commands";
              container port-directions {
                description
                  "otdr port direction";
                list port-direction {
                  key "port-id direction-id";
                  description
                    "otdr port direction";
                  leaf port-id {
                    type uint32 {
                      range "1..2" {
                        description
                          "Select port to configure <1-2>";
                      }
                    }
                    description
                      "otdr port";
                  }
                  leaf direction-id {
                    type enumeration {
                      enum "tx" {
                        value 0;
                        description
                          "Tx direction";
                      }
                      enum "rx" {
                        value 1;
                        description
                          "Rx direction";
                      }
                    }
                    description
                      "otdr direction";
                  }
                  leaf total-loss {
                    type int32 {
                      range "0..500" {
                        description
                          "total loss (in units of 0.1dB)";
                      }
                    }
                    description
                      "total loss decimal value in dB ";
                  }
                  leaf ml-enabled {
                    type uint32 {
                      range "0..1" {
                        description
                          "disable 0 - enable 1";
                      }
                    }
                    description
                      "machine learning event detection ";
                  }
                  leaf refractive-index {
                    type int32 {
                      range "1000000..2000000" {
                        description
                          "refractive index";
                      }
                    }
                    description
                      "refractive index";
                  }
                  leaf back-scattering {
                    type int32 {
                      range "-1000..0" {
                        description
                          "back scattering (in units of 0.1dB)";
                      }
                    }
                    description
                      "back scattering";
                  }
                  container mode-auto {
                    description
                      "mode-auto attributes";
                    leaf loss-sensitivity {
                      type int32 {
                        range "4..50" {
                          description
                            "loss sensitivity (in units of 0.1dB)";
                        }
                      }
                      description
                        "loss sensitivity decimal value in dB";
                    }
                    leaf reflection-sensitivity {
                      type int32 {
                        range "-400..-140" {
                          description
                            "reflection sensitivity (in units of 0.1dB)";
                        }
                      }
                      description
                        "reflection sensitivity decimal value in dB";
                    }
                    leaf loss-relative-threshold {
                      type int32 {
                        range "1..300" {
                          description
                            "loss threshold (in units of 0.1dB)";
                        }
                      }
                      description
                        "relative threshold for loss events";
                    }
                    leaf reflection-relative-threshold {
                      type int32 {
                        range "1..300" {
                          description
                            "reflection threshold (in units of 0.1dB)";
                        }
                      }
                      description
                        "relative threshold for reflection events";
                    }
                  }
                  container mode-expert {
                    description
                      "mode-expert attributes";
                    leaf loss-sensitivity {
                      type int32 {
                        range "4..50" {
                          description
                            "loss sensitivity (in units of 0.1dB)";
                        }
                      }
                      description
                        "loss sensitivity decimal value in dB";
                    }
                    leaf reflection-sensitivity {
                      type int32 {
                        range "-400..-140" {
                          description
                            "reflection sensitivity (in units of 0.1dB)";
                        }
                      }
                      description
                        "reflection sensitivity decimal value in dB";
                    }
                    leaf measure-time {
                      type uint32 {
                        range "1..360" {
                          description
                            "measure time in seconds";
                        }
                      }
                      description
                        "measure time in seconds";
                    }
                    leaf capture-length {
                      type uint32 {
                        range "1..150" {
                          description
                            "capture length in km";
                        }
                      }
                      description
                        "capture length in km";
                    }
                    leaf capture-offset {
                      type uint32 {
                        range "0..150" {
                          description
                            "capture offset in km";
                        }
                      }
                      description
                        "capture offset in km";
                    }
                    leaf span-length {
                      type uint32 {
                        range "1..150" {
                          description
                            "span length in km";
                        }
                      }
                      description
                        "span length in km";
                    }
                    leaf fiber-resolution {
                      type uint32 {
                        range "0..100" {
                          description
                            "fiber resolution in meters";
                        }
                      }
                      description
                        "fiber resolution in meters";
                    }
                    leaf pulse-width {
                      type uint32 {
                        range "8..100000" {
                          description
                            "pulse width in nanoseconds";
                        }
                      }
                      description
                        "pulse width in nanoseconds";
                    }
                    leaf loss-relative-threshold {
                      type int32 {
                        range "1..300" {
                          description
                            "loss threshold (in units of 0.1dB)";
                        }
                      }
                      description
                        "relative threshold for loss events";
                    }
                    leaf reflection-relative-threshold {
                      type int32 {
                        range "1..300" {
                          description
                            "reflection threshold (in units of 0.1dB)";
                        }
                      }
                      description
                        "relative threshold for reflection events";
                    }
                  }
                  container periodic-scan {
                    description
                      "periodic-scan attributes";
                    leaf minutes {
                      type uint32 {
                        range "30..600000" {
                          description
                            "Minutes <30-600000>";
                        }
                      }
                      description
                        "periodic scan minutes";
                    }
                  }
                }
              }
              container ports {
                description
                  "otdr port";
                list port {
                  key "port-id";
                  description
                    "otdr port";
                  leaf port-id {
                    type uint32 {
                      range "1..2" {
                        description
                          "Select port to configure <1-2>";
                      }
                    }
                    description
                      "otdr port";
                  }
                  container otdr-autoscan {
                    description
                      "Enable OTDR auto-scan for this port";
                    leaf otdr-module-ipv4-addr {
                      type inet:ipv4-address-no-zone;
                      must "../ampli-far-end-ipv4-addr";
                      description
                        "Specify OTDR module host address";
                    }
                    leaf ampli-far-end-ipv4-addr {
                      type inet:ipv4-address-no-zone;
                      must "../otdr-module-ipv4-addr and ../ampli-far-end-slot-id";
                      description
                        "Specify OTDR far-end host address";
                    }
                    leaf ampli-far-end-slot-id {
                      type uint32 {
                        range "1..3" {
                          description
                            "Specify OTDR far-end slot number in Range <1-3>";
                        }
                      }
                      must "../ampli-far-end-ipv4-addr and ../scan-type";
                      description
                        "Specify OTDR far-end slot number";
                    }
                    leaf scan-type {
                      type enumeration {
                        enum "AUTO" {
                          value 0;
                          description
                            "OTDR scan type Automatic";
                        }
                      }
                      must "../ampli-far-end-slot-id";
                      description
                        "Specify OTDR scan type";
                    }
                  }
                }
              }
              container ports-abs-threshold {
                description
                  "otdr port abs-threshold";
                list port-abs-threshold {
                  key "port-id";
                  description
                    "otdr port";
                  leaf port-id {
                    type uint32 {
                      range "1..2" {
                        description
                          "Select port to configure <1-2>";
                      }
                    }
                    description
                      "otdr port";
                  }
                  leaf reflection-abs-threshold {
                    type int32 {
                      range "-500..0" {
                        description
                          "reflection threshold (in units of 0.1dB)";
                      }
                    }
                    description
                      "absolute threshold for reflection events";
                  }
                  leaf loss-abs-threshold {
                    type int32 {
                      range "1..300" {
                        description
                          "loss threshold (in units of 0.1dB)";
                      }
                    }
                    description
                      "absolute threshold for loss events";
                  }
                  leaf orl-abs-threshold {
                    type int32 {
                      range "140..400" {
                        description
                          "orl threshold (in units of 0.1dB)";
                      }
                    }
                    description
                      "absolute threshold for orl events";
                  }
                }
              }
            }
          }
        }
      }
    }
  }

  augment "/location:locations/location:location" {
    description
      "This augment extends active nodes configuration";
    uses LOCATION-BODY;
  }
  augment "/location:locations/location:preconfigured-location" {
    description
      "This augment extends preconfigured nodes
       configuration";
    uses LOCATION-BODY;
  }
}
