submodule Cisco-IOS-XR-ncs5500-qos-oper-sub3 {
  belongs-to Cisco-IOS-XR-ncs5500-qos-oper {
    prefix Cisco-IOS-XR-ncs5500-qos-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ncs5500-qos package operational data.
     
     Copyright (c) 2013-2023 by Cisco Systems, Inc.
     All rights reserved.";

  revision 2023-02-01 {
    description
      "Adding changes for BVI.
       2022-09-27
         qos pfc show cmd.
       2022-08-01
         Adding irb-recycle-bandwidth-config and irb-recycle-bandwidth-enable leaf.
       2022-07-28
         Adding qos-policer-scale-config and qos-policer-scale-enable leaf.
       2022-03-09
         qos hwmodule show cmd.";
    semver:module-version "3.0.0";
  }
  revision 2019-08-24 {
    description
      "Fixing pyang compilation error.";
    semver:module-version "2.0.0";
  }
  revision 2019-04-05 {
    description
      "Establish semantic version baseline.";
    semver:module-version "1.1.0";
  }
  revision 2015-11-09 {
    description
      "IOS XR 6.0 revision.";
  }

  grouping DNX-QOSEA-PFC-TC-CFG {
    description
      "DNX QOSEA PFC TC CFG";
    leaf in-use {
      type boolean;
      description
        "Flag to indicate if PFC is configured for the tc";
    }
    leaf pause-threshold {
      type uint32;
      description
        "Pause-threshold configured";
    }
    leaf resume-threshold {
      type uint32;
      description
        "Resume-threshold configured";
    }
    leaf tc-headroom {
      type uint32;
      description
        "Headroom configured";
    }
  }

  grouping DNX-QOSEA-PFC-CFG {
    description
      "DNX QOSEA PFC CFG";
    leaf in-use {
      type boolean;
      description
        "Flag to indicate if PFC is configured for the
         line-card";
    }
    list tc-cfg {
      max-elements "8";
      description
        "Keeps a record of the PFC configuration for the
         line-card";
      uses DNX-QOSEA-PFC-TC-CFG;
    }
  }

  grouping DNX-QOSEA-PFC-PG-VSQ-OCCUPANCY-INFO {
    description
      "DNX QOSEA PFC PG VSQ OCCUPANCY INFO";
    leaf shared-pool-bds {
      type uint32;
      description
        "Vsq occupancy Shared pool bds";
    }
    leaf headroom-bds {
      type uint32;
      description
        "Vsq occupancy headroom bds";
    }
    leaf shared-pool-bytes {
      type uint32;
      units "byte";
      description
        "Vsq occupancy Shared pool bytes";
    }
    leaf headroom-bytes {
      type uint32;
      units "byte";
      description
        "Vsq occupancy Headroom bytes";
    }
  }

  grouping DNX-QOSEA-PFC-VSQ-INGRESS-REJECT-INFO {
    description
      "DNX QOSEA PFC VSQ INGRESS REJECT INFO";
    leaf-list val {
      type uint64;
      max-elements "2";
      description
        "Ingress reject info reg val";
    }
  }

  grouping DNX-QOSEA-PFC-VSQ-FREE-BUFFS-INFO {
    description
      "DNX QOSEA PFC VSQ FREE BUFFS INFO";
    leaf ocb-buff {
      type uint32;
      description
        "Vsq available OCB buffer";
    }
    leaf mnmc-buff {
      type uint32;
      description
        "Vsq available MNMC buffer";
    }
    leaf fmc-buff {
      type uint32;
      description
        "Vsq available FMC buffer";
    }
    leaf ocb-buff-percent {
      type uint32;
      units "percentage";
      description
        "Vsq available OCB buffer Percent";
    }
    leaf mnmc-buff-percent {
      type uint32;
      units "percentage";
      description
        "Vsq available MNMC buffer Percent";
    }
    leaf fmc-buff-percent {
      type uint32;
      units "percentage";
      description
        "Vsq available FMC buffer Percent";
    }
  }

  grouping DNX-QOSEA-PFC-PG-VSQ-THRESHOLD-INFO {
    description
      "DNX QOSEA PFC PG VSQ THRESHOLD INFO";
    leaf id {
      type uint32;
      description
        "VSQ Pg Vsq ID";
    }
    leaf xoff-thr {
      type uint32;
      description
        "PgVsq Xoff threshold";
    }
    leaf xon-thr {
      type uint32;
      description
        "PgVsq Xon threshold";
    }
    leaf headroom {
      type uint32;
      description
        "PgVsq Headroom threshold";
    }
  }

  grouping DNX-QOSEA-PFC-VSQ {
    description
      "DNX QOSEA PFC VSQ";
    leaf intf-handle {
      type uint32;
      description
        "Interface Handle";
    }
    leaf pp-port {
      type uint32;
      description
        "PP port number";
    }
    leaf npu-id {
      type uint8;
      description
        "NPU number";
    }
    leaf core {
      type uint8;
      description
        "Core number";
    }
    list is-inuse {
      min-elements 8;
      max-elements "8";
      description
        "Flag to indicate if PFC is configured for the tc";
      leaf entry {
        type boolean;
        description
          "Array entry.";
      }
    }
    list pg-vsg-info {
      max-elements "8";
      description
        "Keeps a record of vsq threshold info ";
      uses DNX-QOSEA-PFC-PG-VSQ-THRESHOLD-INFO;
    }
    list free-buff {
      max-elements "2";
      description
        "Keeps a record of available buffer info";
      uses DNX-QOSEA-PFC-VSQ-FREE-BUFFS-INFO;
    }
    list reject-reason {
      max-elements "2";
      description
        "Keeps a record of ingress reject info";
      uses DNX-QOSEA-PFC-VSQ-INGRESS-REJECT-INFO;
    }
    list pgvsq-occupancy-info {
      max-elements "8";
      description
        "Keeps a record of vsq occupancy info";
      uses DNX-QOSEA-PFC-PG-VSQ-OCCUPANCY-INFO;
    }
  }
}
