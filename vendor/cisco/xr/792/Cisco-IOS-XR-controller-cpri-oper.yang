module Cisco-IOS-XR-controller-cpri-oper {
  namespace "http://cisco.com/ns/yang/Cisco-IOS-XR-controller-cpri-oper";
  prefix controller-cpri-oper;

  import Cisco-IOS-XR-types {
    prefix xr;
  }
  import cisco-semver {
    prefix semver;
  }
  include Cisco-IOS-XR-controller-cpri-oper-sub1 {
    revision-date 2021-08-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-cpri package operational data.
     
     This module contains definitions
     for the following management objects:
       cpri: CPRI operational data
     
     Copyright (c) 2013-2021 by Cisco Systems, Inc.
     All rights reserved.";

  revision 2021-08-09 {
    description
      "Added RoE and datapath-internal alarms to CPRI port info and stats.";
    semver:module-version "2.2.0";
  }
  revision 2021-06-03 {
    description
      "Added leaf cpri-hfn-sync-event to container stats.";
    semver:module-version "2.1.0";
  }
  revision 2021-05-10 {
    description
      "Added leaf hfn-sync-disable to grouping CPRI-PORT-ROE-PARAMS
       2021-05-03
           Added mapper,demapper roe-profile parameters presync-match-threshold, resync-match-threshold, resync-mismatch-threshold, sync-threshold, drain-threshold, presync-match-count, resync-match-count, resync-mismatch-count.
       2021-04-30
           Added roe-pkt-len-in-use to container info.
       2020-11-04
           Added auto-neg-status, auto-neg-fail-reason, hfn-sync-time, roe-sync-time and auto-neg-completion-time to container info. Added rx-cpri-hyper-frames and tx-cpri-hyper-frames to container stats.
       2020-08-03
           Changed leaf packet-len type to uint16. Renamed leaf errored-packets to errored-length-packets. Added leaves receive-good-packets and receive-roe-lcv-count.";
    semver:module-version "2.0.0";
  }
  revision 2019-12-02 {
    description
      "Show command subtype added for CPRI controller";
    semver:module-version "1.1.0";
  }
  revision 2019-04-05 {
    description
      "Establish semantic version baseline.";
    semver:module-version "1.0.0";
  }
  revision 2015-11-09 {
    description
      "IOS XR 6.0 revision.";
  }

  container cpri {
    config false;
    description
      "CPRI operational data";
    container controllers {
      description
        "All CPRI controller operational data";
      list controller {
        key "controller-name";
        description
          "CPRI controller operational data";
        container detail {
          description
            "CPRI controller detailed data including ROE
             stats";
          uses CPRI-PORT-DETAIL;
        }
        container stats {
          description
            "CPRI controller operational data statistics";
          uses CPRI-PORT-STATS;
        }
        container info {
          description
            "CPRI controller operational data";
          uses CPRI-PORT-INFO;
        }
        container roe-stats {
          description
            "ROE statistics w.r.t CPRI controller";
          uses CPRI-PORT-ROE-STATS;
        }
        container roe-profile {
          description
            "ROE profile params associated with CPRI
             controller";
          uses CPRI-PORT-ROE-PROFILE;
        }
        leaf controller-name {
          type xr:Interface-name;
          description
            "Interface name";
        }
      }
    }
  }
}
