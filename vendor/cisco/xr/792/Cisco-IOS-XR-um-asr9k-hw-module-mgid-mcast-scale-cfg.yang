module Cisco-IOS-XR-um-asr9k-hw-module-mgid-mcast-scale-cfg {
  namespace "http://cisco.com/ns/yang/Cisco-IOS-XR-um-asr9k-hw-module-mgid-mcast-scale-cfg";
  prefix um-asr9k-hw-module-mgid-mcast-scale-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-hw-module-mgid-mcast-scale package configuration.
     
     This YANG module augments the
     modules with configuration data.
     
     Copyright (c) 2022 by Cisco Systems, Inc.
     All rights reserved.";

  revision 2022-08-10 {
    description
      "Initial release";
    semver:module-version "1.0.0";
  }

  container hw-module {
    description
      "Configure h/w module";
    container mgid-mcast-scale {
      description
        "Mgid max mcast scale";
      container enable {
        presence "Indicates a enable node is configured.";
        description
          "enable mgid max mcast scale ";
      }
    }
  }
}
