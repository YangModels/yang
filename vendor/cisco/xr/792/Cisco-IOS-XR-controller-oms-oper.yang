module Cisco-IOS-XR-controller-oms-oper {
  namespace "http://cisco.com/ns/yang/Cisco-IOS-XR-controller-oms-oper";
  prefix controller-oms-oper;

  import Cisco-IOS-XR-types {
    prefix xr;
  }
  import cisco-semver {
    prefix semver;
  }
  include Cisco-IOS-XR-controller-oms-oper-sub1 {
    revision-date 2022-05-23;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-oms package operational data.
     
     This module contains definitions
     for the following management objects:
       oms-oper: Oms operational data
     
     Copyright (c) 2013-2022 by Cisco Systems, Inc.
     All rights reserved.";

  revision 2022-05-23 {
    description
      "total-rx-power leaf is changed to rx-power in oms-info container";
    semver:module-version "1.0.0";
  }
  revision 2022-03-25 {
    description
      "Added transport_admin_state for OMS controller";
  }
  revision 2021-06-28 {
    description
      "New Oper Model Added for Oms Controller";
  }
  revision 2019-04-05 {
    description
      "Establish semantic version baseline.";
  }
  revision 2015-11-09 {
    description
      "IOS XR 6.0 revision.";
  }

  container oms-oper {
    config false;
    description
      "Oms operational data";
    container oms-ports {
      description
        "All Oms Port operational data";
      list oms-port {
        key "name";
        description
          "Oms operational data";
        container oms-info {
          description
            "Oms operational data";
          uses OMS-EDM-INFO;
        }
        leaf name {
          type xr:Interface-name;
          description
            "Port name";
        }
      }
    }
  }
}
