module Cisco-IOS-XR-um-license-smart-cfg {
  namespace "http://cisco.com/ns/yang/Cisco-IOS-XR-um-license-smart-cfg";
  prefix um-license-smart-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR license-smart package configuration.
     
     This YANG module augments the
     modules with configuration data.
     
     Copyright (c) 2021-2022 by Cisco Systems, Inc.
     All rights reserved.";

  revision 2022-03-05 {
    description
      "Model deprecated";
    semver:module-version "1.1.0";
  }
  revision 2021-03-03 {
    description
      "Initial release";
    semver:module-version "1.0.0";
  }

  feature is_software_upgrade_config_visible {
    description
      "is software upgrade config visible";
  }

  feature is_reservation_config_visible {
    description
      "is reservation config visible";
  }

  feature is_config_visible {
    description
      "is config visible";
  }

  container license {
    status deprecated;
    description
      "license";
    container smart {
      description
        "Smart Licensing";
      container transport {
        description
          "Select the type of message transport for Smart Licensing";
        container smart {
          presence "Indicates a smart node is configured.";
          description
            "Use the http as transport";
        }
      }
      leaf url {
        type string {
          length "1..200" {
            description
              "Set the Smart Transport URL";
          }
        }
        description
          "Set the Smart Transport Primary URL";
      }
      container proxy {
        description
          "Proxy related commands";
        leaf hostname {
          type xr:Cisco-ios-xr-string {
            length "1..200" {
              description
                "address/hostname";
            }
          }
          description
            "The IP address or hostname of the Proxy";
        }
        leaf port {
          type uint32 {
            range "0..65535" {
              description
                "proxy port";
            }
          }
          description
            "The proxy port";
        }
      }
    }
  }
  container license-smart-flexible-consumption {
    if-feature "is_config_visible";
    status deprecated;
    description
      "flexible-consumption(Vortex) model";
    container enable {
      presence "Indicates a enable node is configured.";
      description
        "Enable flexible-consumption model";
    }
  }
  container license-smart-software-upgrade {
    if-feature "is_software_upgrade_config_visible";
    status deprecated;
    description
      "Enable or disable the software-upgrade feature";
    container enable {
      presence "Indicates a enable node is configured.";
      description
        "Enable or disable the software-upgrade feature";
    }
  }
  container license-smart-reservation {
    if-feature "is_reservation_config_visible";
    presence "Indicates a reservation node is configured.";
    status deprecated;
    description
      "Enable or disable the license reservation feature";
  }
}
