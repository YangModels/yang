submodule Cisco-IOS-XR-healthcheck-oper-sub2 {
  belongs-to Cisco-IOS-XR-healthcheck-oper {
    prefix Cisco-IOS-XR-healthcheck-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR healthcheck package operational data.
     
     Copyright (c) 2013-2022 by Cisco Systems, Inc.
     All rights reserved.";

  revision 2022-04-07 {
    description
      "Updated Install Metric
       2021-10-19
         Updated Custom Metric
       2021-07-22
         ASIC reset and packet drops use case updated
       2021-05-25
         ASIC reset and packet drops usecases added";
    semver:module-version "1.1.0";
  }
  revision 2020-09-18 {
    description
      "Fabric health metric updated.";
    semver:module-version "1.0.0";
  }
  revision 2019-04-05 {
    description
      "Establish semantic version baseline.";
  }
  revision 2015-11-09 {
    description
      "IOS XR 6.0 revision.";
  }

  typedef String1 {
    type string;
    description
      "String1";
  }

  typedef Hcmgr-metric-health-state {
    type enumeration {
      enum "normal" {
        value 0;
        description
          "Healtchcheck metric in normal state";
      }
      enum "minor" {
        value 1;
        description
          "Healthcheck metric in minor state";
      }
      enum "severe" {
        value 2;
        description
          "Healthcheck metric in severe state";
      }
      enum "critical" {
        value 3;
        description
          "Healthcheck metric in critical state";
      }
      enum "warning" {
        value 4;
        description
          "Healthcheck metric in warning state";
      }
      enum "unknown" {
        value 5;
        description
          "Healthcheck metric in Unknown state";
      }
    }
    description
      "Healthcheck metric health state";
  }

  typedef Hcmgr-metric-service-state {
    type enumeration {
      enum "reset" {
        value 0;
        description
          "Healthcheck metric service in reset state";
      }
      enum "disabled" {
        value 1;
        description
          "Healthcheck metric service in disabled state";
      }
      enum "init-done" {
        value 2;
        description
          "Healthcheck metric service in init done state";
      }
      enum "enabled" {
        value 3;
        description
          "Healthcheck metric service in enabled state";
      }
      enum "configured" {
        value 4;
        description
          "Healthcheck metric service in configured state";
      }
      enum "error" {
        value 5;
        description
          "Healthcheck metric service in error state";
      }
      enum "unsupported" {
        value 6;
        description
          "Healtchcheck metric service in unsupported
           state";
      }
      enum "unknown" {
        value 7;
        description
          "Healthcheck metric service unknown";
      }
    }
    description
      "Healthcheck metric service state";
  }

  grouping HCMGR-USE-CASE-SUMMARY-DATA {
    description
      "Use case summary";
    leaf use-case {
      type string;
      description
        "Use case name";
    }
    leaf timestamp {
      type uint64;
      units "nanosecond";
      description
        "Timestamp in nanoseconds since the UNIX epoch
         (January 1st 1970 00:00:00 UTC)";
    }
    leaf alert {
      type string;
      description
        "Alert message. For display only";
    }
    leaf state {
      type string;
      description
        "NOSI state";
    }
  }

  grouping HCMGR-USE-CASE-DETAIL-DATA {
    description
      "Detail use case data for given NPU";
    leaf timestamp {
      type uint64;
      units "nanosecond";
      description
        "Timestamp in nanoseconds since the UNIX epoch
         (January 1st 1970 00:00:00 UTC)";
    }
    leaf-list alert {
      type String1;
      description
        "Alert message. For display only";
    }
  }

  grouping HCMGR-CPU-METRIC-MDATA {
    description
      "CPU Metric Mdata";
    leaf one-min {
      type uint8;
      description
        "One Minute Utilization";
    }
    leaf five-min {
      type uint8;
      description
        "Five Minute Utilization";
    }
    leaf fifteen-min {
      type uint8;
      description
        "Fifteen Minute Utilization";
    }
    leaf node-name {
      type string;
      description
        "Node Name";
    }
  }

  grouping HCMGR-CPU-METRIC-DATA {
    description
      "CPU Metric Data structure";
    leaf state {
      type string;
      description
        "Metric Current State";
    }
    leaf last-update {
      type string;
      description
        "Last Update Time";
    }
    leaf active-node-count {
      type uint8;
      description
        "Number of Active Nodes";
    }
    leaf srv-state {
      type string;
      description
        "Service State";
    }
    leaf cp-util-sel {
      type uint32;
      description
        "CPU Utilization Selection";
    }
    leaf minor-threshold {
      type uint32;
      description
        "Minor Threshold";
    }
    leaf severe-threshold {
      type uint32;
      description
        "Severe Threshold";
    }
    leaf critical-threshold {
      type uint32;
      description
        "Critical Threshold";
    }
    list mdata {
      description
        "Metric Mdata Array";
      uses HCMGR-CPU-METRIC-MDATA;
    }
  }

  grouping INST-TIMEZONE-INFO {
    description
      "Timezone type info";
    leaf node-name {
      type string;
      description
        "Node name";
    }
    leaf time {
      type string;
      description
        "Timezone";
    }
    leaf vm {
      type string;
      description
        "VM type";
    }
  }

  grouping HCMGR-SYSTEMCLOCK-METRIC-DATA {
    description
      "Systemclock metric Data Structure";
    leaf srv-state {
      type Hcmgr-metric-service-state;
      description
        "Healthcheck metric service state";
    }
    leaf name {
      type string;
      description
        "Name";
    }
    leaf health-state {
      type Hcmgr-metric-health-state;
      description
        "Metric Health State";
    }
    leaf health-msg {
      type string;
      description
        "Metric Health Message";
    }
    leaf last-update {
      type string;
      description
        "Last Update Time";
    }
    list timezone {
      key "node-name";
      description
        "Timezone info ";
      uses INST-TIMEZONE-INFO;
    }
  }

  grouping INST-PROCESS-INFO {
    description
      "Process status detail";
    leaf name {
      type string;
      description
        "Process name";
    }
    leaf location {
      type string;
      description
        "Node location";
    }
    leaf signal {
      type string;
      description
        "Signal type";
    }
    leaf vm {
      type string;
      description
        "VM type";
    }
  }

  grouping HCMGR-PROCESS-STATE-METRIC-DATA {
    description
      "Process state Metric Data Structure";
    leaf srv-state {
      type Hcmgr-metric-service-state;
      description
        "Healthcheck metric service state";
    }
    leaf name {
      type string;
      description
        "Metric Name";
    }
    leaf health-state {
      type Hcmgr-metric-health-state;
      description
        "Metric Health State";
    }
    leaf health-msg {
      type string;
      description
        "Metric Health Message";
    }
    leaf last-update {
      type string;
      description
        "Last Update Time";
    }
    list process {
      description
        "Process info detail";
      uses INST-PROCESS-INFO;
    }
  }

  grouping WATCHDOG-STATUS-INFO {
    description
      "Watchdog status";
    leaf wdog-started {
      type string;
      description
        "Wdog started";
    }
    leaf wdog-running {
      type string;
      description
        "Wdog running";
    }
    leaf wdog-interval {
      type string;
      description
        "Wdog interval";
    }
    leaf last-feed {
      type string;
      description
        "Wdog Last feed";
    }
  }

  grouping HCMGR-WDMON-METRIC-DATA {
    description
      "Watchdog status Metric Data Structure";
    leaf srv-state {
      type Hcmgr-metric-service-state;
      description
        "Healthcheck metric service state";
    }
    leaf name {
      type string;
      description
        "Name";
    }
    leaf health-state {
      type Hcmgr-metric-health-state;
      description
        "Metric Health State";
    }
    leaf health-msg {
      type string;
      description
        "Metric Health Message";
    }
    leaf last-update {
      type string;
      description
        "Last Update Time";
    }
    list watchdog-status {
      description
        "Watchdog status";
      uses WATCHDOG-STATUS-INFO;
    }
  }

  grouping HCMGR-SHARED-MEM-METRIC-MDATA {
    description
      "Shared Memory Metric Mdata";
    leaf shared-memory-usage {
      type uint64;
      description
        "Shared Memory Usage";
    }
    leaf shared-mem-util {
      type uint32;
      description
        "Shared Memory Utilization";
    }
    leaf node-name {
      type string;
      description
        "Node Name";
    }
  }

  grouping HCMGR-SHARED-MEM-METRIC-DATA {
    description
      "Shared Memory Metric Data structure";
    leaf state {
      type string;
      description
        "Metric Current State";
    }
    leaf last-update {
      type string;
      description
        "Last Update Time";
    }
    leaf active-node-count {
      type uint8;
      description
        "Number of Active Nodes";
    }
    leaf srv-state {
      type string;
      description
        "Service State";
    }
    leaf shared-mem-alloc {
      type uint64;
      description
        "Shared Memory Allocation";
    }
    leaf minor-threshold {
      type uint32;
      description
        "Minor Threshold";
    }
    leaf severe-threshold {
      type uint32;
      description
        "Severe Threshold";
    }
    leaf critical-threshold {
      type uint32;
      description
        "Critical Threshold";
    }
    list mdata {
      description
        "Metric Mdata array";
      uses HCMGR-SHARED-MEM-METRIC-MDATA;
    }
  }

  grouping HCMGR-CONFIG-INCONSISTENCY-METRIC-DATA {
    description
      "Config inconsistency Metric Data Structure";
    leaf srv-state {
      type Hcmgr-metric-service-state;
      description
        "Healthcheck metric service state";
    }
    leaf name {
      type string;
      description
        "Metric Name";
    }
    leaf health-state {
      type Hcmgr-metric-health-state;
      description
        "Metric Health State";
    }
    leaf health-msg {
      type string;
      description
        "Metric Health Message";
    }
    leaf last-update {
      type string;
      description
        "Last Update Time";
    }
    leaf metric-info {
      type string;
      description
        "Config inconsistency info";
    }
  }

  grouping HCMGR-FILESYSTEM-PARTITION {
    description
      "Filesystem Partition Data";
    leaf flags {
      type string;
      description
        "Partition Access Attribute";
    }
    leaf prefixes {
      type string;
      description
        "Partition Name";
    }
    leaf type {
      type string;
      description
        "Partition Type";
    }
    leaf size {
      type uint64;
      description
        "Partition Size";
    }
    leaf free {
      type uint64;
      units "byte";
      description
        "Free Bytes";
    }
    leaf avl-free {
      type uint8;
      description
        "Free Space in %";
    }
  }

  grouping HCMGR-FILESYSTEM-METRIC-MDATA {
    description
      "Filesystem Metric Mdata";
    leaf node-name {
      type string;
      description
        "Node Name";
    }
    leaf partition-count {
      type uint8;
      description
        "Partition Count";
    }
    list fs-mdata {
      description
        "Partition Data";
      uses HCMGR-FILESYSTEM-PARTITION;
    }
  }

  grouping HCMGR-FILESYSTEM-METRIC-DATA {
    description
      "Filesystem Metric Data structure";
    leaf state {
      type string;
      description
        "Metric Current State";
    }
    leaf last-update {
      type string;
      description
        "Last Update Time";
    }
    leaf active-node-count {
      type uint8;
      description
        "Number of Active Nodes";
    }
    leaf srv-state {
      type string;
      description
        "Service State";
    }
    leaf minor-threshold {
      type uint32;
      description
        "Minor Threshold";
    }
    leaf severe-threshold {
      type uint32;
      description
        "Severe Threshold";
    }
    leaf critical-threshold {
      type uint32;
      description
        "Critical Threshold";
    }
    list mdata {
      description
        "Metric Mdata Array";
      uses HCMGR-FILESYSTEM-METRIC-MDATA;
    }
  }

  grouping LCMON-TREE-INFO {
    description
      "LC Monitoring details";
    leaf lc-location {
      type string;
      description
        "LC location";
    }
    leaf status {
      type string;
      description
        "LC status";
    }
    leaf app-status {
      type string;
      description
        "App status";
    }
    leaf used-memory {
      type string;
      description
        "Used memory";
    }
  }

  grouping HCMGR-LCMON-METRIC-DATA {
    description
      "LC Monitoring Metric Data Structure";
    leaf srv-state {
      type Hcmgr-metric-service-state;
      description
        "healthcheck metric service state";
    }
    leaf name {
      type string;
      description
        "Name";
    }
    leaf health-state {
      type Hcmgr-metric-health-state;
      description
        "Metric Health State";
    }
    leaf health-msg {
      type string;
      description
        "Metric Health Message";
    }
    leaf last-update {
      type string;
      description
        "Last Update Time";
    }
    list lcmon-status {
      key "lc-location";
      description
        "LC Monitoring detail";
      uses LCMON-TREE-INFO;
    }
  }

  grouping HCMGR-FABRIC-STATS-METRIC-DETAIL-MDATA {
    description
      "Fabric Stats Metric Detail Mdata Structure";
    leaf fabric-plane-key {
      type uint32;
      description
        "Fabric Plane Key";
    }
    leaf planeid {
      type uint32;
      description
        "PlaneID";
    }
    leaf ucast-oper-state {
      type string;
      description
        "Ucast Oper State";
    }
    list counter-mdata {
      description
        "Fabric Stats Metric Counter Mdata";
      uses HCMGR-PFM-STATS-METRICS-DETAIL-COUNTER-MDATA;
    }
  }

  grouping HCMGR-FABRIC-STATS-METRIC-DETAIL-DATA {
    description
      "Fabric Stats Metric Detail Data structure";
    leaf last-update {
      type string;
      description
        "Last Update Time";
    }
    list mdata {
      description
        "Metric Mdata";
      uses HCMGR-FABRIC-STATS-METRIC-DETAIL-MDATA;
    }
  }

  grouping HCMGR-FABRIC-STATS-METRIC-MDATA {
    description
      "Fabric Stats Metric Mdata Structure";
    leaf fabric-plane-key {
      type uint32;
      description
        "Fabric Plane Key";
    }
    leaf planeid {
      type uint32;
      description
        "PlaneID";
    }
    leaf ucast-oper-state {
      type string;
      description
        "Ucast Oper State";
    }
    list counter-mdata {
      description
        "Fabric Stats Metric Counters Mdata";
      uses HCMGR-PFM-STATS-METRICS-COUNTER-MDATA;
    }
  }

  grouping HCMGR-FABRIC-STATS-METRIC-DATA {
    description
      "Fabric Stats Metric Data structure";
    leaf state {
      type string;
      description
        "Metric Current State";
    }
    leaf last-update {
      type string;
      description
        "Last Update Time";
    }
    leaf srv-state {
      type string;
      description
        "Service State";
    }
    list mdata {
      description
        "Metric Mdata";
      uses HCMGR-FABRIC-STATS-METRIC-MDATA;
    }
  }

  grouping HCMGR-CUSTOM-METRIC-DATA {
    description
      "Custom Metric Data Structure";
    leaf srv-state {
      type string;
      description
        "Service State";
    }
    leaf name {
      type string;
      description
        "Metric Name";
    }
    leaf health-state {
      type string;
      description
        "Metric Health State";
    }
    leaf health-msg {
      type string;
      description
        "Metric Health Message";
    }
    leaf last-update {
      type string;
      description
        "Last Update Time";
    }
    leaf metric-info {
      type string;
      description
        "Vendor Proprietary Metric Info";
    }
  }

  grouping INST-PROCESS-RESOURCE-INFO {
    description
      "Process with rlimit value details";
    leaf process-name {
      type string;
      description
        "Process name";
    }
    leaf node-name {
      type string;
      description
        "Node name";
    }
    leaf rlimit {
      type uint32;
      description
        "Rlimit";
    }
    leaf vm {
      type string;
      description
        "VM type";
    }
  }

  grouping HCMGR-PROCESS-RESOURCE-METRIC-DATA {
    description
      "Process resource metric Data Structure";
    leaf srv-state {
      type Hcmgr-metric-service-state;
      description
        "Healthcheck metric service state";
    }
    leaf name {
      type string;
      description
        "Name";
    }
    leaf health-state {
      type Hcmgr-metric-health-state;
      description
        "Metric Health State";
    }
    leaf health-msg {
      type string;
      description
        "Metric Health Message";
    }
    leaf last-update {
      type string;
      description
        "Last Update Time";
    }
    list process-resource {
      description
        "Process info detail";
      uses INST-PROCESS-RESOURCE-INFO;
    }
  }

  grouping HCMGR-FREE-MEM-METRIC-MDATA {
    description
      "Free Memory Metric Mdata";
    leaf free-mem {
      type uint64;
      description
        "Total Free Memory";
    }
    leaf system-mem {
      type uint64;
      description
        "Total System Memory";
    }
    leaf avl-free-mem {
      type uint8;
      description
        "Free Memory Utilization";
    }
    leaf node-name {
      type string;
      description
        "Node Name";
    }
  }

  grouping HCMGR-FREE-MEM-METRIC-DATA {
    description
      "Free Memory Metric Data structure";
    leaf state {
      type string;
      description
        "Metric Current State";
    }
    leaf last-update {
      type string;
      description
        "Last Update Time";
    }
    leaf active-node-count {
      type uint8;
      description
        "Number of Active Nodes";
    }
    leaf srv-state {
      type string;
      description
        "Service State";
    }
    leaf minor-threshold {
      type uint32;
      description
        "Minor Threshold";
    }
    leaf severe-threshold {
      type uint32;
      description
        "Severe Threshold";
    }
    leaf critical-threshold {
      type uint32;
      description
        "Critical Threshold";
    }
    list mdata {
      description
        "Metric Mdata Array";
      uses HCMGR-FREE-MEM-METRIC-MDATA;
    }
  }

  grouping COMMUNICATION-TIMEOUT-STATUS-INFO {
    description
      "Communication timeout status info";
    leaf process-name {
      type string;
      description
        "Process name";
    }
    leaf location {
      type string;
      description
        "Location";
    }
  }

  grouping HCMGR-COMMUNICATION-TIMEOUT-METRIC-DATA {
    description
      "Communication timeout Metric Data Structure";
    leaf srv-state {
      type Hcmgr-metric-service-state;
      description
        "Healthcheck metric service state";
    }
    leaf name {
      type string;
      description
        "Name";
    }
    leaf health-state {
      type Hcmgr-metric-health-state;
      description
        "Metric Health State";
    }
    leaf health-msg {
      type string;
      description
        "Metric Health Message";
    }
    leaf last-update {
      type string;
      description
        "Last Update Time";
    }
    list communication-timeout-status {
      description
        "Communication timeout status Info";
      uses COMMUNICATION-TIMEOUT-STATUS-INFO;
    }
  }

  grouping HCMGR-ASIC-ERRORS-METRIC-INSTANCE-MDATA {
    description
      "Asic Errors Metric Instance Mdata Structure";
    leaf instance-number {
      type uint8;
      description
        "Instance Number";
    }
    list counter-mdata {
      description
        "Asic Errors Metric Counters Mdata";
      uses HCMGR-PFM-STATS-METRICS-COUNTER-MDATA;
    }
  }

  grouping HCMGR-ASIC-ERRORS-METRIC-MDATA {
    description
      "Asic Errors Metric Mdata Structure";
    leaf node-name {
      type string;
      description
        "Node Name";
    }
    list instance-mdata {
      description
        "Asic Errors Metric Mdata";
      uses HCMGR-ASIC-ERRORS-METRIC-INSTANCE-MDATA;
    }
  }

  grouping HCMGR-ASIC-ERRORS-METRIC-DATA {
    description
      "Asic Errors Metric Data structure";
    leaf state {
      type string;
      description
        "Metric Current State";
    }
    leaf last-update {
      type string;
      description
        "Last Update Time";
    }
    leaf srv-state {
      type string;
      description
        "Service State";
    }
    list mdata {
      description
        "Metric Mdata";
      uses HCMGR-ASIC-ERRORS-METRIC-MDATA;
    }
  }

  grouping HCMGR-ASIC-ERRORS-METRIC-DETAIL-INSTANCE-MDATA {
    description
      "Asic Errors Metric Instance Mdata Structure";
    leaf instance-number {
      type uint8;
      description
        "Instance Number";
    }
    list counter-mdata {
      description
        "Asic Errors Metric Mdata";
      uses HCMGR-PFM-STATS-METRICS-DETAIL-COUNTER-MDATA;
    }
  }

  grouping HCMGR-ASIC-ERRORS-METRIC-DETAIL-MDATA {
    description
      "Asic Errors Metric Detail Mdata Structure";
    leaf node-name {
      type string;
      description
        "Node Name";
    }
    list instance-mdata {
      description
        "Asic Errors Metric Mdata";
      uses HCMGR-ASIC-ERRORS-METRIC-DETAIL-INSTANCE-MDATA;
    }
  }

  grouping HCMGR-ASIC-ERRORS-METRIC-DETAIL-DATA {
    description
      "Asic Errors Metric Detail Data structure";
    leaf last-update {
      type string;
      description
        "Last Update Time";
    }
    list mdata {
      description
        "Metric Mdata";
      uses HCMGR-ASIC-ERRORS-METRIC-DETAIL-MDATA;
    }
  }

  grouping HCMGR-PFM-STATS-METRICS-COUNTER-MDATA {
    description
      "Platform Stats Metrics Counter Mdata Structure";
    leaf counter-name {
      type string;
      description
        "Counter Name";
    }
    leaf counter-value {
      type uint64;
      description
        "Counter Value";
    }
    leaf average {
      type uint64;
      description
        "Counter Average Value";
    }
    leaf is-consistently-increasing {
      type boolean;
      description
        "Is Counter Increasing Consistently";
    }
  }

  grouping HCMGR-INTF-COUNTERS-METRIC-MDATA {
    description
      "Interface Counters Metric Mdata Structure";
    leaf interface-name {
      type string;
      description
        "Interface Name Monitored";
    }
    list counter-mdata {
      description
        "Interface Counters Metric Mdata";
      uses HCMGR-PFM-STATS-METRICS-COUNTER-MDATA;
    }
  }

  grouping HCMGR-INTF-COUNTERS-METRIC-DATA {
    description
      "Interface Counters Metric Data structure";
    leaf state {
      type string;
      description
        "Metric Current State";
    }
    leaf last-update {
      type string;
      description
        "Last Update Time";
    }
    leaf srv-state {
      type string;
      description
        "Service State";
    }
    list mdata {
      description
        "Metric Mdata";
      uses HCMGR-INTF-COUNTERS-METRIC-MDATA;
    }
  }

  grouping HCMGR-PFM-STATS-METRICS-DETAIL-COUNTER-MDATA {
    description
      "Platform Stats Metrics Detail Counter Mdata
       Structure";
    leaf counter-name {
      type string;
      description
        "Counter Name";
    }
    list counter-value {
      description
        "Counter Value";
      leaf entry {
        type uint64;
        description
          "Counter Value";
      }
    }
  }

  grouping HCMGR-INTF-COUNTERS-METRIC-DETAIL-MDATA {
    description
      "Interface Counters Metric Detail Mdata Structure";
    leaf interface-name {
      type string;
      description
        "Interface Name Monitored";
    }
    list counter-mdata {
      description
        "Interface Counters Metric Mdata";
      uses HCMGR-PFM-STATS-METRICS-DETAIL-COUNTER-MDATA;
    }
  }

  grouping HCMGR-INTF-COUNTERS-METRIC-DETAIL-DATA {
    description
      "Interface Counters Metric Detail Data structure";
    leaf last-update {
      type string;
      description
        "Last Update Time";
    }
    list mdata {
      description
        "Metric Mdata";
      uses HCMGR-INTF-COUNTERS-METRIC-DETAIL-MDATA;
    }
  }

  grouping HCMGR-PLATFORM-METRIC-INFO {
    description
      "Platform Metric Info Structure";
    leaf node-name {
      type string;
      description
        "Node Name";
    }
    leaf card-type {
      type string;
      description
        "Card Type";
    }
    leaf card-redundancy-state {
      type string;
      description
        "Card Redundancy State";
    }
    leaf admin-state {
      type string;
      description
        "Admin State";
    }
    leaf oper-state {
      type string;
      description
        "Oper State";
    }
  }

  grouping HCMGR-PLATFORM-INSTANCE-MDATA {
    description
      "Platform Metric Instance Mdata Structure";
    container platform-info {
      description
        "Platform Info";
      uses HCMGR-PLATFORM-METRIC-INFO;
    }
    leaf instance-name {
      type string;
      description
        "Instance Name";
    }
  }

  grouping HCMGR-PLATFORM-SLOT-MDATA {
    description
      "Platform Metric Slot Mdata Structure";
    leaf slot-name {
      type string;
      description
        "Slot Name";
    }
    leaf instance-count {
      type uint8;
      description
        "Instance Count";
    }
    list instance-mdata {
      description
        "Instance Mdata";
      uses HCMGR-PLATFORM-INSTANCE-MDATA;
    }
    list platform-info {
      description
        "Platform Info";
      uses HCMGR-PLATFORM-METRIC-INFO;
    }
  }

  grouping HCMGR-PLATFORM-METRIC-RACK-MDATA {
    description
      "Platform Metric Mdata Structure";
    leaf rack-name {
      type string;
      description
        "Rack Name";
    }
    leaf slot-count {
      type uint8;
      description
        "Slot Count";
    }
    list slot-mdata {
      description
        "Slot Mdata";
      uses HCMGR-PLATFORM-SLOT-MDATA;
    }
  }

  grouping HCMGR-PLATFORM-METRIC-DATA {
    description
      "Platform Metric Data structure";
    leaf state {
      type string;
      description
        "Metric Current State";
    }
    leaf last-update {
      type string;
      description
        "Last Update Time";
    }
    leaf rack-count {
      type uint8;
      description
        "Rack Count";
    }
    leaf srv-state {
      type string;
      description
        "Service State";
    }
    list mdata {
      description
        "Metric Mdata";
      uses HCMGR-PLATFORM-METRIC-RACK-MDATA;
    }
  }

  grouping HWMON-TREE-INFO {
    description
      "HW Monitoring Info";
    leaf device-name {
      type string;
      description
        "Device name";
    }
    leaf status {
      type string;
      description
        "Device Status";
    }
  }

  grouping HCMGR-HWMON-METRIC-DATA {
    description
      "HW Monitoring Metric Data Structure";
    leaf srv-state {
      type Hcmgr-metric-service-state;
      description
        "Healthcheck metric service state";
    }
    leaf name {
      type string;
      description
        "Metric Name";
    }
    leaf health-state {
      type Hcmgr-metric-health-state;
      description
        "Metric Health State";
    }
    leaf health-msg {
      type string;
      description
        "Metric Health Message";
    }
    leaf last-update {
      type string;
      description
        "Last Update Time";
    }
    list hwmon-tree-status {
      key "device-name";
      description
        "HW Monitoring Info";
      uses HWMON-TREE-INFO;
    }
  }

  grouping HCMGR-FABRIC-HEALTH-METRIC-SYS-PLANE-MDATA {
    description
      "Fabric Health Metric Mdata structure";
    leaf admin-state {
      type string;
      description
        "Admin State";
    }
    leaf plane-state {
      type string;
      description
        "Plane State";
    }
    leaf racks-w-plane-fault {
      type uint8;
      description
        "Racks With Plane Fault";
    }
    leaf is-data-drop {
      type boolean;
      description
        "Is Data Drop";
    }
  }

  grouping HCMGR-FABRIC-HEALTH-METRIC-RACK-MDATA {
    description
      "Fabric Health Metric Mdata structure";
    leaf rack-num {
      type uint8;
      description
        "Rack Number";
    }
    leaf rack-type {
      type string;
      description
        "Rack Type";
    }
    leaf sfe-asics-total {
      type uint8;
      description
        "SFE Asics Total";
    }
    leaf sfe-asics-up {
      type uint8;
      description
        "SFE Asics Up";
    }
    leaf sfe-asics-dn {
      type uint8;
      description
        "SFE Asics Down";
    }
    leaf fia-asics-total {
      type uint8;
      description
        "FIA Asics Total";
    }
    leaf fia-asics-up {
      type uint8;
      description
        "FIA Asics Up";
    }
    leaf fia-asics-dn {
      type uint8;
      description
        "FIA Asics Down";
    }
    leaf num-valid-fabids {
      type uint8;
      description
        "Number of Valid Fabids";
    }
  }

  grouping HCMGR-FABRIC-HEALTH-METRIC-MSG {
    description
      "Fabric Health Metric Message structure";
    leaf rack-total {
      type uint8;
      description
        "Rack Total";
    }
    leaf rack-fcc {
      type uint8;
      description
        "Rack FCC";
    }
    leaf rack-lcc {
      type uint8;
      description
        "Rack LCC";
    }
    leaf plane-up {
      type uint8;
      description
        "Plane Up";
    }
    leaf plane-dn {
      type uint8;
      description
        "Plane Down";
    }
    leaf plane-mcast-dn {
      type uint8;
      description
        "Plane Mcast Down";
    }
    leaf plane-admin-dn {
      type uint8;
      description
        "Plane Admin Down";
    }
    leaf sfe-asics-total {
      type uint8;
      description
        "SFE Asics Total";
    }
    leaf sfe-asics-up {
      type uint8;
      description
        "SFE Asics Up";
    }
    leaf sfe-asics-dn {
      type uint8;
      description
        "SFE Asics Down";
    }
    leaf fia-asics-total {
      type uint8;
      description
        "FIA Asics Total";
    }
    leaf fia-asics-up {
      type uint8;
      description
        "FIA Asics Up";
    }
    leaf fia-asics-dn {
      type uint8;
      description
        "FIA Asics Down";
    }
    list rack-mdata {
      description
        "Rack Mdata";
      uses HCMGR-FABRIC-HEALTH-METRIC-RACK-MDATA;
    }
    list sys-plane-mdata {
      description
        "Plane Mdata";
      uses HCMGR-FABRIC-HEALTH-METRIC-SYS-PLANE-MDATA;
    }
  }

  grouping HCMGR-FABRIC-HEALTH-METRIC-DATA {
    description
      "Fabric Health Metric Data structure";
    container mdata {
      description
        "Metric Message";
      uses HCMGR-FABRIC-HEALTH-METRIC-MSG;
    }
    leaf state {
      type string;
      description
        "Metric Current State";
    }
    leaf last-update {
      type string;
      description
        "Last Update Time";
    }
    leaf err-rack-count {
      type uint32;
      description
        "Error Rack count";
    }
    leaf err-sys-plane-count {
      type uint32;
      description
        "Error System Plane count";
    }
    leaf srv-state {
      type string;
      description
        "Service State";
    }
  }

  grouping HCMGR-REDUNDANCY-METRIC-MDATA {
    description
      "Redundancy Metric Mdata Structure";
    leaf active {
      type string;
      description
        "Active";
    }
    leaf standby {
      type string;
      description
        "Standby";
    }
    leaf ha-state {
      type string;
      description
        "HA State";
    }
    leaf nsr-state {
      type string;
      description
        "NSR State";
    }
  }

  grouping HCMGR-REDUNDANCY-METRIC-DATA {
    description
      "Redundancy Metric Data structure";
    container mdata {
      description
        "Metric Mdata";
      uses HCMGR-REDUNDANCY-METRIC-MDATA;
    }
    leaf state {
      type string;
      description
        "Metric Current State";
    }
    leaf last-update {
      type string;
      description
        "Last Update Time";
    }
    leaf srv-state {
      type string;
      description
        "Service State";
    }
  }

  grouping PCIMON-TREE-INFO {
    description
      "PCI Monitoring Info";
    leaf device-name {
      type string;
      description
        "Device name";
    }
    leaf status {
      type string;
      description
        "Device Status";
    }
  }

  grouping HCMGR-PCIMON-METRIC-DATA {
    description
      "PCI Monitoring Metric Data Structure";
    leaf srv-state {
      type Hcmgr-metric-service-state;
      description
        "Healthcheck metric service state";
    }
    leaf name {
      type string;
      description
        "Metric Name";
    }
    leaf health-state {
      type Hcmgr-metric-health-state;
      description
        "Metric Health State";
    }
    leaf health-msg {
      type string;
      description
        "Metric Health Message";
    }
    leaf last-update {
      type string;
      description
        "Last Update Time";
    }
    list pci-tree-status {
      key "device-name";
      description
        "PCI Monitoring Info";
      uses PCIMON-TREE-INFO;
    }
  }

  grouping HCMGR-FPD-METRIC-MDATA {
    description
      "FPD Metric Mdata Structure";
    leaf card-name {
      type string;
      description
        "Card Name";
    }
    leaf fpd-name {
      type string;
      description
        "FPD Name";
    }
    leaf hw-version {
      type string;
      description
        "Hardware Version";
    }
    leaf status {
      type string;
      description
        "Status";
    }
    leaf runversion {
      type string;
      description
        "Run Version";
    }
    leaf prgmd-version {
      type string;
      description
        "Programmed Version";
    }
    leaf node-name {
      type string;
      description
        "Node Name";
    }
  }

  grouping HCMGR-FPD-METRIC-DATA {
    description
      "FPD Metric Data structure";
    leaf state {
      type string;
      description
        "Metric Current State";
    }
    leaf last-update {
      type string;
      description
        "Last Update Time";
    }
    leaf active-node-count {
      type uint32;
      description
        "FPD count";
    }
    leaf srv-state {
      type string;
      description
        "Service State";
    }
    list mdata {
      description
        "Metric Mdata";
      uses HCMGR-FPD-METRIC-MDATA;
    }
  }
}
