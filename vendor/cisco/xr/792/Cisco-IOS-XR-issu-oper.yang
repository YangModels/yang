module Cisco-IOS-XR-issu-oper {
  namespace "http://cisco.com/ns/yang/Cisco-IOS-XR-issu-oper";
  prefix issu-oper;

  import Cisco-IOS-XR-types {
    prefix xr;
  }
  import cisco-semver {
    prefix semver;
  }
  include Cisco-IOS-XR-issu-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR issu package operational data.
     
     This module contains definitions
     for the following management objects:
       issu: ISSU operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container issu {
    config false;
    description
      "ISSU operational data";
    container operations {
      description
        "List of ISSU operations";
      list operation {
        key "oper-id";
        description
          "ISSU operation information";
        container orchestration-data {
          description
            "ISSU orchestration data";
          uses ISSU-ORCHESTRATION-DATA;
        }
        container nodes {
          description
            "List of nodes";
          list node {
            key "node";
            description
              "Node information";
            container clients {
              description
                "List of clients";
              list client {
                description
                  "Client information";
                leaf process-name {
                  type xr:Cisco-ios-xr-string;
                  description
                    "Process name";
                }
                leaf instance-id {
                  type xr:Cisco-ios-xr-string;
                  description
                    "Instance ID";
                }
                leaf jid {
                  type uint32;
                  description
                    "Job ID";
                }
                uses ISSU-CLIENT-DATA;
              }
            }
            container node-data {
              description
                "Node data";
              uses ISSU-NODE-DATA;
            }
            leaf node {
              type xr:Node-id;
              description
                "Node ID";
            }
          }
        }
        leaf oper-id {
          type uint32;
          description
            "The operation ID";
        }
      }
    }
  }
}
