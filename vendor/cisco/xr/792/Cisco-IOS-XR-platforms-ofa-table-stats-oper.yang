module Cisco-IOS-XR-platforms-ofa-table-stats-oper {
  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2022-09-12;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platforms-ofa-table-stats package operational data.
     
     This module contains definitions
     for the following management objects:
       ofa: OFA Data
     
     Copyright (c) 2013-2022 by Cisco Systems, Inc.
     All rights reserved.";

  revision 2022-09-12 {
    description
      "Removal of olist, mcolist, rpfif, ipmcfhop, ipmcmergedolist tidl objects IosSetYangSchemaRev Cisco-IOS-XR-platforms-ofa-table-stats-oper
       2021-07-07
         Added Quaratine DB counters to ofa table stats";
    semver:module-version "4.0.0";
  }
  revision 2020-06-19 {
    description
      "Bwalk Error Counters IosSetYangSchemaRev Cisco-IOS-XR-platforms-ofa-table-stats-oper";
    semver:module-version "3.0.0";
  }
  revision 2019-12-14 {
    description
      "Added the Yang Model for ofa sw resources";
    semver:module-version "1.1.0";
  }
  revision 2019-06-06 {
    description
      "Added the Yang Model for ofa sw resources";
    semver:module-version "1.0.0";
  }
  revision 2019-04-05 {
    description
      "Establish semantic version baseline.";
  }
  revision 2015-11-09 {
    description
      "IOS XR 6.0 revision.";
  }

  typedef Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-o-fast-ats" {
        value 13;
        description
          "testofastats";
      }
      enum "test-o-fast-ats1" {
        value 14;
        description
          "testofastats1";
      }
      enum "test-o-fast-ats2" {
        value 15;
        description
          "testofastats2";
      }
      enum "test-dpastats1" {
        value 16;
        description
          "testdpastats1";
      }
      enum "test-dpastats2" {
        value 17;
        description
          "testdpastats2";
      }
      enum "test-srvgrid" {
        value 18;
        description
          "testsrvgrid";
      }
      enum "test-ddel-q" {
        value 19;
        description
          "test ddel q";
      }
      enum "test-mco-list" {
        value 20;
        description
          "testmcolist";
      }
      enum "test-syncmco-list" {
        value 21;
        description
          "testsyncmcolist";
      }
      enum "test-syncmctblstats" {
        value 22;
        description
          "testsyncmctblstats";
      }
      enum "test-dddp" {
        value 23;
        description
          "testdddp";
      }
      enum "test-grid1" {
        value 24;
        description
          "testgrid1";
      }
      enum "test-ssm" {
        value 25;
        description
          "testssm";
      }
      enum "test-encap-mgr" {
        value 26;
        description
          "testencapmgr";
      }
      enum "test-mplsrte" {
        value 27;
        description
          "testmplsrte";
      }
      enum "sys" {
        value 28;
        description
          "sys";
      }
      enum "npu" {
        value 29;
        description
          "npu";
      }
      enum "npu-host-port" {
        value 30;
        description
          "npuhostport";
      }
      enum "npuhwid" {
        value 31;
        description
          "npuhwid";
      }
      enum "optics-port" {
        value 32;
        description
          "opticsport";
      }
      enum "gi-port" {
        value 33;
        description
          "giport";
      }
      enum "l1-port" {
        value 34;
        description
          "l1port";
      }
      enum "mac-port" {
        value 35;
        description
          "macport";
      }
      enum "l2-port" {
        value 36;
        description
          "l2port";
      }
      enum "eth-port" {
        value 37;
        description
          "ethport";
      }
      enum "eth-ports-tats" {
        value 38;
        description
          "ethportstats";
      }
      enum "l2intf" {
        value 39;
        description
          "l2intf";
      }
      enum "l2if" {
        value 40;
        description
          "l2if";
      }
      enum "mplspwe-port" {
        value 41;
        description
          "mplspweport";
      }
      enum "l2xc" {
        value 42;
        description
          "l2xc";
      }
      enum "l2vpnstats" {
        value 43;
        description
          "l2vpnstats";
      }
      enum "l1-ports-tats" {
        value 44;
        description
          "l1portstats";
      }
      enum "mac-ports-tats" {
        value 45;
        description
          "macportstats";
      }
      enum "l3intf" {
        value 46;
        description
          "l3intf";
      }
      enum "l3if" {
        value 47;
        description
          "l3if";
      }
      enum "l3intfrxstats" {
        value 48;
        description
          "l3intfrxstats";
      }
      enum "ip-route" {
        value 49;
        description
          "iproute";
      }
      enum "ip6-route" {
        value 50;
        description
          "ip6route";
      }
      enum "punt-policy-stats" {
        value 51;
        description
          "puntpolicystats";
      }
      enum "lpts-policy-stats" {
        value 52;
        description
          "lptspolicystats";
      }
      enum "tep" {
        value 53;
        description
          "tep";
      }
      enum "ip-punt-policy" {
        value 54;
        description
          "ippuntpolicy";
      }
      enum "ip6-punt-policy" {
        value 55;
        description
          "ip6puntpolicy";
      }
      enum "iplpts-policy" {
        value 56;
        description
          "iplptspolicy";
      }
      enum "ip6lpts-policy" {
        value 57;
        description
          "ip6lptspolicy";
      }
      enum "isis-punt-policy" {
        value 58;
        description
          "isispuntpolicy";
      }
      enum "isislpts-policy" {
        value 59;
        description
          "isislptspolicy";
      }
      enum "nh-group" {
        value 60;
        description
          "nhgroup";
      }
      enum "ipnh-group" {
        value 61;
        description
          "ipnhgroup";
      }
      enum "ip6nh-group" {
        value 62;
        description
          "ip6nhgroup";
      }
      enum "ipnh" {
        value 63;
        description
          "ipnh";
      }
      enum "ip6nh" {
        value 64;
        description
          "ip6nh";
      }
      enum "macllnh" {
        value 65;
        description
          "macllnh";
      }
      enum "ipvrf" {
        value 66;
        description
          "ipvrf";
      }
      enum "vrfid" {
        value 67;
        description
          "vrfid";
      }
      enum "mplsnh" {
        value 68;
        description
          "mplsnh";
      }
      enum "lspnh" {
        value 69;
        description
          "lspnh";
      }
      enum "encap-mgr" {
        value 70;
        description
          "encapmgr";
      }
      enum "mpls-label" {
        value 71;
        description
          "mplslabel";
      }
      enum "punt" {
        value 72;
        description
          "punt";
      }
      enum "punt-police-r" {
        value 73;
        description
          "puntpolicer";
      }
      enum "lpts-police-r" {
        value 74;
        description
          "lptspolicer";
      }
      enum "punt-lpts-police-r" {
        value 75;
        description
          "puntlptspolicer";
      }
      enum "punt-stats" {
        value 76;
        description
          "puntstats";
      }
      enum "tm-port" {
        value 77;
        description
          "tmport";
      }
      enum "span-session" {
        value 78;
        description
          "spansession";
      }
      enum "police-rstats" {
        value 79;
        description
          "policerstats";
      }
      enum "tm-ports-tats" {
        value 80;
        description
          "tmportstats";
      }
      enum "voq-grp" {
        value 81;
        description
          "voqgrp";
      }
      enum "l3intftxstats" {
        value 82;
        description
          "l3intftxstats";
      }
      enum "mplstetxstats" {
        value 83;
        description
          "mplstetxstats";
      }
      enum "mplslblstats" {
        value 84;
        description
          "mplslblstats";
      }
      enum "police-r" {
        value 85;
        description
          "policer";
      }
      enum "l2intfrxstats" {
        value 86;
        description
          "l2intfrxstats";
      }
      enum "l2intftxstats" {
        value 87;
        description
          "l2intftxstats";
      }
      enum "pbr-tt-ipv4" {
        value 88;
        description
          "pbr tt ipv4";
      }
      enum "pbr-tt-ipv6" {
        value 89;
        description
          "pbr tt ipv6";
      }
      enum "bfdhwoff" {
        value 90;
        description
          "bfdhwoff";
      }
      enum "bfdoff" {
        value 91;
        description
          "bfdoff";
      }
      enum "bfdoffstats" {
        value 92;
        description
          "bfdoffstats";
      }
      enum "global" {
        value 93;
        description
          "global";
      }
      enum "lag-port" {
        value 94;
        description
          "lagport";
      }
      enum "agg-port" {
        value 95;
        description
          "aggport";
      }
      enum "agg-member" {
        value 96;
        description
          "aggmember";
      }
      enum "qos-profile" {
        value 97;
        description
          "qosprofile";
      }
      enum "acl-profile" {
        value 98;
        description
          "acl profile";
      }
      enum "tmrate-profile" {
        value 99;
        description
          "tmrateprofile";
      }
      enum "ipacl" {
        value 100;
        description
          "ipacl";
      }
      enum "ip6acl" {
        value 101;
        description
          "ip6acl";
      }
      enum "sched-tree" {
        value 102;
        description
          "schedtree";
      }
      enum "tmcos" {
        value 103;
        description
          "tmcos";
      }
      enum "statsagg" {
        value 104;
        description
          "statsagg";
      }
      enum "nhprotect" {
        value 105;
        description
          "nhprotect";
      }
      enum "sampler" {
        value 106;
        description
          "sampler";
      }
      enum "l2qos" {
        value 107;
        description
          "l2qos";
      }
      enum "peer-qos" {
        value 108;
        description
          "peerqos";
      }
      enum "ipqos" {
        value 109;
        description
          "ipqos";
      }
      enum "ip6qos" {
        value 110;
        description
          "ip6qos";
      }
      enum "mplsqos" {
        value 111;
        description
          "mplsqos";
      }
      enum "qos-group" {
        value 112;
        description
          "qosgroup";
      }
      enum "qosid" {
        value 113;
        description
          "qosid";
      }
      enum "extlif" {
        value 114;
        description
          "extlif";
      }
      enum "elif" {
        value 115;
        description
          "elif";
      }
      enum "ingaclstats" {
        value 116;
        description
          "ingaclstats";
      }
      enum "egraclstats" {
        value 117;
        description
          "egraclstats";
      }
      enum "edpl" {
        value 118;
        description
          "edpl";
      }
      enum "l2protect" {
        value 119;
        description
          "l2protect";
      }
      enum "sat" {
        value 120;
        description
          "sat";
      }
      enum "satstats" {
        value 121;
        description
          "satstats";
      }
      enum "cfmoam-profile-def" {
        value 122;
        description
          "cfmoamprofiledef";
      }
      enum "cfmmaid" {
        value 123;
        description
          "cfmmaid";
      }
      enum "cfmdefmps" {
        value 124;
        description
          "cfmdefmps";
      }
      enum "cfmofflmep" {
        value 125;
        description
          "cfmofflmep";
      }
      enum "cfmoffrmep" {
        value 126;
        description
          "cfmoffrmep";
      }
      enum "cfmnonoff" {
        value 127;
        description
          "cfmnonoff";
      }
      enum "cfmhwoffrxstats" {
        value 128;
        description
          "cfmhwoffrxstats";
      }
      enum "cfmnonoff-load" {
        value 129;
        description
          "cfmnonoffload";
      }
      enum "cfm-default-s" {
        value 130;
        description
          "cfmdefaults";
      }
      enum "cfmmntassocid" {
        value 131;
        description
          "cfmmntassocid";
      }
      enum "ipmc-route" {
        value 132;
        description
          "ipmcroute";
      }
      enum "l2ipmc-route" {
        value 133;
        description
          "l2ipmcroute";
      }
      enum "ipmco-list" {
        value 134;
        description
          "ipmcolist";
      }
      enum "l2mco-list" {
        value 135;
        description
          "l2mcolist";
      }
      enum "meshmc" {
        value 136;
        description
          "meshmc";
      }
      enum "l2-bridge" {
        value 137;
        description
          "l2bridge";
      }
      enum "l2-bridge-port" {
        value 138;
        description
          "l2bridgeport";
      }
      enum "l2-bridge-mac" {
        value 139;
        description
          "l2bridgemac";
      }
      enum "l2brmac" {
        value 140;
        description
          "l2brmac";
      }
      enum "ip-tunnel-decap" {
        value 141;
        description
          "iptunneldecap";
      }
      enum "l2vlan-range" {
        value 142;
        description
          "l2vlanrange";
      }
      enum "ip-tunnel-encap" {
        value 143;
        description
          "iptunnelencap";
      }
      enum "iptnl-encap" {
        value 144;
        description
          "iptnlencap";
      }
      enum "iptnl-encap-vni" {
        value 145;
        description
          "iptnlencapvni";
      }
      enum "iptnldecap" {
        value 146;
        description
          "iptnldecap";
      }
      enum "iptnldecapvni" {
        value 147;
        description
          "iptnldecapvni";
      }
      enum "iptnlnh" {
        value 148;
        description
          "iptnlnh";
      }
      enum "rawget" {
        value 149;
        description
          "rawget";
      }
      enum "ip6mc-route" {
        value 150;
        description
          "ip6mcroute";
      }
      enum "ip6mc-comp-grp" {
        value 151;
        description
          "ip6mc comp grp";
      }
      enum "l2evpnact-remote-peer-id" {
        value 152;
        description
          "l2evpnactremotepeerid";
      }
      enum "l2evpnact-local-shl" {
        value 153;
        description
          "l2evpnactlocalshl";
      }
      enum "l2evpnact-remote-shl" {
        value 154;
        description
          "l2evpnactremoteshl";
      }
      enum "evpn-iml-range" {
        value 155;
        description
          "evpn imlrange";
      }
      enum "l2-bridge-o-list" {
        value 156;
        description
          "l2bridgeolist";
      }
      enum "l2acl" {
        value 157;
        description
          "l2acl";
      }
      enum "l2evpn-nh" {
        value 158;
        description
          "l2evpn nh";
      }
      enum "l2-bridge-port-sc" {
        value 159;
        description
          "l2bridgeport sc";
      }
      enum "l3intfmctxstats" {
        value 160;
        description
          "l3intfmctxstats";
      }
      enum "tidl-sample" {
        value 161;
        description
          "tidl sample";
      }
      enum "tidl-ref-sample" {
        value 162;
        description
          "tidl ref sample";
      }
      enum "ipacl-prefix" {
        value 163;
        description
          "ipaclprefix";
      }
      enum "ip6acl-prefix" {
        value 164;
        description
          "ip6aclprefix";
      }
      enum "ipacl-port" {
        value 165;
        description
          "ipaclport";
      }
      enum "scaleacl" {
        value 166;
        description
          "scaleacl";
      }
      enum "bundle-swoff" {
        value 167;
        description
          "bundle swoff";
      }
      enum "mcidswoff" {
        value 168;
        description
          "mcidswoff";
      }
      enum "dest-map" {
        value 169;
        description
          "destmap";
      }
      enum "l2evpnact-local-shlstats" {
        value 170;
        description
          "l2evpnactlocalshlstats";
      }
      enum "test-hidden" {
        value 171;
        description
          "testhidden";
      }
      enum "test-local" {
        value 172;
        description
          "testlocal";
      }
      enum "test-repeated" {
        value 173;
        description
          "testrepeated";
      }
      enum "limd" {
        value 174;
        description
          "limd";
      }
      enum "litap" {
        value 175;
        description
          "litap";
      }
      enum "l3ifstats" {
        value 176;
        description
          "l3ifstats";
      }
      enum "mplsstats" {
        value 177;
        description
          "mplsstats";
      }
      enum "sr-test-ats" {
        value 178;
        description
          "srtestats";
      }
      enum "srteifstats" {
        value 179;
        description
          "srteifstats";
      }
      enum "exception-nh" {
        value 180;
        description
          "exceptionnh";
      }
      enum "srv6-global" {
        value 181;
        description
          "srv6 global";
      }
      enum "srv6sid" {
        value 182;
        description
          "srv6sid";
      }
      enum "srv6nhstats" {
        value 183;
        description
          "srv6nhstats";
      }
      enum "srv6nh" {
        value 184;
        description
          "srv6nh";
      }
      enum "sr6sid" {
        value 185;
        description
          "sr6sid";
      }
      enum "sr6nh" {
        value 186;
        description
          "sr6nh";
      }
      enum "sr6-global" {
        value 187;
        description
          "sr6 global";
      }
      enum "redirect-vrf" {
        value 188;
        description
          "redirectvrf";
      }
      enum "test-xtf" {
        value 189;
        description
          "test xtf";
      }
      enum "ippbr" {
        value 190;
        description
          "ippbr";
      }
      enum "ippbrstats" {
        value 191;
        description
          "ippbrstats";
      }
      enum "mpls-mdt-bud" {
        value 192;
        description
          "mplsmdtbud";
      }
      enum "mpls-label-rxstats" {
        value 193;
        description
          "mplslabelrxstats";
      }
      enum "l2mac-static" {
        value 194;
        description
          "l2macstatic";
      }
      enum "dot1x" {
        value 195;
        description
          "dot1x";
      }
      enum "iprte" {
        value 196;
        description
          "iprte";
      }
      enum "ip6rte" {
        value 197;
        description
          "ip6rte";
      }
      enum "llnh" {
        value 198;
        description
          "llnh";
      }
      enum "urpfintf" {
        value 199;
        description
          "urpfintf";
      }
      enum "ipmcrxstats" {
        value 200;
        description
          "ipmcrxstats";
      }
      enum "mplsrte" {
        value 201;
        description
          "mplsrte";
      }
      enum "protectnh" {
        value 202;
        description
          "protectnh";
      }
      enum "ipllnh" {
        value 203;
        description
          "ipllnh";
      }
      enum "ip6llnh" {
        value 204;
        description
          "ip6llnh";
      }
      enum "macnh" {
        value 205;
        description
          "macnh";
      }
      enum "qos-match-stats" {
        value 206;
        description
          "qosmatchstats";
      }
      enum "ofal2xc" {
        value 207;
        description
          "ofal2xc";
      }
      enum "ofamplspwe-port" {
        value 208;
        description
          "ofamplspweport";
      }
      enum "pwenh" {
        value 209;
        description
          "pwenh";
      }
      enum "pwenh-group" {
        value 210;
        description
          "pwenhgroup";
      }
      enum "ipmcrte" {
        value 211;
        description
          "ipmcrte";
      }
      enum "ip6mcrte" {
        value 212;
        description
          "ip6mcrte";
      }
      enum "ipmcr-test-ats" {
        value 213;
        description
          "ipmcrtestats";
      }
      enum "ip6mcr-test-ats" {
        value 214;
        description
          "ip6mcrtestats";
      }
      enum "transport-nh" {
        value 215;
        description
          "transportnh";
      }
      enum "port-range" {
        value 216;
        description
          "portrange";
      }
      enum "mcid" {
        value 217;
        description
          "mcid";
      }
      enum "mc-gid" {
        value 218;
        description
          "mc gid";
      }
      enum "mcgidole" {
        value 219;
        description
          "mcgidole";
      }
      enum "test-da" {
        value 220;
        description
          "testda";
      }
      enum "test-ca" {
        value 221;
        description
          "testca";
      }
      enum "test-ba" {
        value 222;
        description
          "testba";
      }
      enum "test-aa" {
        value 223;
        description
          "testaa";
      }
      enum "test-async-aa" {
        value 224;
        description
          "testasyncaa";
      }
      enum "test-reliable-notif" {
        value 225;
        description
          "testreliablenotif";
      }
      enum "test-de" {
        value 226;
        description
          "testde";
      }
      enum "test-ce" {
        value 227;
        description
          "testce";
      }
      enum "test-be" {
        value 228;
        description
          "testbe";
      }
      enum "test-db" {
        value 229;
        description
          "testdb";
      }
      enum "test-cb" {
        value 230;
        description
          "testcb";
      }
      enum "test-bb" {
        value 231;
        description
          "testbb";
      }
      enum "test-df" {
        value 232;
        description
          "testdf";
      }
      enum "test-cf" {
        value 233;
        description
          "testcf";
      }
      enum "test-bf" {
        value 234;
        description
          "testbf";
      }
      enum "test-af" {
        value 235;
        description
          "testaf";
      }
      enum "test-cz" {
        value 236;
        description
          "testcz";
      }
      enum "test-ax" {
        value 237;
        description
          "testax";
      }
      enum "test-ay" {
        value 238;
        description
          "testay";
      }
      enum "test-ef" {
        value 239;
        description
          "testef";
      }
      enum "test-ff" {
        value 240;
        description
          "testff";
      }
      enum "test-npurc" {
        value 241;
        description
          "testnpurc";
      }
      enum "test-gf" {
        value 242;
        description
          "testgf";
      }
      enum "test-eastwestscheduling" {
        value 243;
        description
          "testeastwestscheduling";
      }
      enum "test-transnh" {
        value 244;
        description
          "testtransnh";
      }
      enum "test-eth-port" {
        value 245;
        description
          "testethport";
      }
      enum "test-eastwest" {
        value 246;
        description
          "testeastwest";
      }
      enum "test-ifstats" {
        value 247;
        description
          "testifstats";
      }
      enum "test-async-oor" {
        value 248;
        description
          "testasyncoor";
      }
      enum "test-async-db" {
        value 249;
        description
          "testasyncdb";
      }
      enum "test-syncmcas-too-r" {
        value 250;
        description
          "testsyncmcastoor";
      }
      enum "test-syncdeviceoor" {
        value 251;
        description
          "testsyncdeviceoor";
      }
      enum "test-az" {
        value 252;
        description
          "testaz";
      }
      enum "test-by" {
        value 253;
        description
          "testby";
      }
      enum "police-r-group" {
        value 254;
        description
          "policergroup";
      }
      enum "meter-profile" {
        value 255;
        description
          "meterprofile";
      }
      enum "acl-mirror" {
        value 256;
        description
          "acl mirror";
      }
      enum "meter-action-profile" {
        value 257;
        description
          "meteractionprofile";
      }
      enum "voqrm" {
        value 258;
        description
          "voqrm";
      }
      enum "port-wfq-profile" {
        value 259;
        description
          "portwfqprofile";
      }
      enum "brmac" {
        value 260;
        description
          "brmac";
      }
      enum "br-static-mac" {
        value 261;
        description
          "brstaticmac";
      }
      enum "xconnect" {
        value 262;
        description
          "xconnect";
      }
      enum "bridge" {
        value 263;
        description
          "bridge";
      }
      enum "pwe-port" {
        value 264;
        description
          "pweport";
      }
      enum "lsmprotect" {
        value 265;
        description
          "lsmprotect";
      }
      enum "monitor-session" {
        value 266;
        description
          "monitorsession";
      }
      enum "monitor-session-stats" {
        value 267;
        description
          "monitorsessionstats";
      }
      enum "mplsmcast" {
        value 268;
        description
          "mplsmcast";
      }
      enum "l2ifstats" {
        value 269;
        description
          "l2ifstats";
      }
      enum "member-list" {
        value 270;
        description
          "memberlist";
      }
      enum "test-oor" {
        value 271;
        description
          "testoor";
      }
      enum "hwre-source-s-oor" {
        value 272;
        description
          "hwresources oor";
      }
      enum "qospfcstats" {
        value 273;
        description
          "qospfcstats";
      }
      enum "pfctc" {
        value 274;
        description
          "pfctc";
      }
      enum "pfc-watchdog" {
        value 275;
        description
          "pfc watchdog";
      }
      enum "qos-shared" {
        value 276;
        description
          "qosshared";
      }
      enum "ecntxstats" {
        value 277;
        description
          "ecntxstats";
      }
      enum "tm-remote-credit" {
        value 278;
        description
          "tmremotecredit";
      }
      enum "ipmcole" {
        value 279;
        description
          "ipmcole";
      }
      enum "ip6mcole" {
        value 280;
        description
          "ip6mcole";
      }
      enum "pbr" {
        value 281;
        description
          "pbr";
      }
      enum "pbrstats" {
        value 282;
        description
          "pbrstats";
      }
      enum "punt-stormcontrol" {
        value 283;
        description
          "puntstormcontrol";
      }
      enum "ip6mcrxstats" {
        value 284;
        description
          "ip6mcrxstats";
      }
      enum "ipmctxintf" {
        value 285;
        description
          "ipmctxintf";
      }
      enum "ipmc-mdt-encap" {
        value 286;
        description
          "ipmcmdtencap";
      }
      enum "ipmc-mdt-decap" {
        value 287;
        description
          "ipmcmdtdecap";
      }
      enum "op2tap" {
        value 288;
        description
          "op2tap";
      }
      enum "mplsole" {
        value 289;
        description
          "mplsole";
      }
      enum "syncrpc" {
        value 290;
        description
          "syncrpc";
      }
      enum "tnlstats" {
        value 291;
        description
          "tnlstats";
      }
      enum "l2dhcp" {
        value 292;
        description
          "l2dhcp";
      }
      enum "pbrsbf" {
        value 293;
        description
          "pbrsbf";
      }
      enum "statsrpc" {
        value 294;
        description
          "statsrpc";
      }
      enum "oglpts" {
        value 295;
        description
          "oglpts";
      }
      enum "oglpts-prefix" {
        value 296;
        description
          "oglptsprefix";
      }
      enum "og6lpts-prefix" {
        value 297;
        description
          "og6lptsprefix";
      }
      enum "stormcontrol" {
        value 298;
        description
          "stormcontrol";
      }
      enum "acl-police-r" {
        value 299;
        description
          "aclpolicer";
      }
      enum "acl-police-rstats" {
        value 300;
        description
          "aclpolicerstats";
      }
      enum "aclkey-profile" {
        value 301;
        description
          "aclkeyprofile";
      }
      enum "acl-action-profile" {
        value 302;
        description
          "aclactionprofile";
      }
      enum "dummytable" {
        value 303;
        description
          "dummytable";
      }
      enum "ip-sub" {
        value 304;
        description
          "ipsub";
      }
      enum "test-silverfoxsync" {
        value 305;
        description
          "testsilverfoxsync";
      }
      enum "test-statsreplication" {
        value 306;
        description
          "teststatsreplication";
      }
      enum "dot1x-mac" {
        value 307;
        description
          "dot1x mac";
      }
      enum "mpa" {
        value 308;
        description
          "mpa";
      }
      enum "featacl-group" {
        value 309;
        description
          "feataclgroup";
      }
      enum "l2ipmcrte" {
        value 310;
        description
          "l2ipmcrte";
      }
      enum "l2ip6mcrte" {
        value 311;
        description
          "l2ip6mcrte";
      }
      enum "l2ipmcole" {
        value 312;
        description
          "l2ipmcole";
      }
      enum "l2ip6mcole" {
        value 313;
        description
          "l2ip6mcole";
      }
      enum "pmhwoff" {
        value 314;
        description
          "pmhwoff";
      }
      enum "eoam" {
        value 315;
        description
          "eoam";
      }
      enum "evi" {
        value 316;
        description
          "evi";
      }
      enum "evi-sh-tunnel" {
        value 317;
        description
          "evi sh tunnel";
      }
      enum "l2vni" {
        value 318;
        description
          "l2vni";
      }
      enum "l2vni-mbr" {
        value 319;
        description
          "l2vni mbr";
      }
      enum "l2ipul" {
        value 320;
        description
          "l2ipul";
      }
      enum "evpn-ole" {
        value 321;
        description
          "evpn ole";
      }
      enum "evpn-shg" {
        value 322;
        description
          "evpn shg";
      }
      enum "l2vpn-mh-n-hop" {
        value 323;
        description
          "l2vpn mh nhop";
      }
      enum "msti" {
        value 324;
        description
          "msti";
      }
      enum "gil" {
        value 325;
        description
          "gil";
      }
      enum "pwhe" {
        value 326;
        description
          "pwhe";
      }
      enum "pwhe-port" {
        value 327;
        description
          "pwhe port";
      }
      enum "l2ip6mc-route" {
        value 328;
        description
          "l2ip6mcroute";
      }
      enum "pbr-vrf-redirect" {
        value 329;
        description
          "pbr vrfredirect";
      }
      enum "srv6-pt-intf" {
        value 330;
        description
          "srv6 pt intf";
      }
      enum "test-sdkgetopt" {
        value 331;
        description
          "testsdkgetopt";
      }
      enum "gi-list" {
        value 332;
        description
          "gilist";
      }
      enum "gi-member" {
        value 333;
        description
          "gimember";
      }
      enum "test-async-barrier" {
        value 334;
        description
          "testasyncbarrier";
      }
      enum "test-async-barrier-legacy" {
        value 335;
        description
          "testasyncbarrierlegacy";
      }
      enum "erpl2protect" {
        value 336;
        description
          "erpl2protect";
      }
      enum "test-silverfoxit" {
        value 337;
        description
          "testsilverfoxit";
      }
      enum "iptnldecapsaf" {
        value 338;
        description
          "iptnldecapsaf";
      }
      enum "l3intfrx-bgp-pastats" {
        value 339;
        description
          "l3intfrxbgppastats";
      }
      enum "ack-mark-er" {
        value 340;
        description
          "ack marker";
      }
      enum "fhrp" {
        value 341;
        description
          "fhrp";
      }
      enum "vxlanstats" {
        value 342;
        description
          "vxlanstats";
      }
    }
    description
      "Ofa table";
  }

  container ofa {
    config false;
    description
      "OFA Data";
    container stats {
      description
        "OFA Stats Data";
      container nodes {
        description
          "OFA data for available nodes";
        list node {
          key "node-name";
          description
            "OFA operational data for a particular node";
          container table-datas {
            description
              "OFA Resources table";
            list table-data {
              key "resource";
              description
                "OFA Resources table";
              leaf resource {
                type Ofa-table;
                description
                  "Resource type";
              }
              uses OFA-NPD-SYSDB-TABLE-RESOURCE;
            }
          }
          leaf node-name {
            type xr:Node-id;
            description
              "Node ID";
          }
        }
      }
    }
  }
}
