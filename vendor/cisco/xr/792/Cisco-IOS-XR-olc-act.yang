module Cisco-IOS-XR-olc-act {
  namespace "http://cisco.com/ns/yang/Cisco-IOS-XR-olc-act";
  prefix olc-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR olc-act package configuration.
     
     Copyright (c) 2013-2022 by Cisco Systems, Inc.
     All rights reserved.";

  revision 2022-10-10 {
    description
      "Added BFR Initialize command";
  }
  revision 2022-06-22 {
    description
      "Added Gain Estimator commands";
  }
  revision 2021-11-19 {
    description
      "First revision, establish semantic version baseline";
    semver:module-version "1.0.0";
  }

  rpc start-raman-tuning {
    description
      "Start Raman Tuning";
    input {
      leaf controller {
        type string;
        description
          "Controller name in Ots  R/S/I/P format";
      }
    }
    csc:xr-task "root-lr";
    csc:cli-command "olc start-raman-tuning controller <controller>";
  }
  rpc start-gain-estimation {
    description
      "Start gain estimator";
    input {
      leaf controller {
        type string;
        description
          "Controller name in Ots R/S/I/P format";
      }
    }
    csc:xr-task "root-lr";
    csc:cli-command "olc start-gain-estimation controller <controller>";
  }
  rpc bfr-initialize {
    description
      "Initialize Band Failure and Recovery State Machine";
    input {
      leaf controller {
        type string;
        description
          "Controller name in Ots R/S/I/P format";
      }
    }
    csc:xr-task "root-lr";
    csc:cli-command "olc bfr-initialize controller <controller>";
  }
}
