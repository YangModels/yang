module Cisco-IOS-XR-um-ethernet-sat-cfg {
  namespace "http://cisco.com/ns/yang/Cisco-IOS-XR-um-ethernet-sat-cfg";
  prefix um-ethernet-sat-cfg;

  import Cisco-IOS-XR-types {
    prefix xr;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-sat package configuration.
     
     This YANG module augments the
     modules with configuration data.
     
     Copyright (c) 2022 by Cisco Systems, Inc.
     All rights reserved.";

  revision 2022-07-11 {
    description
      "Added missing description statement to nodes";
    semver:module-version "1.1.0";
  }
  revision 2020-12-10 {
    description
      "Initial release";
    semver:module-version "1.0.0";
  }

  grouping IF-ETHER-BODY {
    description
      "Grouping for if-ether";
    container ethernet {
      description
        "Ethernet per-interface configuration commands";
      container service-activation-test {
        description
          "Service activation test config";
        container permit {
          description
            "Config to allow Service Activation Tests on the interface";
          container internal {
            must "not(../external or ../all)";
            presence "Indicates a internal node is configured.";
            description
              "Config to only allow internal Service Activation Tests";
          }
          container external {
            must "not(../internal or ../all)";
            presence "Indicates a external node is configured.";
            description
              "Config to only allow external Service Activation Tests";
          }
          container all {
            must "not(../internal or ../external)";
            presence "Indicates a all node is configured.";
            description
              "Config to allow Service Activation Tests in either direction";
          }
        }
      }
    }
  }

  augment "/a1:interfaces/a1:interface" {
    description
      "This augment extends active nodes configuration";
    uses IF-ETHER-BODY;
  }
  augment "/a1:interfaces/a1:interface-preconfigure" {
    description
      "This augment extends preconfigured nodes
       configuration";
    uses IF-ETHER-BODY;
  }
  container ethernet {
    description
      "Ethernet configuration commands";
    container service-activation-test {
      description
        "Service activation test config";
      container profiles {
        description
          "Profile name to set config for";
        list profile {
          key "profile-name";
          description
            "Profile name to set config for";
          leaf profile-name {
            type xr:Cisco-ios-xr-string {
              length "1..63" {
                description
                  "The name of the profile";
              }
            }
            description
              "Profile name to set config for";
          }
          container mode {
            description
              "Set the mode for tests";
            container two-way {
              presence "Indicates a two-way node is configured.";
              description
                "Two-way mode";
            }
          }
          container duration {
            description
              "Set the duration config for tests";
            leaf duration-time {
              type uint32 {
                range "1..1440" {
                  description
                    "Duration to run the test for";
                }
              }
              must "../minutes or ../hours";
              description
                "Set the duration config for tests";
            }
            container minutes {
              must "not(../hours) and ../duration-time";
              presence "Indicates a minutes node is configured.";
              description
                "Duration given in minutes";
            }
            container hours {
              when "../duration-time <= 24";
              must "not(../minutes) and ../duration-time";
              presence "Indicates a hours node is configured.";
              description
                "Duration given in hours";
            }
            container per-step {
              must "../duration-time and (../minutes or ../hours)";
              presence "Indicates a per-step node is configured.";
              description
                "Set duration to be duration of each step";
            }
          }
          container information-rate {
            description
              "Set the information rate to use in tests";
            leaf fixed-information-rate {
              type uint32 {
                range "1..4294967295" {
                  description
                    "The fixed information rate to use";
                }
              }
              must "not(../min) and (../kbps or ../mbps or ../gbps)";
              description
                "The fixed information rate to use";
            }
            leaf min {
              type uint32 {
                range "1..4294967295" {
                  description
                    "Minimum information rate";
                }
              }
              must "../step and (../kbps or ../mbps or ../gbps)";
              description
                "The minimum information rate to use";
            }
            leaf step {
              type uint32 {
                range "1..4294967295" {
                  description
                    "Information rate step";
                }
              }
              must "../max";
              description
                "The step in information rate to use";
            }
            leaf max {
              type uint32 {
                range "1..4294967295" {
                  description
                    "Maximum information rate";
                }
              }
              must "../min";
              description
                "The maximum information rate to use";
            }
            container kbps {
              must "not(../mbps or ../gbps)";
              presence "Indicates a kbps node is configured.";
              description
                "Information rate given in kilobits per second";
            }
            container mbps {
              must "not(../kbps or ../gbps)";
              presence "Indicates a mbps node is configured.";
              description
                "Information rate given in megabits per second";
            }
            container gbps {
              must "not(../kbps or ../mbps)";
              presence "Indicates a gbps node is configured.";
              description
                "Information rate given in gigabits per second";
            }
          }
          container color-aware {
            description
              "Set the color-aware config";
            leaf cir {
              type uint32 {
                range "1..4294967295" {
                  description
                    "CIR value";
                }
              }
              must "../kbps or ../mbps or ../gbps";
              description
                "Set the value of the committed information rate (CIR)";
            }
            container kbps {
              must "not(../mbps or ../gbps)";
              presence "Indicates a kbps node is configured.";
              description
                "Information rate given in kilobits per second";
            }
            container mbps {
              must "not(../kbps or ../gbps)";
              presence "Indicates a mbps node is configured.";
              description
                "Information rate given in megabits per second";
            }
            container gbps {
              must "not(../kbps or ../mbps)";
              presence "Indicates a gbps node is configured.";
              description
                "Information rate given in gigabits per second";
            }
            container eir-color {
              description
                "Set config for excess information rate (EIR) packets";
              container set-dei {
                must "../../cir";
                presence "Indicates a set-dei node is configured.";
                description
                  "Set the drop-eligibility-indicator (DEI) bit for EIR packets";
              }
              leaf cos {
                type uint32 {
                  range "0..7" {
                    description
                      "CoS value for EIR packets";
                  }
                }
                must "../../cir";
                description
                  "Set the CoS value for EIR packets";
              }
            }
          }
          container packet-size {
            description
              "Set the packet size and pattern to use for tests";
            container emix {
              must "not(../packet-size-in-bytes)";
              presence "Indicates a emix node is configured.";
              description
                "Use packet size and contents configured in the EMIX profile";
              leaf sequence {
                type xr:Cisco-ios-xr-string {
                  length "1..1024" {
                    description
                      "Pattern defining a sequence of packet sizes as specified by Y.1564";
                  }
                }
                description
                  "Specify an EMIX sequence. Otherwise the default of abceg is used";
              }
              leaf u-value {
                type uint32 {
                  range "64..10236" {
                    description
                      "Packet size in bytes";
                  }
                }
                must "../sequence";
                description
                  "Size to use for 'u' in the pattern string";
              }
            }
            leaf packet-size-in-bytes {
              type uint32 {
                range "64..10236" {
                  description
                    "Packet size in bytes";
                }
              }
              must "not(../emix)";
              description
                "Packet size in bytes";
            }
            container contents {
              description
                "Choose how the packets should be filled";
              container pseudo-random {
                must "not(../hex)";
                presence "Indicates a pseudo-random node is configured.";
                description
                  "Pseudo-random pattern";
              }
              leaf hex {
                type uint32 {
                  range "0..255" {
                    description
                      "Hex pattern";
                  }
                }
                must "not(../pseudo-random)";
                description
                  "Specify hex pattern";
              }
            }
          }
          leaf outer-cos {
            type uint32 {
              range "0..7" {
                description
                  "Outer CoS value";
              }
            }
            description
              "Set the CoS to use in test packets";
          }
          leaf inner-cos {
            type uint32 {
              range "0..7" {
                description
                  "Inner CoS value";
              }
            }
            must "../outer-cos";
            description
              "";
          }
          leaf description {
            type string {
              length "1..63" {
                description
                  "Description";
              }
            }
            description
              "Description or identifier for the test";
          }
        }
      }
    }
  }
}
