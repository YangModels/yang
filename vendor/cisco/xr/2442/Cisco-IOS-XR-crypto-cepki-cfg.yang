module Cisco-IOS-XR-crypto-cepki-cfg {
  namespace "http://cisco.com/ns/yang/Cisco-IOS-XR-crypto-cepki-cfg";
  prefix crypto-cepki-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-cepki package configuration.
     
     This module contains definitions
     for the following management objects:
       crypto-cepki: Crypto CertificateAuthority
     
     Copyright (c) 2013-2024 by Cisco Systems, Inc.
     All rights reserved.";

  revision 2024-07-23 {
    description
      "Added support to configure Extended Key Usage field to match for certificate under trustpoint.
       2024-07-22
         Added new config CLI to support EST protocol.
       2024-01-28
         Added support to configure Subject Alternative Name under trustpoint.
       2023-03-29
         Changed top level container path.
       2022-11-22
         Added configuration option to skip challenge password and add message digest under trsutpoint
       2022-09-07
         Revision to bring renewal-message-type under trustpoint config
       2022-06-15
         Added tuple support for RSA and DSA keys generated in configuration mode
       2022-03-20
         OpenSSH certificate support.
       2022-03-15
         Change string to bounded string for RSA key label.
       2022-03-10
         Added support to config curl timeout
       2022-01-21
         Revision to bring auto-enroll under trustpoint config";
    semver:module-version "2.0.0";
  }
  revision 2021-05-13 {
    description
      "Configuration to discard certificates having rsa key size less than or equal to 1024";
    semver:module-version "1.3.0";
  }
  revision 2021-03-24 {
    description
      "Allowed configuration of crypto keys enhancement in IOS XR
       2020-12-10
           Fips mode enabled for aarch64 platform
       2020-11-24
           Correct the range for ca lifetime for system-trustpoint.
       2020-09-02
           Yang support ed25519 key added";
    semver:module-version "1.2.0";
  }
  revision 2020-07-12 {
    description
      "Associated task-name added
       2020-05-25
         Yang support missing for message digest
       2020-05-10
         Yang support for all cepki features
       2020-02-05
         Yang support to fetch CRL via Source Interface.";
    semver:module-version "1.1.0";
  }
  revision 2019-04-05 {
    description
      "Establish semantic version baseline.";
    semver:module-version "1.0.0";
  }
  revision 2015-11-09 {
    description
      "IOS XR 6.0 revision.";
  }

  typedef Type-key {
    type enumeration {
      enum "rsa" {
        value 1;
        description
          "Rsa key";
      }
      enum "ecdsanistp256" {
        value 2;
        description
          "ecdsa-nistp256 key";
      }
      enum "ecdsanistp384" {
        value 4;
        description
          "ecdsa-nistp384 key";
      }
      enum "ecdsanistp521" {
        value 8;
        description
          "ecdsa-nistp521 key";
      }
      enum "dsa" {
        value 16;
        description
          "Dsa key";
      }
      enum "ed25519" {
        value 32;
        description
          "Ed25519 key";
      }
    }
    description
      "Type key";
  }

  typedef Addr {
    type enumeration {
      enum "ipv4" {
        value 1;
        description
          "IPv4 address family";
      }
      enum "ipv6" {
        value 20;
        description
          "IPv6 address family";
      }
    }
    description
      "Addr";
  }

  typedef Digest {
    type enumeration {
      enum "md5" {
        value 1;
        description
          "md5 algorithm";
      }
      enum "sha1" {
        value 2;
        description
          "sha1 algorithm";
      }
      enum "sha256" {
        value 3;
        description
          "sha256 algorithm";
      }
      enum "sha384" {
        value 4;
        description
          "sha384 algorithm";
      }
      enum "sha512" {
        value 5;
        description
          "sha512 algorithm";
      }
    }
    description
      "Digest";
  }

  typedef Ren-msg {
    type enumeration {
      enum "pkcsreq" {
        value 1;
        description
          "Use PKCSReq for certificate renewal";
      }
      enum "renewalreq" {
        value 2;
        description
          "Use RenewalReq for certificate renewal";
      }
    }
    description
      "Ren msg";
  }

  typedef Enrollment-method-list {
    type string {
      pattern "(est)";
    }
    description
      "est:EST Protocol";
  }

  grouping SFTP {
    description
      "Common node of trustpoint, system-trustpoint";
    container sftp {
      description
        "Secure FTP";
      leaf username {
        type string;
        description
          "Secure FTP username";
      }
      leaf password {
        type xr:Proprietary-password;
        description
          "SFTP password in cleartext or encrypted form";
      }
    }
  }

  grouping VRF-TABLE {
    description
      "Common node of trustpoint, system-trustpoint,
       trustpool";
    container vrf-table {
      description
        "vrf table";
      leaf vrf {
        type xr:Cisco-ios-xr-string {
          length "1..32";
        }
        description
          "VRF name (max:32 chars)";
      }
    }
  }

  grouping CRL {
    description
      "Common node of trustpoint, system-trustpoint,
       trustpool";
    container crl {
      description
        "CRL Parameters";
      leaf optional {
        type empty;
        description
          "Set 'true' if CRL check is optional";
      }
    }
  }

  grouping QUERY {
    description
      "Common node of trustpoint, system-trustpoint";
    container query {
      description
        "Query Parameters";
      leaf url {
        type string;
        description
          "CertificateAuthority Server Query URL";
      }
    }
  }

  grouping MESSAGE-DIGEST {
    description
      "Common node of system-trustpoint, trustpoint";
    leaf message-digest {
      type Digest;
      description
        "Certificate message digest self enrollment";
    }
  }

  grouping AUTO-ENROLL {
    description
      "Common node of trustpoint, system-trustpoint";
    leaf auto-enroll {
      type uint32 {
        range "1..99";
      }
      units "percentage";
      description
        "Percentage of certificate lifetime after which
         renew will be triggered";
    }
  }

  grouping RENEWAL-MESSAGE-TYPE {
    description
      "Common node of trustpoint, system-trustpoint";
    leaf renewal-message-type {
      type Ren-msg;
      description
        "Configure SCEP renewal message type";
    }
  }

  grouping ATTRIBUTE {
    description
      "Common node of trustpoint, system-trustpoint";
    container attribute {
      description
        "Trustpoint Attributes";
      container ip-address {
        description
          "Include IP-Address in certificate";
        leaf address {
          type inet:ipv4-address-no-zone;
          must "not(../no-address)";
          description
            "IP address";
        }
        leaf no-address {
          type empty;
          must "not(../address)";
          description
            "Do not include IP address";
        }
      }
      leaf serial-number {
        type boolean;
        description
          "Include serial number in certificate";
      }
      leaf subject-alternative-name {
        type string;
        description
          "Include subject alternative name in certificate";
      }
      leaf subject-name {
        type string;
        description
          "Include subject name in certificate";
      }
    }
  }

  grouping RSA-KEY-PAIR {
    description
      "Common node of trustpoint, system-trustpoint,
       openssh-trustpoint-name";
    leaf rsa-key-pair {
      type string;
      description
        "RSA key Pair to use for enrolling this
         Trustpoint";
    }
  }

  grouping DESCRIPTION {
    description
      "Common node of trustpoint, system-trustpoint,
       trustpool";
    leaf description {
      type string {
        length "1..80";
      }
      description
        "Description for this trustpoint";
    }
  }

  grouping ENROLLMENT {
    description
      "Common node of trustpoint, system-trustpoint";
    container enrollment {
      description
        "Certificate Enrollment Parameters";
      container retry {
        description
          "Enrollment Retry Parameters";
        leaf period {
          type uint32 {
            range "1..60";
          }
          units "minute";
          default "1";
          description
            "How long to wait between retry requests to
             CertificateAuthority for Certificate";
        }
        leaf count {
          type uint32 {
            range "1..100";
          }
          default "10";
          description
            "How many times the router should poll
             CertificateAuthority for Certificate";
        }
      }
      leaf url {
        type string;
        description
          "CertificateAuthority Server Enrollment URL";
      }
    }
  }

  container crypto-cepki {
    description
      "Crypto CertificateAuthority";
    container fips-mode {
      description
        "fips mode configuration";
      leaf enable {
        type empty;
        description
          "Fips Mode Enabled";
      }
    }
    container certificate-authority {
      description
        "Certification Authority";
      container system-trustpoint {
        description
          "Trustpoint Name";
        container keypair {
          description
            "keypair label";
          leaf type-key {
            type Type-key;
            description
              "dsa/ecdsanistp256/ecdsanistp384/ecdsanistp521/rsa/ed25519";
          }
          leaf name {
            type string;
            description
              "key-pair label";
          }
        }
        container ca-keypair {
          description
            "self-enrollment ca-keypair label";
          leaf type-key {
            type Type-key;
            description
              "dsa/ecdsanistp256/ecdsanistp384/ecdsanistp521/rsa/ed25519";
          }
          leaf name {
            type string;
            description
              "key-pair label";
          }
        }
        container key-usage {
          description
            "key usage field for the certificate";
          leaf dataencipherment {
            type uint32 {
              range "0..1";
            }
            description
              "Key usage field as data-encipherment for
               certificate";
          }
          leaf digitalsignature {
            type uint32 {
              range "0..1";
            }
            description
              "Key usage field as digital-signature for
               certificate";
          }
          leaf keyagreement {
            type uint32 {
              range "0..1";
            }
            description
              "Key usage field as key-agreement for
               certificate";
          }
          leaf keyencipherment {
            type uint32 {
              range "0..1";
            }
            description
              "Key usage field as key-encipherment for
               certificate";
          }
          leaf nonrepudiation {
            type uint32 {
              range "0..1";
            }
            description
              "Key usage field as non-repudiation for
               certificate";
          }
        }
        container key-usage-ca {
          description
            "key usage field for the CA certificate";
          leaf crlsign {
            type uint32 {
              range "0..1";
            }
            description
              "Key usage field as crl-sign for CA
               certificate";
          }
          leaf digitalsignature {
            type uint32 {
              range "0..1";
            }
            description
              "Key usage field as digital-signature for CA
               certificate";
          }
          leaf keycertsign {
            type uint32 {
              range "0..1";
            }
            description
              "Key usage field as key-certsign for CA
               certificate";
          }
          leaf nonrepudiation {
            type uint32 {
              range "0..1";
            }
            description
              "Key usage field as non-repudiation for CA
               certificate";
          }
        }
        leaf subject-name-ca {
          type string;
          description
            "Ca Certificate subject name for self
             enrollment";
        }
        leaf lifetime-ca-cert {
          type uint32 {
            range "30..5475";
          }
          units "day";
          default "365";
          description
            "Validity of ca certficate in days";
        }
        leaf lifetime-cert {
          type uint32 {
            range "30..5474";
          }
          units "day";
          default "200";
          description
            "Validity of leaf certficate in days";
        }
        uses SFTP;
        uses ATTRIBUTE;
        uses RSA-KEY-PAIR;
        uses CRL;
        uses RENEWAL-MESSAGE-TYPE;
        uses ENROLLMENT;
        uses VRF-TABLE;
        uses QUERY;
        uses AUTO-ENROLL;
        uses MESSAGE-DIGEST;
        uses DESCRIPTION;
      }
      container trustpool {
        description
          "Trustpool Related Configuration";
        container cabundle {
          description
            "CA bundle download parameters";
          leaf url {
            type string;
            description
              "CertificateAuthority bundle download
               parameters";
          }
        }
        uses CRL;
        uses VRF-TABLE;
        uses DESCRIPTION;
      }
      container trustpoints {
        description
          "Trustpoint Related Configuration";
        list trustpoint {
          key "name";
          description
            "Trustpoint Name";
          container enrollment-methods {
            description
              "Different methods that can be used for
               enrollment";
            list enrollment-method {
              key "name";
              description
                "Enrollment Method Related Configuration";
              container credential {
                description
                  "Different types of credentials used for
                   authentication";
                leaf certificate {
                  type string;
                  description
                    "Bootstrap Trustpoint to obtain
                     router(client) certificate for mTLS
                     session";
                }
              }
              leaf name {
                type Enrollment-method-list;
                description
                  "Enrollment Method Name";
              }
            }
          }
          container extended-key-usage {
            description
              "Extended Key Usage field associated with the
               certificate";
            container match {
              description
                "Allows PKI to validate a peer certificate
                 only if the specified attribute is present
                 in the certificate's extended key usage
                 field else validation fails";
              leaf server-auth {
                type uint32 {
                  range "0..1";
                }
                description
                  "Server Authentication";
              }
              leaf client-auth {
                type uint32 {
                  range "0..1";
                }
                description
                  "Client Authentication";
              }
            }
          }
          leaf skip-challenge-password {
            type empty;
            description
              "Set to True if challenge password is to be
               skipped for CSR";
          }
          leaf name {
            type xr:Cisco-ios-xr-string;
            description
              "Trustpoint Name";
          }
          uses SFTP;
          uses ATTRIBUTE;
          uses RSA-KEY-PAIR;
          uses CRL;
          uses RENEWAL-MESSAGE-TYPE;
          uses ENROLLMENT;
          uses VRF-TABLE;
          uses QUERY;
          uses AUTO-ENROLL;
          uses MESSAGE-DIGEST;
          uses DESCRIPTION;
        }
      }
      container openssh-trustpoint-names {
        description
          "OpenSSH Trustpoint Related Configuration";
        list openssh-trustpoint-name {
          key "tp-name";
          description
            "Trustpoint Name";
          leaf tp-name {
            type xr:Cisco-ios-xr-string {
              length "1..128";
            }
            description
              "Enter TP name";
          }
          uses RSA-KEY-PAIR;
        }
      }
      leaf curl-timeout {
        type uint32 {
          range "5..50";
        }
        units "second";
        description
          "Value in seconds for a CURL request to timeout";
      }
      leaf rsa1024 {
        type empty;
        description
          "Specify rsa key bit 1024 or lesser size allowed
           or not";
      }
    }
    container keys {
      description
        "Generate rsa/dsa/ecdsa/ed25519 keys";
      container ecdsa-keypair-types {
        description
          "ECDSA keypair";
        list ecdsa-keypair-type {
          key "name";
          description
            "ECDSA Keypair curve type";
          container ecdsa-keypair-label {
            description
              "ECDSA Keypair Label";
            leaf ecdsa-key {
              type boolean;
              default "false";
              description
                "Enables to generate default ecdsa keypair";
            }
          }
          leaf name {
            type xr:Cisco-ios-xr-string;
            description
              "Keypair type";
          }
        }
      }
      container dsa-keypair-table {
        description
          "DSA keypair";
        container dsa-keypair {
          description
            "DSA Keypair Label";
          container dsa-key {
            description
              "Generate DSA keypairs";
            leaf key-modulus {
              type uint32 {
                range "512..2048";
              }
              default "1024";
              description
                "DSA key modulus";
            }
            leaf key {
              type string;
              description
                "DSA key generated";
            }
          }
        }
      }
      container rsa-keypairs {
        description
          "RSA keypair";
        list rsa-keypair {
          key "name";
          description
            "RSA Keypair Label";
          container rsa-key {
            description
              "Generate RSA keypairs";
            leaf key-modulus {
              type uint32 {
                range "512..4096";
              }
              default "2048";
              description
                "RSA key modulus";
            }
            leaf key-type {
              type string;
              default "general-keys";
              description
                "Type of key to generate
                 general-keys/usage-keys";
            }
            leaf key {
              type string;
              description
                "RSA key generated";
            }
          }
          leaf name {
            type xr:Cisco-ios-xr-string {
              length "1..127";
            }
            description
              "Keypair Label";
          }
        }
      }
      container ed25519-keypair-table {
        description
          "ED25519 keypair";
        container ed25519-keypair {
          description
            "ED25519 Keypair Label";
          leaf ed25519-key {
            type boolean;
            default "false";
            description
              "Enables to generate default ed25519 keypair";
          }
        }
      }
    }
    container http-proxy {
      description
        "Specify proxy server and port for http request";
      leaf server {
        type string;
        description
          "Http proxy server";
      }
      leaf port {
        type xr:Cisco-ios-xr-port-number;
        description
          "Http proxy server port";
      }
    }
    container source-interface {
      description
        "Specify source interface for http request";
      leaf source-interface {
        type xr:Interface-name;
        description
          "Source interface for CRL";
      }
      leaf addr-type {
        type Addr;
        description
          "IPv4 / IPv6";
      }
    }
  }
}
