submodule Cisco-IOS-XR-controller-ots-oper-sub1 {
  belongs-to Cisco-IOS-XR-controller-ots-oper {
    prefix Cisco-IOS-XR-controller-ots-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-ots package operational data.
     
     Copyright (c) 2013-2024 by Cisco Systems, Inc.
     All rights reserved.";

  revision 2024-10-15 {
    description
      "Added last link flap field";
    semver:module-version "1.0.0";
  }
  revision 2023-12-07 {
    description
      "Added new enum definition for C+L band type";
  }
  revision 2023-06-23 {
    description
      "Added new enum definition Excess-Attenuation and optical-return-loss leaf for OTDR";
  }
  revision 2023-04-27 {
    description
      "Parameter raman-br-ratio, egress-ampli-br-power, egress-ampli-br-ratio are added in ots_edm_info container";
  }
  revision 2023-02-06 {
    description
      "Amplifier Control Mode introduced in OTS-EDM-INFO group";
  }
  revision 2023-01-18 {
    description
      "Leaves egress-ampli-working-mode-config, ingress-ampli-working-mode-config, egress-ampli-working-mode, ingress-ampli-working-mode and ingress-ampli-power-config added. Leaf egress-ampli-power renamed to egress-ampli-power-config.";
  }
  revision 2022-12-16 {
    description
      "OTS-TRANSCEIVER-DATA group, leaf form-factor, leaf temperature, leaf voltage are introduced in OTS-EDM-INFO group";
  }
  revision 2022-11-17 {
    description
      "description leaf added in container optics-lane";
  }
  revision 2022-10-17 {
    description
      "Egress Amplifier Power, OTS egress amplifier power added";
  }
  revision 2022-08-30 {
    description
      "Egress Amplifier BR Ratio, OTS Port Type and Raman BR Ratio are added in ots-info container";
  }
  revision 2022-06-13 {
    description
      "channel-attenuation-info container separated out from ots info container";
  }
  revision 2022-04-25 {
    description
      "Units added for channel frequency in ots bag.";
  }
  revision 2022-04-18 {
    description
      "ots_och_alarm_info is converted to a pointer";
  }
  revision 2022-03-25 {
    description
      "Units changed for location and accuracy leaf nodes in otdr-info-rx and otdr-info-tx containers.";
  }
  revision 2022-03-15 {
    description
      "Units added for some leaf nodes in spectrum-info, channel-attenuation-info, raman-tx-power and ots_info containers.";
  }
  revision 2022-03-07 {
    description
      "Removed Low-Tx-PWR information for ots controller";
  }
  revision 2022-02-22 {
    description
      "Name of the enum led_state is changed to LedState";
  }
  revision 2022-01-13 {
    description
      "raman-tx-power range extended in ots controller";
  }
  revision 2021-12-23 {
    description
      "Parameters egress_ampli_br, egress_ampli_br_high_th_cfgd, egress_ampli_br_cfgd, raman_br, raman_br_cfgd and raman_br_high_th_cfgd are removed from ots_ui bag";
  }
  revision 2021-12-10 {
    description
      "led_state parameter added for OTS controller";
  }
  revision 2021-12-08 {
    description
      "Added alarms and counters for OTS, OTS-OCH, OSC, DFB, OMS, OCH controllers.";
  }
  revision 2021-12-01 {
    description
      "Parameters br_power and raman_br_power are added in ots_edm_info container";
  }
  revision 2021-11-19 {
    description
      "led_state container and parameters controller_state, led_state are added for OCH and OMS controllers";
  }
  revision 2021-11-13 {
    description
      "Config container added for Raman TX power in OTS controller";
  }
  revision 2021-10-25 {
    description
      "Parameters lower_frequency, upper_frequency, rx_psd and tx_psd are removed and data type of rx_power and tx_power is changed to int16_t in ots_edm_spectrum_power_info_v1 bag and first_slice_frequency added in ots_edm_spectrum_info_v1 bag";
  }
  revision 2021-09-16 {
    description
      "parameter chan_atten_first_slice_freq added in the ots_edm_chan_atten_info bag";
  }
  revision 2021-09-01 {
    description
      "Changed otdr_event_type enum definition";
  }
  revision 2021-08-23 {
    description
      "Added OTS OTDR oper support";
  }
  revision 2021-06-14 {
    description
      "Added support for Channel Slice Attenuation Info and Spectrum Info";
  }
  revision 2021-03-28 {
    description
      "egress-ampli-br, egress-ampli-br-high-th-cfgd, egress-ampli-br-cfgd are added in ots-info container";
  }
  revision 2021-02-17 {
    description
      "Raman Safety Params added";
  }
  revision 2021-02-08 {
    description
      "Ingress/Egress Safety Params added";
  }
  revision 2020-11-10 {
    description
      "Photodiode State Params Added for Ots Controller";
  }
  revision 2020-09-02 {
    description
      "Raman Transmit Params Added for Ots Controller";
  }
  revision 2020-08-21 {
    description
      "New Oper Model Added for Ots Controller";
  }
  revision 2019-04-05 {
    description
      "Establish semantic version baseline.";
  }
  revision 2015-11-09 {
    description
      "IOS XR 6.0 revision.";
  }

  typedef Ots-amplifier-working-mode {
    type enumeration {
      enum "invalid" {
        value 0;
        description
          "Invalid";
      }
      enum "gain" {
        value 1;
        description
          "Gain";
      }
      enum "power" {
        value 2;
        description
          "Power";
      }
    }
    description
      "Ots amplifier working mode";
  }

  typedef Ots-form-factor {
    type enumeration {
      enum "not-set" {
        value 0;
        description
          "Not set";
      }
      enum "invalid" {
        value 1;
        description
          "Invalid";
      }
      enum "cpak" {
        value 2;
        description
          "CPAK";
      }
      enum "cxp" {
        value 3;
        description
          "CXP";
      }
      enum "sfp-plus" {
        value 4;
        description
          "SFP+";
      }
      enum "qsfp" {
        value 5;
        description
          "QSFP";
      }
      enum "qsfp-plus" {
        value 6;
        description
          "QSFP+";
      }
      enum "qsfp28" {
        value 7;
        description
          "QSFP28";
      }
      enum "sfp" {
        value 8;
        description
          "SFP";
      }
      enum "cfp" {
        value 9;
        description
          "CFP";
      }
      enum "cfp2" {
        value 10;
        description
          "CFP2";
      }
      enum "cfp2-aco" {
        value 11;
        description
          "CFP2 ACO";
      }
      enum "cfp2-dco" {
        value 12;
        description
          "CFP2 DCO";
      }
      enum "cfp4" {
        value 13;
        description
          "CFP4";
      }
      enum "xfp" {
        value 14;
        description
          "XFP";
      }
      enum "x2" {
        value 15;
        description
          "X2";
      }
      enum "qsfpdd" {
        value 16;
        description
          "QSFP DD";
      }
      enum "other" {
        value 17;
        description
          "Other";
      }
      enum "sfp28" {
        value 18;
        description
          "SFP28";
      }
      enum "osfp" {
        value 19;
        description
          "OSFP";
      }
      enum "non-pluggable" {
        value 20;
        description
          "Non pluggable";
      }
    }
    description
      "Ots form factor";
  }

  typedef Ots-fiber-connector {
    type enumeration {
      enum "ots-connect-or-not-set" {
        value 0;
        description
          "Not Set";
      }
      enum "ots-sc-connect-or" {
        value 1;
        description
          "SC";
      }
      enum "ots-lc-connect-or" {
        value 2;
        description
          "LC";
      }
      enum "ots-mpo-connect-or" {
        value 3;
        description
          "MPO";
      }
      enum "ots-aoc-connect-or" {
        value 4;
        description
          "AOC";
      }
      enum "ots-dac-connect-or" {
        value 5;
        description
          "DAC";
      }
      enum "ots-cs-connect-or" {
        value 6;
        description
          "CS";
      }
      enum "ots-undefined-connect-or" {
        value 7;
        description
          "Undefined";
      }
    }
    description
      "Ots fiber connector";
  }

  typedef Ots-port {
    type enumeration {
      enum "com" {
        value 0;
        description
          "Com";
      }
      enum "line" {
        value 1;
        description
          "Line";
      }
      enum "osc" {
        value 2;
        description
          "Osc";
      }
      enum "com-check" {
        value 3;
        description
          "Com Check";
      }
      enum "work" {
        value 4;
        description
          "Working";
      }
      enum "prot" {
        value 5;
        description
          "Protected";
      }
      enum "add-drop" {
        value 6;
        description
          "Add Drop";
      }
    }
    description
      "Ots port";
  }

  typedef Ots-back-reflection-state-v1 {
    type enumeration {
      enum "disable" {
        value 0;
        description
          "Disable";
      }
      enum "enable" {
        value 1;
        description
          "Enable";
      }
    }
    description
      "Ots back reflection state v1";
  }

  typedef Conn-verfcn-state {
    type enumeration {
      enum "conn-vrfcn-state-failed" {
        value 0;
        description
          "Failed";
      }
      enum "conn-vrfcn-state-inprogress" {
        value 1;
        description
          "Inprogress";
      }
      enum "conn-vrfcn-state-success" {
        value 2;
        description
          "Success";
      }
      enum "conn-vrfcn-state-not-running" {
        value 3;
        description
          "Notrunning";
      }
    }
    description
      "Conn verfcn state";
  }

  typedef Led-state {
    type enumeration {
      enum "off" {
        value 0;
        description
          "Off";
      }
      enum "green-on" {
        value 1;
        description
          "Green";
      }
      enum "green-flashing" {
        value 2;
        description
          "Green Flashing";
      }
      enum "yellow-on" {
        value 3;
        description
          "Yellow";
      }
      enum "yellow-flashing" {
        value 4;
        description
          "Yellow Flashing";
      }
      enum "red-on" {
        value 5;
        description
          "Red";
      }
      enum "red-flashing" {
        value 6;
        description
          "Red Flashing";
      }
      enum "na" {
        value 7;
        description
          "Not Applicable";
      }
    }
    description
      "Led state";
  }

  typedef Ots-otdr-scan-regionid {
    type enumeration {
      enum "otdr-scan-region-invalid" {
        value 0;
        description
          "N/A";
      }
      enum "otdr-scan-region-office" {
        value 1;
        description
          "Office(8 km)";
      }
      enum "otdr-scan-region-short" {
        value 2;
        description
          "Short(32 km)";
      }
      enum "otdr-scan-region-long" {
        value 3;
        description
          "Long(150 km)";
      }
    }
    description
      "Ots otdr scan regionid";
  }

  typedef Otdr-scan-status {
    type enumeration {
      enum "otdr-scan-status-stopped" {
        value 0;
        description
          "Stopped";
      }
      enum "otdr-scan-status-measuring" {
        value 1;
        description
          "Measuring";
      }
      enum "otdr-scan-status-data-processing" {
        value 2;
        description
          "Data Processing";
      }
      enum "otdr-scan-status-data-ready" {
        value 3;
        description
          "Data Ready";
      }
      enum "otdr-scan-status-error" {
        value 4;
        description
          "Error";
      }
      enum "otdr-scan-status-invalid" {
        value 5;
        description
          "Invalid";
      }
      enum "otdr-scan-status-waiting-span-re-serv-ation" {
        value 6;
        description
          "Waiting Span Reservation";
      }
      enum "otdr-scan-status-timeout" {
        value 7;
        description
          "Timeout";
      }
      enum "otdr-scan-status-otdr-local-res-not-available" {
        value 8;
        description
          "Local Resource Not Available";
      }
      enum "otdr-scan-status-span-res-failed" {
        value 9;
        description
          "Span Reservation Failed";
      }
      enum "otdr-scan-status-comm-failed" {
        value 10;
        description
          "Communication Failed";
      }
      enum "otdr-scan-status-scan-not-allowed" {
        value 11;
        description
          "Scan Not Allowed";
      }
      enum "otdr-scan-status-scan-unknown" {
        value 12;
        description
          "Unknown";
      }
    }
    description
      "Otdr scan status";
  }

  typedef Ots-amplifier-control-mode {
    type enumeration {
      enum "automatic" {
        value 1;
        description
          "Automatic";
      }
      enum "manual" {
        value 2;
        description
          "Manual";
      }
      enum "power" {
        value 3;
        description
          "Power";
      }
    }
    description
      "Ots amplifier control mode";
  }

  typedef Ots-amplifier-safety-control-mode {
    type enumeration {
      enum "ots-amplifier-safety-mode-invalid" {
        value 0;
        description
          "Invalid";
      }
      enum "ots-amplifier-safety-mode-auto" {
        value 1;
        description
          "auto";
      }
      enum "ots-amplifier-safety-mode-disabled" {
        value 2;
        description
          "disabled";
      }
    }
    description
      "Ots amplifier safety control mode";
  }

  typedef Ots-amplifier-gain-range {
    type enumeration {
      enum "ots-amplifier-gain-range-invalid" {
        value 0;
        description
          "Invalid";
      }
      enum "ots-amplifier-gain-range-normal" {
        value 1;
        description
          "Normal";
      }
      enum "ots-amplifier-gain-range-ext-end-ed" {
        value 2;
        description
          "Extended";
      }
    }
    description
      "Ots amplifier gain range";
  }

  typedef Ots-controller-state {
    type enumeration {
      enum "ots-state-up" {
        value 0;
        description
          "Up";
      }
      enum "ots-state-down" {
        value 1;
        description
          "Down";
      }
      enum "ots-state-admin-down" {
        value 2;
        description
          "Administratively Down";
      }
    }
    description
      "Ots controller state";
  }

  typedef Ots-tas {
    type enumeration {
      enum "ots-tas-ui-oos" {
        value 0;
        description
          "Out Of Service";
      }
      enum "ots-tas-ui-main" {
        value 1;
        description
          "Maintenance";
      }
      enum "ots-tas-ui-is" {
        value 2;
        description
          "In Service";
      }
      enum "ots-tas-ui-ains" {
        value 3;
        description
          "Automatic In Service";
      }
    }
    description
      "Ots tas";
  }

  grouping OTS-EDM-SPECTRUM-POWER-INFO-V1 {
    description
      "OTS EDM SPECTRUM POWER INFO V1";
    leaf slice-num {
      type uint32;
      description
        "spectrum slice number";
    }
    leaf rx-power {
      type int16;
      description
        "Received Power in 0.1 dBm multiplied by 100";
    }
    leaf tx-power {
      type int16;
      description
        "Transmit Power in dBm multiplied by 100";
    }
  }

  grouping OTS-EDM-SPECTRUM-INFO-V1 {
    description
      "power information of slices in optical spectrum";
    leaf total-spectrum-slice-count {
      type uint32;
      description
        "Total number of slices in Spectrum";
    }
    leaf spectrum-slice-spacing {
      type uint32;
      description
        "Spacing between spectrum slices (in unit of 0
         .001GHz)";
    }
    leaf first-slice-wavelength {
      type uint32;
      description
        "Wavelength of first slice (in unit of 0.01 nm)";
    }
    leaf first-slice-frequency {
      type uint32;
      description
        "Frequency of first Slice Frequency (in unit of
         GHz)";
    }
    list spectrum-slice-power-info {
      description
        "Power information of spectrum slice info";
      uses OTS-EDM-SPECTRUM-POWER-INFO-V1;
    }
  }

  grouping OTS-EDM-SPECTRUM-BAG-INFO {
    description
      "ots spectrum information";
    container spectrum-info {
      description
        "OTS Spectrum information";
      uses OTS-EDM-SPECTRUM-INFO-V1;
    }
  }

  grouping OTS-TRANSCEIVER-DATA {
    description
      "Ots Transceiver Details";
    leaf vendor-info {
      type string;
      description
        "Vendor Information";
    }
    leaf date {
      type string;
      description
        "Manufacturing date of the Transceiver";
    }
    leaf ots-vendor-rev {
      type string;
      description
        "Transceiver vendor's revision number";
    }
    leaf ots-serial-no {
      type string;
      description
        "Transceiver serial number";
    }
    leaf ots-vendor-part {
      type string;
      description
        "Transceiver vendor's part number";
    }
    leaf ots-type {
      type string;
      description
        "Transceiver ots type";
    }
    leaf vendor-name {
      type string;
      description
        "Transceiver ots vendor name";
    }
    leaf oui-no {
      type string;
      description
        "Transceiver ots oui number";
    }
    leaf optics-pid {
      type string;
      description
        "Transceiver product id";
    }
    leaf optics-vid {
      type string;
      description
        "Transceiver version id";
    }
    leaf connector-type {
      type Ots-fiber-connector;
      description
        "Connector type";
    }
  }

  grouping OTS-TONE-INFO {
    description
      "Ots Tone information";
    leaf tone-freq {
      type string;
      description
        "Tone Frequency";
    }
    leaf tone-rate {
      type uint32;
      description
        "Tone Rate";
    }
    leaf pattern {
      type string;
      description
        "Tone pattern";
    }
    leaf pattern-expected {
      type string;
      description
        "Tone pattern expected";
    }
    leaf dectected-oob {
      type uint32;
      description
        "Detected OOB";
    }
    leaf state {
      type Conn-verfcn-state;
      description
        "Connection verification state";
      xr:event-telemetry "Subscribe Telemetry Event";
    }
    leaf pattern-received {
      type string;
      description
        "Tone pattern received";
    }
  }

  grouping OTS-OCH-EDM-INFO {
    description
      "Ots-Och Alarm information";
    container rx-los-p {
      description
        "RX-LOS-P for ots-och";
      uses OTS-ALARM-INFO;
    }
    container tx-power-fail-low {
      description
        "TX-POWER-FAIL-LOW for ots-och";
      uses OTS-ALARM-INFO;
    }
  }

  grouping OTS-ALARM-INFO {
    description
      "Optics Alarm Detail";
    leaf is-detected {
      type boolean;
      description
        "is defect detected?";
    }
    leaf counter {
      type uint32;
      description
        "Alarm counter";
    }
  }

  grouping OTS-OTDR-SCAN-REGION-INFO {
    description
      "OTS OTDR Scan Region Info";
    leaf region-id {
      type Ots-otdr-scan-regionid;
      description
        "Region Id";
    }
    leaf tracepoint-file {
      type string;
      description
        "Tracepoint File";
    }
    leaf total-events {
      type uint32;
      description
        "Total Events";
    }
    leaf scan-timestamp {
      type string;
      description
        "Scan Timestamp";
    }
    leaf optical-return-loss {
      type int32;
      description
        "Optical Return Loss in the units of 0.1 dB";
    }
    list event-info {
      description
        "Event Info";
      uses OTS-OTDR-EVENT-INFO-BAG;
    }
  }

  grouping OTS-OTDR-MULTI-REGION {
    description
      "OTS OTDR Multi Region Info";
    leaf scan-status {
      type Otdr-scan-status;
      description
        "Scan Status [Stopped | Measuring | Data
         Processing | Data Ready | Error]";
    }
    list otdr-multi-region-info {
      description
        "OTS OTDR Scan Region Info ";
      uses OTS-OTDR-SCAN-REGION-INFO;
    }
  }

  grouping OTS-OTDR-EVENT-INFO-BAG {
    description
      "OTS OTDR EVENT INFO BAG";
    leaf event-number {
      type uint32;
      description
        "Event Number";
    }
    leaf detected-event {
      type uint32;
      description
        "Event Detected [Non-Reflective | Reflective |
         Fiber-End | Excess-Reflection]";
    }
    leaf location {
      type int64;
      description
        "Location (in unit of 0.01m)";
    }
    leaf accuracy {
      type int64;
      description
        "Accuracy (in unit of 0.01m)";
    }
    leaf magnitude {
      type int64;
      description
        "Magnitude (in unit of 0.01db";
    }
    leaf attenuation {
      type int64;
      description
        "Attenuation/km (in unit of 0.01db)";
    }
  }

  grouping OTS-OTDR-INFO-BAG {
    description
      "OTS OTDR Info";
    leaf scan-status {
      type Otdr-scan-status;
      description
        "Scan Status [Stopped | Measuring | Data
         Processing | Data Ready | Error]";
    }
    leaf tracepoint-file {
      type string;
      description
        "Tracepoint File";
    }
    leaf total-events {
      type uint32;
      description
        "Total Events";
    }
    leaf scan-timestamp {
      type string;
      description
        "Scan Timestamp";
    }
    leaf optical-return-loss {
      type int32;
      description
        "Optical Return Loss in the units of 0.1 dB";
    }
    list event-info {
      description
        "Event Info";
      uses OTS-OTDR-EVENT-INFO-BAG;
    }
  }

  grouping OTS-RAMAN-TX-POWER-CONFIG {
    description
      "OTS Raman Transmit Power information";
    leaf raman-tx-power-instance {
      type uint32;
      description
        "Raman Transmit Power Instance";
    }
    leaf raman-tx-power-value {
      type uint32;
      description
        "Raman Transmit Power Value in units of 0.01mW";
    }
  }

  grouping OTS-RAMAN-PARAM-CONFIG {
    description
      "Proprietary Raman transmit power Parameters of
       config";
    list raman-tx-power {
      description
        "raman transmit power count of config";
      uses OTS-RAMAN-TX-POWER-CONFIG;
    }
  }

  grouping OTS-EGRESS-CHANNEL-SLICE-V1 {
    description
      "OTS Egress Channel Slice Attenuation Information";
    leaf egress-channel-slice {
      type uint32;
      description
        "Egress Channel Slice";
    }
    leaf egress-channel-slice-attenuation {
      type int32;
      description
        "Egress Channel Slice Attenuation in units of 0.1
         dB";
    }
  }

  grouping OTS-EGRESS-CHANNEL-SLICE-PARAM-V1 {
    description
      "Egress Channel Slice Attenuation Params";
    list egress-channel-slice {
      description
        "Egress Channel Slice List";
      uses OTS-EGRESS-CHANNEL-SLICE-V1;
    }
  }

  grouping OTS-INGRESS-CHANNEL-SLICE-V1 {
    description
      "OTS Ingress Channel Slice Attenuation Information";
    leaf ingress-channel-slice {
      type uint32;
      description
        "Ingress Channel Slice";
    }
    leaf ingress-channel-slice-attenuation {
      type int32;
      description
        "Ingress Channel Slice Attenuation in units of 0
         .1 dB";
    }
  }

  grouping OTS-INGRESS-CHANNEL-SLICE-PARAM-V1 {
    description
      "Ingress Channel Slice Attenuation Parameters";
    list ingress-channel-slice {
      description
        "Ingress Channel Slice List";
      uses OTS-INGRESS-CHANNEL-SLICE-V1;
    }
  }

  grouping OTS-RECEIVE-POWER-V1 {
    description
      "Proprietary OTS Receive Power Parameters";
    list receive-power {
      description
        "Receive Power count";
      uses OTS-POWER-LIST-V1;
    }
  }

  grouping OTS-POWER-LIST-V1 {
    description
      "Proprietary OTS Transmit/Receive Power Parameters";
    leaf instance {
      type uint32;
      description
        "Transmit/Receive Power Parameter Type(in units
         of 0.01dBm)";
    }
    leaf value {
      type int32;
      description
        "Transmit/Receive Power Parameter Value(in unit
         of 0.01dBm)";
    }
  }

  grouping OTS-TRANSMIT-POWER-V1 {
    description
      "Proprietary OTS Transmit Power Parameters";
    list transmit-power {
      description
        "Transmit Power count";
      uses OTS-POWER-LIST-V1;
    }
  }

  grouping OTS-RAMAN-TX-POWER {
    description
      "OTS Raman Transmit Power information";
    leaf raman-tx-power-instance {
      type uint32;
      description
        "Raman Transmit Power Intance";
    }
    leaf raman-tx-power-value {
      type uint32;
      description
        "Raman Transmit Power Value in units of 0.01mW";
    }
    leaf raman-tx-wavelength {
      type uint32;
      description
        "Raman Transmit Wavelength in units of 0.01 nm";
    }
  }

  grouping OTS-RAMAN-PARAM {
    description
      "Proprietary Raman transmit power Parameters";
    list raman-tx-power {
      description
        "raman transmit power count";
      uses OTS-RAMAN-TX-POWER;
    }
  }

  grouping OTS-EDM-INFO {
    description
      "ots transponder information";
    container raman-tx-power {
      description
        "Raman Tx Power";
      uses OTS-RAMAN-PARAM;
    }
    container transmit-n-power {
      description
        "Transmit N Power in the unit of 0.01dBm";
      uses OTS-TRANSMIT-POWER-V1;
    }
    container receive-n-power {
      description
        "Receive N Power in the unit of 0.01dBm";
      uses OTS-RECEIVE-POWER-V1;
    }
    container ingress-channel-slice-attenuation {
      description
        "Ingress Channel Slice Attenuation in units of 0
         .1 dB";
      uses OTS-INGRESS-CHANNEL-SLICE-PARAM-V1;
    }
    container egress-channel-slice-attenuation {
      description
        "Egress Channel Slice Attenuation in units of 0.1
         dB";
      uses OTS-EGRESS-CHANNEL-SLICE-PARAM-V1;
    }
    container raman-tx-power-config {
      description
        "Raman Tx Power";
      uses OTS-RAMAN-PARAM-CONFIG;
    }
    container ingress-channel-slice-attenuation-configured {
      description
        "Ingress Channel Slice Attenuation Configured in
         units of 0.1 dB";
      uses OTS-INGRESS-CHANNEL-SLICE-PARAM-V1;
    }
    container egress-channel-slice-attenuation-configured {
      description
        "Egress Channel Slice Attenuation Configured in
         units of 0.1 dB";
      uses OTS-EGRESS-CHANNEL-SLICE-PARAM-V1;
    }
    container otdr-info-rx {
      description
        "OTS OTDR Info at RX";
      uses OTS-OTDR-INFO-BAG;
    }
    container otdr-info-tx {
      description
        "OTS OTDR Info at TX";
      uses OTS-OTDR-INFO-BAG;
    }
    container otdr-multiregion-info-rx {
      description
        "OTS OTDR Multi Region Info at RX";
      uses OTS-OTDR-MULTI-REGION;
    }
    container otdr-multiregion-info-tx {
      description
        "OTS OTDR Multi Region Info at TX";
      uses OTS-OTDR-MULTI-REGION;
    }
    container rx-los-p {
      description
        "RX-LOS-P for ots";
      uses OTS-ALARM-INFO;
    }
    container rx-loc {
      description
        "RX-LOC for ots";
      uses OTS-ALARM-INFO;
    }
    container tx-power-fail-low {
      description
        "TX-POWER-FAIL-LOW for ots";
      uses OTS-ALARM-INFO;
    }
    container ingress-auto-laser-shut {
      description
        "INGRESS AUTO LASER SHUT";
      uses OTS-ALARM-INFO;
    }
    container ingress-auto-pow-red {
      description
        "INGRESS AUTO POW RED";
      uses OTS-ALARM-INFO;
    }
    container ingress-ampli-gain-low {
      description
        "INGRESS AMPLI GAIN LOW";
      uses OTS-ALARM-INFO;
    }
    container ingress-ampli-gain-high {
      description
        "INGRESS AMPLI GAIN HIGH";
      uses OTS-ALARM-INFO;
    }
    container egress-auto-laser-shut {
      description
        "EGRESS AUTO LASER SHUT";
      uses OTS-ALARM-INFO;
    }
    container egress-auto-pow-red {
      description
        "EGRESS AUTO POW RED";
      uses OTS-ALARM-INFO;
    }
    container egress-ampli-gain-low {
      description
        "EGRESS AMPLI GAIN LOW";
      uses OTS-ALARM-INFO;
    }
    container egress-ampli-gain-high {
      description
        "EGRESS AMPLI GAIN HIGH";
      uses OTS-ALARM-INFO;
    }
    container high-tx-br-pwr {
      description
        "HIGH TX BR POWER";
      uses OTS-ALARM-INFO;
    }
    container high-rx-br-pwr {
      description
        "HIGH RX BR PWR";
      uses OTS-ALARM-INFO;
    }
    container span-too-short-tx {
      description
        "SPAN TOO SHORT TX";
      uses OTS-ALARM-INFO;
    }
    container span-too-short-rx {
      description
        "SPAN TOO SHORT RX";
      uses OTS-ALARM-INFO;
    }
    container raman-auto-pow-red {
      description
        "RAMAN AUTO POW RED";
      uses OTS-ALARM-INFO;
    }
    container raman1-low-pwr {
      description
        "RAMAN 1 LOW PWR";
      uses OTS-ALARM-INFO;
    }
    container raman2-low-pwr {
      description
        "RAMAN 2 LOW PWR";
      uses OTS-ALARM-INFO;
    }
    container raman3-low-pwr {
      description
        "RAMAN 3 LOW PWR";
      uses OTS-ALARM-INFO;
    }
    container raman4-low-pwr {
      description
        "RAMAN 4 LOW PWR";
      uses OTS-ALARM-INFO;
    }
    container raman5-low-pwr {
      description
        "RAMAN 5 LOW PWR";
      uses OTS-ALARM-INFO;
    }
    container raman1-high-pwr {
      description
        "RAMAN 1 HIGH PWR";
      uses OTS-ALARM-INFO;
    }
    container raman2-high-pwr {
      description
        "RAMAN 2 HIGH PWR";
      uses OTS-ALARM-INFO;
    }
    container raman3-high-pwr {
      description
        "RAMAN 3 HIGH PWR";
      uses OTS-ALARM-INFO;
    }
    container raman4-high-pwr {
      description
        "RAMAN 4 HIGH PWR";
      uses OTS-ALARM-INFO;
    }
    container raman5-high-pwr {
      description
        "RAMAN 5 HIGH PWR";
      uses OTS-ALARM-INFO;
    }
    container ots-och-alamr-info {
      description
        "Ots-Och Alarm Information";
      uses OTS-OCH-EDM-INFO;
    }
    container ots-tone-info {
      description
        "Ots tone info";
      uses OTS-TONE-INFO;
    }
    container transceiver-info {
      description
        "Transceiver Vendor Details";
      uses OTS-TRANSCEIVER-DATA;
    }
    container otdr-info-baseline-rx {
      description
        "OTS OTDR Scan Baseline Info at RX";
      uses OTS-OTDR-INFO-BAG;
    }
    container otdr-info-baseline-tx {
      description
        "OTS OTDR Scan Baseline Info at TX";
      uses OTS-OTDR-INFO-BAG;
    }
    container otdr-multiregion-baseline-info-rx {
      description
        "OTS OTDR Multiregion Scan Baseline Info at RX";
      uses OTS-OTDR-MULTI-REGION;
    }
    container otdr-multiregion-baseline-info-tx {
      description
        "OTS OTDR Multiregion Scan Baseline Info at TX";
      uses OTS-OTDR-MULTI-REGION;
    }
    container ingress-ampli-laser-off {
      description
        "INGRESS AMPLI LASER OFF";
      uses OTS-ALARM-INFO;
    }
    container egress-ampli-laser-off {
      description
        "EGRESS AMPLI LASER OFF";
      uses OTS-ALARM-INFO;
    }
    leaf transport-admin-state {
      type Ots-tas;
      description
        "Transport Admin State";
      xr:event-telemetry "Subscribe Telemetry Event";
    }
    leaf rx-pow-low-threshold {
      type int32;
      description
        "Rx Low threshold value in units of 0.1dBm";
    }
    leaf rx-pow-high-threshold {
      type int32;
      description
        "Rx High threshold value in units of 0.1dBm";
    }
    leaf tx-pow-low-threshold {
      type int32;
      description
        "Tx Low threshold value in units of 0.1dBm";
    }
    leaf tx-pow-high-threshold {
      type int32;
      description
        "Tx High threshold value in units of 0.1dBm";
    }
    leaf pm-enable {
      type uint32;
      description
        "PmEable or Disable";
    }
    leaf controller-state {
      type Ots-controller-state;
      description
        "Ots controller state: Up, Down or
         Administratively Down";
      xr:event-telemetry "Subscribe Telemetry Event";
    }
    leaf rx-voa-attenuation {
      type int32;
      description
        "Rx Voa Attenuation in the units of 0.1dB";
    }
    leaf tx-voa-attenuation {
      type int32;
      description
        "Tx Voa Attenuation in the units of 0.1dB";
    }
    leaf channel-width {
      type uint32;
      description
        "Channel Width (in Unit of 0.1 GHz)";
    }
    leaf central-frequncy {
      type uint32;
      description
        "frequency read from hw in the units of 0.01 THz";
    }
    leaf add-drop-channel {
      type string;
      description
        "Add Drop Channel R/S/I/P/ch";
    }
    leaf line-channel {
      type string;
      description
        "Line Channel R/S/I/P/ch";
    }
    leaf ingress-ampli-gain {
      type int32;
      description
        "Ingress Ampli Gain in the unit of 0.1dB";
    }
    leaf ingress-ampli-tilt {
      type int32;
      description
        "Ingress Ampli Tilt in the unit of 0.1dB";
    }
    leaf ingress-amp-gain-deg-thres-low {
      type uint32;
      description
        "IngressAmpli Gain Deg Low threshold in the unit
         of 0.01dB";
    }
    leaf ingress-amp-gain-deg-thres-high {
      type uint32;
      description
        "Ingress Ampli Gain Deg High threshold in the
         unit of 0.01dB";
    }
    leaf ingress-ampli-gain-range {
      type Ots-amplifier-gain-range;
      description
        "Ingress Ampli gain range";
    }
    leaf egress-ampli-gain {
      type int32;
      description
        "Egress Ampli Gain in the unit of 0.1dB";
    }
    leaf egress-ampli-tilt {
      type int32;
      description
        "Egress Ampli Tilt in the unit of 0.1dB";
    }
    leaf egress-amp-gain-deg-thres-low {
      type uint32;
      description
        "EgressAmpli Gain Deg Low Threshold in the unit
         of 0.01dB";
    }
    leaf egress-amp-gain-deg-thres-high {
      type uint32;
      description
        "Egress Ampli Gain Deg High Threshold in the unit
         of 0.01dB";
    }
    leaf egress-ampli-gain-range {
      type Ots-amplifier-gain-range;
      description
        "Egress Ampli gain range";
    }
    leaf composite-raman-power {
      type uint32;
      description
        "Composite Raman Power in the unit of 0.01 mW";
    }
    leaf wavelength {
      type uint32;
      description
        "Wavelength in unit of 0.01 nm";
    }
    leaf transmit-power {
      type int32;
      description
        "Transmit power in the units of 0.01dBm";
    }
    leaf receive-power {
      type int32;
      description
        "Receive power in the units of 0.01dBm";
    }
    leaf total-cl-tx-power {
      type int32;
      description
        "Total (L+C)-transmit Power in the unit of 0
         .01dBm";
    }
    leaf total-cl-rx-power {
      type int32;
      description
        "Total (L+C)-receive Power in the unit of 0.01dBm";
    }
    leaf receive-signal-power {
      type int32;
      description
        "Transponder receive signal power in the units of
         0.01dBm";
    }
    leaf transmit-signal-power {
      type int32;
      description
        "Transmit Signal power in the units of 0.01dBm";
    }
    leaf ingress-ampli-osri {
      type boolean;
      description
        "Ingress Ampli Osri";
    }
    leaf egress-ampli-osri {
      type boolean;
      description
        "Egress Ampli Osri";
    }
    leaf ingress-ampli-force-apr {
      type boolean;
      description
        "Ingress Ampli Force Apr";
    }
    leaf egress-ampli-force-apr {
      type boolean;
      description
        "Egress Ampli Force Apr";
    }
    leaf ingress-ampli-safety-control-mode {
      type Ots-amplifier-safety-control-mode;
      description
        "Ingress Ampli Safety control mode";
    }
    leaf egress-ampli-safety-control-mode {
      type Ots-amplifier-safety-control-mode;
      description
        "Egress Ampli Safety control mode";
    }
    leaf ingress-ampli-safety-control-mode-configured {
      type Ots-amplifier-safety-control-mode;
      description
        "Ingress Ampli Safety Control Mode Configured";
    }
    leaf egress-ampli-safety-control-mode-configured {
      type Ots-amplifier-safety-control-mode;
      description
        "Egress Ampli Safety Control Mode Configured";
    }
    leaf ingress-ampli-osri-configured {
      type boolean;
      description
        "Ingress Ampli Osri Configured";
    }
    leaf egress-ampli-osri-configured {
      type boolean;
      description
        "Egress Ampli Osri Configured";
    }
    leaf ingress-ampli-force-apr-configured {
      type boolean;
      description
        "Ingress Ampli Force Apr Configured";
    }
    leaf egress-ampli-force-apr-configured {
      type boolean;
      description
        "Egress Ampli Force Apr Configured";
    }
    leaf raman-safety-control-mode {
      type Ots-amplifier-safety-control-mode;
      description
        "Raman Safety control mode";
    }
    leaf raman-safety-control-mode-configured {
      type Ots-amplifier-safety-control-mode;
      description
        "Raman Safety control mode Configured";
    }
    leaf raman-osri {
      type boolean;
      description
        "Raman Osri";
    }
    leaf raman-force-apr {
      type boolean;
      description
        "Raman Force Apr";
    }
    leaf raman-osri-configured {
      type boolean;
      description
        "Raman Osri Configured";
    }
    leaf raman-force-apr-configured {
      type boolean;
      description
        "Raman Force Apr Configured";
    }
    leaf rx-pow-low-warning-threshold {
      type int32;
      description
        "Rx Low Warning threshold value in units of 0
         .1dBm";
    }
    leaf rx-pow-high-warning-threshold {
      type int32;
      description
        "Rx High Warning threshold value in units of 0
         .1dBm";
    }
    leaf tx-pow-low-warning-threshold {
      type int32;
      description
        "Tx Low Warning threshold value in units of 0
         .1dBm";
    }
    leaf tx-pow-high-warning-threshold {
      type int32;
      description
        "Tx High Warning threshold value in units of 0
         .1dBm";
    }
    leaf description {
      type string;
      description
        "Controller description string";
    }
    leaf channel-attenuation {
      type int32;
      description
        "Channel Attenuation in units of 0.1 dB";
    }
    leaf rx-voa-attenuation-config-val {
      type int32;
      description
        "RX VOA attenuation configured value in units of
         0.1dB";
    }
    leaf tx-voa-attenuation-config-val {
      type int32;
      description
        "TX VOA attenuation configured value in units of
         0.1dB";
    }
    leaf ampli-control-mode-config-val {
      type Ots-amplifier-control-mode;
      description
        "ampli control mode config val";
    }
    leaf rx-low-th-psd-config-val {
      type int32;
      description
        "Rx Low threshold psd value in units of 0.001
         nW/MHz";
    }
    leaf total-rx-power {
      type int32;
      description
        "Total Receive Power  -> C/L-band power + OSC
         power (in units of 0.01 dBm)";
    }
    leaf total-tx-power {
      type int32;
      description
        "Total Transmit Power -> C/L-band power + OSC
         power (in units of 0.01 dBm)";
    }
    leaf ingress-ampli-gain-range-config-val {
      type Ots-amplifier-gain-range;
      description
        "ingress ampli gain range config val";
    }
    leaf ingress-ampli-gain-config {
      type uint32;
      description
        "Ingress Ampli gain configured value in units of
         0.1dB";
    }
    leaf ingress-ampli-tilt-config {
      type int32;
      description
        "Ingress Ampli tilt configured value in units of
         0.1dB";
    }
    leaf ingress-ampli-thr-deg-low-config {
      type uint32;
      description
        "Ingress Ampli gain low degrade threshold
         configured value in units of 0.01dB";
    }
    leaf ingress-ampli-thr-deg-high-config {
      type uint32;
      description
        "Ingress Ampli gain high degrade threshold
         configured value in units of 0.01dB";
    }
    leaf egress-ampli-gain-range-config-val {
      type Ots-amplifier-gain-range;
      description
        "egress ampli gain range config val";
    }
    leaf egress-ampli-gain-config {
      type uint32;
      description
        "Egress Ampli gain configured value in units of 0
         .1dB";
    }
    leaf egress-ampli-tilt-config {
      type int32;
      description
        "Egress Ampli tilt configured value in units of 0
         .1dB";
    }
    leaf egress-ampli-gain-thr-deg-low-config {
      type uint32;
      description
        "Egress Ampli gain low degrade threshold
         configured value in units of 0.01dB";
    }
    leaf egress-ampli-gain-thr-deg-high-config {
      type uint32;
      description
        "Egress Ampli gain high degrade threshold
         configured value in units of 0.01dB";
    }
    leaf channel-attenuation-configured {
      type int32;
      description
        "Channel Attenuation Configured in units of 0.1
         dB";
    }
    leaf br-power {
      type int32;
      description
        "BR Power in the units of 0.01dBm";
    }
    leaf raman-br-power {
      type int32;
      description
        "Raman BR Power in the units of 0.01dBm";
    }
    leaf led-state {
      type Led-state;
      description
        "Showing Current Colour of led state";
      xr:event-telemetry "Subscribe Telemetry Event";
    }
    leaf egress-amplifier-back-reflection {
      type Ots-back-reflection-state-v1;
      description
        "Egress Amplifier Back Reflection";
    }
    leaf egress-amplifier-back-reflection-high-threshold {
      type int32;
      description
        "Egress Amplifier Back Reflection High Threshold
         in units of 0.1 dBm";
    }
    leaf egress-amplifier-back-reflection-configured {
      type Ots-back-reflection-state-v1;
      description
        "Egress Amplifier Back Reflection Configured";
    }
    leaf egress-ampli-br-ratio {
      type int32;
      description
        "Egress Amplifier Back Reflection Ratio in the
         units of 0.01 dB";
    }
    leaf raman-br-ratio {
      type int32;
      description
        "Raman Amplifier Back Reflection Ratio in the
         units of 0.01 dB";
    }
    leaf port-type {
      type Ots-port;
      description
        "Port Type Details";
    }
    leaf egress-ampli-power-config {
      type int32;
      description
        "Egress Amplifier Power configured value in the
         units of 0.1 dBm";
    }
    leaf form-factor {
      type Ots-form-factor;
      description
        "Ots form factor";
    }
    leaf temperature {
      type int32;
      description
        "Temperature value in units of 0.01 C";
    }
    leaf voltage {
      type int32;
      description
        "Voltage value in units of 0.01V";
    }
    leaf ingress-ampli-power-config {
      type int32;
      description
        "Ingress Amplifier Power configured value in the
         units of 0.1 dBm";
    }
    leaf egress-ampli-working-mode-config {
      type Ots-amplifier-working-mode;
      description
        "Egress Amplifier configured working mode";
    }
    leaf ingress-ampli-working-mode-config {
      type Ots-amplifier-working-mode;
      description
        "Ingress Amplifier configured working mode";
    }
    leaf egress-ampli-working-mode {
      type Ots-amplifier-working-mode;
      description
        "Egress Amplifier working mode";
    }
    leaf ingress-ampli-working-mode {
      type Ots-amplifier-working-mode;
      description
        "Ingress Amplifier working mode";
    }
    leaf ampli-control-mode {
      type Ots-amplifier-control-mode;
      description
        "Amplifier Control Mode operational value";
    }
    leaf egress-ampli-br-power {
      type int32;
      description
        "Egress Ampli BR Power in the units of 0.01dBm";
    }
    leaf last-link-flap {
      type uint64;
      units "nanosecond";
      description
        "Last Link flap in elapsed nanoseconds since
         epoch";
    }
  }

  grouping OTS-EDM-EGRESS-ATTEN-INFO {
    description
      "OTS EDM EGRESS ATTEN INFO";
    leaf slice-num {
      type uint32;
      description
        "attenuation slice number";
    }
    leaf egress-attenuation {
      type uint32;
      description
        "Egress Attenuation in unit of 0.1 dB";
    }
  }

  grouping OTS-EDM-INGRESS-ATTEN-INFO {
    description
      "OTS EDM INGRESS ATTEN INFO";
    leaf slice-num {
      type uint32;
      description
        "attenuation slice number";
    }
    leaf ingress-attenuation {
      type uint32;
      description
        "Ingress Attenuation";
    }
  }

  grouping OTS-EDM-CHAN-ATTEN-INFO {
    description
      "Channel Attenuation Info";
    leaf total-channel-attenuation-slice-count {
      type uint32;
      description
        "Total Channel Attenuation Slice Count";
    }
    leaf channel-attenuation-slice-spacing {
      type uint32;
      description
        "Channel Attenuation Slice Spacing (in unit of 0
         .001 GHz)";
    }
    leaf channel-attenuation-first-slice-wavelength {
      type uint32;
      description
        "Channel Attenuation First Slice Wavelength (in
         unit of 0.01 nm)";
    }
    leaf channel-attenuation-first-slice-frequency {
      type uint32;
      description
        "Channel Attenuation First Slice Frequency (in
         unit of 0.01 GHz)";
    }
    list ingress-channel-attenuation-info {
      key "slice-num";
      description
        "Ingress information of Channel Slice Attenuation
         Info";
      uses OTS-EDM-INGRESS-ATTEN-INFO;
    }
    list egress-channel-attenuation-info {
      key "slice-num";
      description
        "Egress information of Channel Slice Attenuation
         Info";
      uses OTS-EDM-EGRESS-ATTEN-INFO;
    }
  }
}
