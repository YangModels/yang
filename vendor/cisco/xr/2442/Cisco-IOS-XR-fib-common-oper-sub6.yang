submodule Cisco-IOS-XR-fib-common-oper-sub6 {
  belongs-to Cisco-IOS-XR-fib-common-oper {
    prefix Cisco-IOS-XR-fib-common-oper;
  }

  import Cisco-IOS-XR-types {
    prefix xr;
  }
  import cisco-semver {
    prefix semver;
  }
  include Cisco-IOS-XR-fib-common-oper-sub4 {
    revision-date 2024-09-24;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2024 by Cisco Systems, Inc.
     All rights reserved.";

  revision 2024-09-24 {
    description
      "Added nexthop group named table
       2024-09-20
         Added backup-active leaf to next-hop-group/state container
       2024-09-11
         Moved misc container to global container instead of protocol container
       2024-08-19
         Added viability info to FIB external-client instances
       2024-08-16
         Added FIB oor prevention support to FIB cef summary
       2024-08-12
         Added support for information display of PWHE Interfaces, added new entry (gil-interface-name) to key of RTEP table and modified existing entry type (tunnel-interface-name) of RTEP table
       2024-08-09
         Added aysnc error notify capability
       2024-07-26
         Added per-NHOP nh-idb-usable and per-interface usable elements
       2024-06-28
         Added key to route summary counters
       2024-06-26
         Removed oor-resource-counter
       2024-06-24
         Added misc/per-protocol-debug-statistics/bcdlv2-stats
       2024-06-20
         Added route summary counters per protocol
       2024-05-28
         Added l3-unequal-cost-ip-route-paths-count to platform capabilities
       2024-05-23
         Standardize naming of ipvpn-tunnel-type and add new ipvpn-tunnel-type-nh type
       2024-05-23
         Add is-loadinfo-collapsed flag to basic FIB table information
       2024-05-02
         Added rtep-source, tunnel-id, tunnel-ifh and overlay-proto keys to tunnel tables
       2024-01-25
         Increased ECMP/UCMP capability
       2024-01-12
         Add back error/oor state for telemetry in oc-aft-l3 model
       2023-12-01
         Add platform-pbtsv6-support to platform capabilities
       2023-11-29
         Added Nexthop group ID information
       2023-11-27
         Optimized schema for linklocal. Added is-non-recursive field to IP prefixes.
       2023-10-25
         Added GIL ID in PWHE information and Interface List attribute
       2023-10-24
         Consolidated nh-info tables by type
       2023-10-19
         Added NextHop group ID to ext client output
       2023-10-11
         Added schema for external client, fixed schema for hardware egress/ingress
       2023-10-10
         Added and modified NPU mask and PWHE information
       2023-10-04
         Added encap-id and stat-id to recursive-nexthop dependents.
       2023-10-02
         Added VXLAN TEP tables.
       2023-09-21
         Eliminate name conflicts between keys and values
       2023-09-18
         Separated schema of linklocal prefix table from generic prefix table.
       2023-09-14
         Added via-nexthop-group to show cef output
       2023-08-15
         Added new errors sub-tree.
       2023-07-31
         Made hierarchical-loadbalancing parameters mandatory
       2023-07-28
         Internal cleanup, some type name changes.
       2023-07-26
         Fixed schema for exact-route and linklocal
       2023-07-17
         Changed pbts related variable type from static to dynamic array
       2023-07-13
         Added is-unresolved and is-frr to prefix tables
       2023-07-07
         Standardized leaf names and types throughout.
       2023-06-26
         Fix schema for hardware egress/ingress option
       2023-06-15
         Changed vni-info-key-type to an enum and added tblid-vni-key to vni-info-key-type
       2023-06-02
         Two Stage platform ObjectId capability added for cef-misc
       2023-06-01
         Added new field to ltep-nve-tunnels in order keep track of destination address protocol
       2023-05-31
         SRv6 accounting support added for FIB cef
       2023-05-25
         SRv6 accounting support added for FIB cef-accounting
       2023-05-24
         Added new detail field for hardware egress/ingress option
       2023-05-11
         Added class-id to support full exact-route functionality
       2023-05-08
         Remove oc-aft model from fib oper model
       2023-05-04
         Added new field to rtep-tunnels in order keep track of destination address protocol
       2023-04-24
         Combined separate evni tables for BGP and RTEP-ID to single evni table
       2023-04-15
         Added changes for show cef Interface
       2023-04-14
         Added hardware ingress and egress path for evni
       2023-04-05
         Added srv6_hardware ingress/egress
       2023-03-31
         Added resource-summary-infos and modified ip-prefix-detail
       2023-03-29
         Changed recursive nexthop display to be generic for address types
       2023-03-28
         Modified Interface List ID size from 16-bit to 32-bit
       2023-03-28
         Modifed fib_sh_policy_rl_entry rate field to uint64_t
       2023-03-20
         Added some preprograming related fields.
       2023-03-18
         Removed node tag from cef-accounting container.
       2023-03-06
         Added global policy table
       2023-02-07
         Added Exact route schema changes
       2023-02-06
         Added proto-retry-db-summary.
       2023-02-06
         Added disable-rfc5549-ipv4-over-ipv6-nexthop platform capability.
       2023-01-27
         Updated schema for ResourceHardwareIngress and Egress support
       2023-01-27
         Added exceptions-v4, exceptions-v6 and exceptions-mpls.
       2023-01-25
         Added global-retry-db-summary.
       2023-01-24
         Added cef-table-summary, drops-v6 and drops-mpls.
       2023-01-23
         srv6 accounting support
       2023-01-20
         Summary statistics: Added udp-src-port-msb information
       2023-01-04
         Updated evni-tunnel-bgp keys for VxLAN support
       2022-12-20
         Added changes for NHInfoHardwareIngress and NHInfoHardwareEgress in schema file.
       2022-12-06
         Added destionation address to Tunnel Decap, added destination address and underlay table id to Tunnel Decap-NVE
       2022-11-07
         protocol origin changes
       2022-11-01
         Updated FIB ext-client info bag to support ECD LTEP registrations
       2022-10-17
         CNHG changes
       2022-10-05
         Added PWHE and NPU mask for interface details
       2022-10-04
         Tunnel Encap/Decap: Added Prefix Length to the source and destination addresses
       2022-09-22
         Rate limiter statistics: Added drop stats
       2022-09-15
         Added Internal ID in PW-HE extension
       2022-08-29
         Summary statistics: Added udp-port information
       2022-07-19
         Added async-ack-support to FIB-SH-PLAT-CAPABILITIES, and ack-status, ack-latency, to FIB-GRIBI-ENTRY-INFO and FIB-GLOBAL-GRIBI-ENTRY.
       2022-07-07
         Added VRF base filtering for MPLS label stats
       2022-06-14
         Added program id, dst_ip and src_ip in next-hop and nhg fib.bag
       2022-06-13
         Added destination address to nve-ltep bag
       2022-05-13
         Added aft vrf-id to gribi bags
       2022-04-27
         Added vxlan-vni-id to ltep-tunnel
       2022-04-25
         Added RNH state
       2022-04-08
         Added table statistics
       2022-03-31
         Added sr-frr-nhid to frr-nhinfo-pending
       2022-03-24
         Added retry counts to object summary attributes
       2022-03-15
         Added vxlan-tunnels
       2022-03-01
         Added policy and hardware ingress and egress paths
       2022-02-16
         Added some SRv6 SIDs data
       2021-12-14
         Added gribi-table and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "5.0.0";
  }
  revision 2021-10-17 {
    description
      "Modify the type of list fsum-attr-cnt
       2021-09-17
          Rename lists unicast-prefix, broadcast-prefix and leafs num-retry-objects, old-unresolved-entries, new-unresolved-entries, unresolved-entries
       2021-07-30
          Added evpn bridge ID and SHG ID to srv6-information-for-path bag
       2021-07-06
          Added global-main subtree and support show CLIs for FIB IPC infra
       2021-05-25
          Migrate NHINFO to TI infra";
    semver:module-version "4.0.0";
  }
  revision 2020-12-02 {
    description
      "Adding per-object accounting.
       2020-10-20
           NBC documentation of CSCvu06764, CSCvv14573,CSCvv76648
       2020-05-26
           Update SRv6 Block Space naming convention
       2020-05-05
           changes related to treat SRv6 and SID as well-known when parsing XML for yang";
    semver:module-version "3.0.0";
  }
  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  typedef Fib-bag-adjacency {
    type enumeration {
      enum "none" {
        description
          "Invalid adjacency type";
      }
      enum "tx-nh" {
        description
          "TX Nhinfo";
      }
      enum "tx-interface" {
        description
          "TX Interface";
      }
    }
    description
      "Type of Adjacency";
  }

  typedef Fib-bag-adjaceny-app {
    type enumeration {
      enum "none" {
        description
          "None type";
      }
      enum "rsvp-te" {
        description
          "RSVP-TE type";
      }
      enum "sr-mpls" {
        description
          "SR-MPLS type";
      }
      enum "bundle-member" {
        description
          "Bundle-Member type";
      }
    }
    description
      "Application type of Adjacency";
  }

  typedef Fib-global-aggregation-bag {
    type enumeration {
      enum "aggregation-type-state" {
        description
          "Aggregation OOR and ERROR State";
      }
      enum "aggregation-type-adj" {
        description
          "Aggregation Adj Replication";
      }
    }
    description
      "FIB Aggregation bag type";
  }

  typedef Fib-bag-ao-attribute {
    type enumeration {
      enum "none" {
        description
          "Invalid attribute type";
      }
      enum "error" {
        description
          "Error type attribute";
      }
      enum "out-of-resource" {
        description
          "Out-of-Resource type attribute";
      }
      enum "adjacency" {
        description
          "Adjacency type attribute";
      }
      enum "attribute-count" {
        description
          "Number of attributes";
      }
    }
    description
      "Attribute types for the Aggregation Object (AO)";
  }

  grouping FIB-GLOBAL-CLIENT {
    description
      "FIB GLOBAL CLIENT";
    leaf client-id {
      type uint32;
      description
        "Client ID";
    }
    leaf node-id {
      type uint32;
      description
        "Location of the client";
    }
    leaf client-name {
      type string;
      description
        "Client name";
    }
    leaf create-time {
      type uint64;
      description
        "Time of creation";
    }
  }

  grouping FIB-GLOBAL-AGGREGATION-SUMMARY {
    description
      "FIB Aggregation Summary";
    leaf total {
      type uint32;
      description
        "Total number of Aggregations";
    }
    leaf total-ipv4 {
      type uint32;
      description
        "Total number of Aggregations of V4";
    }
    leaf total-ipv6 {
      type uint32;
      description
        "Total number of Aggregations of V6";
    }
    leaf total-adj-ipv4 {
      type uint32;
      description
        "Total number of V4 Adjacency Replications";
    }
    leaf total-adj-ipv6 {
      type uint32;
      description
        "Total number of V6 Adjacency Replications";
    }
  }

  grouping FIB-GLOBAL-AGGREGATION-ADJ-REPL-ATTR-EXT {
    description
      "FIB Aggregation Data of Adjacency Replication";
    leaf bit-mask-string {
      type string;
      description
        "Adjacency bit mask";
    }
    leaf mac-length {
      type uint32;
      description
        "Adjacency MAC length";
    }
    leaf mac-string {
      type string;
      description
        "Adjacency MAC string";
    }
  }

  grouping FIB-GLOBAL-AGGREGATION-ATTR-EXT {
    description
      "FIB GLOBAL AGGREGATION ATTR EXT";
    container adjacency-attribute-extension {
      when "../type = 'aggregation-type-adj'" {
        description
          "../type = 'AggregationTypeAdj'";
      }
      description
        "adjacency attribute extension";
      uses FIB-GLOBAL-AGGREGATION-ADJ-REPL-ATTR-EXT;
    }
    leaf type {
      type Fib-global-aggregation-bag;
      description
        "type";
    }
  }

  grouping FIB-GLOBAL-AGGREGATION-ATTR {
    description
      "FIB Aggregation Attribute";
    leaf node-id {
      type uint32;
      description
        "NodeID of Aggregation Info from";
    }
  }

  grouping FIB-GLOBAL-AGGREGATION-ADJ-REPL-KEY-EXT {
    description
      "FIB Aggregation Key-Ext of Adjacency Replication";
    leaf interface-name {
      type xr:Interface-name;
      description
        "Adjacency Replication Interface";
    }
    leaf is-mpls {
      type boolean;
      description
        "Adjacency Replication Is MPLS";
    }
    leaf nh-address {
      type string;
      description
        "Next-hop address";
    }
    leaf application-type {
      type Fib-bag-adjaceny-app;
      description
        "NH Replication type";
    }
    leaf adjacency-type {
      type Fib-bag-adjacency;
      description
        "Adjacency type";
    }
  }

  grouping FIB-GLOBAL-AGGREGATION-KEY-EXT {
    description
      "FIB GLOBAL AGGREGATION KEY EXT";
    container adjacency-key-extension {
      when "../type = 'aggregation-type-adj'" {
        description
          "../type = 'AggregationTypeAdj'";
      }
      description
        "adjacency key extension";
      uses FIB-GLOBAL-AGGREGATION-ADJ-REPL-KEY-EXT;
    }
    leaf type {
      type Fib-global-aggregation-bag;
      description
        "type";
    }
  }

  grouping FIB-GLOBAL-AGGREGATION-KEY {
    description
      "FIB Aggregation Key";
    leaf protocol {
      type Fib-bag-protocol;
      description
        "Aggregation AFI Protocol";
    }
    leaf object-type {
      type Fib-bag-object;
      description
        "Aggregation Object Type";
    }
    leaf attribute-type {
      type Fib-bag-ao-attribute;
      description
        "Aggregation Attribute Type";
    }
  }

  grouping FIB-GLOBAL-AGGREGATION-ENTRY {
    description
      "FIB Aggregation Entry Info";
    container key {
      description
        "Aggregation Key";
      uses FIB-GLOBAL-AGGREGATION-KEY;
    }
    container key-extension {
      description
        "Aggregation Key Extension";
      uses FIB-GLOBAL-AGGREGATION-KEY-EXT;
    }
    list attribute {
      description
        "Aggregation Attributes";
      uses FIB-GLOBAL-AGGREGATION-ATTR;
    }
    list attribute-extension {
      description
        "Aggregation Attributes Ext";
      uses FIB-GLOBAL-AGGREGATION-ATTR-EXT;
    }
  }

  grouping FIB-GLOBAL-LTEP-NVE-ENTRY {
    description
      "FIB LTEP NVE Entry Info";
    container dest-address {
      description
        "Destination address";
      uses FIB-IP-ADDR-T-UNION;
    }
    container ltep {
      description
        "LTEP";
      uses FIB-COMMON-LTEP-ENTRY;
    }
    leaf table-id {
      type uint32;
      description
        "Table Id";
    }
    leaf nve-interface-id {
      type uint32;
      description
        "NVE interface ID";
    }
    leaf vni-id {
      type uint32;
      description
        "VNI Id";
    }
    leaf destination-prefix-length {
      type uint8;
      description
        "Prefix length of Destination address";
    }
    leaf underlay-table-id {
      type uint32;
      description
        "Underlay table Id";
    }
  }

  grouping FIB-GLOBAL-GRIBI-NH-UNION {
    description
      "FIB GLOBAL GRIBI NH UNION";
    container ltep {
      when "../object-type = 'ltep'" {
        description
          "../ObjectType = 'LTEP'";
      }
      description
        "ltep";
      uses FIB-COMMON-LTEP-ENTRY;
    }
    container rtep {
      when "../object-type = 'tep'" {
        description
          "../ObjectType = 'TEP'";
      }
      description
        "rtep";
      uses FIB-COMMON-RTEP-ENTRY;
    }
    leaf object-type {
      type Fib-bag-object;
      description
        "ObjectType";
    }
  }

  grouping FIB-GLOBAL-GRIBI-ENTRY {
    description
      "FIB GRIBI Entry Info";
    container aft-next-hop {
      description
        "AFT next hop";
      uses FIB-GLOBAL-GRIBI-NH-UNION;
    }
    leaf vrf-id {
      type uint32;
      description
        "Vrf ID";
    }
    leaf object-id {
      type uint64;
      description
        "Object ID";
    }
    leaf entry-transaction-id {
      type uint64;
      description
        "GRIBI entry transaction ID";
    }
    leaf aft-object-type {
      type Fib-common-aft-nh;
      description
        "AFT object type";
    }
    leaf ack-status {
      type Fib-ack-status;
      description
        "Hardware acknowledgement status";
    }
    leaf ack-latency {
      type uint32;
      units "millisecond";
      description
        "Hardware acknowledgement latency in milliseconds";
    }
  }

  grouping FIB-GLOBAL-SUMMARY-OBJ-HISTORY {
    description
      "FIB Global summary object history";
    leaf count {
      type uint32;
      description
        "Placeholder for obj history counts";
    }
  }

  grouping FIB-GLOBAL-SUMMARY-OBJ-HISTORY-PROTO {
    description
      "FIB GLOBAL SUMMARY OBJ HISTORY PROTO";
    container base-object {
      description
        "Base object";
      uses FIB-GLOBAL-BASE-ST;
    }
    container object-history {
      description
        "Obj History";
      uses FIB-GLOBAL-SUMMARY-OBJ-HISTORY;
    }
  }

  grouping FIB-BAG-ERROR-AGGR-OBJ {
    description
      "Aggregate Object Error";
    leaf error-count {
      type uint32;
      description
        "Aggregate error count";
    }
    leaf oor-count {
      type uint32;
      description
        "Aggregate OOR count";
    }
  }

  grouping FIB-BAG-ERROR-ATTR {
    description
      "Error attributes";
    leaf error-count {
      type uint32;
      description
        "Error count";
    }
    leaf oor-count {
      type uint32;
      description
        "OOR count";
    }
  }

  grouping FIB-BAG-ERROR-OBJ {
    description
      "Object error";
    container object-attributes {
      description
        "Errors attributes";
      uses FIB-BAG-ERROR-ATTR;
    }
    leaf object-type {
      type uint32;
      description
        "Object type";
    }
    leaf object-name {
      type string;
      description
        "Object name";
    }
  }

  grouping FIB-GLOBAL-SUMMARY-HEALTH {
    description
      "FIB Global summary health";
    leaf is-retry-db-empty {
      type boolean;
      description
        "Boolean to indicate if the retry database is
         empty or not";
    }
  }

  grouping FIB-GLOBAL-BASE-ST {
    description
      "FIB Global Base st";
    leaf protocol {
      type uint32;
      description
        "Fib Global base protocol";
    }
  }

  grouping FIB-GLOBAL-SUMMARY {
    description
      "FIB Global summary";
    container base-object {
      description
        "Base object";
      uses FIB-GLOBAL-BASE-ST;
    }
    container summary-counts {
      description
        "Global Summary counts";
      uses FIB-GLOBAL-SUMMARY-COUNTS;
    }
    container health {
      description
        "Global summary health";
      uses FIB-GLOBAL-SUMMARY-HEALTH;
    }
  }

  grouping FIB-GLOBAL-SUMMARY-PROTO {
    description
      "FIB GLOBAL SUMMARY PROTO";
    container common-info {
      description
        "Common Info";
      uses FIB-GLOBAL-SUMMARY-COMMON-INFO;
    }
    container summary {
      description
        "Global summary";
      uses FIB-GLOBAL-SUMMARY;
    }
  }

  grouping FIB-BAG-GLBL-SUM {
    description
      "FIB BAG GLBL SUM";
    container obj-attr {
      description
        "Aggregate Summary across protocols";
      uses FIB-BAG-SUM-OBJ-ATTR;
    }
  }

  grouping FIB-GLOBAL-NUM-OBJECTS-ST {
    description
      "FIB Global summary num retries";
    leaf object-type {
      type string {
        length "0..30";
      }
      description
        "object";
    }
    leaf num-objects {
      type uint32;
      description
        "number of elements for this obj type";
    }
  }

  grouping FIB-GLOBAL-NUM-RETRIES-ST {
    description
      "FIB Global summary num retries";
    leaf retry-object-type {
      type string {
        length "0..30";
      }
      description
        "retry object";
    }
    leaf num-retries {
      type uint64;
      description
        "number of elements for this obj type in retry db";
    }
  }

  grouping FIB-GLOBAL-SUMMARY-COUNTS {
    description
      "FIB Global summary counts";
    leaf num-retry-timeouts {
      type uint64;
      description
        "number of retry timeouts";
    }
    leaf num-retry-objects {
      type uint32;
      description
        "number of elements in retry db";
    }
    list array-number-of-retry {
      description
        "number of objects in retry db";
      uses FIB-GLOBAL-NUM-RETRIES-ST;
    }
    list array-number-of-object {
      description
        "total number of objects";
      uses FIB-GLOBAL-NUM-OBJECTS-ST;
    }
  }

  grouping FIB-GLOBAL-SUMMARY-COMMON-INFO {
    description
      "FIB Global summary common";
    leaf count {
      type uint32;
      description
        "Placeholder for common info counts";
    }
  }

  grouping FIB-GLOBAL-SUMMARY-TOTAL {
    description
      "FIB GLOBAL SUMMARY TOTAL";
    container common-info {
      description
        "FIB global Summary Common info";
      uses FIB-GLOBAL-SUMMARY-COMMON-INFO;
    }
    container total-counters {
      description
        "Aggregate counters of all protocols";
      uses FIB-GLOBAL-SUMMARY-COUNTS;
    }
    container global-summary {
      description
        "Global Summary";
      uses FIB-BAG-GLBL-SUM;
    }
  }

  grouping FIB-BAG-RSRC-NOTIFY-ST {
    description
      "FIB rsrc notify struct";
    leaf rsrc-proto {
      type Fib-bag-protocol;
      description
        "RSRC protocol";
    }
    leaf rsrc-mode {
      type string;
      description
        "RSRC mode";
    }
    leaf rsrc-type {
      type string;
      description
        "RSRC type";
    }
    leaf rsrc-value-type {
      type string;
      description
        "RSRC value type";
    }
    leaf rsrc-value {
      type uint32;
      description
        "RSRC value";
    }
  }

  grouping FIB-BAG-SUM-OBJ-ATTR {
    description
      "Object summary attributes";
    leaf-list summary-attribute-count {
      type uint32;
      max-elements "6";
      description
        "summary attribute count";
    }
  }

  grouping FIB-BAG-SUM-OBJ {
    description
      "Object summary";
    container object-attributes {
      description
        "Object's attributes";
      uses FIB-BAG-SUM-OBJ-ATTR;
    }
    leaf object-type {
      type uint32;
      description
        "Object type";
    }
    leaf object-name {
      type string;
      description
        "Object name";
    }
    leaf oor-mode-enabled {
      type boolean;
      description
        "LB OOR mode enabled";
    }
    leaf rsrc-enabled {
      type boolean;
      description
        "RSRC mode enabled";
    }
    leaf rsrc-nfns-sent-num {
      type uint32;
      description
        "Number of RSRC Nfns Sent";
    }
    leaf rsrc-arr-num {
      type uint8;
      description
        "RSRC array number of elements";
    }
    list rsrc-arr {
      max-elements "4";
      description
        "RSRC array";
      uses FIB-BAG-RSRC-NOTIFY-ST;
    }
  }
}
