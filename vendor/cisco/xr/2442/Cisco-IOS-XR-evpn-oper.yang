module Cisco-IOS-XR-evpn-oper {
  namespace "http://cisco.com/ns/yang/Cisco-IOS-XR-evpn-oper";
  prefix evpn-oper;

  import ietf-inet-types {
    prefix inet;
  }
  import ietf-yang-types {
    prefix yang;
  }
  import Cisco-IOS-XR-types {
    prefix xr;
  }
  import cisco-semver {
    prefix semver;
  }
  include Cisco-IOS-XR-evpn-oper-sub1 {
    revision-date 2024-06-18;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR evpn package operational data.
     
     This module contains definitions
     for the following management objects:
       evpn: EVPN Operational Table
     
     Copyright (c) 2013-2024 by Cisco Systems, Inc.
     All rights reserved.";

  revision 2024-06-18 {
    description
      "- Remove SA & SFA bools from ethernet-auto-discovery, internal-label, internal-id
       2024-06-18
         - Modify lb-mode enum values in ethernet-segment
       2024-06-18
         - Add lb-mode to ethernet-auto-discovery, internal-label, internal-id
       2024-03-08
         - Add local-split-horizon-group-id to l2vpn-evpn-es
       2024-02-09
         - Add l3vrf-label-mode to l2vpn-evpn-evi-detail
       2024-01-30
         - Remove mac-fsm-state leaf from macs
       2024-01-25
         - Added evi-bd-count to summary
       2024-01-20
         - Add host-down timer information to l2vpn-evpn-tep
       2024-01-12
         - Added ARP/ND local+remote info to mac
       2023-12-12
         - Remove ECMPDisable from EVPN label preffered-nh-mode
       2023-12-06
         - Add type disable to EVPN Mac Flush message mode
       2023-11-29
         - Add sg-id to EVPN mac entry
       2023-11-26
         - Add sg-id to EVPN label entry
       2023-11-26
         - Add service group to label resource type
       2023-11-17
         - Remove EVI from PBB core. Feature is no longer supported
       2023-10-02
         - Add interface name to tep entries
       2023-09-20
         - Add missing unresolved states to internal-label and internal-id entries
       2023-09-05
         - Add mac-fsm-state leaf to macs
       2023-08-31
         - Added MGMT_L2FIB_DATA_TYPE_SG defn
       2023-08-24
         - Removed multicast-source-connected
       2023-07-13
         - Add evpn-type-evpn-fxc-vlan-aware
       2023-07-10
         - Rename evpn-type-evpn-vpws-vlan-aware to evpn-type-evpn-fxc-vlan-aware
       2023-06-24
         - Added flow-label-mismatch EVPN Down reasons - Increased the value of evpn-down-reason-max
       2023-06-19
         - Added flow-label-mismatch BGP error
       2023-06-05
         - add non-revertive timer to Ethernet Segment
       2023-05-08
         - Add Signaled Designated Forwarder role to l2vpn-evpn-l2-attrs
       2023-05-04
         - Added Non-Revertive fields to Ethernet-Segment
       2023-04-26
         - Restructure EVPN path lists into an l2vpn-label-path-buffer container
       2023-04-25
         - Updated es-l3-sub-interface to hold evpn-srg-df-role.
       2023-03-27
         - Added L2 Attribute Extended Community to EVPN Inclusive Multicast.
       2023-01-27
         - Add EVPN ES Detail Table - Add EVPN ES L3 Sub-interface Table
       2022-11-15
         - Add inclusive-multicast-path-buffers to internal-label
       2022-10-28
         - Add ip-tunnel-path-buffer to internal-label
       2022-10-21
         Added hot-standby ES access signal mode.
       2022-08-29
         - Modifying key field of L2VPN-LABEL-PATH-BUFFER to support subelements fetch.
       2022-07-25
         - Added Label Type and IP to internal-label and internal-id schema.
       2022-06-27
         - Change keys to evpn-label-key and evpn-type in internal-label and internal-id
       2022-06-25
         - Add CAC info to policy info display
       2022-05-11
         - Changed ESI type from uint array to string
       2022-02-08
         - Removed vES pending up refcount
       2022-01-24
         - Added keys for multiple lists under evi-detail, added interface-name as a key in core-interface.
       2021-12-03
         - Added SRv6 locator flags
       2021-12-03
         - Added SRV6 SIDs to EVPN MACs.
       2021-12-01
         - Added originating-PE output on EAD, I-L.
       2021-09-27
         - Added keys for ethernet-segments/ethernet-segment list.
       2021-09-17
         - Added SRv6 ELAN list support in l2vpn_evpn_es bag.
       2021-09-14
         Display PLE-CEM attributes in xconnect info";
    semver:module-version "6.0.0";
  }
  revision 2021-08-13 {
    description
      "Added multicast SID information for SRv6 ELAN
       2021-07-07
          Updated main port gES-MAC field in bag for clarity
       2021-05-06
          Added union-path-buffer to l2vpn evpn label.
       2021-04-30
          Added vES nexthop list to EVPN Ethernet Segment
       2021-03-16
          Added support to retrieve multiple EVPN clients under ClientTable";
    semver:module-version "5.0.0";
  }
  revision 2020-05-05 {
    description
      "changes related to treat SRv6 and SID as well-known when parsing XML for yang
       2020-04-02
           EVPN DF Election Synchronization with NTP related changes";
    semver:module-version "4.0.0";
  }
  revision 2019-12-20 {
    description
      "EVPN SRv6 related changes";
    semver:module-version "3.0.0";
  }
  revision 2019-04-05 {
    description
      "Establish semantic version baseline.";
    semver:module-version "2.0.0";
  }
  revision 2018-09-26 {
    description
      "Duplicate detection parameters config moved from l2vpn to l2rib.";
  }
  revision 2017-09-07 {
    description
      "Fixed type translation error.";
  }
  revision 2017-05-01 {
    description
      "Fixing backward compatibility error in module.";
  }
  revision 2015-11-09 {
    description
      "IOS XR 6.0 revision.";
  }

  typedef Rd-addr-index {
    type uint32 {
      range "0..65535";
    }
    description
      "Rd addr index";
  }

  typedef Bgp-route-target-role {
    type enumeration {
      enum "both" {
        value 0;
        description
          "Both Import and export roles";
      }
      enum "import" {
        value 1;
        description
          "Import role";
      }
      enum "export" {
        value 2;
        description
          "Export role";
      }
    }
    description
      "Bgp route target role";
  }

  typedef Evpn-bgp-encap {
    type enumeration {
      enum "unknown" {
        value 0;
        description
          "Unknown Encapsulation";
      }
      enum "vx-lan" {
        value 8;
        description
          "VxLAN Encapsulation";
      }
      enum "mpls" {
        value 10;
        description
          "MPLS Encapsulation";
      }
      enum "es-global" {
        value 253;
        description
          "ES GLOBAL Encapsulation";
      }
      enum "route-sync" {
        value 254;
        description
          "ROUTE SYNC Encapsulation";
      }
      enum "srv6" {
        value 255;
        description
          "SRv6 Encapsulation";
      }
    }
    description
      "Evpn bgp encap";
  }

  typedef Evpn-client-source {
    type enumeration {
      enum "local" {
        value 0;
        description
          "Source Local";
      }
      enum "remote" {
        value 1;
        description
          "Source Remote";
      }
    }
    description
      "Evpn client source";
  }

  typedef Evpn-client {
    type enumeration {
      enum "igmpsn" {
        value 0;
        description
          "IGMPSN client";
      }
      enum "igmp" {
        value 1;
        description
          "IGMP client";
      }
    }
    description
      "Evpn client";
  }

  typedef Evpnrdas-display-range {
    type uint32 {
      range "0..4294967295";
    }
    description
      "Evpnrdas display range";
  }

  typedef Rdas-index {
    type uint32 {
      range "0..4294967295";
    }
    description
      "Rdas index";
  }

  typedef Evpn-internal-label {
    type enumeration {
      enum "evpn-esi" {
        value 0;
        description
          "ESI based EVPN Label";
      }
      enum "evpn-ip-nh" {
        value 1;
        description
          "IP Nexthop based EVPN Label";
      }
      enum "ip-tunnel" {
        value 2;
        description
          "IP Tunnel based EVPN Label";
      }
    }
    description
      "Evpn internal label";
  }

  typedef Bgp-route-target-format {
    type enumeration {
      enum "none" {
        value 0;
        description
          "No route target";
      }
      enum "two-byte-as" {
        value 1;
        description
          "2 Byte AS:nn format";
      }
      enum "four-byte-as" {
        value 2;
        description
          "4 byte AS:nn format";
      }
      enum "ipv4-address" {
        value 3;
        description
          "IP:nn format";
      }
      enum "es-import" {
        value 1538;
        description
          "a.a.i format";
      }
    }
    description
      "Bgp route target format";
  }

  typedef Evpn-multicast-entry {
    type enumeration {
      enum "join" {
        value 0;
        description
          "Sync join entry";
      }
      enum "leave" {
        value 1;
        description
          "Sync leave entry";
      }
      enum "proxy" {
        value 2;
        description
          "Proxy join entry";
      }
    }
    description
      "Evpn multicast entry";
  }

  grouping ETHERNET-SEGMENT-DETAIL-TABLE {
    description
      "Common node of active, standby, node";
    container ethernet-segment-details {
      description
        "EVPN Ethernet-Segment Detail Table";
      list ethernet-segment-detail {
        key "interface-name esi";
        description
          "EVPN Ethernet-Segment Detailed Container";
        container es-l3-sub-interfaces {
          description
            "EVPN ES Layer-3 SubInterface Table";
          list es-l3-sub-interface {
            key "sub-interface-name";
            description
              "EVPN ES Layer-3 SubInterface Entry";
            leaf sub-interface-name {
              type xr:Interface-name;
              description
                "Sub-Interface Name";
            }
            uses EVPN-ES-L3-SUBIF;
          }
        }
        container ethernet-segment-detail-info {
          description
            "EVPN Ethernet-Segment Detailed Entry";
          uses L2VPN-EVPN-ES;
        }
        leaf interface-name {
          type xr:Interface-name;
          description
            "Interface";
        }
        leaf esi {
          type xr:Cisco-ios-xr-string {
            length "1..24";
          }
          description
            "ES id";
        }
      }
    }
  }

  grouping EVI-TABLE {
    description
      "Common node of active, standby, node";
    container evis {
      description
        "L2VPN EVPN EVI Table";
      list evi {
        description
          "L2VPN EVPN EVI Entry";
        leaf evi {
          type uint32;
          description
            "EVPN id";
        }
        leaf encapsulation {
          type uint32;
          description
            "Encap";
        }
        uses L2VPN-EVPN-EVI-SUMMARY;
      }
    }
  }

  grouping SEGMENT-ROUTING-SRV6 {
    description
      "Common node of active, standby, node";
    container segment-routing-srv6 {
      description
        "L2VPN EVPN Segment Routing SRv6";
      uses L2VPN-EVPN-SRV6;
    }
  }

  grouping AC-ID-TABLE {
    description
      "Common node of active, standby, node";
    container ac-ids {
      description
        "EVPN AC ID table";
      list ac-id {
        description
          "EVPN AC ID table";
        leaf evi {
          type uint32;
          description
            "EVPN id";
        }
        leaf ac-id {
          type uint32;
          description
            "AC ID";
        }
        uses L2VPN-ATOM-ACID;
      }
    }
  }

  grouping EVI-DETAIL {
    description
      "Common node of active, standby, node";
    container evi-detail {
      description
        "L2VPN EVI Detail Table";
      container elements {
        description
          "EVI BGP RT Detail Info Elements";
        list element {
          key "evi encapsulation";
          description
            "EVI BGP RT Detail Info";
          leaf evi {
            type uint32;
            description
              "EVPN id";
          }
          leaf encapsulation {
            type uint32;
            description
              "Encap";
          }
          uses L2VPN-EVPN-EVI-DETAIL;
        }
      }
      container evi-children {
        description
          "Container for all EVI detail info";
        container neighbors {
          description
            "EVPN Neighbor table";
          list neighbor {
            key "evi encapsulation neighbor-ip";
            description
              "EVPN Neighbor table";
            leaf evi {
              type uint32;
              description
                "EVPN id";
            }
            leaf encapsulation {
              type uint32;
              description
                "Encap";
            }
            leaf neighbor-ip {
              type inet:ip-address-no-zone;
              description
                "Neighbor IP";
            }
            uses L2VPN-EVPN-NEIGHBOR;
          }
        }
        container ethernet-auto-discoveries {
          description
            "EVPN Ethernet Auto-Discovery table";
          list ethernet-auto-discovery {
            key "evi encapsulation esi ethernet-tag";
            description
              "EVPN Ethernet Auto-Discovery Entry";
            leaf evi {
              type uint32;
              description
                "EVPN id";
            }
            leaf encapsulation {
              type uint32;
              description
                "Encap";
            }
            leaf esi {
              type xr:Cisco-ios-xr-string {
                length "1..24";
              }
              description
                "ES id";
            }
            leaf ethernet-tag {
              type uint32;
              description
                "Ethernet Tag ID";
            }
            uses L2VPN-EVPN-EAD;
          }
        }
        container inclusive-multicasts {
          description
            "L2VPN EVPN IMCAST table";
          list inclusive-multicast {
            key "evi encapsulation ethernet-tag originating-ip";
            description
              "L2VPN EVPN IMCAST table";
            leaf evi {
              type uint32;
              description
                "EVPN id";
            }
            leaf encapsulation {
              type uint32;
              description
                "Encap";
            }
            leaf ethernet-tag {
              type uint32;
              description
                "Ethernet Tag";
            }
            leaf originating-ip {
              type inet:ip-address-no-zone;
              description
                "Originating IP";
            }
            uses L2VPN-EVPN-IMCAST;
          }
        }
        container route-targets {
          description
            "L2VPN EVPN EVI RT Child Table";
          list route-target {
            description
              "L2VPN EVPN EVI RT Table";
            leaf evi {
              type uint32;
              description
                "EVPN id";
            }
            leaf encapsulation {
              type uint32;
              description
                "Encap";
            }
            leaf role {
              type Bgp-route-target-role;
              description
                "Role of the route target";
            }
            leaf format {
              type Bgp-route-target-format;
              description
                "Format of the route target";
            }
            leaf as {
              type Evpnrdas-display-range;
              description
                "Two or Four byte AS Number";
            }
            leaf as-index {
              type Rdas-index;
              description
                "RT AS Index";
            }
            leaf addr-index {
              type Rd-addr-index;
              description
                "RT IP Index";
            }
            leaf address {
              type inet:ipv4-address-no-zone;
              description
                "RT IPv4 Address";
            }
            uses L2VPN-EVPN-EVI-BGP-RT;
          }
        }
        container macs {
          description
            "L2VPN EVPN EVI MAC table";
          list mac {
            description
              "L2VPN EVPN MAC table";
            leaf evi {
              type uint32;
              description
                "EVPN id";
            }
            leaf encapsulation {
              type uint32;
              description
                "Encap";
            }
            leaf ethernet-tag {
              type uint32;
              description
                "Ethernet Tag ID";
            }
            leaf mac-address {
              type yang:mac-address;
              description
                "MAC address";
            }
            leaf ip-address {
              type inet:ip-address-no-zone;
              description
                "IP Address";
            }
            uses L2VPN-EVPN-MAC;
          }
        }
      }
    }
  }

  grouping IGMP-TABLE {
    description
      "Common node of active, standby, node";
    container igmps {
      description
        "EVPN IGMP table";
      list igmp {
        description
          "IGMP Route";
        leaf client-type {
          type Evpn-client;
          description
            "Client type";
        }
        leaf source-type {
          type Evpn-client-source;
          description
            "Source type";
        }
        leaf entry-type {
          type Evpn-multicast-entry;
          description
            "Join, Leave or Proxy entry";
        }
        leaf evi {
          type uint32;
          description
            "EVI";
        }
        leaf esi {
          type xr:Cisco-ios-xr-string {
            length "1..24";
          }
          description
            "ES id";
        }
        leaf ethernet-tag {
          type uint32;
          description
            "Ethernet Tag ID";
        }
        leaf src-ip {
          type inet:ip-address-no-zone;
          description
            "Source IP Address";
        }
        leaf grp-ip {
          type inet:ip-address-no-zone;
          description
            "Group IP Address";
        }
        leaf originating-ip {
          type inet:ip-address-no-zone;
          description
            "Originating IP Address";
        }
        leaf bd-id {
          type uint32;
          description
            "BD ID";
        }
        leaf bp-xcid {
          type uint32;
          description
            "BP XCID";
        }
        leaf vrf-id {
          type uint32;
          description
            "VRF ID";
        }
        leaf sub-interface-name {
          type xr:Interface-name;
          description
            "Sub-interface name";
        }
        uses L2VPN-EVPN-IGMP;
      }
    }
  }

  grouping INTERNAL-ID-TABLE {
    description
      "Common node of active, standby, node";
    container internal-ids {
      description
        "EVPN Internal ID Table";
      list internal-id {
        description
          "L2VPN EVPN Internal ID";
        leaf label-type {
          type Evpn-internal-label;
          description
            "EVPN Label Type";
        }
        leaf evi {
          type uint32;
          description
            "EVPN id";
        }
        leaf encapsulation {
          type Evpn-bgp-encap;
          description
            "Encap";
        }
        leaf esi {
          type xr:Cisco-ios-xr-string {
            length "1..24";
          }
          description
            "ES id";
        }
        leaf ip {
          type inet:ip-address-no-zone;
          description
            "IP Nexthop";
        }
        leaf tag {
          type uint32;
          description
            "Ethernet Tag ID or NVE ID";
        }
        uses L2VPN-EVPN-LABEL;
      }
    }
  }

  grouping ETHERNET-SEGMENT-TABLE {
    description
      "Common node of active, standby, node";
    container ethernet-segments {
      description
        "EVPN Ethernet-Segment Table";
      list ethernet-segment {
        key "interface-name esi";
        description
          "EVPN Ethernet-Segment Entry";
        leaf interface-name {
          type xr:Interface-name;
          description
            "Interface";
        }
        leaf esi {
          type xr:Cisco-ios-xr-string {
            length "1..24";
          }
          description
            "ES id";
        }
        uses L2VPN-EVPN-ES;
      }
    }
  }

  grouping CLIENT-TABLE {
    description
      "Common node of active, standby, node";
    container clients {
      description
        "L2VPN EVPN Client";
      list client {
        key "client-type";
        description
          "L2VPN EVPN Client";
        leaf client-type {
          type Evpn-client;
          description
            "Client type";
        }
        uses L2VPN-EVPN-CLIENT;
      }
    }
  }

  grouping REMOTE-SHG-TABLE {
    description
      "Common node of active, standby, node";
    container remote-shgs {
      description
        "EVPN Remote SHG table";
      list remote-shg {
        key "evi esi";
        description
          "EVPN Remote SHG";
        leaf evi {
          type uint32;
          description
            "EVPN id";
        }
        leaf esi {
          type xr:Cisco-ios-xr-string {
            length "1..24";
          }
          description
            "ES id";
        }
        uses L2VPN-EVPN-REMOTE-SHG;
      }
    }
  }

  grouping TEP-TABLE {
    description
      "Common node of active, standby, node";
    container teps {
      description
        "L2VPN EVPN TEP Table";
      list tep {
        key "tep-id";
        description
          "L2VPN EVPN TEP Entry";
        container tep-notification-entries {
          description
            "L2VPN EVPN TEP Notification Table";
          list tep-notification-entry {
            key "index";
            description
              "L2VPN EVPN TEP Notification Entry";
            leaf index {
              type uint32;
              description
                "TEP notification index";
            }
            uses L2VPN-EVPN-TEP-NOTIFICATION-ENTRY;
          }
        }
        container tep-info {
          description
            "L2VPN EVPN TEP Entry";
          uses L2VPN-EVPN-TEP;
        }
        leaf tep-id {
          type uint32;
          description
            "TEP id";
        }
      }
    }
  }

  grouping SUMMARY {
    description
      "Common node of active, standby, node";
    container summary {
      description
        "L2VPN EVPN Summary";
      uses L2VPN-EVPN-SUMMARY;
    }
  }

  grouping EVPN-GROUP-TABLE {
    description
      "Common node of active, standby, node";
    container evpn-groups {
      description
        "EVPN Group Table";
      list evpn-group {
        key "group-number";
        description
          "EVPN Group information";
        leaf group-number {
          type uint32 {
            range "1..4294967295";
          }
          description
            "EVPN group number";
        }
        uses EVPN-GRP-INFO;
      }
    }
  }

  grouping INTERNAL-LABEL-TABLE {
    description
      "Common node of active, standby, node";
    container internal-labels {
      description
        "EVPN Internal Label Table";
      list internal-label {
        description
          "L2VPN EVPN Internal Label";
        leaf label-type {
          type Evpn-internal-label;
          description
            "EVPN Label Type";
        }
        leaf evi {
          type uint32;
          description
            "EVPN id";
        }
        leaf encapsulation {
          type Evpn-bgp-encap;
          description
            "Encap";
        }
        leaf esi {
          type xr:Cisco-ios-xr-string {
            length "1..24";
          }
          description
            "ES id";
        }
        leaf ip {
          type inet:ip-address-no-zone;
          description
            "IP Nexthop";
        }
        leaf tag {
          type uint32;
          description
            "Ethernet Tag ID or NVE ID";
        }
        uses L2VPN-EVPN-LABEL;
      }
    }
  }

  container evpn {
    config false;
    description
      "EVPN Operational Table";
    container nodes {
      description
        "Table of EVPN operational data for a particular
         node";
      list node {
        key "node-id";
        description
          "EVPN operational data for a particular node";
        leaf node-id {
          type xr:Node-id;
          description
            "Location";
        }
        uses EVPN-GROUP-TABLE;
        uses REMOTE-SHG-TABLE;
        uses IGMP-TABLE;
        uses EVI-TABLE;
        uses SUMMARY;
        uses EVI-DETAIL;
        uses CLIENT-TABLE;
        uses TEP-TABLE;
        uses INTERNAL-LABEL-TABLE;
        uses INTERNAL-ID-TABLE;
        uses SEGMENT-ROUTING-SRV6;
        uses ETHERNET-SEGMENT-TABLE;
        uses AC-ID-TABLE;
        uses ETHERNET-SEGMENT-DETAIL-TABLE;
      }
    }
    container active {
      description
        "Active EVPN operational data";
      uses EVPN-GROUP-TABLE;
      uses REMOTE-SHG-TABLE;
      uses IGMP-TABLE;
      uses EVI-TABLE;
      uses SUMMARY;
      uses EVI-DETAIL;
      uses CLIENT-TABLE;
      uses TEP-TABLE;
      uses INTERNAL-LABEL-TABLE;
      uses INTERNAL-ID-TABLE;
      uses SEGMENT-ROUTING-SRV6;
      uses ETHERNET-SEGMENT-TABLE;
      uses AC-ID-TABLE;
      uses ETHERNET-SEGMENT-DETAIL-TABLE;
    }
    container standby {
      description
        "Standby EVPN operational data";
      uses EVPN-GROUP-TABLE;
      uses REMOTE-SHG-TABLE;
      uses IGMP-TABLE;
      uses EVI-TABLE;
      uses SUMMARY;
      uses EVI-DETAIL;
      uses CLIENT-TABLE;
      uses TEP-TABLE;
      uses INTERNAL-LABEL-TABLE;
      uses INTERNAL-ID-TABLE;
      uses SEGMENT-ROUTING-SRV6;
      uses ETHERNET-SEGMENT-TABLE;
      uses AC-ID-TABLE;
      uses ETHERNET-SEGMENT-DETAIL-TABLE;
    }
  }
}
