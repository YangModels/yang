module Cisco-IOS-XR-infra-xtc-oper {
  namespace "http://cisco.com/ns/yang/Cisco-IOS-XR-infra-xtc-oper";
  prefix infra-xtc-oper;

  import ietf-inet-types {
    prefix inet;
  }
  import Cisco-IOS-XR-types {
    prefix xr;
  }
  import cisco-semver {
    prefix semver;
  }
  include Cisco-IOS-XR-infra-xtc-oper-sub2 {
    revision-date 2024-08-01;
  }
  include Cisco-IOS-XR-infra-xtc-oper-sub1 {
    revision-date 2024-08-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-xtc package operational data.
     
     This module contains definitions
     for the following management objects:
       pce-lsp-data: PCE LSP's data
       pce-peer: PCE peer data
       pce-topology: PCE topology data
       pce: PCE operational data
     
     Copyright (c) 2013-2024 by Cisco Systems, Inc.
     All rights reserved.";

  revision 2024-08-01 {
    description
      "Modified name of metric type value to include IANA
       2024-06-11
         Added grpc service-instance list
       2024-04-22
         Added Candidate Path and Instance in TreeSID
       2024-03-18
         Added SRv6 MSD list to peer PCEP info
       2024-03-01
         Added Cleanup Timer in TreeSID
       2023-11-30
         Added CommonTopologyTable
       2023-10-12
         Added fields for path-type of a policy and candidate path
       2023-08-08
         Extended SR-MPLS CSPF computation oper command with exclude IP constraint for both paths as well as affinities constraint for second path. Extended LSP display to show received XRO values, as well as added indication of shortest-path flag in disjoint constraints.
       2023-07-26
         Added protection type to BWoD sub-delegation.
       2023-07-04
         Add CPATH Name to cmn bag to display it using show pce lsp private command.
       2023-06-20
         Display override rule override for SID protection-type constraint.
       2023-05-04
         Display Flex-Algo information for P2MP policies.
       2023-04-27
         Add override rule override pcep advertise admin down when no path configure.
       2023-04-06
         Add a field to differentiate SRv6 path in path work group
       2023-03-30
         Changed work group operational data to use an ID based system as the key instead of a complex set of attributes.
       2023-03-21
         Added SID-algo in override rule
       2023-03-09
         Added protection type for path work group
       2023-03-06
         Updated PM CPath info and PM Stats bag
       2023-02-27
         Added fields to differentiate IPV4 or IPV6 TREESID policies
       2023-01-24
         Added fields for Flex-algo ASLA attributes on IPv4 and IPv6 links
       2023-01-18
         Updated description of flex-algo leaf to SID algorithm in cspf-sr-mpls.
       2022-11-11
         Added distribute-ls policy operational data.
       2022-10-20
         Added initiated tunnel operational information including PCE-INITIATED-TUN-BAG grouping.
       2022-09-01
         Added field to display p2mp rest initiated treeSID.
       2022-07-29
         changed default value of initial-verify-startup timer from 120 seconds to 180 seconds.
       2022-07-11
         Added leaves for blocked reoptimization and adjacency SID only
       2022-06-28
         Added weight outputs to srv6 nexthop and lsp sls.
       2022-06-02
         Removed prefix-metric entry from the topology node.
       2022-05-13
         TreeSID PCE HA, added few fields on oper commands
       2022-04-29
         Added some field in oper bag for Dynamic CS policies
       2022-04-26
         TreeSID PCE HA, oper enhancements
       2022-03-09
         Pce-sr-sid enum updated to add unknown-srv6sid element
       2022-03-03
         Modified description for override rules related leaves
       2022-03-03
         Added capability-srv6 in brief-pcep-information container
       2022-02-24
         Added PCE-BWOD-BEST-CLIENT-BAG and PCE-BWOD-SUB-DELEGATION-BAG grouping.
       2022-01-28
         Added maximum-delay in PCE-LSP-DETAIL-INFO grouping.
       2022-01-27
         Adding performance-statistics class
       2022-01-17
         Change the type of extended-value leaf from leaf-list to list.
       2022-01-14
         Added support for metric bounds for CSPF
       2022-01-10
         Added sid-algorithm and sid-algorithm-set in PCE-SIBLING-SYNCED-LSP-BAG grouping. Added sid-algorithm and sid-algorithm-set in PCE-LSP-DETAIL-INFO grouping.
       2022-01-07
         Added SID algorithm constraint to LSP.
       2021-12-14
         Moving algorithm and computation time in the path query results object
       2021-11-21
         Added prefix-metric entry in the topology node.
       2021-11-09
         Added unreliable flag and update drop count in topology summary bag.
       2021-10-21
         Adding algorithm and computation time to path query results
       2021-10-08
         Added support for override rules";
    semver:module-version "5.0.0";
  }
  revision 2021-09-28 {
    description
      "Added protection type set in candidate path constraints.
       2021-08-27
          Added binding-sid to pce sibling synced lsp.
       2021-06-21
          un-hide cspf-srv6 option in cspf srv6 path calculation.
       2021-05-26
          Added keys to topology-summary list.";
    semver:module-version "4.0.0";
  }
  revision 2021-04-22 {
    description
      "Added TE metric field for Flex-algo ASLA.
       2021-04-08
           Change protection type from integer to enum.
       2021-03-31
           Added new enumeration Api-peer-stats-info-oper. Changed type of type in API-PEER-STATS-INFO to use Api-peer-stats-info-oper. This is a non backward compatible change.
       2021-03-04
           Added MSD list per topology link. Added SRLB list per topology node.
       2021-01-29
           Updated SRv6 Endpoint function from int to enum.
       2020-09-16
           Adding operational nodes for new features path invalidation drop protected and unprotected path Operational nodes for PCE segment-routing traffic-eng policy
       2020-09-01
           Added uB6SID field in the LSP object
       2020-08-18
           Added SRv6 LSP details fields in the LSP object
       2020-07-13
           Added NodeID fields in the uN SID object in the IPv6 topology.
       2020-04-20
           Added fields in the PCE IPv6 link object.";
    semver:module-version "3.0.0";
  }
  revision 2020-03-17 {
    description
      "Add flex-algo related operational nodes. Updated description of statistics-nodes. Add SR-PAG related operational nodes. Add PCE authentication related operational nodes.
       2020-02-03
         Added TCP AuthenticationOption related operational model. Implemented show pce authentication. Added classes AuthenticationKeyTable and AuthenticationKey.
       2019-11-07
         Adding leaf preference, leaf interface-name, and leaf profile-id to support a new HTTP API bindpoint for sibling PCEs.
       2019-10-09
         Adding enum sr-flex-algo-prefix-sid, enum pce-cspf-flex-algo-definition-mistmatch, leaf flex-algo-prefix-sids, list sr-flex-algo, and container flex-algos to support Flex-algo info.";
    semver:module-version "2.0.0";
  }
  revision 2019-10-02 {
    description
      "Added REST peer statistic information.
       2019-09-27
         Implement new show pce lsp and show pce initiated tunnels commands for Optima";
    semver:module-version "1.1.0";
  }
  revision 2019-04-05 {
    description
      "Establish semantic version baseline.";
    semver:module-version "1.0.0";
  }
  revision 2017-09-07 {
    description
      "Fixed type translation error.";
  }
  revision 2017-08-24 {
    description
      "Added C flag to pcep flags.";
  }
  revision 2017-06-26 {
    description
      "Change identifiers to be more readable.";
  }
  revision 2017-05-01 {
    description
      "Fixing backward compatibility error in module.";
  }
  revision 2016-05-31 {
    description
      "Revision description string.";
  }
  revision 2015-11-09 {
    description
      "IOS XR 6.0 revision.";
  }

  typedef Pce-address-family-summary {
    type enumeration {
      enum "ipv4" {
        value 1;
        description
          "IPv4 address family";
      }
      enum "ipv6" {
        value 2;
        description
          "IPv6 address family";
      }
      enum "all" {
        value 3;
        description
          "All address families";
      }
    }
    description
      "Pce address family summary";
  }

  typedef Pceigp-protocol {
    type enumeration {
      enum "unknown" {
        value 0;
        description
          "Unknown protocol";
      }
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
    }
    description
      "Pceigp protocol";
  }

  typedef Pceigp-protocol-summary {
    type enumeration {
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
      enum "all" {
        value 5;
        description
          "All protocols";
      }
    }
    description
      "Pceigp protocol summary";
  }

  typedef Pce-asso {
    type enumeration {
      enum "unknown" {
        value 0;
        description
          "Unknown type";
      }
      enum "link" {
        value 1;
        description
          "LINK";
      }
      enum "node" {
        value 2;
        description
          "NODE";
      }
      enum "srlg" {
        value 3;
        description
          "SRLG";
      }
    }
    description
      "Pce asso";
  }

  typedef Xtc-adj-sid-protection {
    type enumeration {
      enum "protected-preferred" {
        value 0;
        description
          "Protected adj SID preferred";
      }
      enum "unprotected-only" {
        value 1;
        description
          "Unprotected adj SID only";
      }
      enum "protected-only" {
        value 2;
        description
          "Protected adj SID only";
      }
      enum "unprotected-preferred" {
        value 3;
        description
          "Unprotected adj SID preferred";
      }
    }
    description
      "Xtc adj sid protection";
  }

  typedef Pce-address-family {
    type enumeration {
      enum "ipv4" {
        value 1;
        description
          "IPv4 address family";
      }
      enum "ipv6" {
        value 2;
        description
          "IPv6 address family";
      }
    }
    description
      "Pce address family";
  }

  grouping PEER-TABLE {
    description
      "Common node of pce, pce-peer";
    container peer-infos {
      description
        "Peers database in XTC";
      list peer-info {
        key "peer-address";
        description
          "PCE peer information";
        leaf peer-address {
          type inet:ip-address-no-zone;
          description
            "Peer Address";
        }
        uses PCE-PEER-BAG;
      }
    }
  }

  grouping INITIATED-TUN-TABLE {
    description
      "Common node of pce, pce-lsp-data";
    container initiated-tun-infos {
      description
        "Initiated Tunnel database in XTC";
      list initiated-tun-info {
        description
          "Initiated Tunnel information";
        leaf pcc-address {
          type inet:ip-address-no-zone;
          description
            "PCC Address";
        }
        leaf tunnel-name {
          type string;
          description
            "Tunnel name";
        }
        uses PCE-INITIATED-TUN-BAG;
      }
    }
  }

  grouping PEER-DETAIL-TABLE {
    description
      "Common node of pce, pce-peer";
    container peer-detail-infos {
      description
        "Detailed peers database in XTC";
      list peer-detail-info {
        key "peer-address";
        description
          "Detailed PCE peer information";
        leaf peer-address {
          type inet:ip-address-no-zone;
          description
            "Peer Address";
        }
        uses PCE-PEER-DETAIL-BAG;
      }
    }
  }

  grouping COMMON-TOPOLOGY-NODE-TABLE {
    description
      "Common node of pce, pce-topology";
    container common-topology-nodes {
      description
        "Node database in XTC";
      list common-topology-node {
        key "ipv4-router-id ipv6-router-id node-identifier";
        description
          "Node information. Only one of the keys will be
           set, rest is set to zeros. With IPv4RouterID
           beeing the highest priority key";
        leaf ipv4-router-id {
          type inet:ip-address-no-zone;
          description
            "IPv4 router ID or 0.0.0.0 if not set";
        }
        leaf ipv6-router-id {
          type inet:ip-address-no-zone;
          description
            "IPv6 router ID or :: if not set";
        }
        leaf node-identifier {
          type uint32;
          description
            "Node Identifier or 0 if not set";
        }
        uses TOPO-NODE-BAG;
      }
    }
  }

  grouping PREFIX-TABLE {
    description
      "Common node of pce, pce-topology";
    container prefix-infos {
      description
        "Prefixes database in XTC";
      list prefix-info {
        key "node-identifier";
        description
          "PCE prefix information";
        leaf node-identifier {
          type uint32;
          description
            "Node ID";
        }
        uses PCE-PFX-BAG;
      }
    }
  }

  grouping TUNNEL-TABLE {
    description
      "Common node of pce, pce-lsp-data";
    container tunnel-infos {
      description
        "Tunnel database in XTC";
      list tunnel-info {
        key "peer-address plsp-id tunnel-name";
        description
          "Tunnel information";
        leaf peer-address {
          type inet:ip-address-no-zone;
          description
            "Peer Address";
        }
        leaf plsp-id {
          type uint32;
          description
            "PCEP LSP ID";
        }
        leaf tunnel-name {
          type string;
          description
            "Tunnel name";
        }
        uses PCE-TUN-BAG;
      }
    }
  }

  grouping REMOTE-PREFIX-TABLE {
    description
      "Common node of pce, pce-topology";
    container remote-prefixes {
      description
        "Remote Prefixes database in PCE";
      list remote-prefix {
        key "remote-pce-id";
        description
          "PCE remote prefix information";
        leaf remote-pce-id {
          type uint32;
          description
            "Remote PCE ID";
        }
        uses PCE-REMOTE-PFX-BAG;
      }
    }
  }

  grouping LSP-SUMMARY {
    description
      "Common node of pce, pce-lsp-data";
    container lsp-summary {
      description
        "LSP summary database in XTC";
      uses PCE-LSP-SUMMARY-BAG;
    }
  }

  grouping TOPOLOGY-SUMMARY-TABLE {
    description
      "Common node of pce, pce-topology";
    container topology-summaries {
      description
        "Node summary database in XTC";
      list topology-summary {
        key "af protocol";
        description
          "Node summary database in XTC";
        leaf af {
          type Pce-address-family-summary;
          description
            "Only show data related to the specified
             address family";
        }
        leaf protocol {
          type Pceigp-protocol-summary;
          description
            "Match nodes from the specified IGP protocol";
        }
        uses PCE-NODE-SUMMARY-BAG;
      }
    }
  }

  grouping TOPOLOGY-NODE-TABLE {
    description
      "Common node of pce, pce-topology";
    container topology-nodes {
      description
        "Node database in XTC";
      list topology-node {
        key "node-identifier";
        description
          "Node information";
        leaf node-identifier {
          type uint32;
          description
            "Node Identifier";
        }
        uses PCE-XTC-NODE-BAG;
      }
    }
  }

  grouping TUNNEL-DETAIL-TABLE {
    description
      "Common node of pce, pce-lsp-data";
    container tunnel-detail-infos {
      description
        "Detailed tunnel database in XTC";
      list tunnel-detail-info {
        key "peer-address plsp-id tunnel-name";
        description
          "Detailed tunnel information";
        leaf peer-address {
          type inet:ip-address-no-zone;
          description
            "Peer Address";
        }
        leaf plsp-id {
          type uint32;
          description
            "PCEP LSP ID";
        }
        leaf tunnel-name {
          type string;
          description
            "Tunnel name";
        }
        uses PCE-TUN-DETAIL-BAG;
      }
    }
  }

  container pce-lsp-data {
    config false;
    description
      "PCE LSP's data";
    uses TUNNEL-TABLE;
    uses INITIATED-TUN-TABLE;
    uses LSP-SUMMARY;
    uses TUNNEL-DETAIL-TABLE;
  }
  container pce-peer {
    config false;
    description
      "PCE peer data";
    uses PEER-DETAIL-TABLE;
    uses PEER-TABLE;
  }
  container pce-topology {
    config false;
    description
      "PCE topology data";
    uses REMOTE-PREFIX-TABLE;
    uses TOPOLOGY-NODE-TABLE;
    uses TOPOLOGY-SUMMARY-TABLE;
    uses PREFIX-TABLE;
    uses COMMON-TOPOLOGY-NODE-TABLE;
  }
  container pce {
    config false;
    description
      "PCE operational data";
    container authentication-keys {
      description
        "Authentication keys";
      list authentication-key {
        key "ip-address";
        description
          "PCE peer IP address";
        leaf ip-address {
          type inet:ip-address-no-zone;
          description
            "IP address";
        }
        uses PCE-PEER-AUTH-OPTION-BAG;
      }
    }
    container cspf-sr-mpls {
      description
        "CSPF for SR MPLS path info";
      container cspf-sr-mpls-paths {
        description
          "This table models the path calculation
           capabilities in XTC.A GET operation for the
           complete table will return no entries.";
        list cspf-sr-mpls-path {
          description
            "A GET operation on this class returns the path
             .";
          leaf af {
            type uint32;
            description
              "Address Family";
          }
          leaf source1 {
            type inet:ip-address-no-zone;
            description
              "Source of path 1";
          }
          leaf destination1 {
            type inet:ip-address-no-zone;
            description
              "Destination of path 1";
          }
          leaf metric-type {
            type uint32;
            description
              "Metric type";
          }
          leaf source2 {
            type inet:ip-address-no-zone;
            description
              "Source of path 2";
          }
          leaf destination2 {
            type inet:ip-address-no-zone;
            description
              "Destination of path 2";
          }
          leaf disjoint-level {
            type uint32;
            description
              "Disjointness level";
          }
          leaf disjoint-strict {
            type uint32;
            description
              "Strict disjointness required";
          }
          leaf shortest-path {
            type uint32;
            description
              "Whether path 1 or 2 should be shortest";
          }
          leaf msd1 {
            type uint32;
            description
              "MSD for path 1";
          }
          leaf msd2 {
            type uint32;
            description
              "MSD for path 2";
          }
          leaf relative-margin {
            type uint32;
            description
              "Relative Margin";
          }
          leaf absolute-margin {
            type uint32;
            description
              "Absolute Margin";
          }
          leaf affinity-include-all {
            type uint32;
            description
              "Affinity include-all constraint";
          }
          leaf affinity-include-any {
            type uint32;
            description
              "Affinity include-any constraint";
          }
          leaf affinity-exclude-any {
            type uint32;
            description
              "Affinity exclude-any constraint";
          }
          leaf affinity-include-all2 {
            type uint32;
            description
              "Affinity include-all constraint for path 2";
          }
          leaf affinity-include-any2 {
            type uint32;
            description
              "Affinity include-any constraint for path 2";
          }
          leaf affinity-exclude-any2 {
            type uint32;
            description
              "Affinity exclude-any constraint for path 2";
          }
          leaf protection-type1 {
            type Xtc-adj-sid-protection;
            description
              "Protection type for path 1";
          }
          leaf protection-type2 {
            type Xtc-adj-sid-protection;
            description
              "Protection type for path 2";
          }
          leaf flex-algo {
            type uint32;
            description
              "SID algorithm number. 0, 1, 128-255";
          }
          leaf anycast-include {
            type boolean;
            description
              "Perform anycast SID inclusion";
          }
          leaf bound-igp {
            type uint32;
            description
              "IGP metric bound";
          }
          leaf bound-te {
            type uint32;
            description
              "TE metric bound";
          }
          leaf bound-latency {
            type uint32;
            description
              "Latency metric bound";
          }
          leaf bound-hop-count {
            type uint32;
            description
              "Hop-count metric bound";
          }
          leaf exclude-ip-list {
            type string;
            description
              "Exclude IP list";
          }
          leaf exclude-ip-list2 {
            type string;
            description
              "Exclude IP list of path 2";
          }
          uses PCE-SR-MPLS-PATH-LIST-BAG;
        }
      }
    }
    container segment-routing {
      description
        "Segment-Routing related data";
      container traffic-engineering {
        description
          "Traffic-engineering related data";
        container policies {
          description
            "PCE policies";
          list policy {
            description
              "PCE policy";
            leaf pcc-address {
              type inet:ip-address-no-zone;
              description
                "PCC Address";
            }
            leaf policy-name {
              type xr:Cisco-ios-xr-string;
              description
                "Policy Name";
            }
            uses PCE-POLICY-BAG;
          }
        }
      }
    }
    container link-state-policies {
      description
        "Distribute link-state policy table";
      list link-state-policy {
        description
          "Distribute link-state policy";
        leaf ipv4-router-id {
          type inet:ip-address-no-zone;
          description
            "IPv4 router ID";
        }
        leaf ipv6-router-id {
          type inet:ip-address-no-zone;
          description
            "IPv6 router ID";
        }
        leaf color {
          type uint32;
          description
            "Policy color";
        }
        leaf endpoint-address {
          type inet:ip-address-no-zone;
          description
            "Policy endpoint";
        }
        leaf protocol-origin {
          type uint32;
          description
            "Policy candidate path protocol origin";
        }
        leaf originator-asn {
          type uint32;
          description
            "Policy candidate path originator ASN";
        }
        leaf originator-address {
          type inet:ip-address-no-zone;
          description
            "Policy candidate path originator address";
        }
        leaf discriminator {
          type uint32;
          description
            "Policy candidate path discriminator";
        }
        uses PCE-BGP-LS-POLICY-BAG;
      }
    }
    container verification-events {
      description
        "PCE Verification events in XTC";
      list verification-event {
        key "event-idx";
        description
          "PCE single verification event";
        leaf event-idx {
          type uint32;
          description
            "Index of an event";
        }
        uses PCE-EVENT-INFO;
      }
    }
    container api {
      description
        "PCE API details";
      container bandwidth-on-demand {
        description
          "PCE BWoD submode";
        container active-client {
          description
            "Active client information";
          uses PCE-BWOD-BEST-CLIENT-BAG;
        }
        container sub-delegations {
          description
            "BWoD sub-delegation table";
          list sub-delegation {
            description
              "BWoD sub-delegation details";
            leaf pcc-address {
              type inet:ip-address-no-zone;
              description
                "PCC Address";
            }
            leaf tunnel-name {
              type string;
              description
                "Name of the tunnel";
            }
            uses PCE-BWOD-SUB-DELEGATION-BAG;
          }
        }
      }
      container sibling {
        description
          "PCE sibling";
        container synced-lsps {
          description
            "Synced LSP table";
          list synced-lsp {
            description
              "Synced LSP details";
            leaf pcc-address {
              type inet:ip-address-no-zone;
              description
                "PCC Address";
            }
            leaf lsp-name {
              type string;
              description
                "Name of the synced LSP";
            }
            leaf remote-flag {
              type boolean;
              description
                "Flag to indicate lsp data is remote";
            }
            uses PCE-SIBLING-SYNCED-LSP-BAG;
          }
        }
        container connection {
          description
            "Connection information";
          uses PCE-SIBLING-CONN-BAG;
        }
      }
    }
    container p2mp-policies {
      description
        "P2MP policy database in SR-PCE";
      list p2mp-policy {
        key "name";
        description
          "Policy information";
        leaf name {
          type xr:Cisco-ios-xr-string;
          description
            "Policy name";
        }
        uses PCE-TREESID-BAG;
      }
    }
    container peer-summaries {
      description
        "Detailed PCE peer information";
      list peer-summary {
        key "af";
        description
          "Summary PCE peer information";
        leaf af {
          type Pce-address-family;
          description
            "Only show data related to the specified
             address family";
        }
        uses PCE-PEER-SUMMARY-BAG;
      }
    }
    container cspf-srv6 {
      description
        "CSPF for SRV6 path info";
      container cspf-srv6-paths {
        description
          "This table models the path calculation
           capabilities in XTC.A GET operation for the
           complete table will return no entries.";
        list cspf-srv6-path {
          description
            "A GET operation on this class returns the path
             .";
          leaf af {
            type uint32;
            description
              "Address Family";
          }
          leaf source1 {
            type inet:ip-address-no-zone;
            description
              "Source of path 1";
          }
          leaf destination1 {
            type inet:ip-address-no-zone;
            description
              "Destination of path 1";
          }
          leaf metric-type {
            type uint32;
            description
              "Metric type";
          }
          leaf source2 {
            type inet:ip-address-no-zone;
            description
              "Source of path 2";
          }
          leaf destination2 {
            type inet:ip-address-no-zone;
            description
              "Destination of path 2";
          }
          leaf disjoint-level {
            type uint32;
            description
              "Disjointness level";
          }
          leaf disjoint-strict {
            type uint32;
            description
              "Strict disjointness required";
          }
          leaf shortest-path {
            type uint32;
            description
              "Whether path 1 or 2 should be shortest";
          }
          leaf msd1 {
            type uint32;
            description
              "MSD for path 1";
          }
          leaf msd2 {
            type uint32;
            description
              "MSD for path 2";
          }
          leaf relative-margin {
            type uint32;
            description
              "Relative Margin";
          }
          leaf absolute-margin {
            type uint32;
            description
              "Absolute Margin";
          }
          leaf affinity-include-all {
            type uint32;
            description
              "Affinity include-all constraint";
          }
          leaf affinity-include-any {
            type uint32;
            description
              "Affinity include-any constraint";
          }
          leaf affinity-exclude-any {
            type uint32;
            description
              "Affinity exclude-any constraint";
          }
          uses PCE-SR-MPLS-PATH-LIST-BAG;
        }
      }
    }
    container flex-algos {
      description
        "FlexAlgo database in PCE";
      list flex-algo {
        description
          "FlexAlgo Definition";
        leaf igp-type {
          type Pceigp-protocol;
          description
            "Match nodes from the specified IGP protocol";
        }
        leaf domain-id {
          type uint32;
          description
            "Domain ID";
        }
        leaf area-id {
          type uint32;
          description
            "Area ID";
        }
        uses PCE-FLEX-ALGO-AREA;
      }
    }
    container work-nodes {
      description
        "Work node database";
      list work-node {
        key "index";
        description
          "Path work node information";
        leaf index {
          type uint32;
          description
            "Position in work list";
        }
        uses PATH-WORK-NODE;
      }
    }
    container override-rules {
      description
        "Override rules";
      list override-rule {
        key "sequence-number";
        description
          "Override rule";
        leaf sequence-number {
          type uint32;
          description
            "Sequence number";
        }
        uses PCE-OV-RULE-BAG;
      }
    }
    container trace-buffer-summaries {
      description
        "Summary of all trace buffers";
      list trace-buffer-summary {
        key "name";
        description
          "Summary of specific trace buffer";
        leaf name {
          type xr:Cisco-ios-xr-string;
          description
            "Trace buffer name";
        }
        uses CMN-TRACE-BUFFER-SUMMARY-BAG;
      }
    }
    container grpc-service-instances {
      description
        "GRPC service instances";
      list grpc-service-instance {
        key "name";
        description
          "GRPC service instance";
        leaf name {
          type xr:Cisco-ios-xr-string;
          description
            "instance name";
        }
        uses XTC-GRPC-SERVICE-INSTANCE-BAG;
      }
    }
    container association-infos {
      description
        "Associaition database in XTC";
      list association-info {
        key "group-id";
        description
          "PCE Association information";
        leaf group-id {
          type uint32;
          description
            "Group ID";
        }
        leaf type {
          type Pce-asso;
          description
            "Type";
        }
        leaf sub-id {
          type inet:ip-address-no-zone;
          description
            "Sub ID";
        }
        uses PCE-ASSO-BAG;
      }
    }
    container work-groups {
      description
        "Work group database";
      list work-group {
        key "id";
        description
          "Path work group information";
        leaf id {
          type uint32;
          description
            "Work group ID";
        }
        uses PATH-WORK-GROUP;
      }
    }
    container paths {
      description
        "This table models the path calculation
         capabilities in XTC.A GET operation for the
         complete table will return no entries.";
      list path {
        key "af source destination";
        description
          "A GET operation on this class returns the path.";
        leaf af {
          type uint32;
          description
            "Address Family";
        }
        leaf source {
          type inet:ip-address-no-zone;
          description
            "Source of path";
        }
        leaf destination {
          type inet:ip-address-no-zone;
          description
            "Destination of path";
        }
        uses PCE-PATH-BAG;
      }
    }
    container p2mp-policy-infos {
      description
        "P2MP policy database indexed by Root address in
         XTC";
      list p2mp-policy-info {
        key "root-address tree-id";
        description
          "P2MP Policy information";
        leaf root-address {
          type inet:ip-address-no-zone;
          description
            "Root Address";
        }
        leaf tree-id {
          type uint32;
          description
            "P2MP Policy Tree-ID";
        }
        uses PCE-TREESID-BAG;
      }
    }
    container cspf {
      description
        "CSPF path info";
      container cspf-paths {
        description
          "This table models the path calculation
           capabilities in XTC.A GET operation for the
           complete table will return no entries.";
        list cspf-path {
          description
            "A GET operation on this class returns the path
             .";
          leaf af {
            type uint32;
            description
              "Address Family";
          }
          leaf source1 {
            type inet:ip-address-no-zone;
            description
              "Source of path 1";
          }
          leaf destination1 {
            type inet:ip-address-no-zone;
            description
              "Destination of path 1";
          }
          leaf metric-type {
            type uint32;
            description
              "Metric type";
          }
          leaf source2 {
            type inet:ip-address-no-zone;
            description
              "Source of path 2";
          }
          leaf destination2 {
            type inet:ip-address-no-zone;
            description
              "Destination of path 2";
          }
          leaf disjoint-level {
            type uint32;
            description
              "Disjointness level";
          }
          leaf disjoint-strict {
            type uint32;
            description
              "Strict disjointness required";
          }
          leaf shortest-path {
            type uint32;
            description
              "Whether path 1 or 2 should be shortest";
          }
          uses PCE-PATH-LIST-BAG;
        }
      }
    }
    container statistics-nodes {
      description
        "PCE API peer statistics";
      list statistics-node {
        key "ip";
        description
          "PCE API peer statistics information";
        leaf ip {
          type inet:ip-address-no-zone;
          description
            "Specify IPv4 or v6 Address";
        }
        uses API-PEER-STATS-BAG;
      }
    }
    container performance-statistics {
      description
        "PCE performance peer statistics";
      uses PCE-PERFORMANCE-STATS-BAG;
    }
    uses REMOTE-PREFIX-TABLE;
    uses TUNNEL-TABLE;
    uses PEER-DETAIL-TABLE;
    uses TOPOLOGY-NODE-TABLE;
    uses TOPOLOGY-SUMMARY-TABLE;
    uses INITIATED-TUN-TABLE;
    uses PREFIX-TABLE;
    uses LSP-SUMMARY;
    uses PEER-TABLE;
    uses TUNNEL-DETAIL-TABLE;
    uses COMMON-TOPOLOGY-NODE-TABLE;
  }
}
