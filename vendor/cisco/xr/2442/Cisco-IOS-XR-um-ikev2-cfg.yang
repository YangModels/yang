module Cisco-IOS-XR-um-ikev2-cfg {
  namespace "http://cisco.com/ns/yang/Cisco-IOS-XR-um-ikev2-cfg";
  prefix um-ikev2-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ikev2 package configuration.
     
     This YANG module augments the
     modules with configuration data.
     
     Copyright (c) 2021-2024 by Cisco Systems, Inc.
     All rights reserved.";

  revision 2024-04-22 {
    description
      "Type6 support for IKE
       2024-03-25
         FQDN domain identity support
       2024-01-25
         Changed the PPK ID Pattern
       2024-01-10
         FQDN identity support
       2023-06-01
         PPK support
       2023-04-26
         Pattern check change under keyring pre shared key
       2022-04-28
         Added fvrf support under match node";
    semver:module-version "1.1.0";
  }
  revision 2021-06-29 {
    description
      "Initial release";
    semver:module-version "1.0.0";
  }

  container ikev2 {
    description
      "IKE configuration commands";
    container profile {
      description
        "Configure IKEV2 profiles";
      container ikev2-profile-names {
        description
          "Enter name of IKEV2 profile of max length 32";
        list ikev2-profile-name {
          key "ikev2-profile-name";
          description
            "Enter name of IKEV2 profile of max length 32";
          leaf ikev2-profile-name {
            type xr:Cisco-ios-xr-string {
              length "1..32" {
                description
                  "Enter name of IKEV2 profile of max length 32";
              }
            }
            description
              "Enter name of IKEV2 profile of max length 32";
          }
          container match {
            description
              "match a profile";
            container identity {
              description
                "match a profile based on identity[remote/local]";
              container remote {
                description
                  "match a profile based on remote identity";
                container addresses {
                  description
                    "remote IP address(es) for matching identity";
                  list address {
                    must "not(../../any)";
                    key "remote-address mask";
                    description
                      "remote IP address(es) for matching identity";
                    leaf remote-address {
                      type inet:ipv4-address-no-zone;
                      description
                        "remote IP address(es) for matching identity";
                    }
                    leaf mask {
                      type inet:ipv4-address-no-zone;
                      description
                        "address mask";
                    }
                  }
                }
                container any {
                  must "not(../addresses/address or ../fqdn/fqdns or ../fqdn-domain/fqdn-domains)";
                  presence "Indicates a any node is configured.";
                  description
                    "match any peer identity";
                }
                container fqdn {
                  description
                    "Fully qualified domain name string for matching identity";
                  list fqdns {
                    must "not(../../any)";
                    key "fqdn-name";
                    description
                      "Enter the fully qualified domain name string";
                    leaf fqdn-name {
                      type xr:Cisco-ios-xr-string {
                        length "1..255" {
                          description
                            "Enter the fully qualified domain name string";
                        }
                      }
                      description
                        "Enter the fully qualified domain name string";
                    }
                  }
                }
                container fqdn-domain {
                  description
                    "Use domain-name to match all peers from same domain";
                  list fqdn-domains {
                    must "not(../../any)";
                    key "fqdn-domain-name";
                    description
                      "Enter domain name string";
                    leaf fqdn-domain-name {
                      type xr:Cisco-ios-xr-string {
                        length "1..255" {
                          description
                            "Enter domain name string";
                        }
                      }
                      description
                        "Enter domain name string";
                    }
                  }
                }
              }
            }
            container fvrf {
              description
                "fvrf of the profile";
              container any {
                must "not(../vrf-name)";
                presence "Indicates a any node is configured.";
                description
                  "any fvrf";
              }
              leaf vrf-name {
                type xr:Cisco-ios-xr-string {
                  length "1..32" {
                    description
                      "Enter the vrf name";
                  }
                }
                must "not(../any)";
                description
                  "Enter the vrf name";
              }
            }
          }
          container identity {
            description
              "specify IKE identity to use";
            container local {
              description
                "Specify the local IKE identity to use for the negotiation";
              leaf address {
                type inet:ipv4-address-no-zone;
                must "not(../fqdn)";
                description
                  "IPv4 address";
              }
              leaf fqdn {
                type xr:Cisco-ios-xr-string {
                  length "1..255" {
                    description
                      "Enter the fqdn string";
                  }
                }
                must "not(../address)";
                description
                  "Fully qualified domain name string";
              }
            }
          }
          leaf lifetime {
            type uint32 {
              range "120..86400" {
                description
                  "Enter the lifetime value in seconds";
              }
            }
            description
              "Lifetime in seconds for IKEV2 SA";
          }
          leaf keyring {
            type xr:Cisco-ios-xr-string {
              length "1..32" {
                description
                  "Enter the ikev2 keyring name of max length 32";
              }
            }
            description
              "Keyring to use with [local/remote] authentication method";
          }
          leaf keyring-ppk {
            type xr:Cisco-ios-xr-string {
              length "1..32" {
                description
                  "Enter the ppk keyring name";
              }
            }
            description
              "PPK keyring";
          }
          container pki {
            description
              "Configure truspoint(s)";
            container trustpoints {
              description
                "Configure trustpoint(s)";
              list trustpoint {
                key "trustpoint-name";
                description
                  "Configure trustpoint(s)";
                leaf trustpoint-name {
                  type xr:Cisco-ios-xr-string {
                    length "1..32" {
                      description
                        "Enter the trustpoint name of max length 32";
                    }
                  }
                  description
                    "Configure trustpoint(s)";
                }
              }
            }
          }
          container authentication {
            description
              "Authentication method to be for use for SA";
            container local {
              description
                "Local authentication method";
              container pre-shared {
                must "not(../rsa-signature)";
                presence "Indicates a pre-shared node is configured.";
                description
                  "Use preshared key authentication method";
              }
              container rsa-signature {
                must "not(../pre-shared)";
                presence "Indicates a rsa-signature node is configured.";
                description
                  "Use RSA signature authentication method";
              }
            }
            container remote {
              description
                "Remote authentication method";
              container pre-shared {
                presence "Indicates a pre-shared node is configured.";
                description
                  "Use pre-shared-key authentication method";
              }
              container rsa-signature {
                presence "Indicates a rsa-signature node is configured.";
                description
                  "Use RSA authentication method";
              }
            }
          }
        }
      }
    }
    container proposal {
      description
        "Configure IKEV2 proposals";
      container ikev2-proposal-names {
        description
          "Enter name of IKEV2 proposal of max length 32";
        list ikev2-proposal-name {
          key "ikev2-proposal-name";
          description
            "Enter name of IKEV2 proposal of max length 32";
          leaf ikev2-proposal-name {
            type xr:Cisco-ios-xr-string {
              length "1..32" {
                description
                  "Enter name of IKEV2 proposal of max length 32";
              }
            }
            description
              "Enter name of IKEV2 proposal of max length 32";
          }
          container encryptions {
            description
              "Specify one or more transforms of encryption";
            leaf-list encryption {
              type xr:Cisco-ios-xr-string {
                length "1..800" {
                  description
                    "choose one or more encryption algorithms in required preference
                     aes-gcm-128
                     aes-gcm-256
                     aes-cbc-128
                     aes-cbc-192
                     aes-cbc-256";
                }
                pattern "aes-gcm-128|aes-gcm-256|aes-cbc-128|aes-cbc-192|aes-cbc-256";
              }
              max-elements "5";
              description
                "Specify one or more transforms of encryption";
            }
          }
          container integrities {
            description
              "Specify one or more transforms of integrity type";
            leaf-list integrity {
              type xr:Cisco-ios-xr-string {
                length "1..800" {
                  description
                    "choose one or more integrity algorithms in required preference
                     sha-1
                     sha-256
                     sha-384
                     sha-512";
                }
                pattern "sha-1|sha-256|sha-384|sha-512";
              }
              max-elements "4";
              description
                "Specify one or more transforms of integrity type";
            }
          }
          container prfs {
            description
              "Specify one or more transforms of prf type";
            leaf-list prf {
              type xr:Cisco-ios-xr-string {
                length "1..800" {
                  description
                    "choose one or more prf algorithms in required preference
                     sha-1
                     sha-256
                     sha-384
                     sha-512";
                }
                pattern "sha-1|sha-256|sha-384|sha-512";
              }
              max-elements "4";
              description
                "Specify one or more transforms of prf type";
            }
          }
          container dh-groups {
            description
              "Specify one or more transforms of DH group";
            leaf-list dh-group {
              type xr:Cisco-ios-xr-string {
                length "1..800" {
                  description
                    "choose one or more group algorithms in required preference
                     19 256-bit ECP group-19
                     20 384-bit ECP group-20
                     21 521-bit ECP group-21";
                }
                pattern "19|20|21";
              }
              max-elements "8";
              description
                "Specify one or more transforms of DH group";
            }
          }
        }
      }
    }
    container policy {
      description
        "Configure IKEV2 policies";
      container ikev2-policy-names {
        description
          "Enter name of IKEV2 policy of max length 32";
        list ikev2-policy-name {
          key "ikev2-policy-name";
          description
            "Enter name of IKEV2 policy of max length 32";
          leaf ikev2-policy-name {
            type xr:Cisco-ios-xr-string {
              length "1..32" {
                description
                  "Enter name of IKEV2 policy of max length 32";
              }
            }
            description
              "Enter name of IKEV2 policy of max length 32";
          }
          container proposal {
            description
              "Proposal name for this policy";
            container ikev2-proposal-names {
              description
                "Enter the name of IKEV2 proposal of max length 32";
              list ikev2-proposal-name {
                key "ikev2-proposal-name";
                description
                  "Enter the name of IKEV2 proposal of max length 32";
                leaf ikev2-proposal-name {
                  type xr:Cisco-ios-xr-string {
                    length "1..32" {
                      description
                        "Enter the name of IKEV2 proposal of max length 32";
                    }
                  }
                  description
                    "Enter the name of IKEV2 proposal of max length 32";
                }
              }
            }
          }
          container match {
            description
              "match a policy";
            container address {
              description
                "address used to match policy";
              container locals {
                description
                  "local address used to match policy";
                list local {
                  key "address";
                  description
                    "local address used to match policy";
                  leaf address {
                    type inet:ipv4-address-no-zone;
                    description
                      "local address used to match policy";
                  }
                }
              }
            }
            container fvrf {
              description
                "user configured vrf default global";
              container any {
                presence "Indicates a any node is configured.";
                description
                  "any fvrf";
              }
              container vrfs {
                description
                  "Enter the vrf name";
                list vrf {
                  key "vrf-name";
                  description
                    "Enter the vrf name";
                  leaf vrf-name {
                    type xr:Cisco-ios-xr-string {
                      length "1..32" {
                        description
                          "Enter the vrf name";
                      }
                    }
                    description
                      "Enter the vrf name";
                  }
                }
              }
            }
          }
        }
      }
    }
  }
  container keyrings {
    description
      "Configure IKEV2 keyrings";
    list keyring {
      key "ikev2-keyring-name";
      description
        "Enter name of IKEV2 keyring of max length 32";
      leaf ikev2-keyring-name {
        type xr:Cisco-ios-xr-string {
          length "1..32" {
            description
              "Enter name of IKEV2 keyring of max length 32";
          }
        }
        description
          "Enter name of IKEV2 keyring of max length 32";
      }
      container peers {
        description
          "Enter the keyring peer submode";
        list peer {
          key "peer-name";
          description
            "Enter the name of peer of max length 32";
          leaf peer-name {
            type xr:Cisco-ios-xr-string {
              length "1..32" {
                description
                  "Enter the name of peer of max length 32";
              }
            }
            description
              "Enter the name of peer of max length 32";
          }
          leaf address {
            type inet:ipv4-address-no-zone;
            must "../mask";
            description
              "IP address to identify the peer";
          }
          leaf mask {
            type inet:ipv4-address-no-zone;
            must "../address";
            description
              "address mask";
          }
          container pre-shared-key {
            description
              "Pre-shared key for the peer";
            leaf password {
              type xr:Proprietary-password {
                length "1..130" {
                  description
                    "Encrypted pre-shared-key as hex string or Plaintext pre-shared-key prefixed with !";
                }
                pattern "([^!](([0-9]+)|([a-f]+)|([A-F]+))+)|(!(([0-9]+)|([a-z]+)|([A-Z]+))+)";
              }
              must "not(../password6) and not(../local) and not(../local6)";
              description
                "Enter encrypted pre-shared-key as hex string ";
            }
            leaf password6 {
              type xr:Type6-password {
                length "1..234" {
                  description
                    "Type6 encrypted pre-shared-key as hex-string or Plaintext pre-shared-key prefixed with !";
                }
                pattern "([^!](([0-9]+)|([a-f]+)|([A-F]+))+)|(!(([0-9]+)|([a-z]+)|([A-Z]+))+)";
              }
              must "not(../password) and not(../local) and not(../local6)";
              description
                "Enter encrypted pre-shared-key as hex string ";
            }
            leaf local {
              type xr:Proprietary-password {
                length "1..130" {
                  description
                    "Encrypted pre-shared-key as hex string or Plaintext pre-shared-key prefixed with !";
                }
                pattern "([^!](([0-9]+)|([a-f]+)|([A-F]+))+)|(!(([0-9]+)|([a-z]+)|([A-Z]+))+)";
              }
              must "not(../local6) and not(../password) and not(../password6)";
              description
                "Enter local pre-share-key";
            }
            leaf remote {
              type xr:Proprietary-password {
                length "1..130" {
                  description
                    "Encrypted pre-shared-key as hex string or Plaintext pre-shared-key prefixed with !";
                }
                pattern "([^!](([0-9]+)|([a-f]+)|([A-F]+))+)|(!(([0-9]+)|([a-z]+)|([A-Z]+))+)";
              }
              must "../local";
              description
                "Enter remote pre-share-key";
            }
            leaf local6 {
              type xr:Type6-password {
                length "1..234" {
                  description
                    "Type6 encrypted pre-shared-key as hex-string or Plaintext pre-shared-key prefixed with !";
                }
                pattern "([^!](([0-9]+)|([a-f]+)|([A-F]+))+)|(!(([0-9]+)|([a-z]+)|([A-Z]+))+)";
              }
              must "not(../local) and not(../password) and not(../password6)";
              description
                "Enter local pre-share-key";
            }
            leaf remote6 {
              type xr:Type6-password {
                length "1..234" {
                  description
                    "Type6 encrypted pre-shared-key as hex-string or Plaintext pre-shared-key prefixed with !";
                }
                pattern "([^!](([0-9]+)|([a-f]+)|([A-F]+))+)|(!(([0-9]+)|([a-z]+)|([A-Z]+))+)";
              }
              must "../local6";
              description
                "Enter remote pre-share-key";
            }
          }
          container ppk {
            description
              "ppk";
            container manual {
              description
                "Use manual";
              leaf id {
                type string {
                  length "1..127" {
                    description
                      "PPK ID";
                  }
                  pattern "(([0-9]+)|([a-z]+)|([A-Z]+)|([+/]))+";
                }
                must "not(../../dynamic/sks-profile) and ../key";
                description
                  "Specify PPK ID";
              }
              container key {
                must "../id";
                presence "Indicates a key node is configured.";
                description
                  "Specify verifying key";
                leaf password {
                  type xr:Proprietary-password {
                    length "1..256" {
                      description
                        "Encrypted ppk as hex string or Plaintext ppk prefixed with !";
                    }
                    pattern "([^!](([0-9]+)|([a-f]+)|([A-F]+))+)|(!(([0-9]+)|([a-z]+)|([A-Z]+)|([+/]))+)";
                  }
                  must "not(../password6)";
                  description
                    "Enter encrypted pre-shared-key as hex string ";
                }
                leaf password6 {
                  type xr:Type6-password {
                    length "1..420" {
                      description
                        "Encrypted ppk as hex string or Plaintext ppk prefixed with !";
                    }
                    pattern "([^!](([0-9]+)|([a-f]+)|([A-F]+))+)|(!(([0-9]+)|([a-z]+)|([A-Z]+)|([+/]))+)";
                  }
                  must "not(../password)";
                  description
                    "Enter encrypted pre-shared as hex string";
                }
              }
              container required {
                presence "Indicates a required node is configured.";
                description
                  "To make mandatory or not";
              }
            }
            container dynamic {
              description
                "Use dynamic";
              leaf sks-profile {
                type xr:Cisco-ios-xr-string {
                  length "1..127" {
                    description
                      "Sks-config-block ID";
                  }
                }
                must "not(../../manual/id)";
                description
                  "Specify SKS ID";
              }
              container required {
                presence "Indicates a required node is configured.";
                description
                  "To make mandatory or not";
              }
            }
          }
          container identity {
            description
              "Specify IKE identity to use";
            leaf address {
              type inet:ipv4-address-no-zone;
              must "not(../fqdn) and not(../fqdn-domain)";
              description
                "IPv4 address";
            }
            leaf fqdn {
              type xr:Cisco-ios-xr-string {
                length "1..255" {
                  description
                    "Enter the fully qualified domain name string";
                }
              }
              must "not(../address) and not(../fqdn-domain)";
              description
                " Use FQDN";
            }
            leaf fqdn-domain {
              type xr:Cisco-ios-xr-string {
                length "1..255" {
                  description
                    "Enter the domain name string";
                }
              }
              must "not(../fqdn) and not(../address)";
              description
                "Use domain-name to match all peers from same domain";
            }
          }
        }
      }
    }
  }
}
