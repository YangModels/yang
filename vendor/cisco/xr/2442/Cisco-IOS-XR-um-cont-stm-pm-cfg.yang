module Cisco-IOS-XR-um-cont-stm-pm-cfg {
  namespace "http://cisco.com/ns/yang/Cisco-IOS-XR-um-cont-stm-pm-cfg";
  prefix um-cont-stm-pm-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-stm-pm package configuration.
     
     This YANG module augments the
     modules with configuration data.
     
     Copyright (c) 2020-2022 by Cisco Systems, Inc.
     All rights reserved.";

  revision 2022-07-11 {
    description
      "Added missing description statement to nodes
       2022-06-01
         Adjusted controller augmentation hierarchy";
    semver:module-version "1.1.0";
  }
  revision 2020-06-11 {
    description
      "Initial release";
    semver:module-version "1.0.0";
  }

  grouping CONT-BODY {
    description
      "Grouping for controller";
    container pm {
      when "../a1:controller-name[starts-with(text(),'STM')]" {
        tailf:dependency "../a1:controller-name";
      }
      description
        "Configure pm parameters";
      container interval-15-min {
        description
          "Configure pm parameters of 15 minute interval";
        container stm {
          description
            "configure stm performance monitoring";
          container threshold {
            description
              "Configure threshold on stm parameters";
            leaf eb-s {
              type uint32 {
                range "0..8850600" {
                  description
                    "eb-s threshold range";
                }
              }
              description
                "set eb-s threshold";
            }
            leaf es-s {
              type uint32 {
                range "0..900" {
                  description
                    "es-s threshold range";
                }
              }
              description
                "set es-s threshold";
            }
            leaf esr-s {
              type uint32 {
                range "0..100000" {
                  description
                    "esr-s threshold range";
                }
              }
              description
                "set esr-s threshold";
            }
            leaf ses-s {
              type uint32 {
                range "0..900" {
                  description
                    "ses-s threshold range";
                }
              }
              description
                "set ses-s threshold";
            }
            leaf sesr-s {
              type uint32 {
                range "0..100000" {
                  description
                    "sesr-s threshold range";
                }
              }
              description
                "set sesr-s threshold";
            }
            leaf bbe-s {
              type uint32 {
                range "0..8850600" {
                  description
                    "bbes-s threshold range";
                }
              }
              description
                "set bbe-s threshold";
            }
            leaf bber-s {
              type uint32 {
                range "0..100000" {
                  description
                    "bber-s threshold range";
                }
              }
              description
                "set bber-s threshold";
            }
            leaf uas-s {
              type uint32 {
                range "0..900" {
                  description
                    "uas-s threshold range";
                }
              }
              description
                "set uas-s threshold";
            }
            leaf eb-l-ne {
              type uint32 {
                range "0..8850600" {
                  description
                    "eb-l-ne threshold";
                }
              }
              description
                "set eb-l-ne threshold";
            }
            leaf es-l-ne {
              type uint32 {
                range "0..900" {
                  description
                    "es-l-ne threshold";
                }
              }
              description
                "set es-l-ne threshold";
            }
            leaf esr-l-ne {
              type uint32 {
                range "0..100000" {
                  description
                    "esr-l-ne threshold";
                }
              }
              description
                "set esr-l-ne threshold";
            }
            leaf ses-l-ne {
              type uint32 {
                range "0..900" {
                  description
                    "ses-l-ne threshold range";
                }
              }
              description
                "set ses-l-ne threshold";
            }
            leaf sesr-l-ne {
              type uint32 {
                range "0..100000" {
                  description
                    "sesr-l-ne threshold range";
                }
              }
              description
                "set sesr-l-ne threshold";
            }
            leaf bbe-l-ne {
              type uint32 {
                range "0..8550600" {
                  description
                    "sesr-l-ne threshold range";
                }
              }
              description
                "set bbe-l-ne threshold";
            }
            leaf bber-l-ne {
              type uint32 {
                range "0..100000" {
                  description
                    "bber-l-ne threshold range";
                }
              }
              description
                "set bber-l-ne threshold";
            }
            leaf uas-l-ne {
              type uint32 {
                range "0..900" {
                  description
                    "uas-l-ne threshold range";
                }
              }
              description
                "set uas-l-ne threshold";
            }
            leaf eb-l-fe {
              type uint32 {
                range "0..8850600" {
                  description
                    "eb-l-fe threshold";
                }
              }
              description
                "set eb-l-fe threshold";
            }
            leaf es-l-fe {
              type uint32 {
                range "0..900" {
                  description
                    "es-l-fe threshold";
                }
              }
              description
                "set es-l-fe threshold";
            }
            leaf esr-l-fe {
              type uint32 {
                range "0..100000" {
                  description
                    "esr-l-fe threshold";
                }
              }
              description
                "set esr-l-fe threshold";
            }
            leaf ses-l-fe {
              type uint32 {
                range "0..900" {
                  description
                    "ses-l-fe threshold range";
                }
              }
              description
                "set ses-l-fe threshold";
            }
            leaf sesr-l-fe {
              type uint32 {
                range "0..100000" {
                  description
                    "sesr-l-fe threshold range";
                }
              }
              description
                "set sesr-l-fe threshold";
            }
            leaf bbe-l-fe {
              type uint32 {
                range "0..8850600" {
                  description
                    "bbe-l-fe threshold range";
                }
              }
              description
                "set bbe-l-fe threshold";
            }
            leaf bber-l-fe {
              type uint32 {
                range "0..100000" {
                  description
                    "bber-l-fe threshold range";
                }
              }
              description
                "set bber-l-fe threshold";
            }
            leaf uas-l-fe {
              type uint32 {
                range "0..900" {
                  description
                    "uas-l-fe threshold range";
                }
              }
              description
                "set uas-l-fe threshold";
            }
          }
          container report {
            description
              "set stm TCA reporting status";
            container eb-s {
              description
                "set eb TCA reporting status";
              container enable {
                presence "Indicates a enable node is configured.";
                description
                  "Enable TCA reporting";
              }
            }
            container es-s {
              description
                "set es TCA reporting status";
              container enable {
                presence "Indicates a enable node is configured.";
                description
                  "Enable TCA reporting";
              }
            }
            container esr-s {
              description
                "set esr TCA reporting status";
              container enable {
                presence "Indicates a enable node is configured.";
                description
                  "Enable TCA reporting";
              }
            }
            container ses-s {
              description
                "set ses TCA reporting status";
              container enable {
                presence "Indicates a enable node is configured.";
                description
                  "Enable TCA reporting";
              }
            }
            container sesr-s {
              description
                "set sesr TCA reporting status";
              container enable {
                presence "Indicates a enable node is configured.";
                description
                  "Enable TCA reporting";
              }
            }
            container bbe-s {
              description
                "set bbe TCA reporting status";
              container enable {
                presence "Indicates a enable node is configured.";
                description
                  "Enable TCA reporting";
              }
            }
            container bber-s {
              description
                "set bber TCA reporting status";
              container enable {
                presence "Indicates a enable node is configured.";
                description
                  "Enable TCA reporting";
              }
            }
            container uas-s {
              description
                "set uas TCA reporting status";
              container enable {
                presence "Indicates a enable node is configured.";
                description
                  "Enable TCA reporting";
              }
            }
            container eb-l-ne {
              description
                "set eb TCA reporting status";
              container enable {
                presence "Indicates a enable node is configured.";
                description
                  "Enable TCA reporting";
              }
            }
            container es-l-ne {
              description
                "set es-l-ne TCA reporting status";
              container enable {
                presence "Indicates a enable node is configured.";
                description
                  "Enable TCA reporting";
              }
            }
            container esr-l-ne {
              description
                "set esr-l-ne TCA reporting status";
              container enable {
                presence "Indicates a enable node is configured.";
                description
                  "Enable TCA reporting";
              }
            }
            container ses-l-ne {
              description
                "set ses-l-le TCA reporting status";
              container enable {
                presence "Indicates a enable node is configured.";
                description
                  "Enable TCA reporting";
              }
            }
            container sesr-l-ne {
              description
                "set sesr-l-le TCA reporting status";
              container enable {
                presence "Indicates a enable node is configured.";
                description
                  "Enable TCA reporting";
              }
            }
            container bbe-l-ne {
              description
                "set bbe-l-le TCA reporting status";
              container enable {
                presence "Indicates a enable node is configured.";
                description
                  "Enable TCA reporting";
              }
            }
            container bber-l-ne {
              description
                "set bber-l-le TCA reporting status";
              container enable {
                presence "Indicates a enable node is configured.";
                description
                  "Enable TCA reporting";
              }
            }
            container uas-l-ne {
              description
                "set uas-l-ne TCA reporting status";
              container enable {
                presence "Indicates a enable node is configured.";
                description
                  "Enable TCA reporting";
              }
            }
            container eb-l-fe {
              description
                "set eb-l-fe TCA reporting status";
              container enable {
                presence "Indicates a enable node is configured.";
                description
                  "Enable TCA reporting";
              }
            }
            container es-l-fe {
              description
                "set es-l-fe TCA reporting status";
              container enable {
                presence "Indicates a enable node is configured.";
                description
                  "Enable TCA reporting";
              }
            }
            container esr-l-fe {
              description
                "set esr-l-fe TCA reporting status";
              container enable {
                presence "Indicates a enable node is configured.";
                description
                  "Enable TCA reporting";
              }
            }
            container ses-l-fe {
              description
                "set ses-l-fe TCA reporting status";
              container enable {
                presence "Indicates a enable node is configured.";
                description
                  "Enable TCA reporting";
              }
            }
            container sesr-l-fe {
              description
                "set sesr-l-fe TCA reporting status";
              container enable {
                presence "Indicates a enable node is configured.";
                description
                  "Enable TCA reporting";
              }
            }
            container bbe-l-fe {
              description
                "set bbe-l-fe TCA reporting status";
              container enable {
                presence "Indicates a enable node is configured.";
                description
                  "Enable TCA reporting";
              }
            }
            container bber-l-fe {
              description
                "set bber-l-fe TCA reporting status";
              container enable {
                presence "Indicates a enable node is configured.";
                description
                  "Enable TCA reporting";
              }
            }
            container uas-l-fe {
              description
                "set uas-l-fe TCA reporting status";
              container enable {
                presence "Indicates a enable node is configured.";
                description
                  "Enable TCA reporting";
              }
            }
          }
        }
      }
      container interval-24-hour {
        description
          "Configure pm parameters of 24 hour interval";
        container stm {
          description
            "configure stm performance monitoring";
          container threshold {
            description
              "Configure threshold on otn parameters";
            leaf eb-s {
              type uint32 {
                range "0..849657600" {
                  description
                    "eb-s threshold range";
                }
              }
              description
                "set eb-s threshold";
            }
            leaf es-s {
              type uint32 {
                range "0..86400" {
                  description
                    "es-s threshold range";
                }
              }
              description
                "set es-s threshold";
            }
            leaf esr-s {
              type uint32 {
                range "0..100000" {
                  description
                    "esr-s threshold range";
                }
              }
              description
                "set esr-s threshold";
            }
            leaf ses-s {
              type uint32 {
                range "0..86400" {
                  description
                    "ses-s threshold range";
                }
              }
              description
                "set ses-s threshold";
            }
            leaf sesr-s {
              type uint32 {
                range "0..100000" {
                  description
                    "sesr-s threshold range";
                }
              }
              description
                "set sesr-s threshold";
            }
            leaf bbe-s {
              type uint32 {
                range "0..849657600" {
                  description
                    "bbe-s threshold range";
                }
              }
              description
                "set bbe-s threshold";
            }
            leaf bber-s {
              type uint32 {
                range "0..100000" {
                  description
                    "bber-s threshold range";
                }
              }
              description
                "set bber-s threshold";
            }
            leaf uas-s {
              type uint32 {
                range "0..86400" {
                  description
                    "uas-s threshold range";
                }
              }
              description
                "set uas-s threshold";
            }
            leaf eb-l-ne {
              type uint32 {
                range "0..849657600" {
                  description
                    "eb-l-ne threshold";
                }
              }
              description
                "set eb-l-ne threshold";
            }
            leaf es-l-ne {
              type uint32 {
                range "0..86400" {
                  description
                    "es-l-ne threshold";
                }
              }
              description
                "set es-l-ne threshold";
            }
            leaf esr-l-ne {
              type uint32 {
                range "0..100000" {
                  description
                    "esr-l-ne threshold";
                }
              }
              description
                "set esr-l-ne threshold";
            }
            leaf ses-l-ne {
              type uint32 {
                range "0..86400" {
                  description
                    "ses-l-ne threshold range";
                }
              }
              description
                "set ses-l-ne threshold";
            }
            leaf sesr-l-ne {
              type uint32 {
                range "0..100000" {
                  description
                    "sesr-l-ne threshold range";
                }
              }
              description
                "set sesr-l-ne threshold";
            }
            leaf bbe-l-ne {
              type uint32 {
                range "0..849657600" {
                  description
                    "bbe-l-ne threshold range";
                }
              }
              description
                "set bbe-l-ne threshold";
            }
            leaf bber-l-ne {
              type uint32 {
                range "0..100000" {
                  description
                    "bber-l-ne threshold range";
                }
              }
              description
                "set bber-l-ne threshold";
            }
            leaf uas-l-ne {
              type uint32 {
                range "0..86400" {
                  description
                    "uas-l-ne threshold range";
                }
              }
              description
                "set uas-l-ne threshold";
            }
            leaf eb-l-fe {
              type uint32 {
                range "0..849657600" {
                  description
                    "eb-l-fe threshold";
                }
              }
              description
                "set eb-l-fe threshold";
            }
            leaf es-l-fe {
              type uint32 {
                range "0..86400" {
                  description
                    "es-l-fe threshold";
                }
              }
              description
                "set es-l-fe threshold";
            }
            leaf esr-l-fe {
              type uint32 {
                range "0..100000" {
                  description
                    "esr-l-fe threshold";
                }
              }
              description
                "set esr-l-fe threshold";
            }
            leaf ses-l-fe {
              type uint32 {
                range "0..86400" {
                  description
                    "ses-l-fe threshold range";
                }
              }
              description
                "set ses-l-fe threshold";
            }
            leaf sesr-l-fe {
              type uint32 {
                range "0..100000" {
                  description
                    "sesr-l-fe threshold range";
                }
              }
              description
                "set sesr-l-fe threshold";
            }
            leaf bbe-l-fe {
              type uint32 {
                range "0..849657600" {
                  description
                    "bbe-l-fe threshold range";
                }
              }
              description
                "set bbe-l-fe threshold";
            }
            leaf bber-l-fe {
              type uint32 {
                range "0..100000" {
                  description
                    "bber-l-fe threshold range";
                }
              }
              description
                "set bber-l-fe threshold";
            }
            leaf uas-l-fe {
              type uint32 {
                range "0..86400" {
                  description
                    "uas-l-fe threshold range";
                }
              }
              description
                "set uas-l-fe threshold";
            }
          }
          container report {
            description
              "set stm TCA reporting status";
            container eb-s {
              description
                "set eb-s TCA reporting status";
              container enable {
                presence "Indicates a enable node is configured.";
                description
                  "Enable TCA reporting";
              }
            }
            container es-s {
              description
                "set es-s TCA reporting status";
              container enable {
                presence "Indicates a enable node is configured.";
                description
                  "Enable TCA reporting";
              }
            }
            container esr-s {
              description
                "set esr-s TCA reporting status";
              container enable {
                presence "Indicates a enable node is configured.";
                description
                  "Enable TCA reporting";
              }
            }
            container ses-s {
              description
                "set ses-s TCA reporting status";
              container enable {
                presence "Indicates a enable node is configured.";
                description
                  "Enable TCA reporting";
              }
            }
            container sesr-s {
              description
                "set sesr-s TCA reporting status";
              container enable {
                presence "Indicates a enable node is configured.";
                description
                  "Enable TCA reporting";
              }
            }
            container bbe-s {
              description
                "set bbe-s TCA reporting status";
              container enable {
                presence "Indicates a enable node is configured.";
                description
                  "Enable TCA reporting";
              }
            }
            container bber-s {
              description
                "set bber-s TCA reporting status";
              container enable {
                presence "Indicates a enable node is configured.";
                description
                  "Enable TCA reporting";
              }
            }
            container uas-s {
              description
                "set bbe-s TCA reporting status";
              container enable {
                presence "Indicates a enable node is configured.";
                description
                  "Enable TCA reporting";
              }
            }
            container eb-l-ne {
              description
                "set eb-l-ne TCA reporting status";
              container enable {
                presence "Indicates a enable node is configured.";
                description
                  "Enable TCA reporting";
              }
            }
            container es-l-ne {
              description
                "set es-l-ne TCA reporting status";
              container enable {
                presence "Indicates a enable node is configured.";
                description
                  "Enable TCA reporting";
              }
            }
            container esr-l-ne {
              description
                "set esr-l-ne TCA reporting status";
              container enable {
                presence "Indicates a enable node is configured.";
                description
                  "Enable TCA reporting";
              }
            }
            container ses-l-ne {
              description
                "set ses-l-ne TCA reporting status";
              container enable {
                presence "Indicates a enable node is configured.";
                description
                  "Enable TCA reporting";
              }
            }
            container sesr-l-ne {
              description
                "set sesr-l-ne TCA reporting status";
              container enable {
                presence "Indicates a enable node is configured.";
                description
                  "Enable TCA reporting";
              }
            }
            container bbe-l-ne {
              description
                "set bbe-l-ne TCA reporting status";
              container enable {
                presence "Indicates a enable node is configured.";
                description
                  "Enable TCA reporting";
              }
            }
            container bber-l-ne {
              description
                "set bber-l-ne TCA reporting status";
              container enable {
                presence "Indicates a enable node is configured.";
                description
                  "Enable TCA reporting";
              }
            }
            container uas-l-ne {
              description
                "set uas-l-ne TCA reporting status";
              container enable {
                presence "Indicates a enable node is configured.";
                description
                  "Enable TCA reporting";
              }
            }
            container eb-l-fe {
              description
                "set eb-l-fe TCA reporting status";
              container enable {
                presence "Indicates a enable node is configured.";
                description
                  "Enable TCA reporting";
              }
            }
            container es-l-fe {
              description
                "set es-l-fe TCA reporting status";
              container enable {
                presence "Indicates a enable node is configured.";
                description
                  "Enable TCA reporting";
              }
            }
            container esr-l-fe {
              description
                "set esr-l-fe TCA reporting status";
              container enable {
                presence "Indicates a enable node is configured.";
                description
                  "Enable TCA reporting";
              }
            }
            container ses-l-fe {
              description
                "set ses-l-fe TCA reporting status";
              container enable {
                presence "Indicates a enable node is configured.";
                description
                  "Enable TCA reporting";
              }
            }
            container sesr-l-fe {
              description
                "set sesr-l-fe TCA reporting status";
              container enable {
                presence "Indicates a enable node is configured.";
                description
                  "Enable TCA reporting";
              }
            }
            container bbe-l-fe {
              description
                "set bbe-l-fe TCA reporting status";
              container enable {
                presence "Indicates a enable node is configured.";
                description
                  "Enable TCA reporting";
              }
            }
            container bber-l-fe {
              description
                "set bber-l-fe TCA reporting status";
              container enable {
                presence "Indicates a enable node is configured.";
                description
                  "Enable TCA reporting";
              }
            }
            container uas-l-fe {
              description
                "set uas-l-fe TCA reporting status";
              container enable {
                presence "Indicates a enable node is configured.";
                description
                  "Enable TCA reporting";
              }
            }
          }
        }
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
