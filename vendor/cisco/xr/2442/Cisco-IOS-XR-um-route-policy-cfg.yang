module Cisco-IOS-XR-um-route-policy-cfg {
  namespace "http://cisco.com/ns/yang/Cisco-IOS-XR-um-route-policy-cfg";
  prefix um-route-policy-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR policy-repository package configuration.
     
     This module contains definitions
     for the following management objects:
       routing-policy: Routing policy configuration
     
     Copyright (c) 2022-2024 by Cisco Systems, Inc.
     All rights reserved.";

  revision 2024-06-20 {
    description
      "Updated the Leaves descriptions";
    semver:module-version "1.0.0";
  }
  revision 2023-10-17 {
    description
      "Removed RPL default editor set option";
    semver:module-version "1.0.0";
  }
  revision 2022-12-10 {
    description
      "EVPN Bandwidth Set inclusion";
  }
  revision 2022-01-17 {
    description
      "Inital release";
  }

  container routing-policy {
    description
      "Routing policy configuration";
    xr:xr-xml-map "rpl_cfg:RoutingPolicy";
    container route-policies {
      description
        "All configured policies";
      xr:xr-xml-map "rpl_cfg:RoutePolicyTable";
      list route-policy {
        key "route-policy-name";
        description
          "Information about an individual policy";
        xr:xr-xml-map "rpl_cfg:RoutePolicy";
        leaf route-policy-name {
          type xr:Cisco-ios-xr-string;
          description
            "Route policy name";
          xr:xr-xml-map "rpl_cfg:RoutePolicyName";
        }
        leaf rpl-route-policy {
          type xr:Rpl-policy;
          mandatory true;
          description
            "Configures a route policy, This leaf accepts a complete Cisco IOS XR CLI configuration string that defines a route-policy by its name and a route-policy contains a sequence of policy statements.
             
             route-policy sample
             [ . . . policy statements . . . ]
             end-policy
             
             Note: The entire route-policy configuration should be provided as a single string. The 'end-policy' keyword indicates the end of the route-policy definition.";
          xr:xr-xml-map "rpl_cfg:PolicyAsText";
        }
      }
    }
    container sets {
      description
        "All configured sets";
      xr:xr-xml-map "rpl_cfg:Sets";
      container prefix-sets {
        description
          "Information about Prefix sets";
        xr:xr-xml-map "rpl_cfg:PrefixSetTable";
        list prefix-set {
          key "set-name";
          description
            "Information about an individual set";
          xr:xr-xml-map "rpl_cfg:PrefixSet";
          leaf set-name {
            type xr:Cisco-ios-xr-string;
            description
              "Set name";
            xr:xr-xml-map "rpl_cfg:SetName";
          }
          leaf rpl-prefix-set {
            type xr:Rpl-set;
            mandatory true;
            description
              "Configures a prefix-set. This leaf accepts a complete Cisco IOS XR CLI configuration string that defines a prefix-set by its name and a prefix-set holds IPv4 or IPv6 prefix match specifications, each of which has four parts: an address, a mask length, a minimum matching length, and a maximum matching length. The address is required, but the other three parts are optional. The address is a standard dotted-decimal IPv4 or colon-separated hexadecimal IPv6 address.
               
               prefix-set legal-ipv4-prefix-examples
               10.0.1.1,
               10.0.2.0/24,
               10.0.3.0/24 ge 28,
               10.0.4.0/24 le 28,
               10.0.5.0/24 ge 26 le 30,
               10.0.6.0/24 eq 28,
               10.0.7.2/32 ge 16 le 24,
               10.0.8.0/26 ge 8 le 16
               end-set
               
               prefix-set legal-ipv6-prefix-examples
               2001:0:0:1::/64,
               2001:0:0:2::/64 ge 96,
               2001:0:0:2::/64 ge 96 le 100,
               2001:0:0:2::/64 eq 100
               end-set
               
               Note: The prefix-set entries should be separated by commas and the entire configuration should be provided as a single string. The 'end-set' keyword indicates the end of the prefix-set definition.";
            xr:xr-xml-map "rpl_cfg:PrefixSetAsText";
          }
        }
      }
      container large-community-sets {
        description
          "Information about Large Community sets";
        xr:xr-xml-map "rpl_cfg:LargeCommunitySetTable";
        list large-community-set {
          key "set-name";
          description
            "Information about an individual set";
          xr:xr-xml-map "rpl_cfg:LargeCommunitySet";
          leaf set-name {
            type xr:Cisco-ios-xr-string;
            description
              "Set name";
            xr:xr-xml-map "rpl_cfg:SetName";
          }
          leaf large-community-set-as-text {
            type xr:Rpl-set;
            mandatory true;
            description
              "Configures a large-community-set. This leaf accepts a complete Cisco IOS XR CLI configuration string that defines a large community-set by its name and a large community-set holds large community values for set or matching against the BGP large community attribute. Large communities in BGP are a more recent extension compared to regular communities and allow for more flexibility in expressing routing policies and preferences.
               
               large-community-set lcom
               874689:937649:0324302
               end-set
               
               Note: The large community-set entries should be separated by commas and the entire configuration should be provided as a single string. The 'end-set' keyword indicates the end of the large community-set definition.";
            xr:xr-xml-map "rpl_cfg:LargeCommunitySetAsText";
          }
        }
      }
      container mac-sets {
        description
          "Information about Mac sets";
        xr:xr-xml-map "rpl_cfg:MacSetTable";
        list mac-set {
          key "set-name";
          description
            "Information about an individual set";
          xr:xr-xml-map "rpl_cfg:MacSet";
          leaf set-name {
            type xr:Cisco-ios-xr-string;
            description
              "Set name";
            xr:xr-xml-map "rpl_cfg:SetName";
          }
          leaf mac-set-as-text {
            type xr:Rpl-set;
            mandatory true;
            description
              "Mac Set";
            xr:xr-xml-map "rpl_cfg:MacSetAsText";
          }
        }
      }
      container extended-community-opaque-sets {
        description
          "Information about Opaque sets";
        xr:xr-xml-map "rpl_cfg:ExtendedCommunityOpaqueSetTable";
        list extended-community-opaque-set {
          key "set-name";
          description
            "Information about an individual set";
          xr:xr-xml-map "rpl_cfg:ExtendedCommunityOpaqueSet";
          leaf set-name {
            type xr:Cisco-ios-xr-string;
            description
              "Set name";
            xr:xr-xml-map "rpl_cfg:SetName";
          }
          leaf rpl-extended-community-opaque-set {
            type xr:Rpl-set;
            mandatory true;
            description
              "Configures a extcommunity-set opaque. This leaf accepts a complete Cisco IOS XR CLI configuration string that defines a extcommunity-set opaque by its name and a opaque set is an extcommunity set configurations used to allows embedding arbitrary, non-interpreted data, This can be used for various custom routing policies.
               
               extcommunity-set opaque opaqueSet
               874239872
               end-set
               
               Note: The extcommunity-set opaque entries should be separated by commas and the entire configuration should be provided as a single string. The 'end-set' keyword indicates the end of the extcommunity-set opaque definition.";
            xr:xr-xml-map "rpl_cfg:ExtendedCommunityOpaqueSetAsText";
          }
        }
      }
      container ospf-area-sets {
        description
          "Information about OSPF Area sets";
        xr:xr-xml-map "rpl_cfg:OSPFAreaSetTable";
        list ospf-area-set {
          key "set-name";
          description
            "Information about an individual OSPF area set.
             Usage: OSPF area set allows to define named
             set of area numbers        which can be
             referenced in the route-policy. Area sets
             may be used during redistribution of the ospf
             protocol.  Example: ospf-area-set EXAMPLE
             1,
             192.168.1.255
             end-set
             Syntax: OSPF area number can be entered as 32
             bit number or in          the ip address
             format. See example.
             Semantic: Area numbers listed in the set will
             be searched for             a match. In the
             example these are areas 1 and
             192.168.1.255.                                ";
          xr:xr-xml-map "rpl_cfg:OSPFAreaSet";
          leaf set-name {
            type xr:Cisco-ios-xr-string;
            description
              "Set name";
            xr:xr-xml-map "rpl_cfg:SetName";
          }
          leaf rplospf-area-set {
            type xr:Rpl-set;
            mandatory true;
            description
              "Configures an ospf-area-set. This leaf accepts a complete Cisco IOS XR CLI configuration string that defines a ospf-area-set by its name and ospf-area-set allows grouping of routers within an OSPF network into distinct areas to optimize routing and reduce overhead.
               
               ospf-area-set areaSet
               124234,
               10.1.1.1
               end-set
               
               Note: The ospf-area-sets entries should be separated by commas and the entire configuration should be provided as a single string. The 'end-set' keyword indicates the end of the ospf-area-sets definition.";
            xr:xr-xml-map "rpl_cfg:OSPFAreaSetAsText";
          }
        }
      }
      container extended-community-cost-sets {
        description
          "Information about Cost sets";
        xr:xr-xml-map "rpl_cfg:ExtendedCommunityCostSetTable";
        list extended-community-cost-set {
          key "set-name";
          description
            "Information about an individual set";
          xr:xr-xml-map "rpl_cfg:ExtendedCommunityCostSet";
          leaf set-name {
            type xr:Cisco-ios-xr-string;
            description
              "Set name";
            xr:xr-xml-map "rpl_cfg:SetName";
          }
          leaf rpl-extended-community-cost-set {
            type xr:Rpl-set;
            mandatory true;
            description
              "Configures a extcommunity-set cost. This leaf accepts a complete Cisco IOS XR CLI configuration string that defines a extcommunity-set cost by its name and
               a cost set is an extcommunity set used to store cost EIGRP Cost Community type extended community type communities.
               
               extcommunity-set cost a_cost_set
               IGP:1:10
               end-set
               
               Note: The extcommunity-set cost entries should be separated by commas and the entire configuration should be provided as a single string. The 'end-set' keyword indicates the end of the extcommunity-set cost definition.";
            xr:xr-xml-map "rpl_cfg:ExtendedCommunityCostSetAsText";
          }
        }
      }
      container extended-community-soo-sets {
        description
          "Information about SOO sets";
        xr:xr-xml-map "rpl_cfg:ExtendedCommunitySOOSetTable";
        list extended-community-soo-set {
          key "set-name";
          description
            "Information about an individual set";
          xr:xr-xml-map "rpl_cfg:ExtendedCommunitySOOSet";
          leaf set-name {
            type xr:Cisco-ios-xr-string;
            description
              "Set name";
            xr:xr-xml-map "rpl_cfg:SetName";
          }
          leaf rpl-extended-community-soo-set {
            type xr:Rpl-set;
            mandatory true;
            description
              "Configures a extcommunity-set soo. This leaf accepts a complete Cisco IOS XR CLI configuration string that defines a extcommunity-set soo by its name and a soo set is an extcommunity set used to store BGP Site-of-Origin (SoO) extended community type communities.
               
               extcommunity-set soo a_soo_set
               1.1.1.1:100,
               100:200
               end-set
               
               Note: The extcommunity-set soo entries should be separated by commas and the entire configuration should be provided as a single string. The 'end-set' keyword indicates the end of the extcommunity-set soo definition.";
            xr:xr-xml-map "rpl_cfg:ExtendedCommunitySOOSetAsText";
          }
        }
      }
      container esi-sets {
        description
          "Information about Esi sets";
        xr:xr-xml-map "rpl_cfg:EsiSetTable";
        list esi-set {
          key "set-name";
          description
            "Information about an individual set";
          xr:xr-xml-map "rpl_cfg:EsiSet";
          leaf set-name {
            type xr:Cisco-ios-xr-string;
            description
              "Set name";
            xr:xr-xml-map "rpl_cfg:SetName";
          }
          leaf esi-set-as-text {
            type xr:Rpl-set;
            mandatory true;
            description
              "Esi Set";
            xr:xr-xml-map "rpl_cfg:EsiSetAsText";
          }
        }
      }
      container extended-community-seg-nh-sets {
        description
          "Information about SegNH sets";
        xr:xr-xml-map "rpl_cfg:ExtendedCommunitySegNHSetTable";
        list extended-community-seg-nh-set {
          key "set-name";
          description
            "Information about an individual set";
          xr:xr-xml-map "rpl_cfg:ExtendedCommunitySegNHSet";
          leaf set-name {
            type xr:Cisco-ios-xr-string;
            description
              "Set name";
            xr:xr-xml-map "rpl_cfg:SetName";
          }
          leaf rpl-extended-community-seg-nh-set {
            type xr:Rpl-set;
            mandatory true;
            description
              "Configures a extcommunity-set seg-nh. This leaf accepts a complete Cisco IOS XR CLI configuration string that defines a extcommunity-set seg-nh by its name and seg-nh indicates the Point-to-Multipoint (P2MP) segmented next-hop extended community to indicate LSPs should be segmented when the BGP MVPN I-PMSI or S-PMSI autodiscovery (AD) routes are advertised or propagated to signal inter-area P2MP service.
               
               extcommunity-set seg-nh seg_set
               1.1.1.1
               end-set
               
               Note: The extcommunity-set seg-nh entries should be separated by commas and the entire configuration should be provided as a single string. The 'end-set' keyword indicates the end of the extcommunity-set seg-nh definition.";
            xr:xr-xml-map "rpl_cfg:ExtendedCommunitySegNHSetAsText";
          }
        }
      }
      container rd-sets {
        description
          "Information about RD sets";
        xr:xr-xml-map "rpl_cfg:RDSetTable";
        list rd-set {
          key "set-name";
          description
            "Information about an individual set";
          xr:xr-xml-map "rpl_cfg:RDSet";
          leaf set-name {
            type xr:Cisco-ios-xr-string;
            description
              "Set name";
            xr:xr-xml-map "rpl_cfg:SetName";
          }
          leaf rplrd-set {
            type xr:Rpl-set;
            mandatory true;
            description
              "Configures a rd-set. This leaf accepts a complete Cisco IOS XR CLI configuration string that defines a rd-set by its name and a rd-set is used to create a set with route distinguisher (RD) elements. RD set is a 64-bit value prepended to an IPv4 address to create a globally unique Border Gateway Protocol (BGP) VPN IPv4 address.
               You can define RD values with the following commands:
               
               * a.b.c.d:m:*—BGP VPN RD in IPv4 format with a wildcard character. For example, 10.0.0.2:255.255.0.0:*.
               * a.b.c.d/m:n—BGP VPN RD in IPv4 format with a mask. For example, 10.0.0.2:255.255.0.0:666.
               * a.b.c.d:** —BGP VPN RD in IPv4 format with a wildcard character. For example, 10.0.0.2:255.255.0.0.
               * a.b.c.d:n— BGP VPN RD in IPv4 format. For example, 10.0.0.2:666.
               * asn:*— BGP VPN RD in ASN format with a wildcard character. For example, 10002:255.255.0.0.
               * asn:n—BGP VPN RD in ASN format. For example, 10002:666.
               
               rd-set rdset
               10.0.0.0/8:*,
               10.0.0.0/8:777,
               10.0.0.0:*,
               10.0.0.0:777,
               65000:*,
               65000:777
               end-set
               
               Note: The rd-set entries should be separated by commas and the entire configuration should be provided as a single string. The 'end-set' keyword indicates the end of the rd-set  definition.";
            xr:xr-xml-map "rpl_cfg:RDSetAsText";
          }
        }
      }
      container policy-global-set-table {
        description
          "Information about PolicyGlobal sets";
        xr:xr-xml-map "rpl_cfg:PolicyGlobalSetTable";
        leaf policy-global-set {
          type xr:Rpl-set;
          description
            "Information about an individual set";
          xr:xr-xml-map "rpl_cfg:PolicyGlobalSet";
        }
      }
      container extended-community-bandwidth-sets {
        description
          "Information about Bandwidth sets";
        xr:xr-xml-map "rpl_cfg:ExtendedCommunityBandwidthSetTable";
        list extended-community-bandwidth-set {
          key "set-name";
          description
            "Information about an individual set";
          xr:xr-xml-map "rpl_cfg:ExtendedCommunityBandwidthSet";
          leaf set-name {
            type xr:Cisco-ios-xr-string;
            description
              "Set name";
            xr:xr-xml-map "rpl_cfg:SetName";
          }
          leaf rpl-extended-community-bandwidth-set {
            type xr:Rpl-set;
            mandatory true;
            description
              "Configures a extcommunity-set bandwidth. This leaf accepts a complete Cisco IOS XR CLI configuration string that defines a extcommunity-set bandwidth by its name and a bandwidth set is an extcommunity set configurations used to to control the routing of traffic based on bandwidth criteria.
               
               extcommunity-set bandwidth bandset
               1678:9876,
               8678:9876
               end-set
               
               Note: The extcommunity-set bandwidth entries should be separated by commas and the entire configuration should be provided as a single string. The 'end-set' keyword indicates the end of the extcommunity-set bandwidth definition.";
            xr:xr-xml-map "rpl_cfg:ExtendedCommunityBandwidthSetAsText";
          }
        }
      }
      container community-sets {
        description
          "Information about Community sets";
        xr:xr-xml-map "rpl_cfg:CommunitySetTable";
        list community-set {
          key "set-name";
          description
            "Information about an individual set";
          xr:xr-xml-map "rpl_cfg:CommunitySet";
          leaf set-name {
            type xr:Cisco-ios-xr-string;
            description
              "Set name";
            xr:xr-xml-map "rpl_cfg:SetName";
          }
          leaf rpl-community-set {
            type xr:Rpl-set;
            mandatory true;
            description
              "Configures a community-set. This leaf accepts a complete Cisco IOS XR CLI configuration string that defines a community-set by its name and a community-set holds community values for set or matching against the BGP community attribute. A community is a 32-bit quantity. Integer community values must be split in half and expressed as two unsigned decimal integers in the range from 0 to 65535, separated by a colon. Single 32-bit community values are not allowed.
               
               community-set comSet
               12:34,
               12:56,
               12:78,
               internet
               end-set
               
               Note: The community-set entries should be separated by commas and the entire configuration should be provided as a single string. The 'end-set' keyword indicates the end of the community-set definition.";
            xr:xr-xml-map "rpl_cfg:CommunitySetAsText";
          }
        }
      }
      container as-path-sets {
        description
          "Information about AS Path sets";
        xr:xr-xml-map "rpl_cfg:ASPathSetTable";
        list as-path-set {
          key "set-name";
          description
            "Information about an individual set";
          xr:xr-xml-map "rpl_cfg:ASPathSet";
          leaf set-name {
            type xr:Cisco-ios-xr-string;
            description
              "Set name";
            xr:xr-xml-map "rpl_cfg:SetName";
          }
          leaf rplas-path-set {
            type xr:Rpl-set;
            mandatory true;
            description
              "Configures an as-path-set. This leaf accepts a complete Cisco IOS XR CLI configuration string that defines an as-path-set by its name and includes a list of autonomous system (AS) numbers that form the set. The AS path set is used in route policy expressions to match AS path attributes in BGP routing updates. Each AS number in the set represents an autonomous system number that can be matched against the AS path of a BGP route.
               
               as-path-set aspathSet
               12345,
               67890
               end-set
               
               Note: The as-path entries should be separated by commas and the entire configuration should be provided as a single string. The 'end-set' keyword indicates the end of the as-path-set definition.";
            xr:xr-xml-map "rpl_cfg:ASPathSetAsText";
          }
        }
      }
      container tag-sets {
        description
          "Information about Tag sets";
        xr:xr-xml-map "rpl_cfg:TagSetTable";
        list tag-set {
          key "set-name";
          description
            "Information about an individual set";
          xr:xr-xml-map "rpl_cfg:TagSet";
          leaf set-name {
            type xr:Cisco-ios-xr-string;
            description
              "Set name";
            xr:xr-xml-map "rpl_cfg:SetName";
          }
          leaf rpl-tag-set {
            type xr:Rpl-set;
            mandatory true;
            description
              "Configures a tag-set. This leaf accepts a complete Cisco IOS XR CLI configuration string that defines a tag-set by its name and a tag-set holds tag values for set or matching against the BGP tag attribute.
               
               tag-set tag_set
               8726,
               1276
               end-set
               
               Note: The tag-set entries should be separated by commas and the entire configuration should be provided as a single string. The 'end-set' keyword indicates the end of the tag-set definition.";
            xr:xr-xml-map "rpl_cfg:TagSetAsText";
          }
        }
      }
      container etag-sets {
        description
          "Information about Etag sets";
        xr:xr-xml-map "rpl_cfg:EtagSetTable";
        list etag-set {
          key "set-name";
          description
            "Information about an individual set";
          xr:xr-xml-map "rpl_cfg:EtagSet";
          leaf set-name {
            type xr:Cisco-ios-xr-string;
            description
              "Set name";
            xr:xr-xml-map "rpl_cfg:SetName";
          }
          leaf etag-set-as-text {
            type xr:Rpl-set;
            mandatory true;
            description
              "Configures a etag-set. This leaf accepts a complete Cisco IOS XR CLI configuration string that defines a etag-set by its name and a etag-set holds etag values for set or matching against the BGP etag attribute.
               
               etag-set etagSet
               876381,
               208730
               end-set
               
               Note: The etag-set entries should be separated by commas and the entire configuration should be provided as a single string. The 'end-set' keyword indicates the end of the etag-set definition.";
            xr:xr-xml-map "rpl_cfg:EtagSetAsText";
          }
        }
      }
      container extended-community-rt-sets {
        description
          "Information about RT sets";
        xr:xr-xml-map "rpl_cfg:ExtendedCommunityRTSetTable";
        list extended-community-rt-set {
          key "set-name";
          description
            "Information about an individual set";
          xr:xr-xml-map "rpl_cfg:ExtendedCommunityRTSet";
          leaf set-name {
            type xr:Cisco-ios-xr-string;
            description
              "Set name";
            xr:xr-xml-map "rpl_cfg:SetName";
          }
          leaf rpl-extended-community-rt-set {
            type xr:Rpl-set;
            mandatory true;
            description
              "Configures a extcommunity-set rt. This leaf accepts a complete Cisco IOS XR CLI configuration string that defines a extcommunity-set rt by its name and a rt set is an extcommunity set used to store BGP Route Target (RT) extended community type communities.
               
               extcommunity-set rt a_rt_set
               1.2.3.4:666
               1234:666,
               1.2.3.4:777,
               4567:777
               end-set
               
               Note: The extcommunity-set rt entries should be separated by commas and the entire configuration should be provided as a single string. The 'end-set' keyword indicates the end of the extcommunity-set rt definition.";
            xr:xr-xml-map "rpl_cfg:ExtendedCommunityRTSetAsText";
          }
        }
      }
      container extended-community-evpn-bandwidth-sets {
        description
          "Information about EVPN Link Bandwidth sets";
        xr:xr-xml-map "rpl_cfg:ExtendedCommunityEVPNBandwidthSetTable";
        list extended-community-evpn-bandwidth-set {
          key "set-name";
          description
            "Information about an individual set";
          xr:xr-xml-map "rpl_cfg:ExtendedCommunityEVPNBandwidthSet";
          leaf set-name {
            type xr:Cisco-ios-xr-string;
            description
              "Set name";
            xr:xr-xml-map "rpl_cfg:SetName";
          }
          leaf rpl-extended-community-evpn-bandwidth-set {
            type xr:Rpl-set;
            mandatory true;
            description
              "Configures a extcommunity-set even link bandwidth. This leaf accepts a complete Cisco IOS XR CLI configuration string that defines a extcommunity-set evpn link bandwidth by its name and a evpn link bandwidth set is an extcommunity set configurations used to setting up specific attributes that are used to signal and control link bandwidth within the EVPN.
               
               extcommunity-set evpn-link-bandwidth lb-set
               1:50001,
               0:50001,
               1:50000
               end-set
               
               Note: The extcommunity-set even link bandwidth entries should be separated by commas and the entire configuration should be provided as a single string. The 'end-set' keyword indicates the end of the extcommunity-set evpn link bandwidth definition.";
            xr:xr-xml-map "rpl_cfg:ExtendedCommunityEVPNBandwidthSetAsText";
          }
        }
      }
    }
    container limits {
      description
        "Limits for Routing Policy";
      xr:xr-xml-map "rpl_cfg:Limits";
      leaf maximum-lines-of-policy {
        type int32;
        default "131072";
        description
          "Maximum number of lines of policy configuration
           that may be configured in total";
        xr:xr-xml-map "rpl_cfg:MaximumLinesOfPolicy";
      }
      leaf maximum-number-of-policies {
        type int32;
        default "5000";
        description
          "Maximum number of policies that may be
           configured";
        xr:xr-xml-map "rpl_cfg:MaximumNumberOfPolicies";
      }
    }
    leaf set-exit-as-abort {
      type empty;
      description
        "Set exit under RPL config to abort";
      xr:xr-xml-map "rpl_cfg:SetExitAsAbort";
      xr:xr-cli-map "rpl set-exit-as-abort ";
    }
  }
}
