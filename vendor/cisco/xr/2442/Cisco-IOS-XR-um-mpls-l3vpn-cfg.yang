module Cisco-IOS-XR-um-mpls-l3vpn-cfg {
  namespace "http://cisco.com/ns/yang/Cisco-IOS-XR-um-mpls-l3vpn-cfg";
  prefix um-mpls-l3vpn-cfg;

  import cisco-semver {
    prefix semver;
  }
  import Cisco-IOS-XR-um-snmp-server-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-te package configuration.
     
     This YANG module augments the
     modules with configuration data.
     
     Copyright (c) 2019-2022 by Cisco Systems, Inc.
     All rights reserved.";

  revision 2022-07-11 {
    description
      "Added missing description statement to nodes";
    semver:module-version "1.0.1";
  }
  revision 2019-06-10 {
    description
      "Establish semantic version baseline.";
    semver:module-version "1.0.1";
  }
  revision 2019-04-04 {
    description
      "Initial version";
  }

  augment "/a1:snmp-server/a1:traps" {
    description
      "This augment extends snmp-server traps nodes
       configuration";
    container mpls {
      description
        "Enable SNMP MPLS traps";
      container l3vpn {
        description
          "Enable MPLS L3VPN traps";
        container all {
          presence "Indicates a all node is configured.";
          description
            "Enable all MPLS L3VPN traps";
        }
        container vrf-up {
          presence "Indicates a vrf-up node is configured.";
          description
            "Enable VRF up traps";
        }
        container vrf-down {
          presence "Indicates a vrf-down node is configured.";
          description
            "Enable VRF down traps";
        }
        container mid-threshold-exceeded {
          presence "Indicates a mid-threshold-exceeded node is configured.";
          description
            "Enable mid-threshold exceeded traps";
        }
        container max-threshold-exceeded {
          presence "Indicates a max-threshold-exceeded node is configured.";
          description
            "Enable max-threshold exceeded traps";
        }
        container max-threshold-cleared {
          presence "Indicates a max-threshold-cleared node is configured.";
          description
            "Enable max-threshold cleared traps";
        }
        leaf max-threshold-reissue-notif-time {
          type uint32 {
            range "0..2147483647" {
              description
                "Time interval in seconds";
            }
          }
          description
            "Time interval (secs) for re-issuing max-threshold notification";
        }
      }
    }
  }
}
