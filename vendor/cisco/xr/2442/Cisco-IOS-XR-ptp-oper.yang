module Cisco-IOS-XR-ptp-oper {
  namespace "http://cisco.com/ns/yang/Cisco-IOS-XR-ptp-oper";
  prefix ptp-oper;

  import Cisco-IOS-XR-types {
    prefix xr;
  }
  import cisco-semver {
    prefix semver;
  }
  include Cisco-IOS-XR-ptp-oper-sub1 {
    revision-date 2024-06-18;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ptp package operational data.
     
     This module contains definitions
     for the following management objects:
       ptp: PTP operational data
     
     Copyright (c) 2013-2024 by Cisco Systems, Inc.
     All rights reserved.";

  revision 2024-06-18 {
    description
      "Corrected ForeignMasterQualified leaf name to NoFMQualified
       2024-06-04
         Add support for virtual port offset from best master
       2024-05-22
         Change timer-expiry type
       2024-03-01
         Add support for performance-monitoring
       2023-05-23
         Add oper for source phase-difference value and status from servo
       2021-10-05
         Add double-failure-clock-class information to show ptp ctrlr database";
    semver:module-version "2.3.0";
  }
  revision 2020-09-07 {
    description
      "Show command updates for APTS and virtual port";
    semver:module-version "2.2.0";
  }
  revision 2020-02-06 {
    description
      "Added valid flags for receiver clock information, sender clock information and master entry properties.
       2019-12-18
         Added checksum related packet drop reasons and servo status enums.";
    semver:module-version "2.1.0";
  }
  revision 2019-10-01 {
    description
      "Corrected enum names for servo.
       2019-09-30
         Added incompatible packet for non-negotiated setting in packet drop reasons.";
    semver:module-version "2.0.0";
  }
  revision 2019-04-05 {
    description
      "Establish semantic version baseline.";
    semver:module-version "1.0.0";
  }
  revision 2017-02-02 {
    description
      "Initial version.";
  }
  revision 2015-11-09 {
    description
      "IOS XR 6.0 revision.";
  }

  container ptp {
    config false;
    description
      "PTP operational data";
    container nodes {
      description
        "Table for node-specific operational data";
      list node {
        key "node-name";
        description
          "Node-specific operational data for a given node";
        container node-interface-foreign-masters {
          description
            "Table for node foreign master clock
             operational data";
          list node-interface-foreign-master {
            key "interface-name";
            description
              "Node interface foreign master clock
               operational data";
            leaf interface-name {
              type xr:Interface-name;
              description
                "Interface name";
            }
            uses PTP-IF-CLOCK-INFO;
          }
        }
        container summary {
          description
            "Node summary operational data";
          uses PTP-SUMMARY-INFO;
        }
        container node-interfaces {
          description
            "Table for node interface operational data";
          list node-interface {
            key "interface-name";
            description
              "Node interface operational data";
            leaf interface-name {
              type xr:Interface-name;
              description
                "Interface name";
            }
            uses PTP-IF-INFO;
          }
        }
        container node-interface-unicast-peers {
          description
            "Table for node unicast peers operational data";
          list node-interface-unicast-peer {
            key "interface-name";
            description
              "Node interface unicast peers operational data";
            leaf interface-name {
              type xr:Interface-name;
              description
                "Interface name";
            }
            uses PTP-IF-UNICAST-PEER-INFO;
          }
        }
        container packet-counters {
          description
            "Node packet counter operational data";
          uses PTP-NODE-PACKET-COUNTER-INFO;
        }
        leaf node-name {
          type xr:Node-id;
          description
            "Node";
        }
      }
    }
    container summary {
      description
        "Summary operational data";
      uses PTP-SUMMARY-INFO;
    }
    container interface-configuration-errors {
      description
        "Table for interface configuration error
         operational data";
      list interface-configuration-error {
        key "interface-name";
        description
          "Interface configuration error operational data";
        leaf interface-name {
          type xr:Interface-name;
          description
            "Interface name";
        }
        uses PTP-IF-CONFIG-ERRORS-ENTRY;
      }
    }
    container interface-foreign-masters {
      description
        "Table for interface foreign master clock
         operational data";
      list interface-foreign-master {
        key "interface-name";
        description
          "Interface foreign master clock operational data";
        leaf interface-name {
          type xr:Interface-name;
          description
            "Interface name";
        }
        uses PTP-IF-CLOCK-INFO;
      }
    }
    container interface-interops {
      description
        "Table for interface interop operational data";
      list interface-interop {
        key "interface-name";
        description
          "Interface interop operational data";
        leaf interface-name {
          type xr:Interface-name;
          description
            "Interface name";
        }
        uses PTP-IF-INTEROP-INFO;
      }
    }
    container local-clock {
      description
        "Local clock operational data";
      uses PTP-LOCAL-CLOCK-INFO;
    }
    container interface-packet-counters {
      description
        "Table for interface packet counter operational
         data";
      list interface-packet-counter {
        key "interface-name";
        description
          "Interface packet counter operational data";
        leaf interface-name {
          type xr:Interface-name;
          description
            "Interface name";
        }
        uses PTP-IF-PACKET-COUNTER-INFO;
      }
    }
    container advertised-clock {
      description
        "Advertised clock operational data";
      uses PTP-ADVERTISED-CLOCK-INFO;
    }
    container interfaces {
      description
        "Table for interface operational data";
      list interface {
        key "interface-name";
        description
          "Interface operational data";
        leaf interface-name {
          type xr:Interface-name;
          description
            "Interface name";
        }
        uses PTP-IF-INFO;
      }
    }
    container dataset {
      description
        "Global PTP datasets";
      container default-ds {
        description
          "defaultDS information as described in IEEE
           1588-2008";
        uses PTP-DEFAULT-DS-INFO;
      }
      container performance-monitoring-dses {
        description
          "Table for performance monitoring datasets as
           described in IEEE 1588-2019 Annex J";
        list performance-monitoring-ds {
          key "clock-id steps-removed receiving-port";
          description
            "Performance monitoring dataset for tracked PTP
             source as described in IEEE 1588-2019 Annex J";
          leaf clock-id {
            type xr:Cisco-ios-xr-string;
            description
              "Clock ID";
          }
          leaf steps-removed {
            type xr:Cisco-ios-xr-string;
            description
              "Steps removed";
          }
          leaf receiving-port {
            type xr:Cisco-ios-xr-string;
            description
              "Receiving port";
          }
          uses PTP-PM-DS-INFO;
        }
      }
      container current-ds {
        description
          "currentDS information as described in IEEE
           1588-2008";
        uses PTP-CURRENT-DS-INFO;
      }
      container parent-ds {
        description
          "parentDS information as described in IEEE
           1588-2008";
        uses PTP-PARENT-DS-INFO;
      }
      container port-dses {
        description
          "Table for portDS information";
        list port-ds {
          key "interface-name";
          description
            "PortDS information";
          leaf interface-name {
            type xr:Interface-name;
            description
              "Interface name";
          }
          uses PTP-PORT-DS-INFO;
        }
      }
      container performance-monitoring-port-dses {
        description
          "Table for port specific performance monitoring
           datasets as described in IEEE 1588-2019 Annex J";
        list performance-monitoring-port-ds {
          key "interface-name";
          description
            "Port specific performance monitoring dataset
             for tracked PTP source as described in IEEE
             1588-2019 Annex J";
          leaf interface-name {
            type xr:Interface-name;
            description
              "Interface name";
          }
          uses PTP-PM-PORT-DS-INFO;
        }
      }
      container time-properties-ds {
        description
          "timePropertiesDS information as described in
           IEEE 1588-2008";
        uses PTP-TIME-PROPERTIES-DS-INFO;
      }
    }
    container global-configuration-error {
      description
        "Global configuration error operational data";
      uses PTP-GL-CONFIG-ERRORS-INFO;
    }
    container grandmaster {
      description
        "Grandmaster clock operational data";
      uses PTP-GRANDMASTER-INFO;
    }
    container interface-unicast-peers {
      description
        "Table for interface unicast peers operational
         data";
      list interface-unicast-peer {
        key "interface-name";
        description
          "Interface unicast peers operational data";
        leaf interface-name {
          type xr:Interface-name;
          description
            "Interface name";
        }
        uses PTP-IF-UNICAST-PEER-INFO;
      }
    }
    container servo-sources-info {
      description
        "Information about sources tracked by servo";
      uses PTP-QUALIFIED-SERVO-SOURCES-INFO;
    }
    container utc-offset-info {
      description
        "UTC offset information";
      uses PTP-LEAP-SECONDS-INFO;
    }
  }
}
