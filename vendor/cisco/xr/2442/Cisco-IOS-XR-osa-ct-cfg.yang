module Cisco-IOS-XR-osa-ct-cfg {
  namespace "http://cisco.com/ns/yang/Cisco-IOS-XR-osa-ct-cfg";
  prefix osa-ct-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa-ct package configuration.
     
     This module contains definitions
     for the following management objects:
       resrv-cli: Reserve Slot Cli Configuration
     
     Copyright (c) 2013-2024 by Cisco Systems, Inc.
     All rights reserved.";

  revision 2024-06-20 {
    description
      "Adding new Callisto LC for NCS1014
       2023-01-17
         Enhancement in CLI for NCS1010.
       2022-12-01
         Adding new bellatrix licenced LC in BH
       2022-08-25
         Updating new PID for ncs1010 Line and Amplifier cards and SkinnyBO license card
       2022-02-07
         Updating new PID Skinny BO LC for BH
       2022-01-17
         Adding new Skinny BO LC for BH
       2021-11-12
         Enhancement in CLI for NCS1010";
    semver:module-version "1.1.0";
  }
  revision 2020-05-28 {
    description
      "Initial Revision.";
    semver:module-version "1.0.0";
  }
  revision 2019-04-05 {
    description
      "Establish semantic version baseline.";
  }
  revision 2015-11-09 {
    description
      "IOS XR 6.0 revision.";
  }

  typedef Card {
    type enumeration {
      enum "ncs1k4-1.2t-k9" {
        value 1;
        description
          "C Band Card";
      }
      enum "ncs1k4-1.2t-l-k9" {
        value 2;
        description
          "Licensed Card";
      }
      enum "ncs1k4-1.2tl-k9" {
        value 3;
        description
          "L Band Card";
      }
      enum "ncs1k4-otn-xp" {
        value 4;
        description
          "BO Card";
      }
      enum "ncs1k4-otn-xpl" {
        value 5;
        description
          "BO Licensed Card";
      }
      enum "ncs1k4-2-qdd-c-k9" {
        value 6;
        description
          "BELLATRIX C Band Card";
      }
      enum "ncs1k4-lc-filler" {
        value 7;
        description
          "Filler Card";
      }
      enum "ncs1k-olt-c" {
        value 8;
        description
          "Line Terminal Card";
      }
      enum "ncs1k-olt-r-c" {
        value 9;
        description
          "Line Terminal + Raman Card";
      }
      enum "ncs1k-ila-c" {
        value 10;
        description
          "Line Amplifier Card";
      }
      enum "ncs1k-ila-r-c" {
        value 11;
        description
          "Line Amplifier + Raman Card";
      }
      enum "ncs1k-ila-2r-c" {
        value 12;
        description
          "Line Amplifier + 2Raman Card";
      }
      enum "ncs1k4-qxp-k9" {
        value 13;
        description
          "SKINNY BO Card";
      }
      enum "ncs1k4-qxp-l-k9" {
        value 14;
        description
          "SKINNY BO Licen";
      }
      enum "ncs1k-olt-l" {
        value 15;
        description
          "L-Band Line Terminal Card";
      }
      enum "ncs1k-ila-l" {
        value 16;
        description
          "L-Band Line Amplifier Card";
      }
      enum "ncs1k4-2-qdd-ck9l" {
        value 17;
        description
          "BELLATRIX Licensed C Band Card";
      }
      enum "ncs1k14-2.4t-k9" {
        value 18;
        description
          "NCS1K14 Pulsar line card";
      }
      enum "ncs1k14-2.4t-l-k9" {
        value 19;
        description
          "NCS1K14 Pulsar Licensed card";
      }
      enum "ncs1k14-blank" {
        value 20;
        description
          "Network Convergence System 1014 Filler";
      }
      enum "ncs1k14-ccmd-16-c" {
        value 21;
        description
          "NCS1014 16 port Colorless Direct attach LC with
           EDFA C-band";
      }
      enum "ncs1k14-ccmd-16-l" {
        value 22;
        description
          "NCS1014 16 port Colorless Direct attach LC with
           EDFA L-band";
      }
      enum "ncs1k14-2.4t-x-k9" {
        value 23;
        description
          "NCS1K14 Dione line card";
      }
      enum "ncs1k14-2.4txl-k9" {
        value 24;
        description
          "NCS1K14 Dione licensed line card";
      }
      enum "ncs1k-e-olt-l" {
        value 25;
        description
          "NCS1K Enceladus Optical Line Terminal L-band
           Card";
      }
      enum "ncs1k-e-olt-c" {
        value 26;
        description
          "NCS1K Enceladus Optical Line Terminal C-band
           Card";
      }
      enum "ncs1k-e-olt-r-c" {
        value 27;
        description
          "NCS1K Enceladus Optical Line Terminal C-band
           Card + Raman Card";
      }
      enum "ncs1k-e-ila-r-c" {
        value 28;
        description
          "NCS1K Enceladus In-Line Amplifier C-band Card +
           Raman Card";
      }
      enum "ncs1k-e-ila-r-c-2" {
        value 29;
        description
          "NCS1K Enceladus In-Line Amplifier C-band Card +
           Raman2 Card";
      }
      enum "ncs1k-e-ila-2r-c" {
        value 30;
        description
          "NCS1K Enceladus In-Line Amplifier L-band Card +
           2 Raman Card";
      }
      enum "ncs1k14-edfa2" {
        value 31;
        description
          "NCS1K14 Callisto EDFA C-band";
      }
    }
    description
      "Card";
  }

  container resrv-cli {
    description
      "Reserve Slot Cli Configuration";
    list slot-info-cli {
      key "lc-slot";
      description
        "location of LC";
      leaf card-type-cli {
        type Card;
        description
          "CardType config type";
      }
      leaf lc-slot {
        type xr:Cisco-ios-xr-string;
        description
          "LC location";
      }
    }
  }
}
