module Cisco-IOS-XR-um-l2snoop-cfg {
  namespace "http://cisco.com/ns/yang/Cisco-IOS-XR-um-l2snoop-cfg";
  prefix um-l2snoop-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR l2snoop package configuration.
     
     This YANG module augments the
     modules with configuration data.
     
     Copyright (c) 2021-2022 by Cisco Systems, Inc.
     All rights reserved.";

  revision 2022-03-08 {
    description
      "Removed Cisco-IOS-XR-types import";
    semver:module-version "1.1.0";
  }
  revision 2021-06-07 {
    description
      "Initial release";
    semver:module-version "1.0.0";
  }

  container l2snoop {
    description
      "Global l2snoop configuration command";
    leaf directory {
      type string {
        length "1..800" {
          description
            "Place debug files in this directory";
        }
      }
      must "../files and ../size";
      description
        "Specify l2snoop debug directory location";
    }
    leaf files {
      type uint32 {
        range "1..10" {
          description
            "Maximum debug files";
        }
      }
      must "../directory";
      description
        "Set maximum debug files";
    }
    leaf size {
      type uint32 {
        range "1024..4294967295" {
          description
            "Maximum file size in bytes";
        }
      }
      must "../directory";
      description
        "Set maximum file size";
    }
    leaf receive-queue {
      type uint32 {
        range "40..800" {
          description
            "Number of packets in receive queue";
        }
      }
      description
        "l2snoop receive packet queue size";
    }
  }
}
