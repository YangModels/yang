module Cisco-IOS-XR-accounting-cfg {
  namespace "http://cisco.com/ns/yang/Cisco-IOS-XR-accounting-cfg";
  prefix accounting-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR accounting package configuration.
     
     This module contains definitions
     for the following management objects:
       accounting: Global Accounting configuration commands
     
     Copyright (c) 2013-2024 by Cisco Systems, Inc.
     All rights reserved.";

  revision 2024-09-17 {
    description
      "Removed deprecated information from FIB external client data
       2024-04-18
         Modified debug info for FIB load balancing oor Dampening and DLB
       2024-03-28
         Added yang support for hardware resmon accounting data
       2024-03-18
         Added debug info of LDI fixup modify delay count in cef misc for FIB load balancing oor protection
       2024-03-14
         Added summary count for objects in FIB load balancing oor DLB
       2024-02-28
         Added more fields of debug info for FIB load balancing oor Dampening and DLB
       2024-02-21
         Added next-hop-group-encap-id to external-client instances
       2024-02-13
         Added Debugability support for FIB load balancing oor Dampening and DLB
       2023-01-13
         Added prefix accounting support with SRv6 as first application";
    semver:module-version "1.1.0";
  }
  revision 2019-04-05 {
    description
      "Establish semantic version baseline.";
    semver:module-version "1.0.1";
  }
  revision 2017-05-31 {
    description
      "Fixing backward compatibility error in module.";
  }
  revision 2015-11-09 {
    description
      "IOS XR 6.0 revision.";
  }

  typedef Acct-rpl-name {
    type xr:Cisco-ios-xr-string {
      length "1..256";
    }
    description
      "Acct rpl name";
  }

  typedef Acct-mode {
    type enumeration {
      enum "per-prefix-per-nexthop" {
        value 3;
        description
          "Per-prefix per-nexthop";
      }
    }
    description
      "Acct mode";
  }

  typedef Acct-prefix {
    type enumeration {
      enum "srv6-locators" {
        value 2;
        description
          "SRv6 locator (IPv6) prefixes";
      }
    }
    description
      "Acct prefix";
  }

  typedef Acct-af {
    type enumeration {
      enum "ipv6" {
        value 2;
        description
          "IPv6";
      }
    }
    description
      "Acct af";
  }

  typedef Acct-prefix-filter {
    type enumeration {
      enum "none" {
        value 0;
        description
          "No filter";
      }
    }
    description
      "Acct prefix filter";
  }

  container accounting {
    description
      "Global Accounting configuration commands";
    container interfaces {
      description
        "Interfaces configuration";
      container mpls {
        description
          "Interfaces MPLS configuration";
        leaf enable {
          type empty;
          description
            "Enable accounting on MPLS";
        }
        leaf enable-v4rsvpte {
          type empty;
          description
            "Enable accounting on MPLS IPv4 RSVP TE";
        }
      }
      container segment-routing {
        description
          "Interfaces Segment Routing configuration";
        leaf enable {
          type empty;
          description
            "Enable accounting on Segment Routing";
        }
        leaf enable-mplsv4 {
          type empty;
          description
            "Enable accounting on Segment Routing MPLS IPv4";
        }
        leaf enable-mplsv6 {
          type empty;
          description
            "Enable accounting on Segment Routing MPLS IPv6";
        }
      }
      leaf enable {
        type empty;
        description
          "Enable accounting on Interfaces";
      }
    }
    container prefixes {
      description
        "Prefixes configuration";
      container address-families {
        description
          "Address-family specific configuration";
        list address-family {
          key "type";
          description
            "Configure data for given address-family";
          container mode {
            presence "Contains mandatory nodes that used to set default values";
            description
              "Configure accounting mode and parameters";
            leaf accounting-mode {
              when "../filter-type = 'none'" {
                description
                  "../FilterType = None";
              }
              type Acct-mode;
              mandatory true;
              description
                "Accounting mode type";
            }
            leaf prefix-type {
              when "../filter-type = 'none'" {
                description
                  "../FilterType = None";
              }
              type Acct-prefix;
              mandatory true;
              description
                "Type of prefixes";
            }
            leaf filter-type {
              type Acct-prefix-filter;
              mandatory true;
              description
                "Prefix filtering type";
            }
            leaf route-policy-name {
              type Acct-rpl-name;
              description
                "Name of route-policy";
            }
          }
          leaf type {
            type Acct-af;
            description
              "Address-family type";
          }
        }
      }
    }
    leaf enable {
      type empty;
      description
        "Enable Accounting";
    }
  }
}
