module Cisco-IOS-XR-ssm-cfg {
  namespace "http://cisco.com/ns/yang/Cisco-IOS-XR-ssm-cfg";
  prefix ssm-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ssm package configuration.
     
     This module contains definitions
     for the following management objects:
       ssmenable: Container Schema for ssm configuration
     
     Copyright (c) 2013-2024 by Cisco Systems, Inc.
     All rights reserved.";

  revision 2024-10-22 {
    description
      "Updated leaf description.";
    semver:module-version "1.0.0";
  }
  revision 2019-04-05 {
    description
      "Establish semantic version baseline.";
    semver:module-version "1.0.0";
  }
  revision 2015-11-09 {
    description
      "IOS XR 6.0 revision.";
  }

  container ssmenable {
    description
      "Container Schema for ssm configuration";
    leaf service {
      type empty;
      description
        "ssm monitoring disable";
    }
  }
}
