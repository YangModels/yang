module Cisco-IOS-XR-8000-platforms-npu-resources-oper {
  namespace "http://cisco.com/ns/yang/Cisco-IOS-XR-8000-platforms-npu-resources-oper";
  prefix xr-8000-platforms-npu-resources-oper;

  import cisco-semver {
    prefix semver;
  }
  import Cisco-IOS-XR-platforms-ofa-oper {
    prefix a1;
  }
  include Cisco-IOS-XR-8000-platforms-npu-resources-oper-sub1 {
    revision-date 2023-09-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-platforms-npu-resources package operational data.
     
     This YANG module augments the
       Cisco-IOS-XR-platforms-ofa-oper
     module with state data.
     
     Copyright (c) 2013-2023 by Cisco Systems, Inc.
     All rights reserved.";

  revision 2023-09-19 {
    description
      "Added high watermark for each resource
       2022-11-29
         Updated yang structure to include keyed lists
       2022-09-26
         Updated to remove unused fields
       2022-08-16
         Added new hwdb resources.";
    semver:module-version "4.0.0";
  }
  revision 2020-10-07 {
    description
      "Updated leaf fields and container stats";
    semver:module-version "3.0.0";
  }
  revision 2019-04-05 {
    description
      "Establish semantic version baseline.";
    semver:module-version "1.0.0";
  }
  revision 2015-11-09 {
    description
      "IOS XR 6.0 revision.";
  }

  typedef Resource {
    type enumeration {
      enum "counter-bank" {
        value 0;
        description
          "counter bank";
      }
      enum "l3-ac-port" {
        value 1;
        description
          "l3 ac port";
      }
      enum "native-fec-entry" {
        value 2;
        description
          "native fec entry";
      }
      enum "stage1-lb-group" {
        value 3;
        description
          "stage1 lb group";
      }
      enum "stage1-lb-member" {
        value 4;
        description
          "stage1 lb member";
      }
      enum "stage2-lb-group" {
        value 5;
        description
          "stage2 lb group";
      }
      enum "stage2-lb-member" {
        value 6;
        description
          "stage2 lb member";
      }
      enum "stage2-protection-monitor" {
        value 7;
        description
          "stage2 protection monitor";
      }
      enum "stage3-lb-member" {
        value 8;
        description
          "stage3 lb member";
      }
      enum "v4-lpts" {
        value 9;
        description
          "v4 lpts";
      }
      enum "v6-lpts" {
        value 10;
        description
          "v6 lpts";
      }
      enum "lpts-meters" {
        value 11;
        description
          "lpts meters";
      }
      enum "central-em" {
        value 12;
        description
          "central em";
      }
      enum "egress-acl-tcam" {
        value 13;
        description
          "egress acl tcam";
      }
      enum "ingress-acl-tcam" {
        value 14;
        description
          "ingress acl tcam";
      }
      enum "lpm-tcam" {
        value 15;
        description
          "lpm tcam";
      }
      enum "mc-emdb" {
        value 16;
        description
          "mc emdb";
      }
      enum "ipv6-compressed-sips" {
        value 17;
        description
          "ipv6 compressed sips";
      }
      enum "egress-large-encap" {
        value 18;
        description
          "egress large encap";
      }
      enum "egress-small-encap" {
        value 19;
        description
          "egress small encap";
      }
      enum "tunnel-termination" {
        value 20;
        description
          "tunnel termination";
      }
      enum "sipidxtbl" {
        value 21;
        description
          "sipidxtbl";
      }
      enum "myipv4tbl" {
        value 22;
        description
          "myipv4tbl";
      }
      enum "l2-service-port" {
        value 23;
        description
          "l2 service port";
      }
      enum "egress-l3-dlp" {
        value 24;
        description
          "egress l3 dlp";
      }
      enum "protection-group" {
        value 25;
        description
          "protection group";
      }
      enum "tunnel-termination-1" {
        value 26;
        description
          "tunnel termination 1";
      }
      enum "dip-index" {
        value 27;
        description
          "dip index";
      }
      enum "mac-service-map-ping" {
        value 28;
        description
          "mac service mapping";
      }
      enum "mac-service-map-ping-1" {
        value 29;
        description
          "mac service mapping 1";
      }
      enum "mac-termination-em-table" {
        value 30;
        description
          "mac termination em table";
      }
      enum "egress-enc-em0" {
        value 31;
        description
          "egress enc em0";
      }
      enum "egress-enc-em1" {
        value 32;
        description
          "egress enc em1";
      }
      enum "egress-enc-em2" {
        value 33;
        description
          "egress enc em2";
      }
      enum "egress-enc-em3" {
        value 34;
        description
          "egress enc em3";
      }
      enum "egress-enc-em4" {
        value 35;
        description
          "egress enc em4";
      }
      enum "egress-enc-em5" {
        value 36;
        description
          "egress enc em5";
      }
      enum "service-lp-attributes-table" {
        value 37;
        description
          "service lp attributes table";
      }
      enum "additional-labels-table" {
        value 38;
        description
          "additional labels table";
      }
      enum "myipv6tbl" {
        value 39;
        description
          "myipv6tbl";
      }
      enum "vxlan-termination-vni-tbl" {
        value 40;
        description
          "vxlan termination vni tbl";
      }
      enum "vxlan-l2-dlp-tbl" {
        value 41;
        description
          "vxlan l2 dlp tbl";
      }
      enum "ipv6-vxlan-l2-dlp-tbl" {
        value 42;
        description
          "ipv6 vxlan l2 dlp tbl";
      }
      enum "l3-vxlan-overlay-mac-tbl" {
        value 43;
        description
          "l3 vxlan overlay mac tbl";
      }
      enum "ip-relay-to-vni-tbl" {
        value 44;
        description
          "ip relay to vni tbl";
      }
      enum "ipv6-relay-to-vni-tbl" {
        value 45;
        description
          "ipv6 relay to vni tbl";
      }
      enum "stage0-associate-data-table" {
        value 46;
        description
          "stage0 associate data table";
      }
      enum "stage1-associate-data-table" {
        value 47;
        description
          "stage1 associate data table";
      }
      enum "stage2-associate-data-table" {
        value 48;
        description
          "stage2 associate data table";
      }
      enum "stage3-associate-data-table" {
        value 49;
        description
          "stage3 associate data table";
      }
    }
    description
      "Resource";
  }

  augment "/a1:ofa/a1:stats/a1:nodes/a1:node" {
    description
      "This augment extends the operational data of
       'Cisco-IOS-XR-platforms-ofa-oper'";
    container hw-resources-datas {
      description
        "OFA HW resources stats ";
      list hw-resources-data {
        key "resource";
        description
          "Hardware resources table";
        leaf resource {
          type Resource;
          description
            "Resource type";
        }
        uses OFA-SYSDB-HW-RESOURCE;
      }
    }
  }
}
