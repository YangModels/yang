module Cisco-IOS-XR-um-pbr-policy-cfg {
  namespace "http://cisco.com/ns/yang/Cisco-IOS-XR-um-pbr-policy-cfg";
  prefix um-pbr-policy-cfg;

  import Cisco-IOS-XR-types {
    prefix xr;
  }
  import ietf-inet-types {
    prefix inet;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pbr package configuration.
     
     This YANG module augments the
     modules with configuration data.
     
     Copyright (c) 2021-2022 by Cisco Systems, Inc.
     All rights reserved.";

  revision 2022-07-11 {
    description
      "Added missing description statement to nodes";
    semver:module-version "1.1.0";
  }
  revision 2021-05-10 {
    description
      "Initial release";
    semver:module-version "1.0.0";
  }

  grouping IF-BODY {
    description
      "Grouping for controller";
    container service-policy {
      description
        "Configure a service policy";
      container type {
        description
          "service policy type";
        container pbr {
          description
            "Policy based routing Service policy";
          container inputs {
            description
              "Configure a policy in the input direction";
            list input {
              key "service-policy-name";
              description
                "Configure a policy in the input direction";
              leaf service-policy-name {
                type string {
                  length "1..800" {
                    description
                      "Name of the service policy";
                  }
                  pattern "[a-zA-Z0-9][a-zA-Z0-9._@$%+#:=<>-]{0,62}";
                }
                description
                  "Configure a policy in the input direction";
              }
            }
          }
        }
      }
    }
    container ipv4 {
      description
        "IPv4 interface subcommands";
      container vrf-policy {
        description
          "vrf policy";
        container type {
          description
            "type of policy";
          container pbr {
            description
              "Policy based routing";
            container disable {
              presence "Indicates a disable node is configured.";
              description
                "disable ipv4 vrf-policy type pbr. ";
            }
          }
        }
      }
    }
    container ipv6 {
      description
        "IPv6 interface subcommands";
      container vrf-policy {
        description
          "vrf policy";
        container type {
          description
            "type of policy";
          container pbr {
            description
              "Policy based routing Service policy";
            container disable {
              presence "Indicates a disable node is configured.";
              description
                "disable ipv6 vrf-policy type pbr. ";
            }
          }
        }
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  container service-policy {
    description
      "Configure global service policy";
    container apply-order {
      description
        "Configure service policy ordering";
      container pbr {
        description
          "Policy based routing";
        container qos {
          must "not(../../qos/pbr)";
          presence "Indicates a qos node is configured.";
          description
            "Quality of service";
        }
      }
      container qos {
        description
          "Quality of service";
        container pbr {
          must "not(../../pbr/qos)";
          presence "Indicates a pbr node is configured.";
          description
            "Policy based routing";
        }
      }
    }
  }
  container vrf-policy {
    presence "Indicates a vrf-policy node is configured.";
    description
      "vrf policy configuration";
    container vrfs {
      description
        "associated vrf of the policy";
      list vrf {
        must "address-family/ipv4/policy/type/pbr/input or address-family/ipv6/policy/type/pbr/input";
        key "vrf-name";
        description
          "associated vrf of the policy";
        leaf vrf-name {
          type xr:Cisco-ios-xr-string {
            length "1..32" {
              description
                "VRF Name";
            }
          }
          description
            "associated vrf of the policy";
        }
        container address-family {
          description
            "Address Family Identifier Type (IPv4/IPv6)";
          container ipv4 {
            description
              "IPv4 Policy";
            container policy {
              description
                "Policy Name";
              container type {
                description
                  "Type of the policy";
                container pbr {
                  description
                    "policy type pbr";
                  leaf input {
                    type string {
                      length "1..800" {
                        description
                          "Policy map name";
                      }
                      pattern "[a-zA-Z0-9][a-zA-Z0-9._@$%+#:=<>-]{0,62}";
                    }
                    description
                      "direction of the policy applied";
                  }
                }
              }
            }
          }
          container ipv6 {
            description
              "IPv6 Policy";
            container policy {
              description
                "Policy Name";
              container type {
                description
                  "Type of the policy";
                container pbr {
                  description
                    "policy type pbr";
                  leaf input {
                    type string {
                      length "1..800" {
                        description
                          "Policy map name";
                      }
                      pattern "[a-zA-Z0-9][a-zA-Z0-9._@$%+#:=<>-]{0,62}";
                    }
                    description
                      "direction of the policy applied";
                  }
                }
              }
            }
          }
        }
      }
    }
  }
  container service-node {
    description
      "configure service node";
    container type {
      description
        "type of service node";
      container vpath {
        presence "Indicates a vpath node is configured.";
        description
          "Specify service node type as vpath";
        container indexes {
          description
            "Specify index of service node";
          list index {
            key "service-node-index";
            description
              "Specify index of service node";
            leaf service-node-index {
              type uint32 {
                range "1..65535" {
                  description
                    "Specify the index of service node";
                }
              }
              description
                "Specify index of service node";
            }
          }
        }
      }
      container output {
        presence "Indicates a output node is configured.";
        description
          "Specify service node type as output";
        container indexes {
          description
            "Specify index of service node";
          list index {
            key "service-node-index";
            description
              "Specify index of service node";
            leaf service-node-index {
              type uint32 {
                range "1..65535" {
                  description
                    "Specify the index of service node";
                }
              }
              description
                "Specify index of service node";
            }
          }
        }
      }
    }
  }
  container service-function-chaining {
    presence "Indicates a service-function-chaining node is configured.";
    description
      "configure service function chaining";
    container paths {
      description
        "Configure service function path";
      list path {
        key "service-function-path-id";
        description
          "Specify the service function path id";
        leaf service-function-path-id {
          type uint32 {
            range "1..16777215" {
              description
                "Specify the service function path id";
            }
          }
          description
            "Specify the service function path id";
        }
        container functions {
          description
            "Specify the id of service function";
          list function {
            must "sf/service-functions/service-function or sff/service-functions/service-function or terminate/default-action/redirect";
            key "service-function-id";
            description
              "Specify the id of service function";
            leaf service-function-id {
              type uint32 {
                range "1..255" {
                  description
                    "Specify the id of service function";
                }
              }
              description
                "Specify the id of service function";
            }
            container sf {
              description
                "service function";
              container service-functions {
                description
                  "service function name";
                list service-function {
                  key "service-function-name";
                  description
                    "service function name";
                  leaf service-function-name {
                    type xr:Cisco-ios-xr-string {
                      length "1..32" {
                        description
                          "service function name";
                      }
                    }
                    description
                      "service function name";
                  }
                }
              }
            }
            container sff {
              description
                "service function forwarder";
              container service-functions {
                description
                  "service function name";
                list service-function {
                  key "service-function-name";
                  description
                    "service function name";
                  leaf service-function-name {
                    type xr:Cisco-ios-xr-string {
                      length "1..32" {
                        description
                          "service function name";
                      }
                    }
                    description
                      "service function name";
                  }
                }
              }
            }
            container terminate {
              description
                "Configure terminate";
              leaf metadata-disposition {
                type xr:Cisco-ios-xr-string {
                  length "1..800" {
                    description
                      "metadata-disposition name";
                  }
                }
                must "../default-action/redirect";
                description
                  "Specify metadata-disposition name";
              }
              container default-action {
                description
                  "Configure the default action for service function path";
                container redirect {
                  must "ipv4/nexthop or ipv4/vrf";
                  presence "Indicates a redirect node is configured.";
                  description
                    "Configure redirect action";
                  container ipv4 {
                    description
                      "Enter ipv4 configuration";
                    leaf nexthop {
                      type inet:ipv4-address-no-zone;
                      description
                        "Configure the nexthop action";
                    }
                    leaf vrf {
                      type union {
                        type string {
                          pattern "default" {
                            description
                              "Redirect to default vrf";
                          }
                        }
                        type xr:Cisco-ios-xr-string {
                          length "1..1024" {
                            description
                              "Enter VRF name";
                          }
                        }
                      }
                      description
                        "Enter vrf name for the nexthop";
                    }
                  }
                }
              }
            }
          }
        }
      }
    }
    container sfs {
      description
        "service function";
      list sf {
        key "sf-name";
        description
          "service function";
        leaf sf-name {
          type xr:Cisco-ios-xr-string {
            length "1..32" {
              description
                "service function name";
            }
          }
          description
            "service function";
        }
        container locators {
          description
            "Specify service function locator id";
          list locator {
            key "locator-id";
            description
              "Specify service function locator id";
            leaf locator-id {
              type uint32 {
                range "1..255" {
                  description
                    "Specify locator id";
                }
              }
              description
                "Specify service function locator id";
            }
            container transport {
              description
                "Choose SFL transport";
              container vxlan-gpe {
                description
                  "transport vxlan-gpe";
                container source-address {
                  description
                    "Local IP address";
                  leaf ipv4 {
                    type inet:ipv4-address-no-zone;
                    description
                      "setup IPv4  path";
                  }
                }
                container destination-address {
                  description
                    "Remote IP address";
                  leaf ipv4 {
                    type inet:ipv4-address-no-zone;
                    description
                      "setup IPv4  path";
                  }
                }
                leaf vni {
                  type uint32 {
                    range "1..65535" {
                      description
                        "Enter vni value";
                    }
                  }
                  description
                    "vni value";
                }
              }
            }
          }
        }
      }
    }
    container sffs {
      description
        "service function forwarder";
      list sff {
        key "sff-name";
        description
          "service function forwarder";
        leaf sff-name {
          type xr:Cisco-ios-xr-string {
            length "1..32" {
              description
                "service function name";
            }
          }
          description
            "service function forwarder";
        }
        container locators {
          description
            "Specify service function locator id";
          list locator {
            key "locator-id";
            description
              "Specify service function locator id";
            leaf locator-id {
              type uint32 {
                range "1..255" {
                  description
                    "Specify locator id";
                }
              }
              description
                "Specify service function locator id";
            }
            container transport {
              description
                "Choose SFL transport";
              container vxlan-gpe {
                description
                  "transport vxlan-gpe";
                container source-address {
                  description
                    "Local IP address";
                  leaf ipv4 {
                    type inet:ipv4-address-no-zone;
                    description
                      "setup IPv4  path";
                  }
                }
                container destination-address {
                  description
                    "Remote IP address";
                  leaf ipv4 {
                    type inet:ipv4-address-no-zone;
                    description
                      "setup IPv4  path";
                  }
                }
                leaf vni {
                  type uint32 {
                    range "1..65535" {
                      description
                        "Enter vni value";
                    }
                  }
                  description
                    "vni value";
                }
              }
            }
          }
        }
      }
    }
    container metadata-impositions {
      description
        "metadata imposition";
      list metadata-imposition {
        key "metadata-profile-name";
        description
          "metadata imposition";
        leaf metadata-profile-name {
          type xr:Cisco-ios-xr-string {
            length "1..32" {
              description
                "metadata profile name";
            }
          }
          description
            "metadata imposition";
        }
        container type {
          description
            "Specify metadata type";
          container one {
            description
              "Type 1 metadata";
            container format {
              description
                "Specify metadata format";
              container dc-allocation {
                description
                  "format dc-allocation";
                leaf tenant-id {
                  type uint32 {
                    range "1..16777215" {
                      description
                        "Enter 24-bit tenant id";
                    }
                  }
                  description
                    "Specify tenant id";
                }
              }
            }
          }
        }
      }
    }
    container metadata-dispositions {
      description
        "metadata disposition";
      list metadata-disposition {
        key "service-disposition-name";
        description
          "metadata disposition";
        leaf service-disposition-name {
          type xr:Cisco-ios-xr-string {
            length "1..32" {
              description
                "specify service disposition name";
            }
          }
          description
            "metadata disposition";
        }
        container type {
          description
            "Specify disposition allocation type";
          container one {
            description
              "Allocation format Type 1 ";
            container format {
              description
                "Specify allocation format";
              container dc-allocation {
                description
                  "data center allocation";
                container match-entries {
                  description
                    "Specify the match entry name";
                  list match-entry {
                    key "match-entry-name";
                    description
                      "Specify the match entry name";
                    leaf match-entry-name {
                      type xr:Cisco-ios-xr-string {
                        length "1..32" {
                          description
                            "match-entry name";
                        }
                      }
                      description
                        "Specify the match entry name";
                    }
                    container tenant {
                      description
                        "Specify the tenant-ids";
                      leaf tenant-id {
                        type uint32 {
                          range "0..4294967295" {
                            description
                              "tenant id";
                          }
                        }
                        description
                          "tenant id";
                      }
                      container redirect {
                        must "ipv4/nexthop/ipv4-address or ipv4/nexthop/vrf";
                        description
                          "Configure redirect action";
                        container ipv4 {
                          description
                            "Enter ipv4 configuration";
                          container nexthop {
                            description
                              "Enter nexthop configuration";
                            leaf ipv4-address {
                              type inet:ipv4-address-no-zone;
                              description
                                "Configure the nexthop action";
                            }
                            leaf vrf {
                              type union {
                                type string {
                                  pattern "default" {
                                    description
                                      "Redirect to default vrf";
                                  }
                                }
                                type xr:Cisco-ios-xr-string {
                                  length "1..1024" {
                                    description
                                      "Enter VRF name";
                                  }
                                }
                              }
                              description
                                "Enter vrf name for the nexthop";
                            }
                          }
                        }
                      }
                    }
                  }
                }
              }
            }
          }
        }
      }
    }
  }
}
