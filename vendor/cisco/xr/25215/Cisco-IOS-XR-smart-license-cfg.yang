module Cisco-IOS-XR-smart-license-cfg {
  namespace "http://cisco.com/ns/yang/Cisco-IOS-XR-smart-license-cfg";
  prefix smart-license-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR smart-license package configuration.
     
     This module contains definitions
     for the following management objects:
       licensing: SmartLicense Root
       flex-consumption: FCM configuration
     
     Copyright (c) 2013-2024 by Cisco Systems, Inc.
     All rights reserved.";

  revision 2024-10-14 {
    description
      "Changed enum values in Transport-type-enum.
       2023-08-22
         Added transport-type-cslu and transport-type-off enums to Transport-type-enum. Added new leaf url-cslu to urls container
       2022-12-22
         Changed parent class of flex-consumption";
    semver:module-version "2.0.0";
  }
  revision 2019-04-05 {
    description
      "Establish semantic version baseline.";
    semver:module-version "1.0.0";
  }
  revision 2017-07-21 {
    description
      "Initial version.";
  }
  revision 2015-11-09 {
    description
      "IOS XR 6.0 revision.";
  }

  typedef Transport-type-enum {
    type enumeration {
      enum "transport-type-callhome" {
        value 2;
        description
          "Use Callhome as transport";
      }
      enum "transport-type-smart" {
        value 3;
        description
          "Use Smart Transport";
      }
      enum "transport-type-cslu" {
        value 4;
        description
          "Use CSLU as transport";
      }
      enum "transport-type-off" {
        value 5;
        description
          "Disable transport";
      }
    }
    description
      "Transport type enum";
  }

  container licensing {
    description
      "SmartLicense Root";
    container transport {
      description
        "Select the type of message transport for Smart
         Agent";
      container transport-smart {
        description
          "Smart transport config for Smart Agent";
        container proxy {
          description
            "Proxy related commands";
          leaf port {
            type inet:port-number;
            description
              "The proxy port";
          }
          leaf host-name {
            type xr:Cisco-ios-xr-string {
              length "1..200";
            }
            description
              "The IP address or hostname of the Proxy";
          }
        }
        container urls {
          description
            "URL for transport";
          leaf url-registration {
            type string {
              length "1..200";
            }
            description
              "Use the URL for Smart Transport registration";
          }
          leaf url-cslu {
            type string {
              length "1..200";
            }
            description
              "Use the URL for CSLU";
          }
        }
      }
      leaf transport-type {
        type Transport-type-enum;
        description
          "Select the type of message transport for Smart
           Licensing";
      }
    }
  }
  container flex-consumption {
    description
      "FCM configuration";
    leaf fcm-enable {
      type boolean;
      description
        "Enable or disable";
    }
    leaf software-upgrade-enable {
      type boolean;
      description
        "Software-upgrade mode enabled";
    }
    leaf reservation {
      type boolean;
      description
        "License Smart Reservation Enabled";
    }
  }
}
