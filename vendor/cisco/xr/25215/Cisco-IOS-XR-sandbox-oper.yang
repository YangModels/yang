module Cisco-IOS-XR-sandbox-oper {
  namespace "http://cisco.com/ns/yang/Cisco-IOS-XR-sandbox-oper";
  prefix sandbox-oper;

  import cisco-semver {
    prefix semver;
  }
  include Cisco-IOS-XR-sandbox-oper-sub1 {
    revision-date 2023-07-28;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sandbox package operational data.
     
     This module contains definitions
     for the following management objects:
       sandbox: Sandbox Operational data space
     
     Copyright (c) 2013-2023 by Cisco Systems, Inc.
     All rights reserved.";

  revision 2023-07-28 {
    description
      "Modified Brief and Detail class pathname";
    semver:module-version "1.0.0";
  }
  revision 2023-07-27 {
    description
      "Added yang support to publish list of RPMs";
  }
  revision 2023-06-12 {
    description
      "Added support to publish list of RPMs and brief logs, detailed logs container renamed";
  }
  revision 2023-05-26 {
    description
      "Support added to list inner rpms and logs";
  }
  revision 2022-07-08 {
    description
      "sandbox show CLI added";
  }
  revision 2019-04-05 {
    description
      "Establish semantic version baseline.";
  }
  revision 2015-11-09 {
    description
      "IOS XR 6.0 revision.";
  }

  container sandbox {
    config false;
    description
      "Sandbox Operational data space";
    container info {
      description
        "Info data bag";
      uses SANDBOXMGR-INTERNAL-INFO;
    }
    container detail {
      description
        "Detail data bag";
      uses SANDBOXMGR-DETAILS;
    }
    container rpms {
      description
        "Sandbox RPMs data space";
      container logs {
        description
          "Logs for inner RPMs installed";
        container brief {
          description
            "Brief logs for inner RPMs installed";
          uses SANDBOXMGR-RPMINSTLOGS;
        }
        container detail {
          description
            "Detailed logs for inner RPMs installed";
          uses SANDBOXMGR-RPMINSTDETLOGS;
        }
      }
      container installed {
        description
          "Details of inner RPMs installed";
        uses SANDBOXMGR-RPMDETAILS;
      }
    }
    container services {
      description
        "Services data bag";
      uses SANDBOXMGR-SERVICES;
    }
  }
}
