module Cisco-IOS-XR-erp-oper {
  namespace "http://cisco.com/ns/yang/Cisco-IOS-XR-erp-oper";
  prefix erp-oper;

  import Cisco-IOS-XR-types {
    prefix xr;
  }
  import cisco-semver {
    prefix semver;
  }
  include Cisco-IOS-XR-erp-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR erp package operational data.
     
     This module contains definitions
     for the following management objects:
       ethernet-ring: Ethernet Ring Protection operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container ethernet-ring {
    config false;
    description
      "Ethernet Ring Protection operational data";
    container global {
      description
        "G.8032 Ethernet Ring Protection global
         operational data";
      container g8032 {
        description
          "G.8032 Ethernet Ring Protection operational
           data";
        container statuses {
          description
            "Detailed status information for Ethernet ring";
          list status {
            description
              "Detailed status information on a particular
               ring instance";
            leaf ring-name {
              type xr:Cisco-ios-xr-string {
                length "1..32";
              }
              description
                "Ring name";
            }
            leaf instance-id {
              type uint32 {
                range "1..2";
              }
              description
                "Ring instance ID";
            }
            uses ERP-STATUS-INFO;
          }
        }
        container profiles {
          description
            "G.8032 Ethernet ring profile table";
          list profile {
            key "profile-name";
            description
              "Ethernet ring profile information for a
               specified profile name";
            leaf profile-name {
              type xr:Cisco-ios-xr-string {
                length "1..32";
              }
              description
                "Profile name";
            }
            uses ERP-PROFILE-INFO;
          }
        }
        container statistics {
          description
            "Ethernet ring statistics for events and
             messages received";
          list statistic {
            description
              "Statistics for a particular ring instance";
            leaf ring-name {
              type xr:Cisco-ios-xr-string {
                length "1..32";
              }
              description
                "Ring Name";
            }
            leaf instance-id {
              type uint32 {
                range "1..2";
              }
              description
                "Ring instance ID";
            }
            uses ERP-STATS-INFO;
          }
        }
        container summary {
          description
            "Summary count of Ethernet ring instances in
             each state";
          uses ERP-SUMMARY-INFO;
        }
        container briefs {
          description
            "Brief functional state of Ethernet ring
             instances";
          list brief {
            description
              "Brief functional state on a particular ring
               instance";
            leaf ring-name {
              type xr:Cisco-ios-xr-string {
                length "1..32";
              }
              description
                "Ring Name";
            }
            leaf instance-id {
              type uint32 {
                range "1..2";
              }
              description
                "Ring instance ID";
            }
            uses ERP-BRIEF-INFO;
          }
        }
      }
    }
  }
}
