module Cisco-IOS-XR-openconfig-policy-forwarding-ext {
  yang-version 1;
  namespace "http://cisco.com/ns/yang/Cisco-IOS-XR-openconfig-policy-forwarding-ext";
  prefix oc-pf-cisco-xr-ext;

  import openconfig-extensions {
    prefix oc-ext;
  }
  import openconfig-network-instance {
    prefix oc-netinst;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This extended module defines configuration and operational state data
     relating to policy-based forwarding for a policy attached to an
     address-family within a network-instance.
     
     A PBR policy can be directly attached to a network-instance(currently
     only DEFAULT). This is then internally applied to all the interfaces
     under this network-instance.";

  revision 2023-01-29 {
    description
      "Update the model to allow selection of IPv4 or IPv6 address-family";
    reference "1.0.0";
  }
  revision 2022-12-21 {
    description
      "Initial version";
    reference "0.1.0";
  }

  grouping pf-ext-forwarding-policy-structural {
    description
      "Configuration parameters relating to the forwarding policy.";
    leaf afi-name {
      type enumeration {
        enum "IPV4" {
          description
            "IPv4 address-family";
        }
        enum "IPV6" {
          description
            "IPv6 address-family";
        }
      }
      description
        "The address-family within the network-instance to which
         the forwarding policy is applied.";
    }
    leaf apply-forwarding-policy {
      type leafref {
        path "/oc-netinst:network-instances/oc-netinst:network-instance/oc-netinst:policy-forwarding/oc-netinst:policies/oc-netinst:policy/oc-netinst:config/oc-netinst:policy-id";
      }
      description
        "A unique name identifying the PBR policy that is
         attached to a network-instance";
    }
  }

  grouping pf-ext-address-family {
    description
      "Grouping that contains the config and state for the
       policy that is applied to a network-instance";
    list af {
      key "afi-name";
      description
        "The address-family associated with the forwarding policy.";
      leaf afi-name {
        type leafref {
          path "../config/afi-name";
        }
        description
          "Reference to the address-family associated to the
           forwarding policy.";
      }
      container config {
        description
          "Configuration options relating to the PBR policy.";
        uses pf-ext-forwarding-policy-structural;
      }
      container state {
        config false;
        description
          "Operational state parameters relating to the PBR policy.";
        uses pf-ext-forwarding-policy-structural;
      }
    }
  }

  grouping pf-extended-afi-top {
    description
      "The top-level container defining the Cisco
       Openconfig policy-forwarding extension";
    container afi {
      description
        "This container defines address-family specific
         configuration and state information.";
      uses pf-ext-address-family;
    }
  }

  augment "/oc-netinst:network-instances/oc-netinst:network-instance/oc-netinst:policy-forwarding" {
    description
      "The policy to be applied on to netork-instance. The policy
       is applied on all the interfaces attached to the VRF.
       Packets ingress on the referenced interface should be
       compared to the match criteria within the specified policy,
       and in the case that these criteria are met, the forwarding
       actions specified applied";
    uses pf-extended-afi-top;
  }
  oc-ext:openconfig-version "0.1.0";
}
