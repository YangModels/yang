module Cisco-IOS-XR-infra-statsd-oper {
  namespace "http://cisco.com/ns/yang/Cisco-IOS-XR-infra-statsd-oper";
  prefix infra-statsd-oper;

  import Cisco-IOS-XR-types {
    prefix xr;
  }
  import cisco-semver {
    prefix semver;
  }
  include Cisco-IOS-XR-infra-statsd-oper-sub1 {
    revision-date 2023-12-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-statsd package operational data.
     
     This module contains definitions
     for the following management objects:
       infra-statistics: Statistics Infrastructure
     
     Copyright (c) 2013-2023 by Cisco Systems, Inc.
     All rights reserved.";

  revision 2023-12-01 {
    description
      "Adding event-driven telemetry support for drops and error counters for generic stats
       2023-05-17
         Adding last-update-time field in Interface Rates container
       2023-01-05
         Modifing the statsd native yang model.
       2022-10-31
         Container names changed for Interface counter rates
       2022-09-30
         Interface counter rates support added";
    semver:module-version "2.0.0";
  }
  revision 2020-12-17 {
    description
      "Unit of bandwidth in datarate container changed from 32-bit to 64-bit.";
    semver:module-version "1.2.0";
  }
  revision 2020-10-08 {
    description
      "Unit of last-data-time in milliseconds reverted to seconds for generic stats
       2020-05-05
           Added Hardware timestamp support for protocol stats.
       2020-04-14
           Unit of last-data-time changed from seconds to milliseconds for generic stats
       2020-04-14
           Data type of last-data-time changed from uint32 to uint64 for generic and proto stats
       2020-04-14
           Adding Hardware timestamp feature in generic structure.";
    semver:module-version "1.1.0";
  }
  revision 2019-04-05 {
    description
      "Establish semantic version baseline.";
    semver:module-version "1.0.1";
  }
  revision 2015-11-09 {
    description
      "IOS XR 6.0 revision.";
  }

  container infra-statistics {
    config false;
    description
      "Statistics Infrastructure";
    container interfaces {
      description
        "List of interfaces";
      list interface {
        key "interface-name";
        description
          "Statistics of an interface";
        container protocols {
          description
            "List of protocols";
          list protocol {
            key "protocol-name";
            description
              "Interface counters per protocol";
            leaf protocol-name {
              type xr:Cisco-ios-xr-string;
              description
                "Name of the protocol";
            }
            uses IFSTATSBAG-PROTO;
          }
        }
        container data-rate {
          description
            "Datarate information";
          uses STATSDBAG-DATARATE;
        }
        container generic-counters {
          description
            "Generic set of interface counters";
          uses IFSTATSBAG-GENERIC;
        }
        leaf interface-name {
          type xr:Interface-name;
          description
            "Name of the interface";
        }
      }
    }
    container counter-rates {
      description
        "Rate data for interface counters";
      container interface-rates {
        description
          "List of interfaces";
        list interface-rate {
          key "interface-name";
          description
            "Rate information";
          leaf interface-name {
            type xr:Interface-name;
            description
              "Name of the interface";
          }
          uses IFCS-RATE-BAG;
        }
      }
    }
  }
}
