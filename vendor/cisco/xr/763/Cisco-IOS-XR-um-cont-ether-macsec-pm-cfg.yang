module Cisco-IOS-XR-um-cont-ether-macsec-pm-cfg {
  namespace "http://cisco.com/ns/yang/Cisco-IOS-XR-um-cont-ether-macsec-pm-cfg";
  prefix um-cont-ether-macsec-pm-cfg;

  import Cisco-IOS-XR-types {
    prefix xr;
  }
  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-ether-macsec-pm package configuration.
     
     This YANG module augments the
     modules with configuration data.
     
     Copyright (c) 2021 by Cisco Systems, Inc.
     All rights reserved.";

  revision 2021-10-14 {
    description
      "Initial release";
    semver:module-version "1.0.0";
  }

  grouping IF-BODY {
    container pm {
      when "../a1:interface-name[starts-with(text(),'HundredGigE')]" {
        tailf:dependency "../a1:interface-name";
      }
      description
        "Configure pm parameters";
      container interval-15-min {
        description
          "Configure pm parameters of 15 minute interval";
        container ether {
          description
            "configure ether performance monitoring";
          container threshold {
            description
              "Configure threshold on ether parameters";
            leaf rx-pkt {
              type uint32 {
                range "1..4294967295" {
                  description
                    "RX-PKT threshold ";
                }
              }
              description
                "set RX-PKT threshold";
            }
            leaf out-ucast {
              type uint32 {
                range "1..4294967295" {
                  description
                    "OUT-UCAST threshold";
                }
              }
              description
                "set OUT-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf if-in-octets {
              type uint32 {
                range "1..4294967295" {
                  description
                    "IFIN_OCTETS threshold";
                }
              }
              description
                "set IFIN_OCTETS threshold";
            }
            leaf out-octets {
              type uint32 {
                range "1..4294967295" {
                  description
                    "OUT-OCTET threshold ";
                }
              }
              description
                "set OUT-OCTET threshold";
            }
            leaf fcs-err {
              type uint32 {
                range "1..4294967295" {
                  description
                    "FCS-ERR threshold";
                }
              }
              description
                "set FCS-ERR threshold";
            }
            leaf tx-pkt {
              type uint32 {
                range "1..4294967295" {
                  description
                    "TX-PKT threshold";
                }
              }
              description
                "set TX-PKT threshold";
            }
            leaf in-ucast {
              type uint32 {
                range "1..4294967295" {
                  description
                    "IN-UCAST threshold";
                }
              }
              description
                "set IN-UCAST threshold";
            }
            leaf out-mcast {
              type uint32 {
                range "1..4294967295" {
                  description
                    "OUT-MCAST threshold ";
                }
              }
              description
                "set OUT-MCAST threshold";
            }
            leaf out-bcast {
              type uint32 {
                range "1..4294967295" {
                  description
                    "OUT-BCAST threshold ";
                }
              }
              description
                "set OUT-BCAST threshold";
            }
            leaf in-pause-frame {
              type uint32 {
                range "1..4294967295" {
                  description
                    "IN-PAUSE-FRAME threshold";
                }
              }
              description
                "set IN-PAUSE-FRAME threshold";
            }
            leaf in-good-bytes {
              type uint32 {
                range "1..4294967295" {
                  description
                    "IN-GOOD-BYTES threshold";
                }
              }
              description
                "set IN-GOOD-BYTES threshold";
            }
            leaf in-802-1q-frames {
              type uint32 {
                range "1..4294967295" {
                  description
                    "IN-802-1Q-FRAMES threshold";
                }
              }
              description
                "set IN-802-1Q-FRAMES threshold";
            }
            leaf in-pkts-1519-max-octets {
              type uint32 {
                range "1..4294967295" {
                  description
                    "IN-PKTS-1519-MAX-OCTETS threshold";
                }
              }
              description
                "set IN-PKTS-1519-MAX-OCTETS threshold";
            }
            leaf in-good-pkts {
              type uint32 {
                range "1..4294967295" {
                  description
                    "IN-GOOD-PKTS threshold";
                }
              }
              description
                "set IN-GOOD-PKTS threshold";
            }
            leaf in-drop-overrun {
              type uint32 {
                range "1..4294967295" {
                  description
                    "IN-DROP-OVERRUN threshold";
                }
              }
              description
                "set IN-DROP-OVERRUN threshold";
            }
            leaf in-drop-abort {
              type uint32 {
                range "1..4294967295" {
                  description
                    "IN-DROP-ABORT threshold";
                }
              }
              description
                "set IN-DROP-ABORT threshold";
            }
            leaf in-drop-invalid-vlan {
              type uint32 {
                range "1..4294967295" {
                  description
                    "IN-DROP-INVALID-VLAN threshold";
                }
              }
              description
                "set IN-DROP-INVALID-VLAN threshold";
            }
            leaf in-drop-invalid-dmac {
              type uint32 {
                range "1..4294967295" {
                  description
                    "IN-DROP-INVALID-DMAC threshold";
                }
              }
              description
                "set IN-DROP-INVALID-DMAC threshold";
            }
            leaf in-drop-invalid-encap {
              type uint32 {
                range "1..4294967295" {
                  description
                    "IN-DROP-INVALID-ENCAP threshold";
                }
              }
              description
                "set IN-DROP-INVALID-ENCAP threshold";
            }
            leaf in-drop-other {
              type uint32 {
                range "1..4294967295" {
                  description
                    "IN-DROP-OTHER threshold";
                }
              }
              description
                "set IN-DROP-OTHER threshold";
            }
            leaf in-mib-giant {
              type uint32 {
                range "1..4294967295" {
                  description
                    "IN-MIB-GIANT threshold";
                }
              }
              description
                "set IN-MIB-GIANT threshold";
            }
            leaf in-mib-jabber {
              type uint32 {
                range "1..4294967295" {
                  description
                    "IN-MIB-JABBER threshold";
                }
              }
              description
                "set IN-MIB-JABBER threshold";
            }
            leaf in-mib-crc {
              type uint32 {
                range "1..4294967295" {
                  description
                    "IN-MIB-CRC threshold";
                }
              }
              description
                "set IN-MIB-CRC threshold";
            }
            leaf in-error-collisions {
              type uint32 {
                range "1..4294967295" {
                  description
                    "IN-ERROR-COLLISIONS threshold";
                }
              }
              description
                "set IN-ERROR-COLLISIONS threshold";
            }
            leaf in-error-symbol {
              type uint32 {
                range "1..4294967295" {
                  description
                    "IN-ERROR-SYMBOL threshold";
                }
              }
              description
                "set IN-ERROR-SYMBOL threshold";
            }
            leaf out-good-bytes {
              type uint32 {
                range "1..4294967295" {
                  description
                    "OUT-GOOD-BYTES threshold";
                }
              }
              description
                "set OUT-GOOD-BYTES threshold";
            }
            leaf out-802-1q-frames {
              type uint32 {
                range "1..4294967295" {
                  description
                    "OUT-802-1Q-FRAMES threshold";
                }
              }
              description
                "set OUT-802-1Q-FRAMES threshold";
            }
            leaf out-pause-frames {
              type uint32 {
                range "1..4294967295" {
                  description
                    "OUT-PAUSE-FRAMES threshold";
                }
              }
              description
                "set OUT-PAUSE-FRAMES threshold";
            }
            leaf out-pkts-1519-max-octets {
              type uint32 {
                range "1..4294967295" {
                  description
                    "OUT-PKTS-1519-MAX-OCTETS threshold";
                }
              }
              description
                "set OUT-PKTS-1519-MAX-OCTETS threshold";
            }
            leaf out-good-pkts {
              type uint32 {
                range "1..4294967295" {
                  description
                    "OUT-GOOD-PKTS threshold";
                }
              }
              description
                "set OUT-GOOD-PKTS threshold";
            }
            leaf out-drop-underrun {
              type uint32 {
                range "1..4294967295" {
                  description
                    "OUT-DROP-UNDERRUN threshold";
                }
              }
              description
                "set OUT-DROP-UNDERRUN threshold";
            }
            leaf out-drop-abort {
              type uint32 {
                range "1..4294967295" {
                  description
                    "OUT-DROP-ABORT threshold";
                }
              }
              description
                "set OUT-DROP-ABORT threshold";
            }
            leaf out-drop-other {
              type uint32 {
                range "1..4294967295" {
                  description
                    "OUT-DROP-OTHER threshold";
                }
              }
              description
                "set OUT-DROP-OTHER threshold";
            }
            leaf out-error-other {
              type uint32 {
                range "1..4294967295" {
                  description
                    "OUT-ERROR-OTHER threshold";
                }
              }
              description
                "set OUT-ERROR-OTHER threshold";
            }
            leaf in-error-giant {
              type uint32 {
                range "1..4294967295" {
                  description
                    "IN-ERROR-GIANT threshold";
                }
              }
              description
                "set IN-ERROR-GIANT threshold";
            }
            leaf in-error-runt {
              type uint32 {
                range "1..4294967295" {
                  description
                    "IN-ERROR-RUNT threshold";
                }
              }
              description
                "set IN-ERROR-RUNT threshold";
            }
            leaf in-error-jabbers {
              type uint32 {
                range "1..4294967295" {
                  description
                    "IN-ERROR-JABBERS threshold";
                }
              }
              description
                "set IN-ERROR-JABBERS threshold";
            }
            leaf in-error-fragments {
              type uint32 {
                range "1..4294967295" {
                  description
                    "IN-ERROR-FRAGMENTS threshold";
                }
              }
              description
                "set IN-ERROR-FRAGMENTS threshold";
            }
            leaf in-error-other {
              type uint32 {
                range "1..4294967295" {
                  description
                    "IN-ERROR-OTHER threshold";
                }
              }
              description
                "set IN-ERROR-OTHER threshold";
            }
            leaf in-pkt-64-octet {
              type uint32 {
                range "1..4294967295" {
                  description
                    "IN-PKT-64-OCTET threshold";
                }
              }
              description
                "set IN-PKT-64-OCTET threshold";
            }
            leaf in-pkts-65-127octets {
              type uint32 {
                range "1..4294967295" {
                  description
                    "IN-PKTS-65-127OCTETS threshold";
                }
              }
              description
                "set IN-PKTS-65-127OCTETS threshold";
            }
            leaf in-pkts-128-255-octets {
              type uint32 {
                range "1..4294967295" {
                  description
                    "IN-PKTS-128-255-OCTETS threshold";
                }
              }
              description
                "set IN-PKTS-128-255-OCTETS threshold";
            }
            leaf in-pkts-256-511-octets {
              type uint32 {
                range "1..4294967295" {
                  description
                    "IN-PKTS-256-511-OCTETS threshold";
                }
              }
              description
                "set IN-PKTS-256-511-OCTETS threshold";
            }
            leaf in-pkts-512-1023-octets {
              type uint32 {
                range "1..4294967295" {
                  description
                    "IN-PKTS-512-1023-OCTETS threshold";
                }
              }
              description
                "set IN-PKTS-512-1023-OCTETS threshold";
            }
            leaf in-pkts-1024-1518-octets {
              type uint32 {
                range "1..4294967295" {
                  description
                    "IN-PKTS-1024-1518-OCTETS threshold";
                }
              }
              description
                "set IN-PKTS-1024-1518-OCTETS threshold";
            }
            leaf out-pkt-64-octet {
              type uint32 {
                range "1..4294967295" {
                  description
                    "OUT-PKT-64-OCTET threshold";
                }
              }
              description
                "set OUT-PKT-64-OCTET threshold";
            }
            leaf out-pkts-65-127octets {
              type uint32 {
                range "1..4294967295" {
                  description
                    "OUT-PKTS-65-127OCTETS threshold";
                }
              }
              description
                "set OUT-PKTS-65-127OCTETS threshold";
            }
            leaf out-pkts-128-255-octets {
              type uint32 {
                range "1..4294967295" {
                  description
                    "OUT-PKTS-128-255-OCTETS threshold";
                }
              }
              description
                "set OUT-PKTS-128-255-OCTETS threshold";
            }
            leaf out-pkts-256-511-octets {
              type uint32 {
                range "1..4294967295" {
                  description
                    "OUT-PKTS-256-511-OCTETS threshold";
                }
              }
              description
                "set OUT-PKTS-256-511-OCTETS threshold";
            }
            leaf out-pkts-512-1023-octets {
              type uint32 {
                range "1..4294967295" {
                  description
                    "OUT-PKTS-512-1023-OCTETS threshold";
                }
              }
              description
                "set OUT-PKTS-512-1023-OCTETS threshold";
            }
            leaf out-pkts-1024-1518-octets {
              type uint32 {
                range "1..4294967295" {
                  description
                    "OUT-PKTS-1024-1518-OCTETS threshold";
                }
              }
              description
                "set OUT-PKTS-1024-1518-OCTETS threshold";
            }
          }
          container report {
            description
              "set ether TCA reporting status";
            container rx-pkt {
              description
                "set rx-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-octets {
              description
                "set ifOut_errors  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-pause-frame {
              description
                "set in-pause-frame TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-802-1q-frames {
              description
                "set in-802-1Q-frames TCA reporting status";
              container enable {
                presence "Indicates a enable node is configured.";
                description
                  "Enable TCA reporting";
              }
            }
            container in-pkts-1519-max-octets {
              description
                "set in-pkts-1519-Max-octets TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-overrun {
              description
                "set in-drop-overrun TCA reporting status";
              container enable {
                presence "Indicates a enable node is configured.";
                description
                  "Enable TCA reporting";
              }
            }
            container in-drop-abort {
              description
                "set in-drop-abort TCA reporting status";
              container enable {
                presence "Indicates a enable node is configured.";
                description
                  "Enable TCA reporting";
              }
            }
            container in-drop-invalid-vlan {
              description
                "set in-drop-invalid-VLAN TCA reporting status";
              container enable {
                presence "Indicates a enable node is configured.";
                description
                  "Enable TCA reporting";
              }
            }
            container in-drop-invalid-dmac {
              description
                "set in-drop-invalid-DMAC TCA reporting status";
              container enable {
                presence "Indicates a enable node is configured.";
                description
                  "Enable TCA reporting";
              }
            }
            container in-drop-invalid-encap {
              description
                "set in-drop-invalid-encap TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container in-mib-giant {
              description
                "set in-MIB-giant TCA reporting status";
              container enable {
                presence "Indicates a enable node is configured.";
                description
                  "Enable TCA reporting";
              }
            }
            container in-mib-jabber {
              description
                "set in-MIB-jabber TCA reporting status";
              container enable {
                presence "Indicates a enable node is configured.";
                description
                  "Enable TCA reporting";
              }
            }
            container in-mib-crc {
              description
                "set in-MIB-CRC TCA reporting status";
              container enable {
                presence "Indicates a enable node is configured.";
                description
                  "Enable TCA reporting";
              }
            }
            container in-error-collisions {
              description
                "set in-error-collisions TCA reporting status";
              container enable {
                presence "Indicates a enable node is configured.";
                description
                  "Enable TCA reporting";
              }
            }
            container in-error-symbol {
              description
                "set in-error-symbol TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-802-1q-frames {
              description
                "set out-802-1Q-frames TCA reporting status";
              container enable {
                presence "Indicates a enable node is configured.";
                description
                  "Enable TCA reporting";
              }
            }
            container out-pause-frames {
              description
                "set out-pause-frames TCA reporting status";
              container enable {
                presence "Indicates a enable node is configured.";
                description
                  "Enable TCA reporting";
              }
            }
            container out-pkts-1519-max-octets {
              description
                "set out-pkts-1519-Max-octets TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container out-drop-underrun {
              description
                "set out-drop-underrun TCA reporting status";
              container enable {
                presence "Indicates a enable node is configured.";
                description
                  "Enable TCA reporting";
              }
            }
            container out-drop-abort {
              description
                "set out-drop-abort TCA reporting status";
              container enable {
                presence "Indicates a enable node is configured.";
                description
                  "Enable TCA reporting";
              }
            }
            container out-drop-other {
              description
                "set out-drop-other TCA reporting status";
              container enable {
                presence "Indicates a enable node is configured.";
                description
                  "Enable TCA reporting";
              }
            }
            container out-error-other {
              description
                "set out-error-other TCA reporting status";
              container enable {
                presence "Indicates a enable node is configured.";
                description
                  "Enable TCA reporting";
              }
            }
            container in-error-giant {
              description
                "set in-error-giant TCA reporting status";
              container enable {
                presence "Indicates a enable node is configured.";
                description
                  "Enable TCA reporting";
              }
            }
            container in-error-runt {
              description
                "set in-error-runt TCA reporting status";
              container enable {
                presence "Indicates a enable node is configured.";
                description
                  "Enable TCA reporting";
              }
            }
            container in-error-jabbers {
              description
                "set in-error-jabbers TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-error-other {
              description
                "set in-error-other TCA reporting status";
              container enable {
                presence "Indicates a enable node is configured.";
                description
                  "Enable TCA reporting";
              }
            }
            container in-pkt-64-octet {
              description
                "set in-pkt-64-octet TCA reporting status";
              container enable {
                presence "Indicates a enable node is configured.";
                description
                  "Enable TCA reporting";
              }
            }
            container in-pkts-65-127octets {
              description
                "set in-pkts-65-127octets TCA reporting status";
              container enable {
                presence "Indicates a enable node is configured.";
                description
                  "Enable TCA reporting";
              }
            }
            container in-pkts-128-255-octets {
              description
                "set in-pkts-128-255-octets TCA reporting status";
              container enable {
                presence "Indicates a enable node is configured.";
                description
                  "Enable TCA reporting";
              }
            }
            container in-pkts-256-511-octets {
              description
                "set in-pkts-256-511-octets TCA reporting status";
              container enable {
                presence "Indicates a enable node is configured.";
                description
                  "Enable TCA reporting";
              }
            }
            container in-pkts-512-1023-octets {
              description
                "set in-pkts-512-1023-octets TCA reporting status";
              container enable {
                presence "Indicates a enable node is configured.";
                description
                  "Enable TCA reporting";
              }
            }
            container in-pkts-1024-1518-octets {
              description
                "set in-pkts-1024-1518-octets TCA reporting status";
              container enable {
                presence "Indicates a enable node is configured.";
                description
                  "Enable TCA reporting";
              }
            }
            container out-pkt-64-octet {
              description
                "set out-pkt-64-octet TCA reporting status";
              container enable {
                presence "Indicates a enable node is configured.";
                description
                  "Enable TCA reporting";
              }
            }
            container out-pkts-65-127octets {
              description
                "set out-pkts-65-127octets TCA reporting status";
              container enable {
                presence "Indicates a enable node is configured.";
                description
                  "Enable TCA reporting";
              }
            }
            container out-pkts-128-255-octets {
              description
                "set out-pkts-128-255-octets TCA reporting status";
              container enable {
                presence "Indicates a enable node is configured.";
                description
                  "Enable TCA reporting";
              }
            }
            container out-pkts-256-511-octets {
              description
                "set out-pkts-256-511-octets TCA reporting status";
              container enable {
                presence "Indicates a enable node is configured.";
                description
                  "Enable TCA reporting";
              }
            }
            container out-pkts-512-1023-octets {
              description
                "set out-pkts-512-1023-octets TCA reporting status";
              container enable {
                presence "Indicates a enable node is configured.";
                description
                  "Enable TCA reporting";
              }
            }
            container out-pkts-1024-1518-octets {
              description
                "set out-pkts-1024-1518-octets TCA reporting status";
              container enable {
                presence "Indicates a enable node is configured.";
                description
                  "Enable TCA reporting";
              }
            }
          }
        }
      }
      container interval-24-hour {
        description
          "Configure pm parameters of 24 hour interval";
        container ether {
          description
            "configure ether performance monitoring";
          container threshold {
            description
              "Configure threshold on ether parameters";
            leaf rx-pkt {
              type uint32 {
                range "1..4294967295" {
                  description
                    "RX-PKT threshold ";
                }
              }
              description
                "set RX-PKT threshold";
            }
            leaf out-ucast {
              type uint32 {
                range "1..4294967295" {
                  description
                    "OUT-UCAST threshold";
                }
              }
              description
                "set OUT-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf if-in-octets {
              type uint32 {
                range "1..4294967295" {
                  description
                    "IFIN_OCTETS threshold";
                }
              }
              description
                "set IFIN_OCTETS threshold";
            }
            leaf out-octets {
              type uint32 {
                range "1..4294967295" {
                  description
                    "OUT-OCTET threshold ";
                }
              }
              description
                "set OUT-OCTET threshold";
            }
            leaf fcs-err {
              type uint32 {
                range "1..4294967295" {
                  description
                    "FCS-ERR threshold";
                }
              }
              description
                "set FCS-ERR threshold";
            }
            leaf tx-pkt {
              type uint32 {
                range "1..4294967295" {
                  description
                    "TX-PKT threshold";
                }
              }
              description
                "set TX-PKT threshold";
            }
            leaf in-ucast {
              type uint32 {
                range "1..4294967295" {
                  description
                    "IN-UCAST threshold";
                }
              }
              description
                "set IN-UCAST threshold";
            }
            leaf out-mcast {
              type uint32 {
                range "1..4294967295" {
                  description
                    "OUT-MCAST threshold ";
                }
              }
              description
                "set OUT-MCAST threshold";
            }
            leaf out-bcast {
              type uint32 {
                range "1..4294967295" {
                  description
                    "OUT-BCAST threshold ";
                }
              }
              description
                "set OUT-BCAST threshold";
            }
            leaf in-pause-frame {
              type uint32 {
                range "1..4294967295" {
                  description
                    "IN-PAUSE-FRAME threshold";
                }
              }
              description
                "set IN-PAUSE-FRAME threshold";
            }
            leaf in-good-bytes {
              type uint32 {
                range "1..4294967295" {
                  description
                    "IN-GOOD-BYTES threshold";
                }
              }
              description
                "set IN-GOOD-BYTES threshold";
            }
            leaf in-802-1q-frames {
              type uint32 {
                range "1..4294967295" {
                  description
                    "IN-802-1Q-FRAMES threshold";
                }
              }
              description
                "set IN-802-1Q-FRAMES threshold";
            }
            leaf in-pkts-1519-max-octets {
              type uint32 {
                range "1..4294967295" {
                  description
                    "IN-PKTS-1519-MAX-OCTETS threshold";
                }
              }
              description
                "set IN-PKTS-1519-MAX-OCTETS threshold";
            }
            leaf in-good-pkts {
              type uint32 {
                range "1..4294967295" {
                  description
                    "IN-GOOD-PKTS threshold";
                }
              }
              description
                "set IN-GOOD-PKTS threshold";
            }
            leaf in-drop-overrun {
              type uint32 {
                range "1..4294967295" {
                  description
                    "IN-DROP-OVERRUN threshold";
                }
              }
              description
                "set IN-DROP-OVERRUN threshold";
            }
            leaf in-drop-abort {
              type uint32 {
                range "1..4294967295" {
                  description
                    "IN-DROP-ABORT threshold";
                }
              }
              description
                "set IN-DROP-ABORT threshold";
            }
            leaf in-drop-invalid-vlan {
              type uint32 {
                range "1..4294967295" {
                  description
                    "IN-DROP-INVALID-VLAN threshold";
                }
              }
              description
                "set IN-DROP-INVALID-VLAN threshold";
            }
            leaf in-drop-invalid-dmac {
              type uint32 {
                range "1..4294967295" {
                  description
                    "IN-DROP-INVALID-DMAC threshold";
                }
              }
              description
                "set IN-DROP-INVALID-DMAC threshold";
            }
            leaf in-drop-invalid-encap {
              type uint32 {
                range "1..4294967295" {
                  description
                    "IN-DROP-INVALID-ENCAP threshold";
                }
              }
              description
                "set IN-DROP-INVALID-ENCAP threshold";
            }
            leaf in-drop-other {
              type uint32 {
                range "1..4294967295" {
                  description
                    "IN-DROP-OTHER threshold";
                }
              }
              description
                "set IN-DROP-OTHER threshold";
            }
            leaf in-mib-giant {
              type uint32 {
                range "1..4294967295" {
                  description
                    "IN-MIB-GIANT threshold";
                }
              }
              description
                "set IN-MIB-GIANT threshold";
            }
            leaf in-mib-jabber {
              type uint32 {
                range "1..4294967295" {
                  description
                    "IN-MIB-JABBER threshold";
                }
              }
              description
                "set IN-MIB-JABBER threshold";
            }
            leaf in-mib-crc {
              type uint32 {
                range "1..4294967295" {
                  description
                    "IN-MIB-CRC threshold";
                }
              }
              description
                "set IN-MIB-CRC threshold";
            }
            leaf in-error-collisions {
              type uint32 {
                range "1..4294967295" {
                  description
                    "IN-ERROR-COLLISIONS threshold";
                }
              }
              description
                "set IN-ERROR-COLLISIONS threshold";
            }
            leaf in-error-symbol {
              type uint32 {
                range "1..4294967295" {
                  description
                    "IN-ERROR-SYMBOL threshold";
                }
              }
              description
                "set IN-ERROR-SYMBOL threshold";
            }
            leaf out-good-bytes {
              type uint32 {
                range "1..4294967295" {
                  description
                    "OUT-GOOD-BYTES threshold";
                }
              }
              description
                "set OUT-GOOD-BYTES threshold";
            }
            leaf out-802-1q-frames {
              type uint32 {
                range "1..4294967295" {
                  description
                    "OUT-802-1Q-FRAMES threshold";
                }
              }
              description
                "set OUT-802-1Q-FRAMES threshold";
            }
            leaf out-pause-frames {
              type uint32 {
                range "1..4294967295" {
                  description
                    "OUT-PAUSE-FRAMES threshold";
                }
              }
              description
                "set OUT-PAUSE-FRAMES threshold";
            }
            leaf out-pkts-1519-max-octets {
              type uint32 {
                range "1..4294967295" {
                  description
                    "OUT-PKTS-1519-MAX-OCTETS threshold";
                }
              }
              description
                "set OUT-PKTS-1519-MAX-OCTETS threshold";
            }
            leaf out-good-pkts {
              type uint32 {
                range "1..4294967295" {
                  description
                    "OUT-GOOD-PKTS threshold";
                }
              }
              description
                "set OUT-GOOD-PKTS threshold";
            }
            leaf out-drop-underrun {
              type uint32 {
                range "1..4294967295" {
                  description
                    "OUT-DROP-UNDERRUN threshold";
                }
              }
              description
                "set OUT-DROP-UNDERRUN threshold";
            }
            leaf out-drop-abort {
              type uint32 {
                range "1..4294967295" {
                  description
                    "OUT-DROP-ABORT threshold";
                }
              }
              description
                "set OUT-DROP-ABORT threshold";
            }
            leaf out-drop-other {
              type uint32 {
                range "1..4294967295" {
                  description
                    "OUT-DROP-OTHER threshold";
                }
              }
              description
                "set OUT-DROP-OTHER threshold";
            }
            leaf out-error-other {
              type uint32 {
                range "1..4294967295" {
                  description
                    "OUT-ERROR-OTHER threshold";
                }
              }
              description
                "set OUT-ERROR-OTHER threshold";
            }
            leaf in-error-giant {
              type uint32 {
                range "1..4294967295" {
                  description
                    "IN-ERROR-GIANT threshold";
                }
              }
              description
                "set IN-ERROR-GIANT threshold";
            }
            leaf in-error-runt {
              type uint32 {
                range "1..4294967295" {
                  description
                    "IN-ERROR-RUNT threshold";
                }
              }
              description
                "set IN-ERROR-RUNT threshold";
            }
            leaf in-error-jabbers {
              type uint32 {
                range "1..4294967295" {
                  description
                    "IN-ERROR-JABBERS threshold";
                }
              }
              description
                "set IN-ERROR-JABBERS threshold";
            }
            leaf in-error-fragments {
              type uint32 {
                range "1..4294967295" {
                  description
                    "IN-ERROR-FRAGMENTS threshold";
                }
              }
              description
                "set IN-ERROR-FRAGMENTS threshold";
            }
            leaf in-error-other {
              type uint32 {
                range "1..4294967295" {
                  description
                    "IN-ERROR-OTHER threshold";
                }
              }
              description
                "set IN-ERROR-OTHER threshold";
            }
            leaf in-pkt-64-octet {
              type uint32 {
                range "1..4294967295" {
                  description
                    "IN-PKT-64-OCTET threshold";
                }
              }
              description
                "set IN-PKT-64-OCTET threshold";
            }
            leaf in-pkts-65-127octets {
              type uint32 {
                range "1..4294967295" {
                  description
                    "IN-PKTS-65-127OCTETS threshold";
                }
              }
              description
                "set IN-PKTS-65-127OCTETS threshold";
            }
            leaf in-pkts-128-255-octets {
              type uint32 {
                range "1..4294967295" {
                  description
                    "IN-PKTS-128-255-OCTETS threshold";
                }
              }
              description
                "set IN-PKTS-128-255-OCTETS threshold";
            }
            leaf in-pkts-256-511-octets {
              type uint32 {
                range "1..4294967295" {
                  description
                    "IN-PKTS-256-511-OCTETS threshold";
                }
              }
              description
                "set IN-PKTS-256-511-OCTETS threshold";
            }
            leaf in-pkts-512-1023-octets {
              type uint32 {
                range "1..4294967295" {
                  description
                    "IN-PKTS-512-1023-OCTETS threshold";
                }
              }
              description
                "set IN-PKTS-512-1023-OCTETS threshold";
            }
            leaf in-pkts-1024-1518-octets {
              type uint32 {
                range "1..4294967295" {
                  description
                    "IN-PKTS-1024-1518-OCTETS threshold";
                }
              }
              description
                "set IN-PKTS-1024-1518-OCTETS threshold";
            }
            leaf out-pkt-64-octet {
              type uint32 {
                range "1..4294967295" {
                  description
                    "OUT-PKT-64-OCTET threshold";
                }
              }
              description
                "set OUT-PKT-64-OCTET threshold";
            }
            leaf out-pkts-65-127octets {
              type uint32 {
                range "1..4294967295" {
                  description
                    "OUT-PKTS-65-127OCTETS threshold";
                }
              }
              description
                "set OUT-PKTS-65-127OCTETS threshold";
            }
            leaf out-pkts-128-255-octets {
              type uint32 {
                range "1..4294967295" {
                  description
                    "OUT-PKTS-128-255-OCTETS threshold";
                }
              }
              description
                "set OUT-PKTS-128-255-OCTETS threshold";
            }
            leaf out-pkts-256-511-octets {
              type uint32 {
                range "1..4294967295" {
                  description
                    "OUT-PKTS-256-511-OCTETS threshold";
                }
              }
              description
                "set OUT-PKTS-256-511-OCTETS threshold";
            }
            leaf out-pkts-512-1023-octets {
              type uint32 {
                range "1..4294967295" {
                  description
                    "OUT-PKTS-512-1023-OCTETS threshold";
                }
              }
              description
                "set OUT-PKTS-512-1023-OCTETS threshold";
            }
            leaf out-pkts-1024-1518-octets {
              type uint32 {
                range "1..4294967295" {
                  description
                    "OUT-PKTS-1024-1518-OCTETS threshold";
                }
              }
              description
                "set OUT-PKTS-1024-1518-OCTETS threshold";
            }
          }
          container report {
            description
              "set ether TCA reporting status";
            container rx-pkt {
              description
                "set rx-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-octets {
              description
                "set ifOut_errors  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-pause-frame {
              description
                "set in-pause-frame TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-802-1q-frames {
              description
                "set in-802-1Q-frames TCA reporting status";
              container enable {
                presence "Indicates a enable node is configured.";
                description
                  "Enable TCA reporting";
              }
            }
            container in-pkts-1519-max-octets {
              description
                "set in-pkts-1519-Max-octets TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-overrun {
              description
                "set in-drop-overrun TCA reporting status";
              container enable {
                presence "Indicates a enable node is configured.";
                description
                  "Enable TCA reporting";
              }
            }
            container in-drop-abort {
              description
                "set in-drop-abort TCA reporting status";
              container enable {
                presence "Indicates a enable node is configured.";
                description
                  "Enable TCA reporting";
              }
            }
            container in-drop-invalid-vlan {
              description
                "set in-drop-invalid-VLAN TCA reporting status";
              container enable {
                presence "Indicates a enable node is configured.";
                description
                  "Enable TCA reporting";
              }
            }
            container in-drop-invalid-dmac {
              description
                "set in-drop-invalid-DMAC TCA reporting status";
              container enable {
                presence "Indicates a enable node is configured.";
                description
                  "Enable TCA reporting";
              }
            }
            container in-drop-invalid-encap {
              description
                "set in-drop-invalid-encap TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container in-mib-giant {
              description
                "set in-MIB-giant TCA reporting status";
              container enable {
                presence "Indicates a enable node is configured.";
                description
                  "Enable TCA reporting";
              }
            }
            container in-mib-jabber {
              description
                "set in-MIB-jabber TCA reporting status";
              container enable {
                presence "Indicates a enable node is configured.";
                description
                  "Enable TCA reporting";
              }
            }
            container in-mib-crc {
              description
                "set in-MIB-CRC TCA reporting status";
              container enable {
                presence "Indicates a enable node is configured.";
                description
                  "Enable TCA reporting";
              }
            }
            container in-error-collisions {
              description
                "set in-error-collisions TCA reporting status";
              container enable {
                presence "Indicates a enable node is configured.";
                description
                  "Enable TCA reporting";
              }
            }
            container in-error-symbol {
              description
                "set in-error-symbol TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-802-1q-frames {
              description
                "set out-802-1Q-frames TCA reporting status";
              container enable {
                presence "Indicates a enable node is configured.";
                description
                  "Enable TCA reporting";
              }
            }
            container out-pause-frames {
              description
                "set out-pause-frames TCA reporting status";
              container enable {
                presence "Indicates a enable node is configured.";
                description
                  "Enable TCA reporting";
              }
            }
            container out-pkts-1519-max-octets {
              description
                "set out-pkts-1519-Max-octets TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container out-drop-underrun {
              description
                "set out-drop-underrun TCA reporting status";
              container enable {
                presence "Indicates a enable node is configured.";
                description
                  "Enable TCA reporting";
              }
            }
            container out-drop-abort {
              description
                "set out-drop-abort TCA reporting status";
              container enable {
                presence "Indicates a enable node is configured.";
                description
                  "Enable TCA reporting";
              }
            }
            container out-drop-other {
              description
                "set out-drop-other TCA reporting status";
              container enable {
                presence "Indicates a enable node is configured.";
                description
                  "Enable TCA reporting";
              }
            }
            container out-error-other {
              description
                "set out-error-other TCA reporting status";
              container enable {
                presence "Indicates a enable node is configured.";
                description
                  "Enable TCA reporting";
              }
            }
            container in-error-giant {
              description
                "set in-error-giant TCA reporting status";
              container enable {
                presence "Indicates a enable node is configured.";
                description
                  "Enable TCA reporting";
              }
            }
            container in-error-runt {
              description
                "set in-error-runt TCA reporting status";
              container enable {
                presence "Indicates a enable node is configured.";
                description
                  "Enable TCA reporting";
              }
            }
            container in-error-jabbers {
              description
                "set in-error-jabbers TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-error-other {
              description
                "set in-error-other TCA reporting status";
              container enable {
                presence "Indicates a enable node is configured.";
                description
                  "Enable TCA reporting";
              }
            }
            container in-pkt-64-octet {
              description
                "set in-pkt-64-octet TCA reporting status";
              container enable {
                presence "Indicates a enable node is configured.";
                description
                  "Enable TCA reporting";
              }
            }
            container in-pkts-65-127octets {
              description
                "set in-pkts-65-127octets TCA reporting status";
              container enable {
                presence "Indicates a enable node is configured.";
                description
                  "Enable TCA reporting";
              }
            }
            container in-pkts-128-255-octets {
              description
                "set in-pkts-128-255-octets TCA reporting status";
              container enable {
                presence "Indicates a enable node is configured.";
                description
                  "Enable TCA reporting";
              }
            }
            container in-pkts-256-511-octets {
              description
                "set in-pkts-256-511-octets TCA reporting status";
              container enable {
                presence "Indicates a enable node is configured.";
                description
                  "Enable TCA reporting";
              }
            }
            container in-pkts-512-1023-octets {
              description
                "set in-pkts-512-1023-octets TCA reporting status";
              container enable {
                presence "Indicates a enable node is configured.";
                description
                  "Enable TCA reporting";
              }
            }
            container in-pkts-1024-1518-octets {
              description
                "set in-pkts-1024-1518-octets TCA reporting status";
              container enable {
                presence "Indicates a enable node is configured.";
                description
                  "Enable TCA reporting";
              }
            }
            container out-pkt-64-octet {
              description
                "set out-pkt-64-octet TCA reporting status";
              container enable {
                presence "Indicates a enable node is configured.";
                description
                  "Enable TCA reporting";
              }
            }
            container out-pkts-65-127octets {
              description
                "set out-pkts-65-127octets TCA reporting status";
              container enable {
                presence "Indicates a enable node is configured.";
                description
                  "Enable TCA reporting";
              }
            }
            container out-pkts-128-255-octets {
              description
                "set out-pkts-128-255-octets TCA reporting status";
              container enable {
                presence "Indicates a enable node is configured.";
                description
                  "Enable TCA reporting";
              }
            }
            container out-pkts-256-511-octets {
              description
                "set out-pkts-256-511-octets TCA reporting status";
              container enable {
                presence "Indicates a enable node is configured.";
                description
                  "Enable TCA reporting";
              }
            }
            container out-pkts-512-1023-octets {
              description
                "set out-pkts-512-1023-octets TCA reporting status";
              container enable {
                presence "Indicates a enable node is configured.";
                description
                  "Enable TCA reporting";
              }
            }
            container out-pkts-1024-1518-octets {
              description
                "set out-pkts-1024-1518-octets TCA reporting status";
              container enable {
                presence "Indicates a enable node is configured.";
                description
                  "Enable TCA reporting";
              }
            }
          }
        }
      }
    }
  }

  grouping CONT-BODY {
    container pm {
      when "../a1:controller-name[starts-with(text(),'FortyGigECtrlr')] or ../a1:controller-name[starts-with(text(),'FourHundredGigECtrlr')] or ../a1:controller-name[starts-with(text(),'GigabitEthCtrlr')] or ../a1:controller-name[starts-with(text(),'HundredGigECtrlr')] or ../a1:controller-name[starts-with(text(),'TenGigECtrlr')] or ../a1:controller-name[starts-with(text(),'MACSecCtrlr')]" {
        tailf:dependency "../a1:controller-name";
      }
      description
        "Configure pm parameters";
      container interval-15-min {
        description
          "Configure pm parameters of 15 minute interval";
        container ether {
          description
            "configure ether performance monitoring";
          container threshold {
            description
              "Configure threshold on ether parameters";
            leaf rx-pkt {
              type uint32 {
                range "1..4294967295" {
                  description
                    "RX-PKT threshold ";
                }
              }
              description
                "set RX-PKT threshold";
            }
            leaf stat-pkt {
              type uint32 {
                range "1..4294967295" {
                  description
                    "PKT-STAT threshold ";
                }
              }
              description
                "set PKT-STAT threshold";
            }
            leaf octet-stat {
              type uint32 {
                range "1..4294967295" {
                  description
                    "OCTET-STAT threshold ";
                }
              }
              description
                "set OCTET-STAT threshold";
            }
            leaf oversize-pkt {
              type uint32 {
                range "1..4294967295" {
                  description
                    "OVERSIZE-PKT threshold";
                }
              }
              description
                "set OVERSIZE-PKT threshold";
            }
            leaf fcs-err {
              type uint32 {
                range "1..4294967295" {
                  description
                    "FCS-ERR threshold";
                }
              }
              description
                "set FCS-ERR threshold";
            }
            leaf long-frame {
              type uint32 {
                range "1..4294967295" {
                  description
                    "LONG-FRAMES threshold ";
                }
              }
              description
                "set LONG-FRAMES threshold";
            }
            leaf jabber-stats {
              type uint32 {
                range "1..4294967295" {
                  description
                    "JABBER-STATS threshold ";
                }
              }
              description
                "set JABBER-STATS threshold";
            }
            leaf sixty-four-octets {
              type uint32 {
                range "1..4294967295" {
                  description
                    "64-OCTET threshold";
                }
              }
              description
                "set 64-OCTET threshold";
            }
            leaf six5-127-octets {
              type uint32 {
                range "1..4294967295" {
                  description
                    "65-127-OCTET threshold";
                }
              }
              description
                "set 65-127-OCTET threshold";
            }
            leaf one-hundred-twenty-eight-255-octets {
              type uint32 {
                range "1..4294967295" {
                  description
                    "128-255-OCTET threshold ";
                }
              }
              description
                "set 128-255-OCTET threshold";
            }
            leaf two-hundred-fifty-six-511-octets {
              type uint32 {
                range "1..4294967295" {
                  description
                    "256-511-OCTET threshold ";
                }
              }
              description
                "set 256-511-OCTET threshold";
            }
            leaf five-hundred-twelve-1023-octets {
              type uint32 {
                range "1..4294967295" {
                  description
                    "512-1023-OCTET threshold";
                }
              }
              description
                "set 512-1023-OCTET threshold";
            }
            leaf one-thousand-twenty-four-1518-octets {
              type uint32 {
                range "1..4294967295" {
                  description
                    "1024-1518-OCTET threshold";
                }
              }
              description
                "set 1024-1518-OCTET threshold";
            }
            leaf in-64-octets {
              type uint32 {
                range "1..4294967295" {
                  description
                    "IN-64-OCTET threshold";
                }
              }
              description
                "set IN-64-OCTET threshold";
            }
            leaf in-65-127-octets {
              type uint32 {
                range "1..4294967295" {
                  description
                    "IN-65-127-OCTET threshold";
                }
              }
              description
                "set IN-65-127-OCTET threshold";
            }
            leaf in-128-255-octets {
              type uint32 {
                range "1..4294967295" {
                  description
                    "IN-128-255-OCTET threshold ";
                }
              }
              description
                "set IN-128-255-OCTET threshold";
            }
            leaf in-256-511-octets {
              type uint32 {
                range "1..4294967295" {
                  description
                    "IN-256-511-OCTET threshold ";
                }
              }
              description
                "set IN-256-511-OCTET threshold";
            }
            leaf in-512-1023-octets {
              type uint32 {
                range "1..4294967295" {
                  description
                    "IN-512-1023-OCTET threshold";
                }
              }
              description
                "set IN-512-1023-OCTET threshold";
            }
            leaf in-1024-1518-octets {
              type uint32 {
                range "1..4294967295" {
                  description
                    "IN-1024-1518-OCTET threshold";
                }
              }
              description
                "set IN-1024-1518-OCTET threshold";
            }
            leaf out-pkt-64-octet {
              type uint32 {
                range "1..4294967295" {
                  description
                    "OUT-PKT-64-OCTET threshold";
                }
              }
              description
                "set OUT-PKT-64-OCTET threshold";
            }
            leaf out-pkts-65-127-octets {
              type uint32 {
                range "1..4294967295" {
                  description
                    "OUT-PKTS-65-127-OCTETS threshold";
                }
              }
              description
                "set OUT-PKTS-65-127-OCTETS threshold";
            }
            leaf out-pkts-128-255-octets {
              type uint32 {
                range "1..4294967295" {
                  description
                    "OUT-PKTS-128-255-OCTETS threshold";
                }
              }
              description
                "set OUT-PKTS-128-255-OCTETS threshold";
            }
            leaf out-pkts-256-511-octets {
              type uint32 {
                range "1..4294967295" {
                  description
                    "OUT-PKTS-256-511-OCTETS threshold";
                }
              }
              description
                "set OUT-PKTS-256-511-OCTETS threshold";
            }
            leaf out-pkts-512-1023-octets {
              type uint32 {
                range "1..4294967295" {
                  description
                    "OUT-PKTS-512-1023-OCTETS threshold";
                }
              }
              description
                "set OUT-PKTS-512-1023-OCTETS threshold";
            }
            leaf out-pkts-1024-1518-octets {
              type uint32 {
                range "1..4294967295" {
                  description
                    "OUT-PKTS-1024-1518-OCTETS threshold";
                }
              }
              description
                "set OUT-PKTS-1024-1518-OCTETS threshold";
            }
            leaf in-drop-other {
              type uint32 {
                range "1..4294967295" {
                  description
                    "IN-DROP-OTHER threshold";
                }
              }
              description
                "set IN_DROP_OTHER threshold";
            }
            leaf in-ucast {
              type uint32 {
                range "1..4294967295" {
                  description
                    "IN-UCAST threshold";
                }
              }
              description
                "set IN-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf in-error-fragments {
              type uint32 {
                range "1..4294967295" {
                  description
                    "IN-ERROR-FRAGMENTS threshold";
                }
              }
              description
                "set IN-ERROR-FRAGMENTS threshold";
            }
            leaf out-ucast {
              type uint32 {
                range "1..4294967295" {
                  description
                    "OUT-UCAST threshold";
                }
              }
              description
                "set OUT-UCAST threshold";
            }
            leaf out-bcast {
              type uint32 {
                range "1..4294967295" {
                  description
                    "OUT-BCAST threshold ";
                }
              }
              description
                "set OUT-BCAST threshold";
            }
            leaf out-mcast {
              type uint32 {
                range "1..4294967295" {
                  description
                    "OUT-MCAST threshold ";
                }
              }
              description
                "set OUT-MCAST threshold";
            }
            leaf tx-pkt {
              type uint32 {
                range "1..4294967295" {
                  description
                    "TX-PKT threshold";
                }
              }
              description
                "set TX-PKT threshold";
            }
            leaf out-octets {
              type uint32 {
                range "1..4294967295" {
                  description
                    "OUT-OCTET threshold ";
                }
              }
              description
                "set OUT-OCTET threshold";
            }
            leaf if-in-errors {
              type uint32 {
                range "1..4294967295" {
                  description
                    "IFIN_ERRORS threshold";
                }
              }
              description
                "set IFIN_ERRORS threshold";
            }
            leaf if-in-octets {
              type uint32 {
                range "1..4294967295" {
                  description
                    "IFIN_OCTETS threshold";
                }
              }
              description
                "set IFIN_OCTETS threshold";
            }
            leaf ether-stat-multicast-pkt {
              type uint32 {
                range "1..4294967295" {
                  description
                    "ETHER_STAT_MULTICAST_PKT threshold";
                }
              }
              description
                "set ETHER_STAT_MULTICAST_PKT threshold";
            }
            leaf ether-stat-broadcast-pkt {
              type uint32 {
                range "1..4294967295" {
                  description
                    " ETHER_STAT_BROADCAST_PKT threshold";
                }
              }
              description
                "set ETHER_STAT_BROADCAST_PKT threshold";
            }
            leaf in-good-bytes {
              type uint32 {
                range "1..4294967295" {
                  description
                    "set IN_GOOD_BYTES threshold";
                }
              }
              description
                "set IN_GOOD_BYTES threshold";
            }
            leaf in-good-pkts {
              type uint32 {
                range "1..4294967295" {
                  description
                    "set IN_GOOD_PKTS threshold";
                }
              }
              description
                "set IN_GOOD_PKTS threshold";
            }
            leaf out-good-bytes {
              type uint32 {
                range "1..4294967295" {
                  description
                    "set OUT_GOOD_BYTES threshold";
                }
              }
              description
                "set OUT_GOOD_BYTES threshold";
            }
            leaf out-good-pkts {
              type uint32 {
                range "1..4294967295" {
                  description
                    "set GOOD_PKTS threshold";
                }
              }
              description
                "set THRESH_OUT_GOOD_PKTS threshold";
            }
            leaf rx-util {
              type uint32 {
                range "1..10000" {
                  description
                    "set RX_UTIL threshold(in units of 0.01%)";
                }
              }
              description
                "set RX_UTIL threshold(in units of 0.01%)";
            }
            leaf tx-util {
              type uint32 {
                range "1..10000" {
                  description
                    "set TX_UTIL threshold(in units of 0.01%)";
                }
              }
              description
                "set TX_UTIL threshold(in units of 0.01%)";
            }
            leaf ether-stat-undersized-pkt {
              type uint32 {
                range "1..4294967295" {
                  description
                    "ETHER_STAT_UNDERSIZED_PKT threshold";
                }
              }
              description
                "set ETHER_STAT_UNDERSIZED_PKT threshold";
            }
            leaf tx-undersized-pkt {
              type uint32 {
                range "1..4294967295" {
                  description
                    "TX_UNDERSIZED_PKT threshold";
                }
              }
              description
                "set TX_UNDERSIZED_PKT threshold";
            }
            leaf tx-oversized-pkt {
              type uint32 {
                range "1..4294967295" {
                  description
                    "TX_OVERSIZED_PKT threshold";
                }
              }
              description
                "set TX_OVERSIZED_PKT threshold";
            }
            leaf tx-fragments {
              type uint32 {
                range "1..4294967295" {
                  description
                    "TX_FRAGMENTS threshold";
                }
              }
              description
                "set TX_FRAGMENTS threshold";
            }
            leaf tx-jabber {
              type uint32 {
                range "1..4294967295" {
                  description
                    "TX_JABBER threshold";
                }
              }
              description
                "set TX_JABBER threshold";
            }
            leaf tx-bad-fcs {
              type uint32 {
                range "1..4294967295" {
                  description
                    "TX_BAD_FCS threshold";
                }
              }
              description
                "set TX_BAD_FCS threshold";
            }
          }
          container report {
            description
              "set ether TCA reporting status";
            container rx-pkt {
              description
                "set rx-pkt TCA reporting status";
              container enable {
                presence "Indicates a enable node is configured.";
                description
                  "Enable TCA reporting";
              }
            }
            container rx-util {
              description
                "set rx-util TCA reporting status";
              container enable {
                presence "Indicates a enable node is configured.";
                description
                  "Enable TCA reporting";
              }
            }
            container tx-util {
              description
                "set tx-util TCA reporting status";
              container enable {
                presence "Indicates a enable node is configured.";
                description
                  "Enable TCA reporting";
              }
            }
            container stat-pkt {
              description
                "set stat-pkt TCA reporting status";
              container enable {
                presence "Indicates a enable node is configured.";
                description
                  "Enable TCA reporting";
              }
            }
            container octet-stat {
              description
                "set octet-stat TCA reporting status";
              container enable {
                presence "Indicates a enable node is configured.";
                description
                  "Enable TCA reporting";
              }
            }
            container oversize-pkt {
              description
                "set oversize-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container long-frame {
              description
                "set long-frame TCA reporting status";
              container enable {
                presence "Indicates a enable node is configured.";
                description
                  "Enable TCA reporting";
              }
            }
            container jabber-stats {
              description
                "set jabber-stats TCA reporting status";
              container enable {
                presence "Indicates a enable node is configured.";
                description
                  "Enable TCA reporting";
              }
            }
            container _64-octets {
              description
                "set 64-octets TCA reporting status";
              container enable {
                presence "Indicates a enable node is configured.";
                description
                  "Enable TCA reporting";
              }
            }
            container _65-127-octets {
              description
                "set 65-127-octets TCA reporting status";
              container enable {
                presence "Indicates a enable node is configured.";
                description
                  "Enable TCA reporting";
              }
            }
            container _128-255-octets {
              description
                "set 128-255-octets TCA reporting status";
              container enable {
                presence "Indicates a enable node is configured.";
                description
                  "Enable TCA reporting";
              }
            }
            container _256-511-octets {
              description
                "set 256-511-octets TCA reporting status";
              container enable {
                presence "Indicates a enable node is configured.";
                description
                  "Enable TCA reporting";
              }
            }
            container _512-1023-octets {
              description
                "set 512-1023-octets TCA reporting status";
              container enable {
                presence "Indicates a enable node is configured.";
                description
                  "Enable TCA reporting";
              }
            }
            container _1024-1518-octets {
              description
                "set 1024-1518-octets TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-errors {
              description
                "set ifIn_errors TCA reporting status";
              container enable {
                presence "Indicates a enable node is configured.";
                description
                  "Enable TCA reporting";
              }
            }
            container if-in-octets {
              description
                "set ifOut_errors  TCA reporting status";
              container enable {
                presence "Indicates a enable node is configured.";
                description
                  "Enable TCA reporting";
              }
            }
            container ether-stat-multicast-pkt {
              description
                "set ether_stat_multicast_pkt TCA reporting status";
              container enable {
                presence "Indicates a enable node is configured.";
                description
                  "Enable TCA reporting";
              }
            }
            container ether-stat-broadcast-pkt {
              description
                "set ether_stat_broadcast_pkt TCA reporting status";
              container enable {
                presence "Indicates a enable node is configured.";
                description
                  "Enable TCA reporting";
              }
            }
            container ether-stat-undersized-pkt {
              description
                "set ether_stat_undersized_pkt  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-64-octets {
              description
                "set in-64-octets TCA reporting status";
              container enable {
                presence "Indicates a enable node is configured.";
                description
                  "Enable TCA reporting";
              }
            }
            container in-65-127-octets {
              description
                "set in-65-127-octets TCA reporting status";
              container enable {
                presence "Indicates a enable node is configured.";
                description
                  "Enable TCA reporting";
              }
            }
            container in-128-255-octets {
              description
                "set in-128-255-octets TCA reporting status";
              container enable {
                presence "Indicates a enable node is configured.";
                description
                  "Enable TCA reporting";
              }
            }
            container in-256-511-octets {
              description
                "set in-256-511-octets TCA reporting status";
              container enable {
                presence "Indicates a enable node is configured.";
                description
                  "Enable TCA reporting";
              }
            }
            container in-512-1023-octets {
              description
                "set in-512-1023-octets TCA reporting status";
              container enable {
                presence "Indicates a enable node is configured.";
                description
                  "Enable TCA reporting";
              }
            }
            container in-1024-1518-octets {
              description
                "set in-1024-1518-octets TCA reporting status";
              container enable {
                presence "Indicates a enable node is configured.";
                description
                  "Enable TCA reporting";
              }
            }
            container out-pkt-64-octet {
              description
                "set out-pkt-64-octet TCA reporting status";
              container enable {
                presence "Indicates a enable node is configured.";
                description
                  "Enable TCA reporting";
              }
            }
            container out-pkts-65-127-octets {
              description
                "set out-pkts-65-127-octets TCA reporting status";
              container enable {
                presence "Indicates a enable node is configured.";
                description
                  "Enable TCA reporting";
              }
            }
            container out-pkts-128-255-octets {
              description
                "set out-pkts-128-255-octets TCA reporting status";
              container enable {
                presence "Indicates a enable node is configured.";
                description
                  "Enable TCA reporting";
              }
            }
            container out-pkts-256-511-octets {
              description
                "set out-pkts-256-511-octets TCA reporting status";
              container enable {
                presence "Indicates a enable node is configured.";
                description
                  "Enable TCA reporting";
              }
            }
            container out-pkts-512-1023-octets {
              description
                "set out-pkts-512-1023-octets TCA reporting status";
              container enable {
                presence "Indicates a enable node is configured.";
                description
                  "Enable TCA reporting";
              }
            }
            container out-pkts-1024-1518-octets {
              description
                "set out-pkts-1024-1518-octets TCA reporting status";
              container enable {
                presence "Indicates a enable node is configured.";
                description
                  "Enable TCA reporting";
              }
            }
            container tx-undersized-pkt {
              description
                "set tx_undersized_pkt  TCA reporting status";
              container enable {
                presence "Indicates a enable node is configured.";
                description
                  "Enable TCA reporting";
              }
            }
            container tx-oversized-pkt {
              description
                "set tx_oversized_pkt  TCA reporting status";
              container enable {
                presence "Indicates a enable node is configured.";
                description
                  "Enable TCA reporting";
              }
            }
            container tx-fragments {
              description
                "set tx_fragments  TCA reporting status";
              container enable {
                presence "Indicates a enable node is configured.";
                description
                  "Enable TCA reporting";
              }
            }
            container tx-jabber {
              description
                "set tx_jabber  TCA reporting status";
              container enable {
                presence "Indicates a enable node is configured.";
                description
                  "Enable TCA reporting";
              }
            }
            container tx-bad-fcs {
              description
                "set tx_bad_fcs  TCA reporting status";
              container enable {
                presence "Indicates a enable node is configured.";
                description
                  "Enable TCA reporting";
              }
            }
          }
        }
        container fec {
          description
            "Configure fec performance monitoring";
          container threshold {
            description
              "Configure fec threshold";
            leaf ec-words {
              type xr:Cisco-ios-xr-string {
                length "1..20" {
                  description
                    "ec-words threshold <range:1-18446744073709551615>";
                }
              }
              description
                "set EC-Words threshold";
            }
            leaf uc-words {
              type xr:Cisco-ios-xr-string {
                length "1..20" {
                  description
                    "uc-words threshold <range:1-18446744073709551615>";
                }
              }
              description
                "set UC-WORDS threshold";
            }
            container pre-fec-ber {
              description
                "Set PRE-FEC-BER Thresholds";
              leaf min {
                type xr:Cisco-ios-xr-string {
                  length "1..20" {
                    description
                      "pre-fec-ber min threshold <range:1-18446744073709551615>";
                  }
                }
                description
                  "set pre-fec-ber min threshold";
              }
              leaf max {
                type xr:Cisco-ios-xr-string {
                  length "1..20" {
                    description
                      "pre-fec-ber max threshold <range:1-18446744073709551615>";
                  }
                }
                description
                  "set pre-fec-ber max threshold";
              }
            }
            container post-fec-ber {
              description
                "Set POST-FEC-BER Thresholds";
              leaf min {
                type xr:Cisco-ios-xr-string {
                  length "1..20" {
                    description
                      "post-fec-ber min threshold <range:1-18446744073709551615>";
                  }
                }
                description
                  "set post-fec-ber min threshold";
              }
              leaf max {
                type xr:Cisco-ios-xr-string {
                  length "1..20" {
                    description
                      "post-fec-ber max threshold <range:1-18446744073709551615>";
                  }
                }
                description
                  "set post-fec-ber max threshold";
              }
            }
          }
          container report {
            description
              "set fec TCA reporting status";
            container uc-words {
              description
                "set uc-words TCA reporting status";
              container enable {
                presence "Indicates a enable node is configured.";
                description
                  "Enable TCA reporting";
              }
            }
            container ec-words {
              description
                "set ec-words TCA reporting status";
              container enable {
                presence "Indicates a enable node is configured.";
                description
                  "Enable TCA reporting";
              }
            }
            container pre-fec-ber {
              description
                "set PRE FEC BER TCA reporting status";
              container max-tca {
                description
                  "set PRE FEC BER max TCA reporting status";
                container enable {
                  presence "Indicates a enable node is configured.";
                  description
                    "Enable TCA reporting";
                }
              }
              container min-tca {
                description
                  "set PRE FEC BER min TCA reporting status";
                container enable {
                  presence "Indicates a enable node is configured.";
                  description
                    "Enable TCA reporting";
                }
              }
            }
            container post-fec-ber {
              description
                "set POST FEC BER TCA reporting status";
              container max-tca {
                description
                  "set POST FEC BER max TCA reporting status";
                container enable {
                  presence "Indicates a enable node is configured.";
                  description
                    "Enable TCA reporting";
                }
              }
              container min-tca {
                description
                  "set POST FEC BER min TCA reporting status";
                container enable {
                  presence "Indicates a enable node is configured.";
                  description
                    "Enable TCA reporting";
                }
              }
            }
          }
        }
        container pcs {
          description
            "configure pcs performance monitoring";
          container threshold {
            description
              "Configure threshold on pcs parameters";
            leaf bip {
              type xr:Cisco-ios-xr-string {
                length "1..20" {
                  description
                    "BIP threshold range <1-18446744073709551615>";
                }
              }
              description
                "set BIP threshold";
            }
            leaf frm-err {
              type xr:Cisco-ios-xr-string {
                length "1..20" {
                  description
                    "FRM-ERR threshold range <1-18446744073709551615>";
                }
              }
              description
                "set FRM-ERR threshold";
            }
            leaf bad-sh {
              type xr:Cisco-ios-xr-string {
                length "1..20" {
                  description
                    "Bad-sh threshold range <1-18446744073709551615>";
                }
              }
              description
                "set Bad-sh threshold";
            }
            leaf es {
              type xr:Cisco-ios-xr-string {
                length "1..20" {
                  description
                    "Es threshold range <0-900>";
                }
              }
              description
                "set Es threshold";
            }
            leaf ses {
              type xr:Cisco-ios-xr-string {
                length "1..20" {
                  description
                    "Ses threshold range <0-900>";
                }
              }
              description
                "set Ses threshold";
            }
            leaf uas {
              type xr:Cisco-ios-xr-string {
                length "1..20" {
                  description
                    "Uas threshold range <0-900>";
                }
              }
              description
                "set Uas threshold";
            }
            leaf es-fe {
              type xr:Cisco-ios-xr-string {
                length "1..20" {
                  description
                    "Es fe threshold range <0-900>";
                }
              }
              description
                "set es_fe threshold";
            }
            leaf ses-fe {
              type xr:Cisco-ios-xr-string {
                length "1..20" {
                  description
                    "Ses fe threshold range <0-900>";
                }
              }
              description
                "set Ses fe threshold";
            }
            leaf uas-fe {
              type xr:Cisco-ios-xr-string {
                length "1..20" {
                  description
                    "Uas fe threshold range <0-900>";
                }
              }
              description
                "set Ses threshold";
            }
          }
          container report {
            description
              "set pcs TCA reporting status";
            container bip {
              description
                "set bip TCA reporting status";
              container enable {
                presence "Indicates a enable node is configured.";
                description
                  "Enable TCA reporting";
              }
            }
            container frm-err {
              description
                "set frm-err TCA reporting status";
              container enable {
                presence "Indicates a enable node is configured.";
                description
                  "Enable TCA reporting";
              }
            }
            container bad-sh {
              description
                "set bad-sh TCA reporting status";
              container enable {
                presence "Indicates a enable node is configured.";
                description
                  "Enable TCA reporting";
              }
            }
            container es {
              description
                "set es TCA reporting status";
              container enable {
                presence "Indicates a enable node is configured.";
                description
                  "Enable TCA reporting";
              }
            }
            container ses {
              description
                "set ses TCA reporting status";
              container enable {
                presence "Indicates a enable node is configured.";
                description
                  "Enable TCA reporting";
              }
            }
            container uas {
              description
                "set uas TCA reporting status";
              container enable {
                presence "Indicates a enable node is configured.";
                description
                  "Enable TCA reporting";
              }
            }
            container es-fe {
              description
                "set es-fe TCA reporting status";
              container disable {
                presence "Indicates a disable node is configured.";
                description
                  "Disable TCA reporting";
              }
            }
            container ses-fe {
              description
                "set ses-fe TCA reporting status";
              container disable {
                presence "Indicates a disable node is configured.";
                description
                  "Disable TCA reporting";
              }
            }
            container uas-fe {
              description
                "set uas-fe TCA reporting status";
              container disable {
                presence "Indicates a disable node is configured.";
                description
                  "Disable TCA reporting";
              }
            }
          }
        }
        container macsec-secy-tx {
          description
            "Configure pm parameters of macsec-secy-tx";
          container threshold {
            description
              "Configure threshold on macsec-secy-tx parameters";
            leaf out-pkts-protected {
              type uint32 {
                range "1..4294967295" {
                  description
                    "OutPktsProtected threshold range";
                }
              }
              description
                "Set Threshold for OutPktsProtected";
            }
            leaf out-pkts-encrypted {
              type uint32 {
                range "1..4294967295" {
                  description
                    "OutPktsEncrypted threshold range";
                }
              }
              description
                "Set Threshold for OutPktsEncrypted";
            }
            leaf out-octets-protected {
              type uint32 {
                range "1..4294967295" {
                  description
                    "OutOctetsProtected threshold range";
                }
              }
              description
                "Set Threshold for OutOctetsProtected";
            }
            leaf out-octets-encrypted {
              type uint32 {
                range "1..4294967295" {
                  description
                    "OutOctetsEncrypted threshold range";
                }
              }
              description
                "Set Threshold for OutOctetsEncrypted";
            }
            leaf out-pkts-too-long {
              type uint32 {
                range "1..4294967295" {
                  description
                    "OutPktsTooLong threshold range";
                }
              }
              description
                "Set Threshold for OutPktsTooLong";
            }
          }
          container report {
            description
              "Configure Report for macsec-secy-tx Parameters";
            container out-pkts-protected {
              description
                "set OutPktsProtected TCA reporting status";
              container enable {
                presence "Indicates a enable node is configured.";
                description
                  "Enable TCA reporting";
              }
            }
            container out-pkts-encrypted {
              description
                "set OutPktsEncrypted TCA reporting status";
              container enable {
                presence "Indicates a enable node is configured.";
                description
                  "Enable TCA reporting";
              }
            }
            container out-octets-protected {
              description
                "set OutOctetsProtected TCA reporting status";
              container enable {
                presence "Indicates a enable node is configured.";
                description
                  "Enable TCA reporting";
              }
            }
            container out-octets-encrypted {
              description
                "set OutOctetsEncrypted TCA reporting status";
              container enable {
                presence "Indicates a enable node is configured.";
                description
                  "Enable TCA reporting";
              }
            }
            container out-pkts-too-long {
              description
                "set OutPktsTooLong TCA reporting status";
              container enable {
                presence "Indicates a enable node is configured.";
                description
                  "Enable TCA reporting";
              }
            }
          }
        }
        container macsec-secy-rx {
          description
            "Configure pm parameters of macsec-secy-rx";
          container threshold {
            description
              "Configure threshold on macsec-secy-rx parameters";
            leaf in-pkts-unchecked {
              type uint32 {
                range "1..4294967295" {
                  description
                    "InPktsUnchecked threshold range";
                }
              }
              description
                "Set Threshold for InPktsUnchecked";
            }
            leaf in-pkts-delayed {
              type uint32 {
                range "1..4294967295" {
                  description
                    "InPktsDelayed threshold range";
                }
              }
              description
                "Set Threshold for InPktsDelayed";
            }
            leaf in-pkts-late {
              type uint32 {
                range "1..4294967295" {
                  description
                    "InPktsLate threshold range";
                }
              }
              description
                "Set Threshold for InPktsLate";
            }
            leaf in-pkts-ok {
              type uint32 {
                range "1..4294967295" {
                  description
                    "InPktsOK threshold range";
                }
              }
              description
                "Set Threshold for InPktsOK";
            }
            leaf in-pkts-invalid {
              type uint32 {
                range "1..4294967295" {
                  description
                    "InPktsInvalid threshold range";
                }
              }
              description
                "Set Threshold for InPktsInvalid";
            }
            leaf in-pkts-not-valid {
              type uint32 {
                range "1..4294967295" {
                  description
                    "InPktsNotValid threshold range";
                }
              }
              description
                "Set Threshold for InPktsNotValid";
            }
            leaf in-pkts-not-using-sa {
              type uint32 {
                range "1..4294967295" {
                  description
                    "InPktsNotUsingSA threshold range";
                }
              }
              description
                "Set Threshold for InPktsNotUsingSA";
            }
            leaf in-pkts-unused-sa {
              type uint32 {
                range "1..4294967295" {
                  description
                    "InPktsUnusedSA threshold range";
                }
              }
              description
                "Set Threshold for InPktsUnusedSA";
            }
            leaf in-pkts-untagged-hit {
              type uint32 {
                range "1..4294967295" {
                  description
                    "InPktsUntaggedHit threshold range";
                }
              }
              description
                "Set Threshold for InPktsUntaggedHit";
            }
            leaf in-octets-validated {
              type uint32 {
                range "1..4294967295" {
                  description
                    "InOctetsValidated threshold range";
                }
              }
              description
                "Set Threshold for InOctetsValidated";
            }
            leaf in-octets-decrypted {
              type uint32 {
                range "1..4294967295" {
                  description
                    "InOctetsDecrypted threshold range";
                }
              }
              description
                "Set Threshold for InOctetsDecrypted ";
            }
          }
          container report {
            description
              "Configure Report for macsec-secy-rx Parameters";
            container in-pkts-unchecked {
              description
                "set InPktsUnchecked TCA reporting status";
              container enable {
                presence "Indicates a enable node is configured.";
                description
                  "Enable TCA reporting";
              }
            }
            container in-pkts-delayed {
              description
                "set InPktsDelayed TCA reporting status";
              container enable {
                presence "Indicates a enable node is configured.";
                description
                  "Enable TCA reporting";
              }
            }
            container in-pkts-late {
              description
                "set InPktsLate TCA reporting status";
              container enable {
                presence "Indicates a enable node is configured.";
                description
                  "Enable TCA reporting";
              }
            }
            container in-pkts-ok {
              description
                "set InPktsOK TCA reporting status";
              container enable {
                presence "Indicates a enable node is configured.";
                description
                  "Enable TCA reporting";
              }
            }
            container in-pkts-invalid {
              description
                "set InPktsInvalid TCA reporting status";
              container enable {
                presence "Indicates a enable node is configured.";
                description
                  "Enable TCA reporting";
              }
            }
            container in-pkts-not-valid {
              description
                "set InPktsNotValid TCA reporting status";
              container enable {
                presence "Indicates a enable node is configured.";
                description
                  "Enable TCA reporting";
              }
            }
            container in-pkts-not-using-sa {
              description
                "set InPktsNotUsingSA TCA reporting status";
              container enable {
                presence "Indicates a enable node is configured.";
                description
                  "Enable TCA reporting";
              }
            }
            container in-pkts-unused-sa {
              description
                "set InPktsUnusedSA TCA reporting status";
              container enable {
                presence "Indicates a enable node is configured.";
                description
                  "Enable TCA reporting";
              }
            }
            container in-pkts-untagged-hit {
              description
                "set InPktsUntaggedHit TCA reporting status";
              container enable {
                presence "Indicates a enable node is configured.";
                description
                  "Enable TCA reporting";
              }
            }
            container in-octets-validated {
              description
                "set InOctetsValidated TCA reporting status";
              container enable {
                presence "Indicates a enable node is configured.";
                description
                  "Enable TCA reporting";
              }
            }
            container in-octets-decrypted {
              description
                "set InOctetsDecrypted TCA reporting status";
              container enable {
                presence "Indicates a enable node is configured.";
                description
                  "Enable TCA reporting";
              }
            }
          }
        }
        container macsec-secy-if {
          description
            "Configure pm parameters of macsec-secy-if";
          container threshold {
            description
              "Configure threshold on macsec-secy-if parameters";
            leaf in-pkts-untagged {
              type uint32 {
                range "1..4294967295" {
                  description
                    "InPktsUntagged threshold range";
                }
              }
              description
                "Set Threshold for InPktsUntagged";
            }
            leaf in-pkts-no-tag {
              type uint32 {
                range "1..4294967295" {
                  description
                    "InPktsNoTag threshold range";
                }
              }
              description
                "Set Threshold for InPktsNoTag";
            }
            leaf in-pkts-bad-tag {
              type uint32 {
                range "1..4294967295" {
                  description
                    "InPktsBadTag threshold range";
                }
              }
              description
                "Set Threshold for InPktsBadTag";
            }
            leaf in-pkts-unknown-sci {
              type uint32 {
                range "1..4294967295" {
                  description
                    "InPktsUnknownSCI threshold range";
                }
              }
              description
                "Set Threshold for InPktsUnknownSCI";
            }
            leaf in-pkts-no-sci {
              type uint32 {
                range "1..4294967295" {
                  description
                    "InPktsNoSCI threshold range";
                }
              }
              description
                "Set Threshold for InPktsNoSCI";
            }
            leaf in-pkts-overrun {
              type uint32 {
                range "1..4294967295" {
                  description
                    "InPktsOverrun threshold range";
                }
              }
              description
                "Set Threshold for InPktsOverrun";
            }
            leaf in-octets-validated {
              type uint32 {
                range "1..4294967295" {
                  description
                    "InOctetsValidated threshold range";
                }
              }
              description
                "Set Threshold for InOctetsValidated";
            }
            leaf in-octets-decrypted {
              type uint32 {
                range "1..4294967295" {
                  description
                    "InOctetsDecrypted threshold range";
                }
              }
              description
                "Set Threshold for InOctetsDecrypted";
            }
            leaf out-pkts-untagged {
              type uint32 {
                range "1..4294967295" {
                  description
                    "OutPktsUntagged threshold range";
                }
              }
              description
                "Set Threshold for OutPktsUntagged ";
            }
            leaf out-pkts-too-long {
              type uint32 {
                range "1..4294967295" {
                  description
                    "OutPktsTooLong threshold range";
                }
              }
              description
                "Set Threshold for OutPktsTooLong";
            }
            leaf out-octets-encrypted {
              type uint32 {
                range "1..4294967295" {
                  description
                    "OutOctetsEncrypted threshold range";
                }
              }
              description
                "Set Threshold for OutOctetsEncrypted";
            }
            leaf out-octets-protected {
              type uint32 {
                range "1..4294967295" {
                  description
                    "OutOctetsProtected threshold range";
                }
              }
              description
                "Set Threshold for OutOctetsProtected";
            }
          }
          container report {
            description
              "Configure Report for macsec-secy-if Parameters";
            container in-pkts-untagged {
              description
                "set InPktsUntagged TCA reporting status";
              container enable {
                presence "Indicates a enable node is configured.";
                description
                  "Enable TCA reporting";
              }
            }
            container in-pkts-no-tag {
              description
                "set InPktsNoTag TCA reporting status";
              container enable {
                presence "Indicates a enable node is configured.";
                description
                  "Enable TCA reporting";
              }
            }
            container in-pkts-bad-tag {
              description
                "set InPktsBadTag TCA reporting status";
              container enable {
                presence "Indicates a enable node is configured.";
                description
                  "Enable TCA reporting";
              }
            }
            container in-pkts-unknown-sci {
              description
                "set InPktsUnknownSCI TCA reporting status";
              container enable {
                presence "Indicates a enable node is configured.";
                description
                  "Enable TCA reporting";
              }
            }
            container in-pkts-no-sci {
              description
                "set InPktsNoSCI TCA reporting status";
              container enable {
                presence "Indicates a enable node is configured.";
                description
                  "Enable TCA reporting";
              }
            }
            container in-pkts-overrun {
              description
                "set InPktsOverrun TCA reporting status";
              container enable {
                presence "Indicates a enable node is configured.";
                description
                  "Enable TCA reporting";
              }
            }
            container in-octets-validated {
              description
                "set InOctetsValidated TCA reporting status";
              container enable {
                presence "Indicates a enable node is configured.";
                description
                  "Enable TCA reporting";
              }
            }
            container in-octets-decrypted {
              description
                "set InOctetsDecrypted TCA reporting status";
              container enable {
                presence "Indicates a enable node is configured.";
                description
                  "Enable TCA reporting";
              }
            }
            container out-pkts-untagged {
              description
                "set OutPktsUntagged TCA reporting status";
              container enable {
                presence "Indicates a enable node is configured.";
                description
                  "Enable TCA reporting";
              }
            }
            container out-pkts-too-long {
              description
                "set OutPktsTooLong TCA reporting status";
              container enable {
                presence "Indicates a enable node is configured.";
                description
                  "Enable TCA reporting";
              }
            }
            container out-octets-protected {
              description
                "set OutOctetsProtected TCA reporting status";
              container enable {
                presence "Indicates a enable node is configured.";
                description
                  "Enable TCA reporting";
              }
            }
            container out-octets-encrypted {
              description
                "set OutOctetsEncrypted TCA reporting status";
              container enable {
                presence "Indicates a enable node is configured.";
                description
                  "Enable TCA reporting";
              }
            }
          }
        }
        container macsec-ether {
          description
            "configure ether performance monitoring";
          container threshold {
            description
              "Configure threshold on macsec ether parameters";
            leaf rx-pkt {
              type uint32 {
                range "1..4294967295" {
                  description
                    "RX-PKT threshold ";
                }
              }
              description
                "set RX-PKT threshold";
            }
            leaf stat-pkt {
              type uint32 {
                range "1..4294967295" {
                  description
                    "PKT-STAT threshold ";
                }
              }
              description
                "set PKT-STAT threshold";
            }
            leaf octet-stat {
              type uint32 {
                range "1..4294967295" {
                  description
                    "OCTET-STAT threshold ";
                }
              }
              description
                "set OCTET-STAT threshold";
            }
            leaf oversize-pkt {
              type uint32 {
                range "1..4294967295" {
                  description
                    "OVERSIZE-PKT threshold";
                }
              }
              description
                "set OVERSIZE-PKT threshold";
            }
            leaf fcs-err {
              type uint32 {
                range "1..4294967295" {
                  description
                    "FCS-ERR threshold";
                }
              }
              description
                "set FCS-ERR threshold";
            }
            leaf long-frame {
              type uint32 {
                range "1..4294967295" {
                  description
                    "LONG-FRAMES threshold ";
                }
              }
              description
                "set LONG-FRAMES threshold";
            }
            leaf jabber-stats {
              type uint32 {
                range "1..4294967295" {
                  description
                    "JABBER-STATS threshold ";
                }
              }
              description
                "set JABBER-STATS threshold";
            }
            leaf sixty-four-octets {
              type uint32 {
                range "1..4294967295" {
                  description
                    "64-OCTET threshold";
                }
              }
              description
                "set 64-OCTET threshold";
            }
            leaf six5-127-octets {
              type uint32 {
                range "1..4294967295" {
                  description
                    "65-127-OCTET threshold";
                }
              }
              description
                "set 65-127-OCTET threshold";
            }
            leaf one-hundred-twenty-eight-255-octets {
              type uint32 {
                range "1..4294967295" {
                  description
                    "128-255-OCTET threshold ";
                }
              }
              description
                "set 128-255-OCTET threshold";
            }
            leaf two-hundred-fifty-six-511-octets {
              type uint32 {
                range "1..4294967295" {
                  description
                    "256-511-OCTET threshold ";
                }
              }
              description
                "set 256-511-OCTET threshold";
            }
            leaf five-hundred-twelve-1023-octets {
              type uint32 {
                range "1..4294967295" {
                  description
                    "512-1023-OCTET threshold";
                }
              }
              description
                "set 512-1023-OCTET threshold";
            }
            leaf one-thousand-twenty-four-1518-octets {
              type uint32 {
                range "1..4294967295" {
                  description
                    "1024-1518-OCTET threshold";
                }
              }
              description
                "set 1024-1518-OCTET threshold";
            }
            leaf in-64-octets {
              type uint32 {
                range "1..4294967295" {
                  description
                    "IN-64-OCTET threshold";
                }
              }
              description
                "set IN-64-OCTET threshold";
            }
            leaf in-65-127-octets {
              type uint32 {
                range "1..4294967295" {
                  description
                    "IN-65-127-OCTET threshold";
                }
              }
              description
                "set IN-65-127-OCTET threshold";
            }
            leaf in-128-255-octets {
              type uint32 {
                range "1..4294967295" {
                  description
                    "IN-128-255-OCTET threshold ";
                }
              }
              description
                "set IN-128-255-OCTET threshold";
            }
            leaf in-256-511-octets {
              type uint32 {
                range "1..4294967295" {
                  description
                    "IN-256-511-OCTET threshold ";
                }
              }
              description
                "set IN-256-511-OCTET threshold";
            }
            leaf in-512-1023-octets {
              type uint32 {
                range "1..4294967295" {
                  description
                    "IN-512-1023-OCTET threshold";
                }
              }
              description
                "set IN-512-1023-OCTET threshold";
            }
            leaf in-1024-1518-octets {
              type uint32 {
                range "1..4294967295" {
                  description
                    "IN-1024-1518-OCTET threshold";
                }
              }
              description
                "set IN-1024-1518-OCTET threshold";
            }
            leaf in-drop-other {
              type uint32 {
                range "1..4294967295" {
                  description
                    "IN-DROP-OTHER threshold";
                }
              }
              description
                "set IN_DROP_OTHER threshold";
            }
            leaf in-ucast {
              type uint32 {
                range "1..4294967295" {
                  description
                    "IN-UCAST threshold";
                }
              }
              description
                "set IN-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf in-error-fragments {
              type uint32 {
                range "1..4294967295" {
                  description
                    "IN-ERROR-FRAGMENTS threshold";
                }
              }
              description
                "set IN-ERROR-FRAGMENTS threshold";
            }
            leaf out-ucast {
              type uint32 {
                range "1..4294967295" {
                  description
                    "OUT-UCAST threshold";
                }
              }
              description
                "set OUT-UCAST threshold";
            }
            leaf out-bcast {
              type uint32 {
                range "1..4294967295" {
                  description
                    "OUT-BCAST threshold ";
                }
              }
              description
                "set OUT-BCAST threshold";
            }
            leaf out-mcast {
              type uint32 {
                range "1..4294967295" {
                  description
                    "OUT-MCAST threshold ";
                }
              }
              description
                "set OUT-MCAST threshold";
            }
            leaf tx-pkt {
              type uint32 {
                range "1..4294967295" {
                  description
                    "TX-PKT threshold";
                }
              }
              description
                "set TX-PKT threshold";
            }
            leaf out-octets {
              type uint32 {
                range "1..4294967295" {
                  description
                    "OUT-OCTET threshold ";
                }
              }
              description
                "set OUT-OCTET threshold";
            }
            leaf if-in-errors {
              type uint32 {
                range "1..4294967295" {
                  description
                    "IFIN_ERRORS threshold";
                }
              }
              description
                "set IFIN_ERRORS threshold";
            }
            leaf if-in-octets {
              type uint32 {
                range "1..4294967295" {
                  description
                    "IFIN_OCTETS threshold";
                }
              }
              description
                "set IFIN_OCTETS threshold";
            }
            leaf ether-stat-multicast-pkt {
              type uint32 {
                range "1..4294967295" {
                  description
                    "ETHER_STAT_MULTICAST_PKT threshold";
                }
              }
              description
                "set ETHER_STAT_MULTICAST_PKT threshold";
            }
            leaf ether-stat-broadcast-pkt {
              type uint32 {
                range "1..4294967295" {
                  description
                    " ETHER_STAT_BROADCAST_PKT threshold";
                }
              }
              description
                "set ETHER_STAT_BROADCAST_PKT threshold";
            }
            leaf in-good-bytes {
              type uint32 {
                range "1..4294967295" {
                  description
                    "set IN_GOOD_BYTES threshold";
                }
              }
              description
                "set IN_GOOD_BYTES threshold";
            }
            leaf in-good-pkts {
              type uint32 {
                range "1..4294967295" {
                  description
                    "set IN_GOOD_PKTS threshold";
                }
              }
              description
                "set IN_GOOD_PKTS threshold";
            }
            leaf out-good-bytes {
              type uint32 {
                range "1..4294967295" {
                  description
                    "set OUT_GOOD_BYTES threshold";
                }
              }
              description
                "set OUT_GOOD_BYTES threshold";
            }
            leaf out-good-pkts {
              type uint32 {
                range "1..4294967295" {
                  description
                    "set GOOD_PKTS threshold";
                }
              }
              description
                "set THRESH_OUT_GOOD_PKTS threshold";
            }
            leaf rx-util {
              type uint32 {
                range "1..10000" {
                  description
                    "set RX_UTIL threshold(in units of 0.01%)";
                }
              }
              description
                "set RX_UTIL threshold(in units of 0.01%)";
            }
            leaf tx-util {
              type uint32 {
                range "1..10000" {
                  description
                    "set TX_UTIL threshold(in units of 0.01%)";
                }
              }
              description
                "set TX_UTIL threshold(in units of 0.01%)";
            }
            leaf ether-stat-undersized-pkt {
              type uint32 {
                range "1..4294967295" {
                  description
                    "ETHER_STAT_UNDERSIZED_PKT threshold";
                }
              }
              description
                "set ETHER_STAT_UNDERSIZED_PKT threshold";
            }
            leaf tx-undersized-pkt {
              type uint32 {
                range "1..4294967295" {
                  description
                    "TX_UNDERSIZED_PKT threshold";
                }
              }
              description
                "set TX_UNDERSIZED_PKT threshold";
            }
            leaf tx-oversized-pkt {
              type uint32 {
                range "1..4294967295" {
                  description
                    "TX_OVERSIZED_PKT threshold";
                }
              }
              description
                "set TX_OVERSIZED_PKT threshold";
            }
            leaf tx-fragments {
              type uint32 {
                range "1..4294967295" {
                  description
                    "TX_FRAGMENTS threshold";
                }
              }
              description
                "set TX_FRAGMENTS threshold";
            }
            leaf tx-jabber {
              type uint32 {
                range "1..4294967295" {
                  description
                    "TX_JABBER threshold";
                }
              }
              description
                "set TX_JABBER threshold";
            }
            leaf tx-bad-fcs {
              type uint32 {
                range "1..4294967295" {
                  description
                    "TX_BAD_FCS threshold";
                }
              }
              description
                "set TX_BAD_FCS threshold";
            }
          }
          container report {
            description
              "set ether TCA reporting status";
            container rx-pkt {
              description
                "set rx-pkt TCA reporting status";
              container enable {
                presence "Indicates a enable node is configured.";
                description
                  "Enable TCA reporting";
              }
            }
            container rx-util {
              description
                "set rx-util TCA reporting status";
              container enable {
                presence "Indicates a enable node is configured.";
                description
                  "Enable TCA reporting";
              }
            }
            container tx-util {
              description
                "set tx-util TCA reporting status";
              container enable {
                presence "Indicates a enable node is configured.";
                description
                  "Enable TCA reporting";
              }
            }
            container stat-pkt {
              description
                "set stat-pkt TCA reporting status";
              container enable {
                presence "Indicates a enable node is configured.";
                description
                  "Enable TCA reporting";
              }
            }
            container octet-stat {
              description
                "set octet-stat TCA reporting status";
              container enable {
                presence "Indicates a enable node is configured.";
                description
                  "Enable TCA reporting";
              }
            }
            container oversize-pkt {
              description
                "set oversize-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container long-frame {
              description
                "set long-frame TCA reporting status";
              container enable {
                presence "Indicates a enable node is configured.";
                description
                  "Enable TCA reporting";
              }
            }
            container jabber-stats {
              description
                "set jabber-stats TCA reporting status";
              container enable {
                presence "Indicates a enable node is configured.";
                description
                  "Enable TCA reporting";
              }
            }
            container _64-octets {
              description
                "set 64-octets TCA reporting status";
              container enable {
                presence "Indicates a enable node is configured.";
                description
                  "Enable TCA reporting";
              }
            }
            container _65-127-octets {
              description
                "set 65-127-octets TCA reporting status";
              container enable {
                presence "Indicates a enable node is configured.";
                description
                  "Enable TCA reporting";
              }
            }
            container _128-255-octets {
              description
                "set 128-255-octets TCA reporting status";
              container enable {
                presence "Indicates a enable node is configured.";
                description
                  "Enable TCA reporting";
              }
            }
            container _256-511-octets {
              description
                "set 256-511-octets TCA reporting status";
              container enable {
                presence "Indicates a enable node is configured.";
                description
                  "Enable TCA reporting";
              }
            }
            container _512-1023-octets {
              description
                "set 512-1023-octets TCA reporting status";
              container enable {
                presence "Indicates a enable node is configured.";
                description
                  "Enable TCA reporting";
              }
            }
            container _1024-1518-octets {
              description
                "set 1024-1518-octets TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-errors {
              description
                "set ifIn_errors TCA reporting status";
              container enable {
                presence "Indicates a enable node is configured.";
                description
                  "Enable TCA reporting";
              }
            }
            container if-in-octets {
              description
                "set ifOut_errors  TCA reporting status";
              container enable {
                presence "Indicates a enable node is configured.";
                description
                  "Enable TCA reporting";
              }
            }
            container ether-stat-multicast-pkt {
              description
                "set ether_stat_multicast_pkt TCA reporting status";
              container enable {
                presence "Indicates a enable node is configured.";
                description
                  "Enable TCA reporting";
              }
            }
            container ether-stat-broadcast-pkt {
              description
                "set ether_stat_broadcast_pkt TCA reporting status";
              container enable {
                presence "Indicates a enable node is configured.";
                description
                  "Enable TCA reporting";
              }
            }
            container ether-stat-undersized-pkt {
              description
                "set ether_stat_undersized_pkt  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-64-octets {
              description
                "set in-64-octets TCA reporting status";
              container enable {
                presence "Indicates a enable node is configured.";
                description
                  "Enable TCA reporting";
              }
            }
            container in-65-127-octets {
              description
                "set in-65-127-octets TCA reporting status";
              container enable {
                presence "Indicates a enable node is configured.";
                description
                  "Enable TCA reporting";
              }
            }
            container in-128-255-octets {
              description
                "set in-128-255-octets TCA reporting status";
              container enable {
                presence "Indicates a enable node is configured.";
                description
                  "Enable TCA reporting";
              }
            }
            container in-256-511-octets {
              description
                "set in-256-511-octets TCA reporting status";
              container enable {
                presence "Indicates a enable node is configured.";
                description
                  "Enable TCA reporting";
              }
            }
            container in-512-1023-octets {
              description
                "set in-512-1023-octets TCA reporting status";
              container enable {
                presence "Indicates a enable node is configured.";
                description
                  "Enable TCA reporting";
              }
            }
            container in-1024-1518-octets {
              description
                "set in-1024-1518-octets TCA reporting status";
              container enable {
                presence "Indicates a enable node is configured.";
                description
                  "Enable TCA reporting";
              }
            }
            container tx-undersized-pkt {
              description
                "set tx_undersized_pkt  TCA reporting status";
              container enable {
                presence "Indicates a enable node is configured.";
                description
                  "Enable TCA reporting";
              }
            }
            container tx-oversized-pkt {
              description
                "set tx_oversized_pkt  TCA reporting status";
              container enable {
                presence "Indicates a enable node is configured.";
                description
                  "Enable TCA reporting";
              }
            }
            container tx-fragments {
              description
                "set tx_fragments  TCA reporting status";
              container enable {
                presence "Indicates a enable node is configured.";
                description
                  "Enable TCA reporting";
              }
            }
            container tx-jabber {
              description
                "set tx_jabber  TCA reporting status";
              container enable {
                presence "Indicates a enable node is configured.";
                description
                  "Enable TCA reporting";
              }
            }
            container tx-bad-fcs {
              description
                "set tx_bad_fcs  TCA reporting status";
              container enable {
                presence "Indicates a enable node is configured.";
                description
                  "Enable TCA reporting";
              }
            }
          }
        }
      }
      container interval-24-hour {
        description
          "Configure pm parameters of 24 hour interval";
        container ether {
          description
            "configure ether performance monitoring";
          container threshold {
            description
              "Configure threshold on ether parameters";
            leaf rx-pkt {
              type uint32 {
                range "1..4294967295" {
                  description
                    "RX-PKT threshold ";
                }
              }
              description
                "set RX-PKT threshold";
            }
            leaf stat-pkt {
              type uint32 {
                range "1..4294967295" {
                  description
                    "STAT-PKT threshold ";
                }
              }
              description
                "set STAT-PKT threshold";
            }
            leaf octet-stat {
              type uint32 {
                range "1..4294967295" {
                  description
                    "OCTET-STAT threshold ";
                }
              }
              description
                "set OCTET-STAT threshold";
            }
            leaf oversize-pkt {
              type uint32 {
                range "1..4294967295" {
                  description
                    "OVERSIZEPKT-STATS threshold";
                }
              }
              description
                "set OVERSIZE-PKT threshold";
            }
            leaf fcs-err {
              type uint32 {
                range "1..4294967295" {
                  description
                    "FCS-ERR threshold";
                }
              }
              description
                "set FCS-ERR threshold";
            }
            leaf long-frame {
              type uint32 {
                range "1..4294967295" {
                  description
                    "LONG-FRAMES threshold ";
                }
              }
              description
                "set LONG-FRAMES threshold";
            }
            leaf jabber-stats {
              type uint32 {
                range "1..4294967295" {
                  description
                    "JABBER-STATS threshold ";
                }
              }
              description
                "set JABBER-STATS threshold";
            }
            leaf sixty-four-octets {
              type uint32 {
                range "1..4294967295" {
                  description
                    "64-OCTET threshold";
                }
              }
              description
                "set 64-OCTET threshold";
            }
            leaf six5-127-octets {
              type uint32 {
                range "1..4294967295" {
                  description
                    "65-127-OCTET threshold";
                }
              }
              description
                "set 65-127-OCTET threshold";
            }
            leaf one-hundred-twenty-eight-255-octets {
              type uint32 {
                range "1..4294967295" {
                  description
                    "128-255-OCTET threshold ";
                }
              }
              description
                "set 128-255-OCTET threshold";
            }
            leaf two-hundred-fifty-six-511-octets {
              type uint32 {
                range "1..4294967295" {
                  description
                    "256-511-OCTET threshold ";
                }
              }
              description
                "set 256-511-OCTET threshold";
            }
            leaf five-hundred-twelve-1023-octets {
              type uint32 {
                range "1..4294967295" {
                  description
                    "512-1023-OCTET threshold";
                }
              }
              description
                "set 512-1023-OCTET threshold";
            }
            leaf one-thousand-twenty-four-1518-octets {
              type uint32 {
                range "1..4294967295" {
                  description
                    "1024-1518-OCTET threshold";
                }
              }
              description
                "set 1024-1518-OCTET threshold";
            }
            leaf in-64-octets {
              type uint32 {
                range "1..4294967295" {
                  description
                    "IN-64-OCTET threshold";
                }
              }
              description
                "set IN-64-OCTET threshold";
            }
            leaf in-65-127-octets {
              type uint32 {
                range "1..4294967295" {
                  description
                    "IN-65-127-OCTET threshold";
                }
              }
              description
                "set IN-65-127-OCTET threshold";
            }
            leaf in-128-255-octets {
              type uint32 {
                range "1..4294967295" {
                  description
                    "IN-128-255-OCTET threshold ";
                }
              }
              description
                "set 128-255-OCTET threshold";
            }
            leaf in-256-511-octets {
              type uint32 {
                range "1..4294967295" {
                  description
                    "IN-256-511-OCTET threshold ";
                }
              }
              description
                "set IN-256-511-OCTET threshold";
            }
            leaf in-512-1023-octets {
              type uint32 {
                range "1..4294967295" {
                  description
                    "IN-512-1023-OCTET threshold";
                }
              }
              description
                "set IN-512-1023-OCTET threshold";
            }
            leaf in-1024-1518-octets {
              type uint32 {
                range "1..4294967295" {
                  description
                    "IN-1024-1518-OCTET threshold";
                }
              }
              description
                "set IN-1024-1518-OCTET threshold";
            }
            leaf out-pkt-64-octet {
              type uint32 {
                range "1..4294967295" {
                  description
                    "OUT-PKT-64-OCTET threshold";
                }
              }
              description
                "set OUT-PKT-64-OCTET threshold";
            }
            leaf out-pkts-65-127-octets {
              type uint32 {
                range "1..4294967295" {
                  description
                    "OUT-PKTS-65-127-OCTETS threshold";
                }
              }
              description
                "set OUT-PKTS-65-127-OCTETS threshold";
            }
            leaf out-pkts-128-255-octets {
              type uint32 {
                range "1..4294967295" {
                  description
                    "OUT-PKTS-128-255-OCTETS threshold";
                }
              }
              description
                "set OUT-PKTS-128-255-OCTETS threshold";
            }
            leaf out-pkts-256-511-octets {
              type uint32 {
                range "1..4294967295" {
                  description
                    "OUT-PKTS-256-511-OCTETS threshold";
                }
              }
              description
                "set OUT-PKTS-256-511-OCTETS threshold";
            }
            leaf out-pkts-512-1023-octets {
              type uint32 {
                range "1..4294967295" {
                  description
                    "OUT-PKTS-512-1023-OCTETS threshold";
                }
              }
              description
                "set OUT-PKTS-512-1023-OCTETS threshold";
            }
            leaf out-pkts-1024-1518-octets {
              type uint32 {
                range "1..4294967295" {
                  description
                    "OUT-PKTS-1024-1518-OCTETS threshold";
                }
              }
              description
                "set OUT-PKTS-1024-1518-OCTETS threshold";
            }
            leaf in-drop-other {
              type uint32 {
                range "1..4294967295" {
                  description
                    "IN-DROP-OTHER threshold";
                }
              }
              description
                "set IN_DROP_OTHER threshold";
            }
            leaf in-ucast {
              type uint32 {
                range "1..4294967295" {
                  description
                    "IN-UCAST threshold";
                }
              }
              description
                "set IN-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf in-error-fragments {
              type uint32 {
                range "1..4294967295" {
                  description
                    "IN-ERROR-FRAGMENTS threshold";
                }
              }
              description
                "set IN-ERROR-FRAGMENTS threshold";
            }
            leaf out-ucast {
              type uint32 {
                range "1..4294967295" {
                  description
                    "OUT-UCAST threshold";
                }
              }
              description
                "set OUT-UCAST threshold";
            }
            leaf out-bcast {
              type uint32 {
                range "1..4294967295" {
                  description
                    "OUT-BCAST threshold )";
                }
              }
              description
                "set OUT-BCAST threshold";
            }
            leaf out-mcast {
              type uint32 {
                range "1..4294967295" {
                  description
                    "OUT-MCAST threshold (seconds)";
                }
              }
              description
                "set OUT-MCAST threshold";
            }
            leaf tx-pkt {
              type uint32 {
                range "1..4294967295" {
                  description
                    "TX-PKT threshold";
                }
              }
              description
                "set TX-PKT threshold";
            }
            leaf out-octets {
              type uint32 {
                range "1..4294967295" {
                  description
                    "OUT-OCTET threshold (seconds)";
                }
              }
              description
                "set OUT-OCTET threshold";
            }
            leaf if-in-errors {
              type uint32 {
                range "1..4294967295" {
                  description
                    "IFIN_ERRORS threshold";
                }
              }
              description
                "set IFIN_ERRORS threshold";
            }
            leaf in-good-bytes {
              type uint32 {
                range "1..4294967295" {
                  description
                    "set IN_GOOD_BYTES threshold";
                }
              }
              description
                "set IN_GOOD_BYTES threshold";
            }
            leaf in-good-pkts {
              type uint32 {
                range "1..4294967295" {
                  description
                    "set IN_GOOD_PKTS threshold";
                }
              }
              description
                "set IN_GOOD_PKTS threshold";
            }
            leaf out-good-bytes {
              type uint32 {
                range "1..4294967295" {
                  description
                    "set OUT_GOOD_BYTES threshold";
                }
              }
              description
                "set OUT_GOOD_BYTES threshold";
            }
            leaf out-good-pkts {
              type uint32 {
                range "1..4294967295" {
                  description
                    "set GOOD_PKTS threshold";
                }
              }
              description
                "set THRESH_OUT_GOOD_PKTS threshold";
            }
            leaf rx-util {
              type uint32 {
                range "1..10000" {
                  description
                    "set RX_UTIL threshold (in units of 0.01%)";
                }
              }
              description
                "set THRESH_RX_UTIL threshold(in units of 0.01%)";
            }
            leaf tx-util {
              type uint32 {
                range "1..10000" {
                  description
                    "set TX_UTIL threshold(in units of 0.01%)";
                }
              }
              description
                "set TX_UTIL threshold(in units of 0.01%)";
            }
            leaf if-in-octets {
              type uint32 {
                range "1..4294967295" {
                  description
                    "IFIN_OCTETS threshold";
                }
              }
              description
                "set IFIN_OCTETS threshold";
            }
            leaf ether-stat-multicast-pkt {
              type uint32 {
                range "1..4294967295" {
                  description
                    "ETHER_STAT_MULTICAST_PKT threshold";
                }
              }
              description
                "set ETHER_STAT_MULTICAST_PKT threshold";
            }
            leaf ether-stat-broadcast-pkt {
              type uint32 {
                range "1..4294967295" {
                  description
                    " ETHER_STAT_BROADCAST_PKT threshold";
                }
              }
              description
                " set ETHER_STAT_BROADCAST_PKT threshold";
            }
            leaf ether-stat-undersized-pkt {
              type uint32 {
                range "1..4294967295" {
                  description
                    "ETHER_STAT_UNDERSIZED_PKT threshold";
                }
              }
              description
                "set ETHER_STAT_UNDERSIZED_PKT threshold";
            }
            leaf tx-undersized-pkt {
              type uint32 {
                range "1..4294967295" {
                  description
                    "TX_UNDERSIZED_PKT threshold";
                }
              }
              description
                "set TX_UNDERSIZED_PKT threshold";
            }
            leaf tx-oversized-pkt {
              type uint32 {
                range "1..4294967295" {
                  description
                    "TX_OVERSIZED_PKT threshold";
                }
              }
              description
                "set TX_OVERSIZED_PKT threshold";
            }
            leaf tx-fragments {
              type uint32 {
                range "1..4294967295" {
                  description
                    "TX_FRAGMENTS threshold";
                }
              }
              description
                "set TX_FRAGMENTS threshold";
            }
            leaf tx-jabber {
              type uint32 {
                range "1..4294967295" {
                  description
                    "TX_JABBER threshold";
                }
              }
              description
                "set TX_JABBER threshold";
            }
            leaf tx-bad-fcs {
              type uint32 {
                range "1..4294967295" {
                  description
                    "TX_BAD_FCS threshold";
                }
              }
              description
                "set TX_BAD_FCS threshold";
            }
          }
          container report {
            description
              "set ether TCA reporting status";
            container rx-pkt {
              description
                "set rx-pkt TCA reporting status";
              container enable {
                presence "Indicates a enable node is configured.";
                description
                  "Enable TCA reporting";
              }
            }
            container rx-util {
              description
                "set rx-util TCA reporting status";
              container enable {
                presence "Indicates a enable node is configured.";
                description
                  "Enable TCA reporting";
              }
            }
            container tx-util {
              description
                "set tx-util TCA reporting status";
              container enable {
                presence "Indicates a enable node is configured.";
                description
                  "Enable TCA reporting";
              }
            }
            container stat-pkt {
              description
                "set stat-pkt TCA reporting status";
              container enable {
                presence "Indicates a enable node is configured.";
                description
                  "Enable TCA reporting";
              }
            }
            container octet-stat {
              description
                "set octet-stat TCA reporting status";
              container enable {
                presence "Indicates a enable node is configured.";
                description
                  "Enable TCA reporting";
              }
            }
            container oversize-pkt {
              description
                "set oversize-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container long-frame {
              description
                "set long-frame TCA reporting status";
              container enable {
                presence "Indicates a enable node is configured.";
                description
                  "Enable TCA reporting";
              }
            }
            container jabber-stats {
              description
                "set jabber-stats TCA reporting status";
              container enable {
                presence "Indicates a enable node is configured.";
                description
                  "Enable TCA reporting";
              }
            }
            container _64-octets {
              description
                "set 64-octets TCA reporting status";
              container enable {
                presence "Indicates a enable node is configured.";
                description
                  "Enable TCA reporting";
              }
            }
            container _65-127-octets {
              description
                "set 65-127-octets TCA reporting status";
              container enable {
                presence "Indicates a enable node is configured.";
                description
                  "Enable TCA reporting";
              }
            }
            container _128-255-octets {
              description
                "set 128-255-octets TCA reporting status";
              container enable {
                presence "Indicates a enable node is configured.";
                description
                  "Enable TCA reporting";
              }
            }
            container _256-511-octets {
              description
                "set 256-511-octets TCA reporting status";
              container enable {
                presence "Indicates a enable node is configured.";
                description
                  "Enable TCA reporting";
              }
            }
            container _512-1023-octets {
              description
                "set 512-1023-octets TCA reporting status";
              container enable {
                presence "Indicates a enable node is configured.";
                description
                  "Enable TCA reporting";
              }
            }
            container _1024-1518-octets {
              description
                "set 1024-1518-octets TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-errors {
              description
                "set ifIn_errors TCA reporting status";
              container enable {
                presence "Indicates a enable node is configured.";
                description
                  "Enable TCA reporting";
              }
            }
            container if-in-octets {
              description
                "set ifIn_Octets  TCA reporting status";
              container enable {
                presence "Indicates a enable node is configured.";
                description
                  "Enable TCA reporting";
              }
            }
            container ether-stat-multicast-pkt {
              description
                "set ether_stat_multicast_pkt TCA reporting status";
              container enable {
                presence "Indicates a enable node is configured.";
                description
                  "Enable TCA reporting";
              }
            }
            container ether-stat-broadcast-pkt {
              description
                "set ether_stat_broadcast_pkt TCA reporting status";
              container enable {
                presence "Indicates a enable node is configured.";
                description
                  "Enable TCA reporting";
              }
            }
            container ether-stat-undersized-pkt {
              description
                "set ether_stat_undersized_pkt  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-64-octets {
              description
                "set in-64-octets TCA reporting status";
              container enable {
                presence "Indicates a enable node is configured.";
                description
                  "Enable TCA reporting";
              }
            }
            container in-65-127-octets {
              description
                "set in-65-127-octets TCA reporting status";
              container enable {
                presence "Indicates a enable node is configured.";
                description
                  "Enable TCA reporting";
              }
            }
            container in-128-255-octets {
              description
                "set in-128-255-octets TCA reporting status";
              container enable {
                presence "Indicates a enable node is configured.";
                description
                  "Enable TCA reporting";
              }
            }
            container in-256-511-octets {
              description
                "set in-256-511-octets TCA reporting status";
              container enable {
                presence "Indicates a enable node is configured.";
                description
                  "Enable TCA reporting";
              }
            }
            container in-512-1023-octets {
              description
                "set in-512-1023-octets TCA reporting status";
              container enable {
                presence "Indicates a enable node is configured.";
                description
                  "Enable TCA reporting";
              }
            }
            container in-1024-1518-octets {
              description
                "set in-1024-1518-octets TCA reporting status";
              container enable {
                presence "Indicates a enable node is configured.";
                description
                  "Enable TCA reporting";
              }
            }
            container out-pkt-64-octet {
              description
                "set out-pkt-64-octet TCA reporting status";
              container enable {
                presence "Indicates a enable node is configured.";
                description
                  "Enable TCA reporting";
              }
            }
            container out-pkts-65-127-octets {
              description
                "set out-pkts-65-127-octets TCA reporting status";
              container enable {
                presence "Indicates a enable node is configured.";
                description
                  "Enable TCA reporting";
              }
            }
            container out-pkts-128-255-octets {
              description
                "set out-pkts-128-255-octets TCA reporting status";
              container enable {
                presence "Indicates a enable node is configured.";
                description
                  "Enable TCA reporting";
              }
            }
            container out-pkts-256-511-octets {
              description
                "set out-pkts-256-511-octets TCA reporting status";
              container enable {
                presence "Indicates a enable node is configured.";
                description
                  "Enable TCA reporting";
              }
            }
            container out-pkts-512-1023-octets {
              description
                "set out-pkts-512-1023-octets TCA reporting status";
              container enable {
                presence "Indicates a enable node is configured.";
                description
                  "Enable TCA reporting";
              }
            }
            container out-pkts-1024-1518-octets {
              description
                "set out-pkts-1024-1518-octets TCA reporting status";
              container enable {
                presence "Indicates a enable node is configured.";
                description
                  "Enable TCA reporting";
              }
            }
            container tx-undersized-pkt {
              description
                "set tx_undersized_pkt  TCA reporting status";
              container enable {
                presence "Indicates a enable node is configured.";
                description
                  "Enable TCA reporting";
              }
            }
            container tx-oversized-pkt {
              description
                "set tx_oversized_pkt  TCA reporting status";
              container enable {
                presence "Indicates a enable node is configured.";
                description
                  "Enable TCA reporting";
              }
            }
            container tx-fragments {
              description
                "set tx_fragments  TCA reporting status";
              container enable {
                presence "Indicates a enable node is configured.";
                description
                  "Enable TCA reporting";
              }
            }
            container tx-jabber {
              description
                "set tx_jabber  TCA reporting status";
              container enable {
                presence "Indicates a enable node is configured.";
                description
                  "Enable TCA reporting";
              }
            }
            container tx-bad-fcs {
              description
                "set tx_bad_fcs  TCA reporting status";
              container enable {
                presence "Indicates a enable node is configured.";
                description
                  "Enable TCA reporting";
              }
            }
          }
        }
        container fec {
          description
            "Configure fec performance monitoring";
          container threshold {
            description
              "Configure fec threshold";
            leaf ec-words {
              type xr:Cisco-ios-xr-string {
                length "1..20" {
                  description
                    "ec-words threshold <range:1-18446744073709551615>";
                }
              }
              description
                "set EC-Words threshold";
            }
            leaf uc-words {
              type xr:Cisco-ios-xr-string {
                length "1..20" {
                  description
                    "uc-words threshold <range:1-18446744073709551615>";
                }
              }
              description
                "set UC-WORDS threshold";
            }
            container pre-fec-ber {
              description
                "Set PRE-FEC-BER Thresholds";
              leaf min {
                type xr:Cisco-ios-xr-string {
                  length "1..20" {
                    description
                      "pre-fec-ber min threshold <range:1-18446744073709551615>";
                  }
                }
                description
                  "set pre-fec-ber min threshold";
              }
              leaf max {
                type xr:Cisco-ios-xr-string {
                  length "1..20" {
                    description
                      "pre-fec-ber max threshold <range:1-18446744073709551615>";
                  }
                }
                description
                  "set pre-fec-ber max threshold";
              }
            }
            container post-fec-ber {
              description
                "Set POST-FEC-BER Thresholds";
              leaf min {
                type xr:Cisco-ios-xr-string {
                  length "1..20" {
                    description
                      "post-fec-ber min threshold <range:1-18446744073709551615>";
                  }
                }
                description
                  "set post-fec-ber min threshold <range:0-18446744073709551615>";
              }
              leaf max {
                type xr:Cisco-ios-xr-string {
                  length "1..20" {
                    description
                      "post-fec-ber max threshold <range:1-18446744073709551615>";
                  }
                }
                description
                  "set post-fec-ber max threshold";
              }
            }
          }
          container report {
            description
              "set fec TCA reporting status";
            container uc-words {
              description
                "set uc-words TCA reporting status";
              container enable {
                presence "Indicates a enable node is configured.";
                description
                  "Enable TCA reporting";
              }
            }
            container ec-words {
              description
                "set ec-words TCA reporting status";
              container enable {
                presence "Indicates a enable node is configured.";
                description
                  "Enable TCA reporting";
              }
            }
            container pre-fec-ber {
              description
                "set PRE FEC BER TCA reporting status";
              container max-tca {
                description
                  "set PRE FEC BER max TCA reporting status";
                container enable {
                  presence "Indicates a enable node is configured.";
                  description
                    "Enable TCA reporting";
                }
              }
              container min-tca {
                description
                  "set PRE FEC BER min TCA reporting status";
                container enable {
                  presence "Indicates a enable node is configured.";
                  description
                    "Enable TCA reporting";
                }
              }
            }
            container post-fec-ber {
              description
                "set POST FEC BER TCA reporting status";
              container max-tca {
                description
                  "set POST FEC BER max TCA reporting status";
                container enable {
                  presence "Indicates a enable node is configured.";
                  description
                    "Enable TCA reporting";
                }
              }
              container min-tca {
                description
                  "set POST FEC BER min TCA reporting status";
                container enable {
                  presence "Indicates a enable node is configured.";
                  description
                    "Enable TCA reporting";
                }
              }
            }
          }
        }
        container pcs {
          description
            "configure pcs performance monitoring";
          container threshold {
            description
              "Configure threshold on pcs parameters";
            leaf bip {
              type xr:Cisco-ios-xr-string {
                length "1..20" {
                  description
                    "BIP threshold range <1-18446744073709551615>";
                }
              }
              description
                "set BIP threshold";
            }
            leaf frm-err {
              type xr:Cisco-ios-xr-string {
                length "1..20" {
                  description
                    "FRM-ERR threshold range <1-18446744073709551615>";
                }
              }
              description
                "set FRM-ERR threshold";
            }
            leaf bad-sh {
              type xr:Cisco-ios-xr-string {
                length "1..20" {
                  description
                    "Bad-sh threshold range <1-18446744073709551615>";
                }
              }
              description
                "set Bad-sh threshold";
            }
            leaf es {
              type xr:Cisco-ios-xr-string {
                length "1..20" {
                  description
                    "Es threshold range <0-86400>";
                }
              }
              description
                "set Es threshold";
            }
            leaf ses {
              type xr:Cisco-ios-xr-string {
                length "1..20" {
                  description
                    "Ses threshold range <0-86400>";
                }
              }
              description
                "set Ses threshold";
            }
            leaf uas {
              type xr:Cisco-ios-xr-string {
                length "1..20" {
                  description
                    "Uas threshold range <0-86400>";
                }
              }
              description
                "set Uas threshold";
            }
            leaf es-fe {
              type xr:Cisco-ios-xr-string {
                length "1..20" {
                  description
                    "Es fe threshold range <0-86400>";
                }
              }
              description
                "set Es fe threshold";
            }
            leaf ses-fe {
              type xr:Cisco-ios-xr-string {
                length "1..20" {
                  description
                    "Ses fe threshold range <0-86400>";
                }
              }
              description
                "set Ses fe threshold";
            }
            leaf uas-fe {
              type xr:Cisco-ios-xr-string {
                length "1..20" {
                  description
                    "Ses threshold range <0-86400>";
                }
              }
              description
                "set Uas threshold";
            }
          }
          container report {
            description
              "set pcs TCA reporting status";
            container bip {
              description
                "set bip TCA reporting status";
              container enable {
                presence "Indicates a enable node is configured.";
                description
                  "Enable TCA reporting";
              }
            }
            container frm-err {
              description
                "set frm-err TCA reporting status";
              container enable {
                presence "Indicates a enable node is configured.";
                description
                  "Enable TCA reporting";
              }
            }
            container bad-sh {
              description
                "set bad-sh TCA reporting status";
              container enable {
                presence "Indicates a enable node is configured.";
                description
                  "Enable TCA reporting";
              }
            }
            container es {
              description
                "set es TCA reporting status";
              container enable {
                presence "Indicates a enable node is configured.";
                description
                  "Enable TCA reporting";
              }
            }
            container ses {
              description
                "set ses TCA reporting status";
              container enable {
                presence "Indicates a enable node is configured.";
                description
                  "Enable TCA reporting";
              }
            }
            container uas {
              description
                "set uas TCA reporting status";
              container enable {
                presence "Indicates a enable node is configured.";
                description
                  "Enable TCA reporting";
              }
            }
            container es-fe {
              description
                "set es-fe TCA reporting status";
              container disable {
                presence "Indicates a disable node is configured.";
                description
                  "Disable TCA reporting";
              }
            }
            container ses-fe {
              description
                "set ses-fe TCA reporting status";
              container disable {
                presence "Indicates a disable node is configured.";
                description
                  "Disable TCA reporting";
              }
            }
            container uas-fe {
              description
                "set uas-fe TCA reporting status";
              container disable {
                presence "Indicates a disable node is configured.";
                description
                  "Disable TCA reporting";
              }
            }
          }
        }
      }
      container interval-30-sec {
        description
          "Configure pm parameters of 30-second interval";
        container ether {
          description
            "configure ether performance monitoring";
          container threshold {
            description
              "Configure threshold on ether parameters";
            leaf rx-pkt {
              type uint32 {
                range "1..4294967295" {
                  description
                    "RX-PKT threshold ";
                }
              }
              description
                "set RX-PKT threshold";
            }
            leaf stat-pkt {
              type uint32 {
                range "1..4294967295" {
                  description
                    "PKT-STAT threshold ";
                }
              }
              description
                "set PKT-STAT threshold";
            }
            leaf octet-stat {
              type uint32 {
                range "1..4294967295" {
                  description
                    "OCTET-STAT threshold ";
                }
              }
              description
                "set OCTET-STAT threshold";
            }
            leaf oversize-pkt {
              type uint32 {
                range "1..4294967295" {
                  description
                    "OVERSIZE-PKT threshold";
                }
              }
              description
                "set OVERSIZE-PKT threshold";
            }
            leaf fcs-err {
              type uint32 {
                range "1..4294967295" {
                  description
                    "FCS-ERR threshold";
                }
              }
              description
                "set FCS-ERR threshold";
            }
            leaf long-frame {
              type uint32 {
                range "1..4294967295" {
                  description
                    "LONG-FRAMES threshold ";
                }
              }
              description
                "set LONG-FRAMES threshold";
            }
            leaf jabber-stats {
              type uint32 {
                range "1..4294967295" {
                  description
                    "JABBER-STATS threshold ";
                }
              }
              description
                "set JABBER-STATS threshold";
            }
            leaf sixty-four-octets {
              type uint32 {
                range "1..4294967295" {
                  description
                    "64-OCTET threshold";
                }
              }
              description
                "set 64-OCTET threshold";
            }
            leaf six5-127-octets {
              type uint32 {
                range "1..4294967295" {
                  description
                    "65-127-OCTET threshold";
                }
              }
              description
                "set 65-127-OCTET threshold";
            }
            leaf one-hundred-twenty-eight-255-octets {
              type uint32 {
                range "1..4294967295" {
                  description
                    "128-255-OCTET threshold ";
                }
              }
              description
                "set 128-255-OCTET threshold";
            }
            leaf two-hundred-fifty-six-511-octets {
              type uint32 {
                range "1..4294967295" {
                  description
                    "256-511-OCTET threshold ";
                }
              }
              description
                "set 256-511-OCTET threshold";
            }
            leaf five-hundred-twelve-1023-octets {
              type uint32 {
                range "1..4294967295" {
                  description
                    "512-1023-OCTET threshold";
                }
              }
              description
                "set 512-1023-OCTET threshold";
            }
            leaf one-thousand-twenty-four-1518-octets {
              type uint32 {
                range "1..4294967295" {
                  description
                    "1024-1518-OCTET threshold";
                }
              }
              description
                "set 1024-1518-OCTET threshold";
            }
            leaf in-64-octets {
              type uint32 {
                range "1..4294967295" {
                  description
                    "IN-64-OCTET threshold";
                }
              }
              description
                "set IN-64-OCTET threshold";
            }
            leaf in-65-127-octets {
              type uint32 {
                range "1..4294967295" {
                  description
                    "IN-65-127-OCTET threshold";
                }
              }
              description
                "set IN-65-127-OCTET threshold";
            }
            leaf in-128-255-octets {
              type uint32 {
                range "1..4294967295" {
                  description
                    "IN-128-255-OCTET threshold ";
                }
              }
              description
                "set IN-128-255-OCTET threshold";
            }
            leaf in-256-511-octets {
              type uint32 {
                range "1..4294967295" {
                  description
                    "IN-256-511-OCTET threshold ";
                }
              }
              description
                "set IN-256-511-OCTET threshold";
            }
            leaf in-512-1023-octets {
              type uint32 {
                range "1..4294967295" {
                  description
                    "IN-512-1023-OCTET threshold";
                }
              }
              description
                "set IN-512-1023-OCTET threshold";
            }
            leaf in-1024-1518-octets {
              type uint32 {
                range "1..4294967295" {
                  description
                    "IN-1024-1518-OCTET threshold";
                }
              }
              description
                "set IN-1024-1518-OCTET threshold";
            }
            leaf out-pkt-64-octet {
              type uint32 {
                range "1..4294967295" {
                  description
                    "OUT-PKT-64-OCTET threshold";
                }
              }
              description
                "set OUT-PKT-64-OCTET threshold";
            }
            leaf out-pkts-65-127-octets {
              type uint32 {
                range "1..4294967295" {
                  description
                    "OUT-PKTS-65-127-OCTETS threshold";
                }
              }
              description
                "set OUT-PKTS-65-127-OCTETS threshold";
            }
            leaf out-pkts-128-255-octets {
              type uint32 {
                range "1..4294967295" {
                  description
                    "OUT-PKTS-128-255-OCTETS threshold";
                }
              }
              description
                "set OUT-PKTS-128-255-OCTETS threshold";
            }
            leaf out-pkts-256-511-octets {
              type uint32 {
                range "1..4294967295" {
                  description
                    "OUT-PKTS-256-511-OCTETS threshold";
                }
              }
              description
                "set OUT-PKTS-256-511-OCTETS threshold";
            }
            leaf out-pkts-512-1023-octets {
              type uint32 {
                range "1..4294967295" {
                  description
                    "OUT-PKTS-512-1023-OCTETS threshold";
                }
              }
              description
                "set OUT-PKTS-512-1023-OCTETS threshold";
            }
            leaf out-pkts-1024-1518-octets {
              type uint32 {
                range "1..4294967295" {
                  description
                    "OUT-PKTS-1024-1518-OCTETS threshold";
                }
              }
              description
                "set OUT-PKTS-1024-1518-OCTETS threshold";
            }
            leaf in-drop-other {
              type uint32 {
                range "1..4294967295" {
                  description
                    "IN-DROP-OTHER threshold";
                }
              }
              description
                "set IN_DROP_OTHER threshold";
            }
            leaf in-ucast {
              type uint32 {
                range "1..4294967295" {
                  description
                    "IN-UCAST threshold";
                }
              }
              description
                "set IN-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf in-error-fragments {
              type uint32 {
                range "1..4294967295" {
                  description
                    "IN-ERROR-FRAGMENTS threshold";
                }
              }
              description
                "set IN-ERROR-FRAGMENTS threshold";
            }
            leaf out-ucast {
              type uint32 {
                range "1..4294967295" {
                  description
                    "OUT-UCAST threshold";
                }
              }
              description
                "set OUT-UCAST threshold";
            }
            leaf out-bcast {
              type uint32 {
                range "1..4294967295" {
                  description
                    "OUT-BCAST threshold ";
                }
              }
              description
                "set OUT-BCAST threshold";
            }
            leaf out-mcast {
              type uint32 {
                range "1..4294967295" {
                  description
                    "OUT-MCAST threshold ";
                }
              }
              description
                "set OUT-MCAST threshold";
            }
            leaf tx-pkt {
              type uint32 {
                range "1..4294967295" {
                  description
                    "TX-PKT threshold";
                }
              }
              description
                "set TX-PKT threshold";
            }
            leaf out-octets {
              type uint32 {
                range "1..4294967295" {
                  description
                    "OUT-OCTET threshold ";
                }
              }
              description
                "set OUT-OCTET threshold";
            }
            leaf if-in-errors {
              type uint32 {
                range "1..4294967295" {
                  description
                    "IFIN_ERRORS threshold";
                }
              }
              description
                "set IFIN_ERRORS threshold";
            }
            leaf if-in-octets {
              type uint32 {
                range "1..4294967295" {
                  description
                    "IFIN_OCTETS threshold";
                }
              }
              description
                "set IFIN_OCTETS threshold";
            }
            leaf ether-stat-multicast-pkt {
              type uint32 {
                range "1..4294967295" {
                  description
                    "ETHER_STAT_MULTICAST_PKT threshold";
                }
              }
              description
                "set ETHER_STAT_MULTICAST_PKT threshold";
            }
            leaf ether-stat-broadcast-pkt {
              type uint32 {
                range "1..4294967295" {
                  description
                    " ETHER_STAT_BROADCAST_PKT threshold";
                }
              }
              description
                "set ETHER_STAT_BROADCAST_PKT threshold";
            }
            leaf in-good-bytes {
              type uint32 {
                range "1..4294967295" {
                  description
                    "set IN_GOOD_BYTES threshold";
                }
              }
              description
                "set IN_GOOD_BYTES threshold";
            }
            leaf in-good-pkts {
              type uint32 {
                range "1..4294967295" {
                  description
                    "set IN_GOOD_PKTS threshold";
                }
              }
              description
                "set IN_GOOD_PKTS threshold";
            }
            leaf out-good-bytes {
              type uint32 {
                range "1..4294967295" {
                  description
                    "set OUT_GOOD_BYTES threshold";
                }
              }
              description
                "set OUT_GOOD_BYTES threshold";
            }
            leaf out-good-pkts {
              type uint32 {
                range "1..4294967295" {
                  description
                    "set GOOD_PKTS threshold";
                }
              }
              description
                "set THRESH_OUT_GOOD_PKTS threshold";
            }
            leaf rx-util {
              type uint32 {
                range "1..10000" {
                  description
                    "set RX_UTIL threshold(in units of 0.01%)";
                }
              }
              description
                "set RX_UTIL threshold(in units of 0.1%)";
            }
            leaf tx-util {
              type uint32 {
                range "1..10000" {
                  description
                    "set TX_UTIL threshold(in units of 0.01%)";
                }
              }
              description
                "set TX_UTIL threshold(in units of 0.1%)";
            }
            leaf ether-stat-undersized-pkt {
              type uint32 {
                range "1..4294967295" {
                  description
                    "ETHER_STAT_UNDERSIZED_PKT threshold";
                }
              }
              description
                "set ETHER_STAT_UNDERSIZED_PKT threshold";
            }
            leaf tx-undersized-pkt {
              type uint32 {
                range "1..4294967295" {
                  description
                    "TX_UNDERSIZED_PKT threshold";
                }
              }
              description
                "set TX_UNDERSIZED_PKT threshold";
            }
            leaf tx-oversized-pkt {
              type uint32 {
                range "1..4294967295" {
                  description
                    "TX_OVERSIZED_PKT threshold";
                }
              }
              description
                "set TX_OVERSIZED_PKT threshold";
            }
            leaf tx-fragments {
              type uint32 {
                range "1..4294967295" {
                  description
                    "TX_FRAGMENTS threshold";
                }
              }
              description
                "set TX_FRAGMENTS threshold";
            }
            leaf tx-jabber {
              type uint32 {
                range "1..4294967295" {
                  description
                    "TX_JABBER threshold";
                }
              }
              description
                "set TX_JABBER threshold";
            }
            leaf tx-bad-fcs {
              type uint32 {
                range "1..4294967295" {
                  description
                    "TX_BAD_FCS threshold";
                }
              }
              description
                "set TX_BAD_FCS threshold";
            }
          }
          container report {
            description
              "set ether TCA reporting status";
            container rx-pkt {
              description
                "set rx-pkt TCA reporting status";
              container enable {
                presence "Indicates a enable node is configured.";
                description
                  "Enable TCA reporting";
              }
            }
            container rx-util {
              description
                "set rx-util TCA reporting status";
              container enable {
                presence "Indicates a enable node is configured.";
                description
                  "Enable TCA reporting";
              }
            }
            container tx-util {
              description
                "set tx-util TCA reporting status";
              container enable {
                presence "Indicates a enable node is configured.";
                description
                  "Enable TCA reporting";
              }
            }
            container stat-pkt {
              description
                "set stat-pkt TCA reporting status";
              container enable {
                presence "Indicates a enable node is configured.";
                description
                  "Enable TCA reporting";
              }
            }
            container octet-stat {
              description
                "set octet-stat TCA reporting status";
              container enable {
                presence "Indicates a enable node is configured.";
                description
                  "Enable TCA reporting";
              }
            }
            container oversize-pkt {
              description
                "set oversize-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container long-frame {
              description
                "set long-frame TCA reporting status";
              container enable {
                presence "Indicates a enable node is configured.";
                description
                  "Enable TCA reporting";
              }
            }
            container jabber-stats {
              description
                "set jabber-stats TCA reporting status";
              container enable {
                presence "Indicates a enable node is configured.";
                description
                  "Enable TCA reporting";
              }
            }
            container _64-octets {
              description
                "set 64-octets TCA reporting status";
              container enable {
                presence "Indicates a enable node is configured.";
                description
                  "Enable TCA reporting";
              }
            }
            container _65-127-octets {
              description
                "set 65-127-octets TCA reporting status";
              container enable {
                presence "Indicates a enable node is configured.";
                description
                  "Enable TCA reporting";
              }
            }
            container _128-255-octets {
              description
                "set 128-255-octets TCA reporting status";
              container enable {
                presence "Indicates a enable node is configured.";
                description
                  "Enable TCA reporting";
              }
            }
            container _256-511-octets {
              description
                "set 256-511-octets TCA reporting status";
              container enable {
                presence "Indicates a enable node is configured.";
                description
                  "Enable TCA reporting";
              }
            }
            container _512-1023-octets {
              description
                "set 512-1023-octets TCA reporting status";
              container enable {
                presence "Indicates a enable node is configured.";
                description
                  "Enable TCA reporting";
              }
            }
            container _1024-1518-octets {
              description
                "set 1024-1518-octets TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-errors {
              description
                "set ifIn_errors TCA reporting status";
              container enable {
                presence "Indicates a enable node is configured.";
                description
                  "Enable TCA reporting";
              }
            }
            container if-in-octets {
              description
                "set ifOut_errors  TCA reporting status";
              container enable {
                presence "Indicates a enable node is configured.";
                description
                  "Enable TCA reporting";
              }
            }
            container ether-stat-multicast-pkt {
              description
                "set ether_stat_multicast_pkt TCA reporting status";
              container enable {
                presence "Indicates a enable node is configured.";
                description
                  "Enable TCA reporting";
              }
            }
            container ether-stat-broadcast-pkt {
              description
                "set ether_stat_broadcast_pkt TCA reporting status";
              container enable {
                presence "Indicates a enable node is configured.";
                description
                  "Enable TCA reporting";
              }
            }
            container ether-stat-undersized-pkt {
              description
                "set ether_stat_undersized_pkt  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-64-octets {
              description
                "set in-64-octets TCA reporting status";
              container enable {
                presence "Indicates a enable node is configured.";
                description
                  "Enable TCA reporting";
              }
            }
            container in-65-127-octets {
              description
                "set in-65-127-octets TCA reporting status";
              container enable {
                presence "Indicates a enable node is configured.";
                description
                  "Enable TCA reporting";
              }
            }
            container in-128-255-octets {
              description
                "set in-128-255-octets TCA reporting status";
              container enable {
                presence "Indicates a enable node is configured.";
                description
                  "Enable TCA reporting";
              }
            }
            container in-256-511-octets {
              description
                "set in-256-511-octets TCA reporting status";
              container enable {
                presence "Indicates a enable node is configured.";
                description
                  "Enable TCA reporting";
              }
            }
            container in-512-1023-octets {
              description
                "set in-512-1023-octets TCA reporting status";
              container enable {
                presence "Indicates a enable node is configured.";
                description
                  "Enable TCA reporting";
              }
            }
            container in-1024-1518-octets {
              description
                "set in-1024-1518-octets TCA reporting status";
              container enable {
                presence "Indicates a enable node is configured.";
                description
                  "Enable TCA reporting";
              }
            }
            container out-pkt-64-octet {
              description
                "set out-pkt-64-octet TCA reporting status";
              container enable {
                presence "Indicates a enable node is configured.";
                description
                  "Enable TCA reporting";
              }
            }
            container out-pkts-65-127-octets {
              description
                "set out-pkts-65-127-octets TCA reporting status";
              container enable {
                presence "Indicates a enable node is configured.";
                description
                  "Enable TCA reporting";
              }
            }
            container out-pkts-128-255-octets {
              description
                "set out-pkts-128-255-octets TCA reporting status";
              container enable {
                presence "Indicates a enable node is configured.";
                description
                  "Enable TCA reporting";
              }
            }
            container out-pkts-256-511-octets {
              description
                "set out-pkts-256-511-octets TCA reporting status";
              container enable {
                presence "Indicates a enable node is configured.";
                description
                  "Enable TCA reporting";
              }
            }
            container out-pkts-512-1023-octets {
              description
                "set out-pkts-512-1023-octets TCA reporting status";
              container enable {
                presence "Indicates a enable node is configured.";
                description
                  "Enable TCA reporting";
              }
            }
            container out-pkts-1024-1518-octets {
              description
                "set out-pkts-1024-1518-octets TCA reporting status";
              container enable {
                presence "Indicates a enable node is configured.";
                description
                  "Enable TCA reporting";
              }
            }
            container tx-undersized-pkt {
              description
                "set tx_undersized_pkt  TCA reporting status";
              container enable {
                presence "Indicates a enable node is configured.";
                description
                  "Enable TCA reporting";
              }
            }
            container tx-oversized-pkt {
              description
                "set tx_oversized_pkt  TCA reporting status";
              container enable {
                presence "Indicates a enable node is configured.";
                description
                  "Enable TCA reporting";
              }
            }
            container tx-fragments {
              description
                "set tx_fragments  TCA reporting status";
              container enable {
                presence "Indicates a enable node is configured.";
                description
                  "Enable TCA reporting";
              }
            }
            container tx-jabber {
              description
                "set tx_jabber  TCA reporting status";
              container enable {
                presence "Indicates a enable node is configured.";
                description
                  "Enable TCA reporting";
              }
            }
            container tx-bad-fcs {
              description
                "set tx_bad_fcs  TCA reporting status";
              container enable {
                presence "Indicates a enable node is configured.";
                description
                  "Enable TCA reporting";
              }
            }
          }
        }
        container fec {
          description
            "Configure fec performance monitoring";
          container threshold {
            description
              "Configure fec threshold";
            leaf ec-words {
              type xr:Cisco-ios-xr-string {
                length "1..20" {
                  description
                    "ec-words threshold <range:1-18446744073709551615>";
                }
              }
              description
                "set EC-Words threshold";
            }
            leaf uc-words {
              type xr:Cisco-ios-xr-string {
                length "1..20" {
                  description
                    "uc-words threshold <range:1-18446744073709551615>";
                }
              }
              description
                "set UC-WORDS threshold";
            }
            container pre-fec-ber {
              description
                "Set PRE-FEC-BER Thresholds";
              leaf min {
                type xr:Cisco-ios-xr-string {
                  length "1..20" {
                    description
                      "pre-fec-ber min threshold <range:1-18446744073709551615>";
                  }
                }
                description
                  "set pre-fec-ber min threshold";
              }
              leaf max {
                type xr:Cisco-ios-xr-string {
                  length "1..20" {
                    description
                      "pre-fec-ber max threshold <range:1-18446744073709551615>";
                  }
                }
                description
                  "set pre-fec-ber max threshold";
              }
            }
            container post-fec-ber {
              description
                "Set POST-FEC-BER Thresholds";
              leaf min {
                type xr:Cisco-ios-xr-string {
                  length "1..20" {
                    description
                      "post-fec-ber min threshold <range:1-18446744073709551615>";
                  }
                }
                description
                  "set post-fec-ber min threshold";
              }
              leaf max {
                type xr:Cisco-ios-xr-string {
                  length "1..20" {
                    description
                      "post-fec-ber max threshold <range:1-18446744073709551615>";
                  }
                }
                description
                  "set post-fec-ber max threshold";
              }
            }
          }
          container report {
            description
              "set fec TCA reporting status";
            container uc-words {
              description
                "set uc-words TCA reporting status";
              container enable {
                presence "Indicates a enable node is configured.";
                description
                  "Enable TCA reporting";
              }
            }
            container ec-words {
              description
                "set ec-words TCA reporting status";
              container enable {
                presence "Indicates a enable node is configured.";
                description
                  "Enable TCA reporting";
              }
            }
            container pre-fec-ber {
              description
                "set PRE FEC BER TCA reporting status";
              container max-tca {
                description
                  "set PRE FEC BER max TCA reporting status";
                container enable {
                  presence "Indicates a enable node is configured.";
                  description
                    "Enable TCA reporting";
                }
              }
              container min-tca {
                description
                  "set PRE FEC BER min TCA reporting status";
                container enable {
                  presence "Indicates a enable node is configured.";
                  description
                    "Enable TCA reporting";
                }
              }
            }
            container post-fec-ber {
              description
                "set POST FEC BER TCA reporting status";
              container max-tca {
                description
                  "set POST FEC BER max TCA reporting status";
                container enable {
                  presence "Indicates a enable node is configured.";
                  description
                    "Enable TCA reporting";
                }
              }
              container min-tca {
                description
                  "set POST FEC BER min TCA reporting status";
                container enable {
                  presence "Indicates a enable node is configured.";
                  description
                    "Enable TCA reporting";
                }
              }
            }
          }
        }
        container pcs {
          description
            "configure pcs performance monitoring";
          container threshold {
            description
              "Configure threshold on pcs parameters";
            leaf bip {
              type xr:Cisco-ios-xr-string {
                length "1..20" {
                  description
                    "BIP threshold range <1-18446744073709551615>";
                }
              }
              description
                "set BIP threshold";
            }
            leaf frm-err {
              type xr:Cisco-ios-xr-string {
                length "1..20" {
                  description
                    "FRM-ERR threshold range <1-18446744073709551615>";
                }
              }
              description
                "set FRM-ERR threshold";
            }
            leaf bad-sh {
              type xr:Cisco-ios-xr-string {
                length "1..20" {
                  description
                    "Bad-sh threshold range <1-18446744073709551615>";
                }
              }
              description
                "set Bad-sh threshold";
            }
            leaf es {
              type xr:Cisco-ios-xr-string {
                length "1..20" {
                  description
                    "Es threshold range <0-30>";
                }
              }
              description
                "set Es threshold";
            }
            leaf ses {
              type xr:Cisco-ios-xr-string {
                length "1..20" {
                  description
                    "Ses threshold range <0-30>";
                }
              }
              description
                "set Ses threshold";
            }
            leaf uas {
              type xr:Cisco-ios-xr-string {
                length "1..20" {
                  description
                    "Uas threshold range <0-30>";
                }
              }
              description
                "set Uas threshold";
            }
            leaf es-fe {
              type xr:Cisco-ios-xr-string {
                length "1..20" {
                  description
                    "Es-fe threshold range <0-30>";
                }
              }
              description
                "set Es-fe threshold";
            }
            leaf ses-fe {
              type xr:Cisco-ios-xr-string {
                length "1..20" {
                  description
                    "Ses-fe threshold range <0-30>";
                }
              }
              description
                "set Ses-fe threshold";
            }
            leaf uas-fe {
              type xr:Cisco-ios-xr-string {
                length "1..20" {
                  description
                    "Uas-fe threshold range <0-30>";
                }
              }
              description
                "set Uas-fe threshold";
            }
          }
          container report {
            description
              "set pcs TCA reporting status";
            container bip {
              description
                "set bip TCA reporting status";
              container enable {
                presence "Indicates a enable node is configured.";
                description
                  "Enable TCA reporting";
              }
            }
            container frm-err {
              description
                "set frm-err TCA reporting status";
              container enable {
                presence "Indicates a enable node is configured.";
                description
                  "Enable TCA reporting";
              }
            }
            container bad-sh {
              description
                "set bad-sh TCA reporting status";
              container enable {
                presence "Indicates a enable node is configured.";
                description
                  "Enable TCA reporting";
              }
            }
            container es {
              description
                "set es TCA reporting status";
              container enable {
                presence "Indicates a enable node is configured.";
                description
                  "Enable TCA reporting";
              }
            }
            container ses {
              description
                "set ses TCA reporting status";
              container enable {
                presence "Indicates a enable node is configured.";
                description
                  "Enable TCA reporting";
              }
            }
            container uas {
              description
                "set uas TCA reporting status";
              container enable {
                presence "Indicates a enable node is configured.";
                description
                  "Enable TCA reporting";
              }
            }
            container es-fe {
              description
                "set es-fe TCA reporting status";
              container disable {
                presence "Indicates a disable node is configured.";
                description
                  "Disable TCA reporting";
              }
            }
            container ses-fe {
              description
                "set ses-fe TCA reporting status";
              container disable {
                presence "Indicates a disable node is configured.";
                description
                  "Disable TCA reporting";
              }
            }
            container uas-fe {
              description
                "set uas-fe TCA reporting status";
              container disable {
                presence "Indicates a disable node is configured.";
                description
                  "Disable TCA reporting";
              }
            }
          }
        }
        container macsec-secy-tx {
          description
            "Configure pm parameters of macsec-secy-tx";
          container threshold {
            description
              "Configure threshold on macsec-secy-tx parameters";
            leaf out-pkts-protected {
              type uint32 {
                range "1..4294967295" {
                  description
                    "OutPktsProtected threshold range";
                }
              }
              description
                "Set Threshold for OutPktsProtected";
            }
            leaf out-pkts-encrypted {
              type uint32 {
                range "1..4294967295" {
                  description
                    "OutPktsEncrypted threshold range";
                }
              }
              description
                "Set Threshold for OutPktsEncrypted";
            }
            leaf out-octets-protected {
              type uint32 {
                range "1..4294967295" {
                  description
                    "OutOctetsProtected threshold range";
                }
              }
              description
                "Set Threshold for OutOctetsProtected";
            }
            leaf out-octets-encrypted {
              type uint32 {
                range "1..4294967295" {
                  description
                    "OutOctetsEncrypted threshold range";
                }
              }
              description
                "Set Threshold for OutOctetsEncrypted";
            }
            leaf out-pkts-too-long {
              type uint32 {
                range "1..4294967295" {
                  description
                    "OutPktsTooLong threshold range";
                }
              }
              description
                "Set Threshold for OutPktsTooLong";
            }
          }
          container report {
            description
              "Configure Report for macsec-secy-tx Parameters";
            container out-pkts-protected {
              description
                "set OutPktsProtected TCA reporting status";
              container enable {
                presence "Indicates a enable node is configured.";
                description
                  "Enable TCA reporting";
              }
            }
            container out-pkts-encrypted {
              description
                "set OutPktsEncrypted TCA reporting status";
              container enable {
                presence "Indicates a enable node is configured.";
                description
                  "Enable TCA reporting";
              }
            }
            container out-octets-protected {
              description
                "set OutOctetsProtected TCA reporting status";
              container enable {
                presence "Indicates a enable node is configured.";
                description
                  "Enable TCA reporting";
              }
            }
            container out-octets-encrypted {
              description
                "set OutOctetsEncrypted TCA reporting status";
              container enable {
                presence "Indicates a enable node is configured.";
                description
                  "Enable TCA reporting";
              }
            }
            container out-pkts-too-long {
              description
                "set OutPktsTooLong TCA reporting status";
              container enable {
                presence "Indicates a enable node is configured.";
                description
                  "Enable TCA reporting";
              }
            }
          }
        }
        container macsec-secy-rx {
          description
            "Configure pm parameters of macsec-secy-rx";
          container threshold {
            description
              "Configure threshold on macsec-secy-rx parameters";
            leaf in-pkts-unchecked {
              type uint32 {
                range "1..4294967295" {
                  description
                    "InPktsUnchecked threshold range";
                }
              }
              description
                "Set Threshold for InPktsUnchecked";
            }
            leaf in-pkts-delayed {
              type uint32 {
                range "1..4294967295" {
                  description
                    "InPktsDelayed threshold range";
                }
              }
              description
                "Set Threshold for InPktsDelayed";
            }
            leaf in-pkts-late {
              type uint32 {
                range "1..4294967295" {
                  description
                    "InPktsLate threshold range";
                }
              }
              description
                "Set Threshold for InPktsLate";
            }
            leaf in-pkts-ok {
              type uint32 {
                range "1..4294967295" {
                  description
                    "InPktsOK threshold range";
                }
              }
              description
                "Set Threshold for InPktsOK";
            }
            leaf in-pkts-invalid {
              type uint32 {
                range "1..4294967295" {
                  description
                    "InPktsInvalid threshold range";
                }
              }
              description
                "Set Threshold for InPktsInvalid";
            }
            leaf in-pkts-not-valid {
              type uint32 {
                range "1..4294967295" {
                  description
                    "InPktsNotValid threshold range";
                }
              }
              description
                "Set Threshold for InPktsNotValid";
            }
            leaf in-pkts-not-using-sa {
              type uint32 {
                range "1..4294967295" {
                  description
                    "InPktsNotUsingSA threshold range";
                }
              }
              description
                "Set Threshold for InPktsNotUsingSA";
            }
            leaf in-pkts-unused-sa {
              type uint32 {
                range "1..4294967295" {
                  description
                    "InPktsUnusedSA threshold range";
                }
              }
              description
                "Set Threshold for InPktsUnusedSA";
            }
            leaf in-pkts-untagged-hit {
              type uint32 {
                range "1..4294967295" {
                  description
                    "InPktsUntaggedHit threshold range";
                }
              }
              description
                "Set Threshold for InPktsUntaggedHit";
            }
            leaf in-octets-validated {
              type uint32 {
                range "1..4294967295" {
                  description
                    "InOctetsValidated threshold range";
                }
              }
              description
                "Set Threshold for InOctetsValidated";
            }
            leaf in-octets-decrypted {
              type uint32 {
                range "1..4294967295" {
                  description
                    "InOctetsDecrypted threshold range";
                }
              }
              description
                "Set Threshold for InOctetsDecrypted";
            }
          }
          container report {
            description
              "Configure Report for macsec-secy-rx Parameters";
            container in-pkts-unchecked {
              description
                "set InPktsUnchecked TCA reporting status";
              container enable {
                presence "Indicates a enable node is configured.";
                description
                  "Enable TCA reporting";
              }
            }
            container in-pkts-delayed {
              description
                "set InPktsDelayed TCA reporting status";
              container enable {
                presence "Indicates a enable node is configured.";
                description
                  "Enable TCA reporting";
              }
            }
            container in-pkts-late {
              description
                "set InPktsLate TCA reporting status";
              container enable {
                presence "Indicates a enable node is configured.";
                description
                  "Enable TCA reporting";
              }
            }
            container in-pkts-ok {
              description
                "set InPktsOK TCA reporting status";
              container enable {
                presence "Indicates a enable node is configured.";
                description
                  "Enable TCA reporting";
              }
            }
            container in-pkts-invalid {
              description
                "set InPktsInvalid TCA reporting status";
              container enable {
                presence "Indicates a enable node is configured.";
                description
                  "Enable TCA reporting";
              }
            }
            container in-pkts-not-valid {
              description
                "set InPktsNotValid TCA reporting status";
              container enable {
                presence "Indicates a enable node is configured.";
                description
                  "Enable TCA reporting";
              }
            }
            container in-pkts-not-using-sa {
              description
                "set InPktsNotUsingSA TCA reporting status";
              container enable {
                presence "Indicates a enable node is configured.";
                description
                  "Enable TCA reporting";
              }
            }
            container in-pkts-unused-sa {
              description
                "set InPktsUnusedSA TCA reporting status";
              container enable {
                presence "Indicates a enable node is configured.";
                description
                  "Enable TCA reporting";
              }
            }
            container in-pkts-untagged-hit {
              description
                "set InPktsUntaggedHit TCA reporting status";
              container enable {
                presence "Indicates a enable node is configured.";
                description
                  "Enable TCA reporting";
              }
            }
            container in-octets-validated {
              description
                "set InOctetsValidated TCA reporting status";
              container enable {
                presence "Indicates a enable node is configured.";
                description
                  "Enable TCA reporting";
              }
            }
            container in-octets-decrypted {
              description
                "set InOctetsDecrypted TCA reporting status";
              container enable {
                presence "Indicates a enable node is configured.";
                description
                  "Enable TCA reporting";
              }
            }
          }
        }
        container macsec-secy-if {
          description
            "Configure pm parameters of macsec-secy-if";
          container threshold {
            description
              "Configure threshold on macsec-secy-if parameters";
            leaf in-pkts-untagged {
              type uint32 {
                range "1..4294967295" {
                  description
                    "InPktsUntagged threshold range";
                }
              }
              description
                "Set Threshold for InPktsUntagged";
            }
            leaf in-pkts-no-tag {
              type uint32 {
                range "1..4294967295" {
                  description
                    "InPktsNoTag threshold range";
                }
              }
              description
                "Set Threshold for InPktsNoTag";
            }
            leaf in-pkts-bad-tag {
              type uint32 {
                range "1..4294967295" {
                  description
                    "InPktsBadTag threshold range";
                }
              }
              description
                "Set Threshold for InPktsBadTag";
            }
            leaf in-pkts-unknown-sci {
              type uint32 {
                range "1..4294967295" {
                  description
                    "InPktsUnknownSCI threshold range";
                }
              }
              description
                "Set Threshold for InPktsUnknownSCI";
            }
            leaf in-pkts-no-sci {
              type uint32 {
                range "1..4294967295" {
                  description
                    "InPktsNoSCI threshold range";
                }
              }
              description
                "Set Threshold for InPktsNoSCI";
            }
            leaf in-pkts-overrun {
              type uint32 {
                range "1..4294967295" {
                  description
                    "InPktsOverrun threshold range";
                }
              }
              description
                "Set Threshold for InPktsOverrun";
            }
            leaf in-octets-validated {
              type uint32 {
                range "1..4294967295" {
                  description
                    "InOctetsValidated threshold range";
                }
              }
              description
                "Set Threshold for InOctetsValidated";
            }
            leaf in-octets-decrypted {
              type uint32 {
                range "1..4294967295" {
                  description
                    "InOctetsDecrypted threshold range";
                }
              }
              description
                "Set Threshold for InOctetsDecrypted";
            }
            leaf out-pkts-untagged {
              type uint32 {
                range "1..4294967295" {
                  description
                    "OutPktsUntagged threshold range";
                }
              }
              description
                "Set Threshold for OutPktsUntagged ";
            }
            leaf out-pkts-too-long {
              type uint32 {
                range "1..4294967295" {
                  description
                    "OutPktsTooLong threshold range";
                }
              }
              description
                "Set Threshold for OutPktsTooLong";
            }
            leaf out-octets-encrypted {
              type uint32 {
                range "1..4294967295" {
                  description
                    "OutOctetsEncrypted threshold range";
                }
              }
              description
                "Set Threshold for OutOctetsEncrypted";
            }
            leaf out-octets-protected {
              type uint32 {
                range "1..4294967295" {
                  description
                    "OutOctetsProtected threshold range";
                }
              }
              description
                "Set Threshold for OutOctetsProtected";
            }
          }
          container report {
            description
              "Configure Report for macsec-secy-if Parameters";
            container in-pkts-untagged {
              description
                "set InPktsUntagged TCA reporting status";
              container enable {
                presence "Indicates a enable node is configured.";
                description
                  "Enable TCA reporting";
              }
            }
            container in-pkts-no-tag {
              description
                "set InPktsNoTag TCA reporting status";
              container enable {
                presence "Indicates a enable node is configured.";
                description
                  "Enable TCA reporting";
              }
            }
            container in-pkts-bad-tag {
              description
                "set InPktsBadTag TCA reporting status";
              container enable {
                presence "Indicates a enable node is configured.";
                description
                  "Enable TCA reporting";
              }
            }
            container in-pkts-unknown-sci {
              description
                "set InPktsUnknownSCI TCA reporting status";
              container enable {
                presence "Indicates a enable node is configured.";
                description
                  "Enable TCA reporting";
              }
            }
            container in-pkts-no-sci {
              description
                "set InPktsNoSCI TCA reporting status";
              container enable {
                presence "Indicates a enable node is configured.";
                description
                  "Enable TCA reporting";
              }
            }
            container in-pkts-overrun {
              description
                "set InPktsOverrun TCA reporting status";
              container enable {
                presence "Indicates a enable node is configured.";
                description
                  "Enable TCA reporting";
              }
            }
            container in-octets-validated {
              description
                "set InOctetsValidated TCA reporting status";
              container enable {
                presence "Indicates a enable node is configured.";
                description
                  "Enable TCA reporting";
              }
            }
            container in-octets-decrypted {
              description
                "set InOctetsDecrypted TCA reporting status";
              container enable {
                presence "Indicates a enable node is configured.";
                description
                  "Enable TCA reporting";
              }
            }
            container out-pkts-untagged {
              description
                "set OutPktsUntagged TCA reporting status";
              container enable {
                presence "Indicates a enable node is configured.";
                description
                  "Enable TCA reporting";
              }
            }
            container out-pkts-too-long {
              description
                "set OutPktsTooLong TCA reporting status";
              container enable {
                presence "Indicates a enable node is configured.";
                description
                  "Enable TCA reporting";
              }
            }
            container out-octets-protected {
              description
                "set OutOctetsProtected TCA reporting status";
              container enable {
                presence "Indicates a enable node is configured.";
                description
                  "Enable TCA reporting";
              }
            }
            container out-octets-encrypted {
              description
                "set OutOctetsEncrypted TCA reporting status";
              container enable {
                presence "Indicates a enable node is configured.";
                description
                  "Enable TCA reporting";
              }
            }
          }
        }
        container macsec-ether {
          description
            "configure ether performance monitoring";
          container threshold {
            description
              "Configure threshold on ether parameters";
            leaf rx-pkt {
              type uint32 {
                range "1..4294967295" {
                  description
                    "RX-PKT threshold ";
                }
              }
              description
                "set RX-PKT threshold";
            }
            leaf stat-pkt {
              type uint32 {
                range "1..4294967295" {
                  description
                    "PKT-STAT threshold ";
                }
              }
              description
                "set PKT-STAT threshold";
            }
            leaf octet-stat {
              type uint32 {
                range "1..4294967295" {
                  description
                    "OCTET-STAT threshold ";
                }
              }
              description
                "set OCTET-STAT threshold";
            }
            leaf oversize-pkt {
              type uint32 {
                range "1..4294967295" {
                  description
                    "OVERSIZE-PKT threshold";
                }
              }
              description
                "set OVERSIZE-PKT threshold";
            }
            leaf fcs-err {
              type uint32 {
                range "1..4294967295" {
                  description
                    "FCS-ERR threshold";
                }
              }
              description
                "set FCS-ERR threshold";
            }
            leaf long-frame {
              type uint32 {
                range "1..4294967295" {
                  description
                    "LONG-FRAMES threshold ";
                }
              }
              description
                "set LONG-FRAMES threshold";
            }
            leaf jabber-stats {
              type uint32 {
                range "1..4294967295" {
                  description
                    "JABBER-STATS threshold ";
                }
              }
              description
                "set JABBER-STATS threshold";
            }
            leaf sixty-four-octets {
              type uint32 {
                range "1..4294967295" {
                  description
                    "64-OCTET threshold";
                }
              }
              description
                "set 64-OCTET threshold";
            }
            leaf six5-127-octets {
              type uint32 {
                range "1..4294967295" {
                  description
                    "65-127-OCTET threshold";
                }
              }
              description
                "set 65-127-OCTET threshold";
            }
            leaf one-hundred-twenty-eight-255-octets {
              type uint32 {
                range "1..4294967295" {
                  description
                    "128-255-OCTET threshold ";
                }
              }
              description
                "set 128-255-OCTET threshold";
            }
            leaf two-hundred-fifty-six-511-octets {
              type uint32 {
                range "1..4294967295" {
                  description
                    "256-511-OCTET threshold ";
                }
              }
              description
                "set 256-511-OCTET threshold";
            }
            leaf five-hundred-twelve-1023-octets {
              type uint32 {
                range "1..4294967295" {
                  description
                    "512-1023-OCTET threshold";
                }
              }
              description
                "set 512-1023-OCTET threshold";
            }
            leaf one-thousand-twenty-four-1518-octets {
              type uint32 {
                range "1..4294967295" {
                  description
                    "1024-1518-OCTET threshold";
                }
              }
              description
                "set 1024-1518-OCTET threshold";
            }
            leaf in-64-octets {
              type uint32 {
                range "1..4294967295" {
                  description
                    "IN-64-OCTET threshold";
                }
              }
              description
                "set IN-64-OCTET threshold";
            }
            leaf in-65-127-octets {
              type uint32 {
                range "1..4294967295" {
                  description
                    "IN-65-127-OCTET threshold";
                }
              }
              description
                "set IN-65-127-OCTET threshold";
            }
            leaf in-128-255-octets {
              type uint32 {
                range "1..4294967295" {
                  description
                    "IN-128-255-OCTET threshold ";
                }
              }
              description
                "set IN-128-255-OCTET threshold";
            }
            leaf in-256-511-octets {
              type uint32 {
                range "1..4294967295" {
                  description
                    "IN-256-511-OCTET threshold ";
                }
              }
              description
                "set IN-256-511-OCTET threshold";
            }
            leaf in-512-1023-octets {
              type uint32 {
                range "1..4294967295" {
                  description
                    "IN-512-1023-OCTET threshold";
                }
              }
              description
                "set IN-512-1023-OCTET threshold";
            }
            leaf in-1024-1518-octets {
              type uint32 {
                range "1..4294967295" {
                  description
                    "IN-1024-1518-OCTET threshold";
                }
              }
              description
                "set IN-1024-1518-OCTET threshold";
            }
            leaf in-drop-other {
              type uint32 {
                range "1..4294967295" {
                  description
                    "IN-DROP-OTHER threshold";
                }
              }
              description
                "set IN_DROP_OTHER threshold";
            }
            leaf in-ucast {
              type uint32 {
                range "1..4294967295" {
                  description
                    "IN-UCAST threshold";
                }
              }
              description
                "set IN-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf in-error-fragments {
              type uint32 {
                range "1..4294967295" {
                  description
                    "IN-ERROR-FRAGMENTS threshold";
                }
              }
              description
                "set IN-ERROR-FRAGMENTS threshold";
            }
            leaf out-ucast {
              type uint32 {
                range "1..4294967295" {
                  description
                    "OUT-UCAST threshold";
                }
              }
              description
                "set OUT-UCAST threshold";
            }
            leaf out-bcast {
              type uint32 {
                range "1..4294967295" {
                  description
                    "OUT-BCAST threshold ";
                }
              }
              description
                "set OUT-BCAST threshold";
            }
            leaf out-mcast {
              type uint32 {
                range "1..4294967295" {
                  description
                    "OUT-MCAST threshold ";
                }
              }
              description
                "set OUT-MCAST threshold";
            }
            leaf tx-pkt {
              type uint32 {
                range "1..4294967295" {
                  description
                    "TX-PKT threshold";
                }
              }
              description
                "set TX-PKT threshold";
            }
            leaf out-octets {
              type uint32 {
                range "1..4294967295" {
                  description
                    "OUT-OCTET threshold ";
                }
              }
              description
                "set OUT-OCTET threshold";
            }
            leaf if-in-errors {
              type uint32 {
                range "1..4294967295" {
                  description
                    "IFIN_ERRORS threshold";
                }
              }
              description
                "set IFIN_ERRORS threshold";
            }
            leaf if-in-octets {
              type uint32 {
                range "1..4294967295" {
                  description
                    "IFIN_OCTETS threshold";
                }
              }
              description
                "set IFIN_OCTETS threshold";
            }
            leaf ether-stat-multicast-pkt {
              type uint32 {
                range "1..4294967295" {
                  description
                    "ETHER_STAT_MULTICAST_PKT threshold";
                }
              }
              description
                "set ETHER_STAT_MULTICAST_PKT threshold";
            }
            leaf ether-stat-broadcast-pkt {
              type uint32 {
                range "1..4294967295" {
                  description
                    " ETHER_STAT_BROADCAST_PKT threshold";
                }
              }
              description
                "set ETHER_STAT_BROADCAST_PKT threshold";
            }
            leaf in-good-bytes {
              type uint32 {
                range "1..4294967295" {
                  description
                    "set IN_GOOD_BYTES threshold";
                }
              }
              description
                "set IN_GOOD_BYTES threshold";
            }
            leaf in-good-pkts {
              type uint32 {
                range "1..4294967295" {
                  description
                    "set IN_GOOD_PKTS threshold";
                }
              }
              description
                "set IN_GOOD_PKTS threshold";
            }
            leaf out-good-bytes {
              type uint32 {
                range "1..4294967295" {
                  description
                    "set OUT_GOOD_BYTES threshold";
                }
              }
              description
                "set OUT_GOOD_BYTES threshold";
            }
            leaf out-good-pkts {
              type uint32 {
                range "1..4294967295" {
                  description
                    "set GOOD_PKTS threshold";
                }
              }
              description
                "set THRESH_OUT_GOOD_PKTS threshold";
            }
            leaf rx-util {
              type uint32 {
                range "1..10000" {
                  description
                    "set RX_UTIL threshold(in units of 0.01%)";
                }
              }
              description
                "set RX_UTIL threshold(in units of 0.1%)";
            }
            leaf tx-util {
              type uint32 {
                range "1..10000" {
                  description
                    "set TX_UTIL threshold(in units of 0.01%)";
                }
              }
              description
                "set TX_UTIL threshold(in units of 0.1%)";
            }
            leaf ether-stat-undersized-pkt {
              type uint32 {
                range "1..4294967295" {
                  description
                    "ETHER_STAT_UNDERSIZED_PKT threshold";
                }
              }
              description
                "set ETHER_STAT_UNDERSIZED_PKT threshold";
            }
            leaf tx-undersized-pkt {
              type uint32 {
                range "1..4294967295" {
                  description
                    "TX_UNDERSIZED_PKT threshold";
                }
              }
              description
                "set TX_UNDERSIZED_PKT threshold";
            }
            leaf tx-oversized-pkt {
              type uint32 {
                range "1..4294967295" {
                  description
                    "TX_OVERSIZED_PKT threshold";
                }
              }
              description
                "set TX_OVERSIZED_PKT threshold";
            }
            leaf tx-fragments {
              type uint32 {
                range "1..4294967295" {
                  description
                    "TX_FRAGMENTS threshold";
                }
              }
              description
                "set TX_FRAGMENTS threshold";
            }
            leaf tx-jabber {
              type uint32 {
                range "1..4294967295" {
                  description
                    "TX_JABBER threshold";
                }
              }
              description
                "set TX_JABBER threshold";
            }
            leaf tx-bad-fcs {
              type uint32 {
                range "1..4294967295" {
                  description
                    "TX_BAD_FCS threshold";
                }
              }
              description
                "set TX_BAD_FCS threshold";
            }
          }
          container report {
            description
              "set ether TCA reporting status";
            container rx-pkt {
              description
                "set rx-pkt TCA reporting status";
              container enable {
                presence "Indicates a enable node is configured.";
                description
                  "Enable TCA reporting";
              }
            }
            container rx-util {
              description
                "set rx-util TCA reporting status";
              container enable {
                presence "Indicates a enable node is configured.";
                description
                  "Enable TCA reporting";
              }
            }
            container tx-util {
              description
                "set tx-util TCA reporting status";
              container enable {
                presence "Indicates a enable node is configured.";
                description
                  "Enable TCA reporting";
              }
            }
            container stat-pkt {
              description
                "set stat-pkt TCA reporting status";
              container enable {
                presence "Indicates a enable node is configured.";
                description
                  "Enable TCA reporting";
              }
            }
            container octet-stat {
              description
                "set octet-stat TCA reporting status";
              container enable {
                presence "Indicates a enable node is configured.";
                description
                  "Enable TCA reporting";
              }
            }
            container oversize-pkt {
              description
                "set oversize-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container long-frame {
              description
                "set long-frame TCA reporting status";
              container enable {
                presence "Indicates a enable node is configured.";
                description
                  "Enable TCA reporting";
              }
            }
            container jabber-stats {
              description
                "set jabber-stats TCA reporting status";
              container enable {
                presence "Indicates a enable node is configured.";
                description
                  "Enable TCA reporting";
              }
            }
            container _64-octets {
              description
                "set 64-octets TCA reporting status";
              container enable {
                presence "Indicates a enable node is configured.";
                description
                  "Enable TCA reporting";
              }
            }
            container _65-127-octets {
              description
                "set 65-127-octets TCA reporting status";
              container enable {
                presence "Indicates a enable node is configured.";
                description
                  "Enable TCA reporting";
              }
            }
            container _128-255-octets {
              description
                "set 128-255-octets TCA reporting status";
              container enable {
                presence "Indicates a enable node is configured.";
                description
                  "Enable TCA reporting";
              }
            }
            container _256-511-octets {
              description
                "set 256-511-octets TCA reporting status";
              container enable {
                presence "Indicates a enable node is configured.";
                description
                  "Enable TCA reporting";
              }
            }
            container _512-1023-octets {
              description
                "set 512-1023-octets TCA reporting status";
              container enable {
                presence "Indicates a enable node is configured.";
                description
                  "Enable TCA reporting";
              }
            }
            container _1024-1518-octets {
              description
                "set 1024-1518-octets TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-errors {
              description
                "set ifIn_errors TCA reporting status";
              container enable {
                presence "Indicates a enable node is configured.";
                description
                  "Enable TCA reporting";
              }
            }
            container if-in-octets {
              description
                "set ifOut_errors  TCA reporting status";
              container enable {
                presence "Indicates a enable node is configured.";
                description
                  "Enable TCA reporting";
              }
            }
            container ether-stat-multicast-pkt {
              description
                "set ether_stat_multicast_pkt TCA reporting status";
              container enable {
                presence "Indicates a enable node is configured.";
                description
                  "Enable TCA reporting";
              }
            }
            container ether-stat-broadcast-pkt {
              description
                "set ether_stat_broadcast_pkt TCA reporting status";
              container enable {
                presence "Indicates a enable node is configured.";
                description
                  "Enable TCA reporting";
              }
            }
            container ether-stat-undersized-pkt {
              description
                "set ether_stat_undersized_pkt  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-64-octets {
              description
                "set in-64-octets TCA reporting status";
              container enable {
                presence "Indicates a enable node is configured.";
                description
                  "Enable TCA reporting";
              }
            }
            container in-65-127-octets {
              description
                "set in-65-127-octets TCA reporting status";
              container enable {
                presence "Indicates a enable node is configured.";
                description
                  "Enable TCA reporting";
              }
            }
            container in-128-255-octets {
              description
                "set in-128-255-octets TCA reporting status";
              container enable {
                presence "Indicates a enable node is configured.";
                description
                  "Enable TCA reporting";
              }
            }
            container in-256-511-octets {
              description
                "set in-256-511-octets TCA reporting status";
              container enable {
                presence "Indicates a enable node is configured.";
                description
                  "Enable TCA reporting";
              }
            }
            container in-512-1023-octets {
              description
                "set in-512-1023-octets TCA reporting status";
              container enable {
                presence "Indicates a enable node is configured.";
                description
                  "Enable TCA reporting";
              }
            }
            container in-1024-1518-octets {
              description
                "set in-1024-1518-octets TCA reporting status";
              container enable {
                presence "Indicates a enable node is configured.";
                description
                  "Enable TCA reporting";
              }
            }
            container tx-undersized-pkt {
              description
                "set tx_undersized_pkt  TCA reporting status";
              container enable {
                presence "Indicates a enable node is configured.";
                description
                  "Enable TCA reporting";
              }
            }
            container tx-oversized-pkt {
              description
                "set tx_oversized_pkt  TCA reporting status";
              container enable {
                presence "Indicates a enable node is configured.";
                description
                  "Enable TCA reporting";
              }
            }
            container tx-fragments {
              description
                "set tx_fragments  TCA reporting status";
              container enable {
                presence "Indicates a enable node is configured.";
                description
                  "Enable TCA reporting";
              }
            }
            container tx-jabber {
              description
                "set tx_jabber  TCA reporting status";
              container enable {
                presence "Indicates a enable node is configured.";
                description
                  "Enable TCA reporting";
              }
            }
            container tx-bad-fcs {
              description
                "set tx_bad_fcs  TCA reporting status";
              container enable {
                presence "Indicates a enable node is configured.";
                description
                  "Enable TCA reporting";
              }
            }
          }
        }
      }
      container interval-24-hr {
        description
          "Configure pm parameters of 24 hrs interval";
        container macsec-secy-tx {
          description
            "Configure pm parameters of macsec-secy-tx";
          container threshold {
            description
              "Configure threshold on macsec-secy-tx parameters";
            leaf out-pkts-protected {
              type uint32 {
                range "1..4294967295" {
                  description
                    "OutPktsProtected threshold range";
                }
              }
              description
                "Set Threshold for OutPktsProtected ";
            }
            leaf out-pkts-encrypted {
              type uint32 {
                range "1..4294967295" {
                  description
                    "OutPktsEncrypted threshold range";
                }
              }
              description
                "Set Threshold for OutPktsEncrypted";
            }
            leaf out-octets-protected {
              type uint32 {
                range "1..4294967295" {
                  description
                    "OutOctetsProtected threshold range";
                }
              }
              description
                "Set Threshold for OutOctetsProtected";
            }
            leaf out-octets-encrypted {
              type uint32 {
                range "1..4294967295" {
                  description
                    "OutOctetsEncrypted threshold range";
                }
              }
              description
                "Set Threshold for OutOctetsEncrypted";
            }
            leaf out-pkts-too-long {
              type uint32 {
                range "1..4294967295" {
                  description
                    "OutPktsTooLong threshold range";
                }
              }
              description
                "Set Threshold for OutPktsTooLong";
            }
          }
          container report {
            description
              "Configure Report for macsec-secy-tx Parameters";
            container out-pkts-protected {
              description
                "set OutPktsProtected TCA reporting status";
              container enable {
                presence "Indicates a enable node is configured.";
                description
                  "Enable TCA reporting";
              }
            }
            container out-pkts-encrypted {
              description
                "set OutPktsEncrypted TCA reporting status";
              container enable {
                presence "Indicates a enable node is configured.";
                description
                  "Enable TCA reporting";
              }
            }
            container out-octets-protected {
              description
                "set OutOctetsProtected TCA reporting status";
              container enable {
                presence "Indicates a enable node is configured.";
                description
                  "Enable TCA reporting";
              }
            }
            container out-octets-encrypted {
              description
                "set OutOctetsEncrypted TCA reporting status";
              container enable {
                presence "Indicates a enable node is configured.";
                description
                  "Enable TCA reporting";
              }
            }
            container out-pkts-too-long {
              description
                "set OutPktsTooLong TCA reporting status";
              container enable {
                presence "Indicates a enable node is configured.";
                description
                  "Enable TCA reporting";
              }
            }
          }
        }
        container macsec-secy-rx {
          description
            "Configure pm parameters of macsec-secy-rx";
          container threshold {
            description
              "Configure threshold on macsec-secy-rx parameters";
            leaf in-pkts-unchecked {
              type uint32 {
                range "1..4294967295" {
                  description
                    "InPktsUnchecked threshold range";
                }
              }
              description
                "Set Threshold for InPktsUnchecked";
            }
            leaf in-pkts-delayed {
              type uint32 {
                range "1..4294967295" {
                  description
                    "InPktsDelayed threshold range";
                }
              }
              description
                "Set Threshold for InPktsDelayed";
            }
            leaf in-pkts-late {
              type uint32 {
                range "1..4294967295" {
                  description
                    "InPktsLate threshold range";
                }
              }
              description
                "Set Threshold for InPktsLate";
            }
            leaf in-pkts-ok {
              type uint32 {
                range "1..4294967295" {
                  description
                    "InPktsOK threshold range";
                }
              }
              description
                "Set Threshold for InPktsOK";
            }
            leaf in-pkts-invalid {
              type uint32 {
                range "1..4294967295" {
                  description
                    "InPktsInvalid threshold range";
                }
              }
              description
                "Set Threshold for InPktsInvalid";
            }
            leaf in-pkts-not-valid {
              type uint32 {
                range "1..4294967295" {
                  description
                    "InPktsNotValid threshold range";
                }
              }
              description
                "Set Threshold for InPktsNotValid";
            }
            leaf in-pkts-not-using-sa {
              type uint32 {
                range "1..4294967295" {
                  description
                    "InPktsNotUsingSA threshold range";
                }
              }
              description
                "Set Threshold for InPktsNotUsingSA";
            }
            leaf in-pkts-unused-sa {
              type uint32 {
                range "1..4294967295" {
                  description
                    "InPktsUnusedSA threshold range";
                }
              }
              description
                "Set Threshold for InPktsUnusedSA";
            }
            leaf in-pkts-untagged-hit {
              type uint32 {
                range "1..4294967295" {
                  description
                    "InPktsUntaggedHit threshold range";
                }
              }
              description
                "Set Threshold for InPktsUntaggedHit";
            }
            leaf in-octets-validated {
              type uint32 {
                range "1..4294967295" {
                  description
                    "InOctetsValidated threshold range";
                }
              }
              description
                "Set Threshold for InOctetsValidated";
            }
            leaf in-octets-decrypted {
              type uint32 {
                range "1..4294967295" {
                  description
                    "InOctetsDecrypted threshold range";
                }
              }
              description
                "Set Threshold for InOctetsDecrypted";
            }
          }
          container report {
            description
              "Configure Report for macsec-secy-rx Parameters";
            container in-pkts-unchecked {
              description
                "set InPktsUnchecked TCA reporting status";
              container enable {
                presence "Indicates a enable node is configured.";
                description
                  "Enable TCA reporting";
              }
            }
            container in-pkts-delayed {
              description
                "set InPktsDelayed TCA reporting status";
              container enable {
                presence "Indicates a enable node is configured.";
                description
                  "Enable TCA reporting";
              }
            }
            container in-pkts-late {
              description
                "set InPktsLate TCA reporting status";
              container enable {
                presence "Indicates a enable node is configured.";
                description
                  "Enable TCA reporting";
              }
            }
            container in-pkts-ok {
              description
                "set InPktsOK TCA reporting status";
              container enable {
                presence "Indicates a enable node is configured.";
                description
                  "Enable TCA reporting";
              }
            }
            container in-pkts-invalid {
              description
                "set InPktsInvalid TCA reporting status";
              container enable {
                presence "Indicates a enable node is configured.";
                description
                  "Enable TCA reporting";
              }
            }
            container in-pkts-not-valid {
              description
                "set InPktsNotValid TCA reporting status";
              container enable {
                presence "Indicates a enable node is configured.";
                description
                  "Enable TCA reporting";
              }
            }
            container in-pkts-not-using-sa {
              description
                "set InPktsNotUsingSA TCA reporting status";
              container enable {
                presence "Indicates a enable node is configured.";
                description
                  "Enable TCA reporting";
              }
            }
            container in-pkts-unused-sa {
              description
                "set InPktsUnusedSA TCA reporting status";
              container enable {
                presence "Indicates a enable node is configured.";
                description
                  "Enable TCA reporting";
              }
            }
            container in-pkts-untagged-hit {
              description
                "set InPktsUntaggedHit TCA reporting status";
              container enable {
                presence "Indicates a enable node is configured.";
                description
                  "Enable TCA reporting";
              }
            }
            container in-octets-validated {
              description
                "set InOctetsValidated TCA reporting status";
              container enable {
                presence "Indicates a enable node is configured.";
                description
                  "Enable TCA reporting";
              }
            }
            container in-octets-decrypted {
              description
                "set InOctetsDecrypted TCA reporting status";
              container enable {
                presence "Indicates a enable node is configured.";
                description
                  "Enable TCA reporting";
              }
            }
          }
        }
        container macsec-secy-if {
          description
            "Configure pm parameters of macsec-secy-if";
          container threshold {
            description
              "Configure threshold on macsec-secy-if parameters";
            leaf in-pkts-untagged {
              type uint32 {
                range "1..4294967295" {
                  description
                    "InPktsUntagged threshold range";
                }
              }
              description
                "Set Threshold for InPktsUntagged";
            }
            leaf in-pkts-no-tag {
              type uint32 {
                range "1..4294967295" {
                  description
                    "InPktsNoTag threshold range";
                }
              }
              description
                "Set Threshold for InPktsNoTag";
            }
            leaf in-pkts-bad-tag {
              type uint32 {
                range "1..4294967295" {
                  description
                    "InPktsBadTag threshold range";
                }
              }
              description
                "Set Threshold for InPktsBadTag";
            }
            leaf in-pkts-unknown-sci {
              type uint32 {
                range "1..4294967295" {
                  description
                    "InPktsUnknownSCI threshold range";
                }
              }
              description
                "Set Threshold for InPktsUnknownSCI";
            }
            leaf in-pkts-no-sci {
              type uint32 {
                range "1..4294967295" {
                  description
                    "InPktsNoSCI threshold range";
                }
              }
              description
                "Set Threshold for InPktsNoSCI";
            }
            leaf in-pkts-overrun {
              type uint32 {
                range "1..4294967295" {
                  description
                    "InPktsOverrun threshold range";
                }
              }
              description
                "Set Threshold for InPktsOverrun";
            }
            leaf in-octets-validated {
              type uint32 {
                range "1..4294967295" {
                  description
                    "InOctetsValidated threshold range";
                }
              }
              description
                "Set Threshold for InOctetsValidated";
            }
            leaf in-octets-decrypted {
              type uint32 {
                range "1..4294967295" {
                  description
                    "InOctetsDecrypted threshold range";
                }
              }
              description
                "Set Threshold for InOctetsDecrypted";
            }
            leaf out-pkts-untagged {
              type uint32 {
                range "1..4294967295" {
                  description
                    "OutPktsUntagged threshold range";
                }
              }
              description
                "Set Threshold for OutPktsUntagged ";
            }
            leaf out-pkts-too-long {
              type uint32 {
                range "1..4294967295" {
                  description
                    "OutPktsTooLong threshold range";
                }
              }
              description
                "Set Threshold for OutPktsTooLong";
            }
            leaf out-octets-encrypted {
              type uint32 {
                range "1..4294967295" {
                  description
                    "OutOctetsEncrypted threshold range";
                }
              }
              description
                "Set Threshold for OutOctetsEncrypted";
            }
            leaf out-octets-protected {
              type uint32 {
                range "1..4294967295" {
                  description
                    "OutOctetsProtected threshold range";
                }
              }
              description
                "Set Threshold for OutOctetsProtected";
            }
          }
          container report {
            description
              "Configure Report for macsec-secy-if Parameters";
            container in-pkts-untagged {
              description
                "set InPktsUntagged TCA reporting status";
              container enable {
                presence "Indicates a enable node is configured.";
                description
                  "Enable TCA reporting";
              }
            }
            container in-pkts-no-tag {
              description
                "set InPktsNoTag TCA reporting status";
              container enable {
                presence "Indicates a enable node is configured.";
                description
                  "Enable TCA reporting";
              }
            }
            container in-pkts-bad-tag {
              description
                "set InPktsBadTag TCA reporting status";
              container enable {
                presence "Indicates a enable node is configured.";
                description
                  "Enable TCA reporting";
              }
            }
            container in-pkts-unknown-sci {
              description
                "set InPktsUnknownSCI TCA reporting status";
              container enable {
                presence "Indicates a enable node is configured.";
                description
                  "Enable TCA reporting";
              }
            }
            container in-pkts-no-sci {
              description
                "set InPktsNoSCI TCA reporting status";
              container enable {
                presence "Indicates a enable node is configured.";
                description
                  "Enable TCA reporting";
              }
            }
            container in-pkts-overrun {
              description
                "set InPktsOverrun TCA reporting status";
              container enable {
                presence "Indicates a enable node is configured.";
                description
                  "Enable TCA reporting";
              }
            }
            container in-octets-validated {
              description
                "set InOctetsValidated TCA reporting status";
              container enable {
                presence "Indicates a enable node is configured.";
                description
                  "Enable TCA reporting";
              }
            }
            container in-octets-decrypted {
              description
                "set InOctetsDecrypted TCA reporting status";
              container enable {
                presence "Indicates a enable node is configured.";
                description
                  "Enable TCA reporting";
              }
            }
            container out-pkts-untagged {
              description
                "set OutPktsUntagged TCA reporting status";
              container enable {
                presence "Indicates a enable node is configured.";
                description
                  "Enable TCA reporting";
              }
            }
            container out-pkts-too-long {
              description
                "set OutPktsTooLong TCA reporting status";
              container enable {
                presence "Indicates a enable node is configured.";
                description
                  "Enable TCA reporting";
              }
            }
            container out-octets-protected {
              description
                "set OutOctetsProtected TCA reporting status";
              container enable {
                presence "Indicates a enable node is configured.";
                description
                  "Enable TCA reporting";
              }
            }
            container out-octets-encrypted {
              description
                "set OutOctetsEncrypted TCA reporting status";
              container enable {
                presence "Indicates a enable node is configured.";
                description
                  "Enable TCA reporting";
              }
            }
          }
        }
        container macsec-ether {
          description
            "configure ether performance monitoring";
          container threshold {
            description
              "Configure threshold on ether parameters";
            leaf rx-pkt {
              type uint32 {
                range "1..4294967295" {
                  description
                    "RX-PKT threshold ";
                }
              }
              description
                "set RX-PKT threshold";
            }
            leaf stat-pkt {
              type uint32 {
                range "1..4294967295" {
                  description
                    "STAT-PKT threshold ";
                }
              }
              description
                "set STAT-PKT threshold";
            }
            leaf octet-stat {
              type uint32 {
                range "1..4294967295" {
                  description
                    "OCTET-STAT threshold ";
                }
              }
              description
                "set OCTET-STAT threshold";
            }
            leaf oversize-pkt {
              type uint32 {
                range "1..4294967295" {
                  description
                    "OVERSIZEPKT-STATS threshold";
                }
              }
              description
                "set OVERSIZE-PKT threshold";
            }
            leaf fcs-err {
              type uint32 {
                range "1..4294967295" {
                  description
                    "FCS-ERR threshold";
                }
              }
              description
                "set FCS-ERR threshold";
            }
            leaf long-frame {
              type uint32 {
                range "1..4294967295" {
                  description
                    "LONG-FRAMES threshold ";
                }
              }
              description
                "set LONG-FRAMES threshold";
            }
            leaf jabber-stats {
              type uint32 {
                range "1..4294967295" {
                  description
                    "JABBER-STATS threshold ";
                }
              }
              description
                "set JABBER-STATS threshold";
            }
            leaf sixty-four-octets {
              type uint32 {
                range "1..4294967295" {
                  description
                    "64-OCTET threshold";
                }
              }
              description
                "set 64-OCTET threshold";
            }
            leaf six5-127-octets {
              type uint32 {
                range "1..4294967295" {
                  description
                    "65-127-OCTET threshold";
                }
              }
              description
                "set 65-127-OCTET threshold";
            }
            leaf one-hundred-twenty-eight-255-octets {
              type uint32 {
                range "1..4294967295" {
                  description
                    "128-255-OCTET threshold ";
                }
              }
              description
                "set 128-255-OCTET threshold";
            }
            leaf two-hundred-fifty-six-511-octets {
              type uint32 {
                range "1..4294967295" {
                  description
                    "256-511-OCTET threshold ";
                }
              }
              description
                "set 256-511-OCTET threshold";
            }
            leaf five-hundred-twelve-1023-octets {
              type uint32 {
                range "1..4294967295" {
                  description
                    "512-1023-OCTET threshold";
                }
              }
              description
                "set 512-1023-OCTET threshold";
            }
            leaf one-thousand-twenty-four-1518-octets {
              type uint32 {
                range "1..4294967295" {
                  description
                    "1024-1518-OCTET threshold";
                }
              }
              description
                "set 1024-1518-OCTET threshold";
            }
            leaf in-64-octets {
              type uint32 {
                range "1..4294967295" {
                  description
                    "IN-64-OCTET threshold";
                }
              }
              description
                "set IN-64-OCTET threshold";
            }
            leaf in-65-127-octets {
              type uint32 {
                range "1..4294967295" {
                  description
                    "IN-65-127-OCTET threshold";
                }
              }
              description
                "set IN-65-127-OCTET threshold";
            }
            leaf in-128-255-octets {
              type uint32 {
                range "1..4294967295" {
                  description
                    "IN-128-255-OCTET threshold ";
                }
              }
              description
                "set 128-255-OCTET threshold";
            }
            leaf in-256-511-octets {
              type uint32 {
                range "1..4294967295" {
                  description
                    "IN-256-511-OCTET threshold ";
                }
              }
              description
                "set IN-256-511-OCTET threshold";
            }
            leaf in-512-1023-octets {
              type uint32 {
                range "1..4294967295" {
                  description
                    "IN-512-1023-OCTET threshold";
                }
              }
              description
                "set IN-512-1023-OCTET threshold";
            }
            leaf in-1024-1518-octets {
              type uint32 {
                range "1..4294967295" {
                  description
                    "IN-1024-1518-OCTET threshold";
                }
              }
              description
                "set IN-1024-1518-OCTET threshold";
            }
            leaf in-drop-other {
              type uint32 {
                range "1..4294967295" {
                  description
                    "IN-DROP-OTHER threshold";
                }
              }
              description
                "set IN_DROP_OTHER threshold";
            }
            leaf in-ucast {
              type uint32 {
                range "1..4294967295" {
                  description
                    "IN-UCAST threshold";
                }
              }
              description
                "set IN-UCAST threshold";
            }
            leaf in-mcast {
              type uint32 {
                range "1..4294967295" {
                  description
                    "IN-MCAST threshold";
                }
              }
              description
                "set IN-MCAST threshold";
            }
            leaf in-bcast {
              type uint32 {
                range "1..4294967295" {
                  description
                    "IN-BCAST threshold";
                }
              }
              description
                "set IN-BCAST threshold";
            }
            leaf in-error-fragments {
              type uint32 {
                range "1..4294967295" {
                  description
                    "IN-ERROR-FRAGMENTS threshold";
                }
              }
              description
                "set IN-ERROR-FRAGMENTS threshold";
            }
            leaf out-ucast {
              type uint32 {
                range "1..4294967295" {
                  description
                    "OUT-UCAST threshold";
                }
              }
              description
                "set OUT-UCAST threshold";
            }
            leaf out-bcast {
              type uint32 {
                range "1..4294967295" {
                  description
                    "OUT-BCAST threshold )";
                }
              }
              description
                "set OUT-BCAST threshold";
            }
            leaf out-mcast {
              type uint32 {
                range "1..4294967295" {
                  description
                    "OUT-MCAST threshold (seconds)";
                }
              }
              description
                "set OUT-MCAST threshold";
            }
            leaf tx-pkt {
              type uint32 {
                range "1..4294967295" {
                  description
                    "TX-PKT threshold";
                }
              }
              description
                "set TX-PKT threshold";
            }
            leaf out-octets {
              type uint32 {
                range "1..4294967295" {
                  description
                    "OUT-OCTET threshold (seconds)";
                }
              }
              description
                "set OUT-OCTET threshold";
            }
            leaf if-in-errors {
              type uint32 {
                range "1..4294967295" {
                  description
                    "IFIN_ERRORS threshold";
                }
              }
              description
                "set IFIN_ERRORS threshold";
            }
            leaf in-good-bytes {
              type uint32 {
                range "1..4294967295" {
                  description
                    "set IN_GOOD_BYTES threshold";
                }
              }
              description
                "set IN_GOOD_BYTES threshold";
            }
            leaf in-good-pkts {
              type uint32 {
                range "1..4294967295" {
                  description
                    "set IN_GOOD_PKTS threshold";
                }
              }
              description
                "set IN_GOOD_PKTS threshold";
            }
            leaf out-good-bytes {
              type uint32 {
                range "1..4294967295" {
                  description
                    "set OUT_GOOD_BYTES threshold";
                }
              }
              description
                "set OUT_GOOD_BYTES threshold";
            }
            leaf out-good-pkts {
              type uint32 {
                range "1..4294967295" {
                  description
                    "set GOOD_PKTS threshold";
                }
              }
              description
                "set THRESH_OUT_GOOD_PKTS threshold";
            }
            leaf rx-util {
              type uint32 {
                range "1..10000" {
                  description
                    "set RX_UTIL threshold (in units of 0.01%)";
                }
              }
              description
                "set THRESH_RX_UTIL threshold(in units of 0.01%)";
            }
            leaf tx-util {
              type uint32 {
                range "1..10000" {
                  description
                    "set TX_UTIL threshold(in units of 0.01%)";
                }
              }
              description
                "set TX_UTIL threshold(in units of 0.01%)";
            }
            leaf if-in-octets {
              type uint32 {
                range "1..4294967295" {
                  description
                    "IFIN_OCTETS threshold";
                }
              }
              description
                "set IFIN_OCTETS threshold";
            }
            leaf ether-stat-multicast-pkt {
              type uint32 {
                range "1..4294967295" {
                  description
                    "ETHER_STAT_MULTICAST_PKT threshold";
                }
              }
              description
                "set ETHER_STAT_MULTICAST_PKT threshold";
            }
            leaf ether-stat-broadcast-pkt {
              type uint32 {
                range "1..4294967295" {
                  description
                    " ETHER_STAT_BROADCAST_PKT threshold";
                }
              }
              description
                " set ETHER_STAT_BROADCAST_PKT threshold";
            }
            leaf ether-stat-undersized-pkt {
              type uint32 {
                range "1..4294967295" {
                  description
                    "ETHER_STAT_UNDERSIZED_PKT threshold";
                }
              }
              description
                "set ETHER_STAT_UNDERSIZED_PKT threshold";
            }
            leaf tx-undersized-pkt {
              type uint32 {
                range "1..4294967295" {
                  description
                    "TX_UNDERSIZED_PKT threshold";
                }
              }
              description
                "set TX_UNDERSIZED_PKT threshold";
            }
            leaf tx-oversized-pkt {
              type uint32 {
                range "1..4294967295" {
                  description
                    "TX_OVERSIZED_PKT threshold";
                }
              }
              description
                "set TX_OVERSIZED_PKT threshold";
            }
            leaf tx-fragments {
              type uint32 {
                range "1..4294967295" {
                  description
                    "TX_FRAGMENTS threshold";
                }
              }
              description
                "set TX_FRAGMENTS threshold";
            }
            leaf tx-jabber {
              type uint32 {
                range "1..4294967295" {
                  description
                    "TX_JABBER threshold";
                }
              }
              description
                "set TX_JABBER threshold";
            }
            leaf tx-bad-fcs {
              type uint32 {
                range "1..4294967295" {
                  description
                    "TX_BAD_FCS threshold";
                }
              }
              description
                "set TX_BAD_FCS threshold";
            }
          }
          container report {
            description
              "set ether TCA reporting status";
            container rx-pkt {
              description
                "set rx-pkt TCA reporting status";
              container enable {
                presence "Indicates a enable node is configured.";
                description
                  "Enable TCA reporting";
              }
            }
            container rx-util {
              description
                "set rx-util TCA reporting status";
              container enable {
                presence "Indicates a enable node is configured.";
                description
                  "Enable TCA reporting";
              }
            }
            container tx-util {
              description
                "set tx-util TCA reporting status";
              container enable {
                presence "Indicates a enable node is configured.";
                description
                  "Enable TCA reporting";
              }
            }
            container stat-pkt {
              description
                "set stat-pkt TCA reporting status";
              container enable {
                presence "Indicates a enable node is configured.";
                description
                  "Enable TCA reporting";
              }
            }
            container octet-stat {
              description
                "set octet-stat TCA reporting status";
              container enable {
                presence "Indicates a enable node is configured.";
                description
                  "Enable TCA reporting";
              }
            }
            container oversize-pkt {
              description
                "set oversize-pkt TCA reporting status";
              container enable {
                presence "Indicates a enable node is configured.";
                description
                  "Enable TCA reporting";
              }
            }
            container fcs-err {
              description
                "set fcs-err TCA reporting status";
              container enable {
                presence "Indicates a enable node is configured.";
                description
                  "Enable TCA reporting";
              }
            }
            container long-frame {
              description
                "set long-frame TCA reporting status";
              container enable {
                presence "Indicates a enable node is configured.";
                description
                  "Enable TCA reporting";
              }
            }
            container jabber-stats {
              description
                "set jabber-stats TCA reporting status";
              container enable {
                presence "Indicates a enable node is configured.";
                description
                  "Enable TCA reporting";
              }
            }
            container _64-octets {
              description
                "set 64-octets TCA reporting status";
              container enable {
                presence "Indicates a enable node is configured.";
                description
                  "Enable TCA reporting";
              }
            }
            container _65-127-octets {
              description
                "set 65-127-octets TCA reporting status";
              container enable {
                presence "Indicates a enable node is configured.";
                description
                  "Enable TCA reporting";
              }
            }
            container _128-255-octets {
              description
                "set 128-255-octets TCA reporting status";
              container enable {
                presence "Indicates a enable node is configured.";
                description
                  "Enable TCA reporting";
              }
            }
            container _256-511-octets {
              description
                "set 256-511-octets TCA reporting status";
              container enable {
                presence "Indicates a enable node is configured.";
                description
                  "Enable TCA reporting";
              }
            }
            container _512-1023-octets {
              description
                "set 512-1023-octets TCA reporting status";
              container enable {
                presence "Indicates a enable node is configured.";
                description
                  "Enable TCA reporting";
              }
            }
            container _1024-1518-octets {
              description
                "set 1024-1518-octets TCA reporting status";
              container enable {
                presence "Indicates a enable node is configured.";
                description
                  "Enable TCA reporting";
              }
            }
            container in-ucast {
              description
                "set in-Ucast TCA reporting status";
              container enable {
                presence "Indicates a enable node is configured.";
                description
                  "Enable TCA reporting";
              }
            }
            container in-mcast {
              description
                "set in-Mcast TCA reporting status";
              container enable {
                presence "Indicates a enable node is configured.";
                description
                  "Enable TCA reporting";
              }
            }
            container in-bcast {
              description
                "set in-Bcast TCA reporting status";
              container enable {
                presence "Indicates a enable node is configured.";
                description
                  "Enable TCA reporting";
              }
            }
            container out-ucast {
              description
                "set es-pm TCA reporting status";
              container enable {
                presence "Indicates a enable node is configured.";
                description
                  "Enable TCA reporting";
              }
            }
            container out-mcast {
              description
                "set esr-pm TCA reporting status";
              container enable {
                presence "Indicates a enable node is configured.";
                description
                  "Enable TCA reporting";
              }
            }
            container out-bcast {
              description
                "set es-sm TCA reporting status";
              container enable {
                presence "Indicates a enable node is configured.";
                description
                  "Enable TCA reporting";
              }
            }
            container tx-pkt {
              description
                "set esr-sm TCA reporting status";
              container enable {
                presence "Indicates a enable node is configured.";
                description
                  "Enable TCA reporting";
              }
            }
            container if-in-errors {
              description
                "set ifIn_errors TCA reporting status";
              container enable {
                presence "Indicates a enable node is configured.";
                description
                  "Enable TCA reporting";
              }
            }
            container if-in-octets {
              description
                "set ifIn_Octets  TCA reporting status";
              container enable {
                presence "Indicates a enable node is configured.";
                description
                  "Enable TCA reporting";
              }
            }
            container ether-stat-multicast-pkt {
              description
                "set ether_stat_multicast_pkt TCA reporting status";
              container enable {
                presence "Indicates a enable node is configured.";
                description
                  "Enable TCA reporting";
              }
            }
            container ether-stat-broadcast-pkt {
              description
                "set ether_stat_broadcast_pkt TCA reporting status";
              container enable {
                presence "Indicates a enable node is configured.";
                description
                  "Enable TCA reporting";
              }
            }
            container ether-stat-undersized-pkt {
              description
                "set ether_stat_undersized_pkt  TCA reporting status";
              container enable {
                presence "Indicates a enable node is configured.";
                description
                  "Enable TCA reporting";
              }
            }
            container out-octets {
              description
                "set out-octets TCA reporting status";
              container enable {
                presence "Indicates a enable node is configured.";
                description
                  "Enable TCA reporting";
              }
            }
            container in-good-bytes {
              description
                "set in-good-bytes TCA reporting status";
              container enable {
                presence "Indicates a enable node is configured.";
                description
                  "Enable TCA reporting";
              }
            }
            container in-good-pkts {
              description
                "set in-good-pkts TCA reporting status";
              container enable {
                presence "Indicates a enable node is configured.";
                description
                  "Enable TCA reporting";
              }
            }
            container in-drop-other {
              description
                "set in-drop-other TCA reporting status";
              container enable {
                presence "Indicates a enable node is configured.";
                description
                  "Enable TCA reporting";
              }
            }
            container out-good-bytes {
              description
                "set out-good-bytes TCA reporting status";
              container enable {
                presence "Indicates a enable node is configured.";
                description
                  "Enable TCA reporting";
              }
            }
            container out-good-pkts {
              description
                "set out-good-pkts TCA reporting status";
              container enable {
                presence "Indicates a enable node is configured.";
                description
                  "Enable TCA reporting";
              }
            }
            container in-error-fragments {
              description
                "set in-error-fragments TCA reporting status";
              container enable {
                presence "Indicates a enable node is configured.";
                description
                  "Enable TCA reporting";
              }
            }
            container in-64-octets {
              description
                "set in-64-octets TCA reporting status";
              container enable {
                presence "Indicates a enable node is configured.";
                description
                  "Enable TCA reporting";
              }
            }
            container in-65-127-octets {
              description
                "set in-65-127-octets TCA reporting status";
              container enable {
                presence "Indicates a enable node is configured.";
                description
                  "Enable TCA reporting";
              }
            }
            container in-128-255-octets {
              description
                "set in-128-255-octets TCA reporting status";
              container enable {
                presence "Indicates a enable node is configured.";
                description
                  "Enable TCA reporting";
              }
            }
            container in-256-511-octets {
              description
                "set in-256-511-octets TCA reporting status";
              container enable {
                presence "Indicates a enable node is configured.";
                description
                  "Enable TCA reporting";
              }
            }
            container in-512-1023-octets {
              description
                "set in-512-1023-octets TCA reporting status";
              container enable {
                presence "Indicates a enable node is configured.";
                description
                  "Enable TCA reporting";
              }
            }
            container in-1024-1518-octets {
              description
                "set in-1024-1518-octets TCA reporting status";
              container enable {
                presence "Indicates a enable node is configured.";
                description
                  "Enable TCA reporting";
              }
            }
            container tx-undersized-pkt {
              description
                "set tx_undersized_pkt  TCA reporting status";
              container enable {
                presence "Indicates a enable node is configured.";
                description
                  "Enable TCA reporting";
              }
            }
            container tx-oversized-pkt {
              description
                "set tx_oversized_pkt  TCA reporting status";
              container enable {
                presence "Indicates a enable node is configured.";
                description
                  "Enable TCA reporting";
              }
            }
            container tx-fragments {
              description
                "set tx_fragments  TCA reporting status";
              container enable {
                presence "Indicates a enable node is configured.";
                description
                  "Enable TCA reporting";
              }
            }
            container tx-jabber {
              description
                "set tx_jabber  TCA reporting status";
              container enable {
                presence "Indicates a enable node is configured.";
                description
                  "Enable TCA reporting";
              }
            }
            container tx-bad-fcs {
              description
                "set tx_bad_fcs  TCA reporting status";
              container enable {
                presence "Indicates a enable node is configured.";
                description
                  "Enable TCA reporting";
              }
            }
          }
        }
      }
    }
  }

  augment "/a1:interfaces/a1:interface" {
    uses IF-BODY;
  }
  augment "/a1:interfaces/a1:interface-preconfigure" {
    uses IF-BODY;
  }
  augment "/a1:interfaces/a1:controller" {
    uses CONT-BODY;
  }
  augment "/a1:interfaces/a1:controller-preconfigure" {
    uses CONT-BODY;
  }
}
