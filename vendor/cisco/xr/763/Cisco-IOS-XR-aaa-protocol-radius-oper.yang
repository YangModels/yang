module Cisco-IOS-XR-aaa-protocol-radius-oper {
  namespace "http://cisco.com/ns/yang/Cisco-IOS-XR-aaa-protocol-radius-oper";
  prefix aaa-protocol-radius-oper;

  import ietf-inet-types {
    prefix inet;
  }
  import Cisco-IOS-XR-types {
    prefix xr;
  }
  import cisco-semver {
    prefix semver;
  }
  import Cisco-IOS-XR-aaa-locald-oper {
    prefix a1;
  }
  include Cisco-IOS-XR-aaa-protocol-radius-oper-sub2 {
    revision-date 2021-02-23;
  }
  include Cisco-IOS-XR-aaa-protocol-radius-oper-sub1 {
    revision-date 2021-02-23;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-protocol-radius package operational data.
     
     This module contains definitions
     for the following management objects:
       radius: RADIUS operational data
     
     This YANG module augments the
       Cisco-IOS-XR-aaa-locald-oper
     module with state data.
     
     Copyright (c) 2013-2021 by Cisco Systems, Inc.
     All rights reserved.";

  revision 2021-02-23 {
    description
      "Adding yang support for coa";
    semver:module-version "1.1.0";
  }
  revision 2019-04-05 {
    description
      "Establish semantic version baseline.";
    semver:module-version "1.0.1";
  }
  revision 2017-11-13 {
    description
      "Adding yang support for new cli.";
  }
  revision 2017-05-01 {
    description
      "Fixing backward compatibility error in module.";
  }
  revision 2015-11-09 {
    description
      "IOS XR 6.0 revision.";
  }

  typedef Radius-port-range {
    type uint32 {
      range "1..65535";
    }
    description
      "Radius port range";
  }

  typedef Aaa-radius-port-range {
    type uint32 {
      range "1..65535";
    }
    description
      "Aaa radius port range";
  }

  augment "/a1:aaa" {
    description
      "This augment extends the operational data of
       'Cisco-IOS-XR-aaa-locald-oper'";
    container radius {
      description
        "RADIUS operational data";
      container servers {
        description
          "List of RADIUS servers configured";
        list server {
          description
            "RADIUS Server";
          leaf ip-address {
            type inet:ip-address-no-zone;
            description
              "IP address of RADIUS server";
          }
          leaf auth-port-number {
            type Aaa-radius-port-range;
            description
              "Authentication Port number (standard port
               1645)";
          }
          leaf acct-port-number {
            type Aaa-radius-port-range;
            description
              "Accounting Port number (standard port 1646)";
          }
          uses RADIUS-SERVERBAG;
        }
      }
      container radius-source-interface {
        description
          "RADIUS source interfaces";
        uses SOURCE-INTERFACES;
      }
      container global {
        description
          "RADIUS Client Information";
        uses RADIUS-CLIENTBAG;
      }
    }
  }
  container radius {
    config false;
    description
      "RADIUS operational data";
    container nodes {
      description
        "Contains all the nodes";
      list node {
        key "node-name";
        description
          "RADIUS operational data for a particular node";
        container client {
          description
            "RADIUS client data";
          uses RADIUS-CLIENT-XML;
        }
        container dead-criteria {
          description
            "RADIUS dead criteria information";
          container hosts {
            description
              "RADIUS server dead criteria host table";
            list host {
              description
                "RADIUS Server";
              leaf ip-address {
                type inet:ip-address-no-zone;
                description
                  "IP address of RADIUS server";
              }
              leaf auth-port-number {
                type Radius-port-range;
                description
                  "Authentication Port number (standard port
                   1645)";
              }
              leaf acct-port-number {
                type Radius-port-range;
                description
                  "Accounting Port number (standard port 1646)";
              }
              uses RADIUS-DEAD-CRITERIA;
            }
          }
        }
        container servergroups {
          description
            "RADIUS server group table";
          list servergroup {
            description
              "RADIUS server group information";
            leaf server-group-name {
              type xr:Cisco-ios-xr-string;
              description
                "Server group name";
            }
            leaf server-ipaddress {
              type xr:Cisco-ios-xr-string;
              description
                "IP address of RADIUS server";
            }
            leaf auth-port-number {
              type Radius-port-range;
              description
                "Authentication Port number (standard port
                 1645)";
            }
            leaf acct-port-number {
              type Radius-port-range;
              description
                "Accounting Port number (standard port 1646)";
            }
            uses RADIUS-SERVER-GROUP-DATA;
          }
        }
        container dynamic-author-clients {
          description
            "Dynamic authorization client data";
          list dynamic-author-client {
            description
              "Dynamic authorization client data";
            leaf coa-client-ipaddress {
              type xr:Cisco-ios-xr-string;
              description
                "IP address of Coa Client server";
            }
            leaf vrf {
              type xr:Cisco-ios-xr-string;
              description
                "vrf name";
            }
            uses RADIUS-DYNAMIC-CLIENT-DATA;
          }
        }
        container authentication {
          description
            "RADIUS authentication data";
          uses RADIUS-SERVER-AUTHENTICATION;
        }
        container accounting {
          description
            "RADIUS accounting data";
          uses RADIUS-SERVER-ACCOUNTING;
        }
        container dynamic-authorization-clients {
          description
            "Dynamic authorization client data";
          uses RADIUS-DYNAMIC-CLIENT;
        }
        container server-groups {
          description
            "RADIUS server group table";
          list server-group {
            key "server-group-name";
            description
              "RADIUS server group data";
            leaf server-group-name {
              type xr:Cisco-ios-xr-string;
              description
                "Group name";
            }
            uses RADIUS-GROUPS-SERVERS;
          }
        }
        container dynamic-authorization {
          description
            "Dynamic authorization data";
          uses RADIUS-DYNAMIC-SERVER;
        }
        leaf node-name {
          type xr:Node-id;
          description
            "Node name";
        }
      }
    }
  }
}
