module Cisco-IOS-XR-um-event-manager-cfg {
  namespace "http://cisco.com/ns/yang/Cisco-IOS-XR-um-event-manager-cfg";
  prefix um-event-manager-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR event-manager package configuration.
     
     This YANG module augments the
     modules with configuration data.
     
     Copyright (c) 2021-2022 by Cisco Systems, Inc.
     All rights reserved.";

  revision 2022-10-12 {
    description
      "Moved pam-agent under event manager";
  }
  revision 2022-07-15 {
    description
      "Added pam-agent node under event manager";
  }
  revision 2021-08-10 {
    description
      "Initial release";
  }

  container event {
    description
      "Event related commands";
    container manager {
      description
        "Event Manager configuration commands";
      leaf refresh-time {
        type uint32 {
          range "10..4294967295" {
            description
              "A valid positive integer greater than 9";
          }
        }
        description
          "Set refresh time (in seconds) for policy username's AAA taskmap";
      }
      container directory {
        description
          "Set Embedded Event Manager directory information";
        container user {
          description
            "Set Embedded Event Manager user directory information";
          leaf policy {
            type string {
              length "1..800" {
                description
                  "Path of the Embedded Event Manager user policy directory";
              }
            }
            description
              "Set Embedded Event Manager user policy directory";
          }
          leaf library {
            type string {
              length "1..800" {
                description
                  "Path of the Embedded Event Manager user library directory";
              }
            }
            description
              "Set Embedded Event Manager user library directory";
          }
        }
      }
      container scheduler {
        description
          "Set Embedded Event Manager scheduler options";
        container suspend {
          presence "Indicates a suspend node is configured.";
          description
            "Suspend Embedded Event Manager policy scheduling";
        }
        container script {
          description
            "TCL script type internal data for EEM component";
          container thread {
            description
              "Internal thread data for EEM component";
            container class {
              description
                "Internal class data for EEM component";
              container default {
                description
                  "default class type";
                leaf number {
                  type uint32 {
                    range "1..5" {
                      description
                        "value of the threads to schedule";
                    }
                  }
                  description
                    "Number of scheduler threads";
                }
              }
            }
          }
        }
      }
      container environment {
        description
          "Set an Embedded Event Manager global variable for policies";
        list global-variable {
          key "global-variable-name";
          description
            "Name of the global variable";
          leaf global-variable-name {
            type xr:Cisco-ios-xr-string {
              length "1..800" {
                description
                  "Name of the global variable";
              }
            }
            description
              "Name of the global variable";
          }
          leaf value {
            type string {
              length "1..800" {
                description
                  "Value of the global variable";
              }
            }
            description
              "Value of the global variable";
          }
        }
      }
      container policy {
        description
          "Register an Event Manager policy";
        list policy-file {
          key "policy-file-name";
          description
            "Name of the policy file";
          leaf policy-file-name {
            type xr:Cisco-ios-xr-string {
              length "1..800" {
                description
                  "Name of the policy file";
              }
            }
            description
              "Name of the policy file";
          }
          leaf username {
            type xr:Cisco-ios-xr-string {
              length "1..800" {
                description
                  "A Configured username";
              }
            }
            description
              "Username under whom this policy will execute";
          }
          container persist-time {
            description
              "Time of validity (in seconds) for cached AAA taskmap of username (default is 3600)";
            leaf value {
              type uint32 {
                range "0..4294967294" {
                  description
                    "Integer value for this policy's persist-time";
                }
              }
              must "not(../infinite)";
              description
                "Integer value for this policy's persist-time";
            }
            container infinite {
              must "not(../value)";
              presence "Indicates a infinite node is configured.";
              description
                "Cached AAA taskmap of username is always treated valid";
            }
          }
          container type {
            description
              "The Event Manager type of this policy";
            container system {
              must "not(../user)";
              presence "Indicates a system node is configured.";
              description
                "Event Manager system policy";
            }
            container user {
              must "not(../system)";
              presence "Indicates a user node is configured.";
              description
                "Event Manager user policy";
            }
          }
          container checksum {
            description
              "Specify Embedded Event Manager policy checksum";
            leaf md5 {
              type xr:Cisco-ios-xr-string {
                length "1..800" {
                  description
                    "MD5 checksum";
                }
              }
              must "not(../sha-1)";
              description
                "Use MD5 checksum";
            }
            leaf sha-1 {
              type xr:Cisco-ios-xr-string {
                length "1..800" {
                  description
                    "SHA-1 checksum";
                }
              }
              must "not(../md5)";
              description
                "Use SHA-1 checksum";
            }
          }
          container secure-mode {
            description
              "Specify Embedded Event Manager policy security policy";
            container trust {
              presence "Indicates a trust node is configured.";
              description
                "Requires Trust Signature";
            }
            container cisco {
              description
                "Requires Cisco Digital Signature";
              container rsa-2048 {
                presence "Indicates a rsa-2048 node is configured.";
                description
                  "Requires Cisco Digital Signature";
              }
            }
          }
        }
      }
      container pam-agent {
        description
          "Embedded Event Manager pam-agent";
        container run {
          presence "Indicates a run node is configured.";
          description
            "Start Embedded Event Manager pam-agent";
        }
      }
    }
  }
}
