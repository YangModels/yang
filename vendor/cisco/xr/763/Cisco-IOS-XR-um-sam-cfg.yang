module Cisco-IOS-XR-um-sam-cfg {
  namespace "http://cisco.com/ns/yang/Cisco-IOS-XR-um-sam-cfg";
  prefix um-sam-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sam package configuration.
     
     This YANG module augments the
     modules with configuration data.
     
     Copyright (c) 2020 by Cisco Systems, Inc.
     All rights reserved.";

  revision 2020-04-24 {
    description
      "Initial release";
    semver:module-version "1.0.0";
  }

  container sam {
    description
      "Software Authentication Config";
    leaf prompt-interval {
      type uint32 {
        range "0..300" {
          description
            "Prompt time from 0 - 300 seconds";
        }
      }
      description
        "Set prompt interval at reboot time";
    }
    container proceed {
      must "not(../terminate)";
      presence "Indicates a proceed node is configured.";
      description
        "To respond YES to the SAM prompt";
    }
    container terminate {
      must "not(../proceed)";
      presence "Indicates a terminate node is configured.";
      description
        "To respond NO to the SAM prompt";
    }
  }
}
