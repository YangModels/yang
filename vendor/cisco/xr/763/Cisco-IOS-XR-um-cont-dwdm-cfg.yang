module Cisco-IOS-XR-um-cont-dwdm-cfg {
  namespace "http://cisco.com/ns/yang/Cisco-IOS-XR-um-cont-dwdm-cfg";
  prefix um-cont-dwdm-cfg;

  import Cisco-IOS-XR-types {
    prefix xr;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-dwdm package configuration.
     
     This YANG module augments the
     modules with configuration data.
     
     Copyright (c) 2020-2021 by Cisco Systems, Inc.
     All rights reserved.";

  revision 2021-02-02 {
    description
      "Initial release";
    semver:module-version "1.0.0";
  }

  feature dwdm_cont {
    description
      "dwdm controller";
  }

  grouping IF-BODY {
    container maintenance {
      description
        "Configure maintenance embargo flag on the given interface";
      container disable {
        presence "Indicates a disable node is configured.";
        description
          "Configure maintenance embargo flag on the given interface";
      }
    }
  }

  grouping CONT-BODY {
    container admin-state {
      description
        "Configure the transport admin state of the controller: in-service, out-of-service or maintenance";
      container in-service {
        must
          "not(../out-of-service or ../maintenance
           or ../in-service-config-allowed)";
        presence "Indicates a in-service node is configured.";
        description
          "change the admin-state to In-service (IS)";
      }
      container out-of-service {
        must
          "not(../in-service or ../maintenance
           or ../in-service-config-allowed)";
        presence "Indicates a out-of-service node is configured.";
        description
          "change the admin-state to Out-of-service (OOS)";
      }
      container maintenance {
        must
          "not(../in-service or ../out-of-service
           or ../in-service-config-allowed)";
        presence "Indicates a maintenance node is configured.";
        description
          "change the admin-state to Out-of-service-Maintenance (OOS-MT)";
      }
      container in-service-config-allowed {
        must
          "not(../in-service or ../out-of-service
           or ../maintenance)";
        presence "Indicates a in-service-config-allowed node is configured.";
        description
          "change the admin-state to In-service-config-allowed (IS-CFG)";
      }
    }
    container wavelength {
      description
        "Configure ITU Channel, Wavelength and Frequency";
      container fifty-ghz-grid {
        description
          "Configure Wavelength / Frequency / Channel Number";
        leaf itu-channel-number {
          type uint32 {
            range "1..100" {
              description
                "Select an ITU channel number; C Band: 1-100";
            }
          }
          must
            "not(../frequency or ../update or
                 ../../one-hundred-mhz-grid/frequency)";
          description
            "Select an ITU channel number; C Band: 1-100";
        }
        leaf frequency {
          type uint32 {
            range "19115..19610" {
              description
                "Enter 5-digit Frequency data; e.g. 19580 for 195.8 THz";
            }
          }
          must
            "not(../itu-channel-number or ../update or
                 ../../one-hundred-mhz-grid/frequency)";
          description
            "Configure Frequency and Map to ITU Channel";
        }
        leaf update {
          type uint32 {
            range "1528773..1568362" {
              description
                "Enter 7-digit Wavelength data; e.g. 1532290 for 1532.29 nm";
            }
          }
          must
            "not(../itu-channel-number or ../frequency or
                 ../../one-hundred-mhz-grid/frequency)";
          description
            "Configure Wavelength and Map to ITU Channel";
        }
      }
      container one-hundred-mhz-grid {
        description
          "Specify frequency directly instead of wave channel numbers";
        leaf frequency {
          type xr:Cisco-ios-xr-string {
            length "1..8" {
              description
                "Enter Frequency Data in THz (e.g. 195.7314)";
            }
          }
          must
            "not(../../fifty-ghz-grid/itu-channel-number or
                 ../../fifty-ghz-grid/frequency or
                 ../../fifty-ghz-grid/update)";
          description
            "Configure frequency in steps of 100MHz";
        }
      }
    }
    leaf transmit-power {
      type int32 {
        range "-190..10" {
          description
            "Select power level (in units of 0.1dBm)";
        }
      }
      description
        "Configure transponder transmit power ";
    }
    leaf rx-los-threshold {
      type int32 {
        range "-350..50" {
          description
            "Select power level (in units of 0.1dBm)";
        }
      }
      description
        "Configure transponder receive power LOS threshold";
    }
    leaf loopback {
      type enumeration {
        enum "line" {
          value 1;
          description
            "Select line loopback mode";
        }
        enum "internal" {
          value 2;
          description
            "Select internal loopback mode";
        }
      }
      description
        "Configure loopback mode ";
    }
    container g709 {
      description
        "Configure G709 parameters";
      container disable {
        must "not(../enable)";
        presence "Indicates a disable node is configured.";
        description
          "Disable G709 function";
      }
      container enable {
        must "not(../disable)";
        presence "Indicates a enable node is configured.";
        description
          "Enable G709 function";
      }
      leaf framing {
        type enumeration {
          enum "opu1e" {
            value 1;
            description
              "opu1e framing mode";
          }
          enum "opu2e" {
            value 2;
            description
              "opu2e framing mode";
          }
        }
        description
          "Configure Framing mode";
      }
      container prbs {
        description
          "Enable PRBS with specifc mode and pattern ";
        leaf mode {
          type enumeration {
            enum "source" {
              value 0;
              description
                "Select Source mode ";
            }
            enum "sink" {
              value 1;
              description
                "Select Sink mode ";
            }
            enum "source-sink" {
              value 2;
              description
                "Select Source-sink mode ";
            }
          }
          must "../pattern";
          description
            "Configure PRBS mode";
        }
        leaf pattern {
          type enumeration {
            enum "null" {
              value 1;
              description
                "Select NULL Pattern ";
            }
            enum "pn11" {
              value 2;
              description
                "Select PN11 Pattern ";
            }
            enum "pn23" {
              value 3;
              description
                "Select PN23 Pattern ";
            }
            enum "pn31" {
              value 4;
              description
                "Select PN31 Pattern ";
            }
          }
          must "../mode";
          description
            "Configure PRBS pattern";
        }
      }
      container fec {
        description
          "Configure FEC mode";
        container standard {
          must
            "not(../high-gain-hd-fec or ../high-gain-sd-fec
             or ../high-gain-multivendor-hd-fec or ../ci-bch
             or ../long-haul-hd-fec or ../long-haul-sd-fec
             or ../disable or ../one5sdfecde
             or ../one5sdfec)";
          presence "Indicates a standard node is configured.";
          description
            "Standard FEC mode";
        }
        container enhanced {
          presence "Indicates a enhanced node is configured.";
          description
            "Enhanced FEC mode";
          container i-4 {
            must "not(../i-7)";
            presence "Indicates a i-4 node is configured.";
            description
              "efec i.4";
          }
          container i-7 {
            must "not(../i-4)";
            presence "Indicates a i-7 node is configured.";
            description
              "efec i.7";
          }
        }
        container high-gain-hd-fec {
          must
            "not(../standard or ../high-gain-sd-fec
             or ../high-gain-multivendor-hd-fec or ../ci-bch
             or ../long-haul-hd-fec or ../long-haul-sd-fec
             or ../disable or ../one5sdfecde
             or ../one5sdfec)";
          presence "Indicates a high-gain-hd-fec node is configured.";
          description
            "7% HD FEC (Staircase FEC)";
        }
        container high-gain-sd-fec {
          must
            "not(../standard or ../high-gain-hd-fec
             or ../high-gain-multivendor-hd-fec or ../ci-bch
             or ../long-haul-hd-fec or ../long-haul-sd-fec
             or ../disable or ../one5sdfecde
             or ../one5sdfec)";
          presence "Indicates a high-gain-sd-fec node is configured.";
          description
            "7% CISCO SD FEC (Soft-Decision FEC)";
        }
        container high-gain-multivendor-hd-fec {
          must
            "not(../standard or ../high-gain-hd-fec
             or ../high-gain-sd-fec or ../ci-bch
             or ../long-haul-hd-fec or ../long-haul-sd-fec
             or ../disable or ../one5sdfecde
             or ../one5sdfec)";
          presence "Indicates a high-gain-multivendor-hd-fec node is configured.";
          description
            "7% HD FEC (Staircase FEC) Multivendor Interoperable";
        }
        container ci-bch {
          must
            "not(../standard or ../high-gain-hd-fec
             or ../high-gain-sd-fec or ../high-gain-multivendor-hd-fec
             or ../long-haul-hd-fec or ../long-haul-sd-fec
             or ../disable or ../one5sdfecde
             or ../one5sdfec)";
          presence "Indicates a ci-bch node is configured.";
          description
            "Continuously Interleaved BCH FEC";
        }
        container long-haul-hd-fec {
          must
            "not(../standard or ../high-gain-hd-fec
             or ../high-gain-sd-fec or ../high-gain-multivendor-hd-fec
             or ../ci-bch or ../long-haul-sd-fec
             or ../disable or ../one5sdfecde
             or ../one5sdfec)";
          presence "Indicates a long-haul-hd-fec node is configured.";
          description
            "20% HD FEC (Staircase FEC)";
        }
        container long-haul-sd-fec {
          must
            "not(../standard or ../high-gain-hd-fec
             or ../high-gain-sd-fec or ../high-gain-multivendor-hd-fec
             or ../ci-bch or ../long-haul-hd-fec
             or ../disable or ../one5sdfecde
             or ../one5sdfec)";
          presence "Indicates a long-haul-sd-fec node is configured.";
          description
            "20% CISCO SD FEC (Soft-Decision FEC)";
        }
        container disable {
          must
            "not(../standard or ../high-gain-hd-fec
             or ../high-gain-sd-fec or ../high-gain-multivendor-hd-fec
             or ../ci-bch or ../long-haul-hd-fec
             or ../long-haul-sd-fec or ../one5sdfecde
             or ../one5sdfec)";
          presence "Indicates a disable node is configured.";
          description
            "Disable FEC";
        }
        container one5sdfecde {
          must
            "not(../standard or ../high-gain-hd-fec
             or ../high-gain-sd-fec or ../high-gain-multivendor-hd-fec
             or ../ci-bch or ../long-haul-hd-fec
             or ../long-haul-sd-fec or ../disable
             or ../one5sdfec)";
          presence "Indicates a one5sdfecde node is configured.";
          description
            "15%-SD Forward Error Correction with Diff";
        }
        container one5sdfec {
          must
            "not(../standard or ../high-gain-hd-fec
             or ../high-gain-sd-fec or ../high-gain-multivendor-hd-fec
             or ../ci-bch or ../long-haul-hd-fec
             or ../long-haul-sd-fec or ../disable
             or ../one5sdfecde)";
          presence "Indicates a one5sdfec node is configured.";
          description
            "15%-SD Forward Error Correction";
        }
      }
      container bdi-to-client-gais {
        presence "Indicates a bdi-to-client-gais node is configured.";
        description
          "Enable gais insertion";
      }
      container tti-processing {
        presence "Indicates a tti-processing node is configured.";
        description
          "Enable Trail Trace Identifier processing";
      }
      container tim-to-client-gais {
        presence "Indicates a tim-to-client-gais node is configured.";
        description
          "Enable Generic AIS insertion for Trace Identifier Mismatch alarm";
      }
      container otu {
        description
          "Configure OTU parameters";
        container reports {
          description
            "Configure OTU alarm reporting";
          list report {
            key "report-id";
            description
              "Configure OTU alarm reporting";
            leaf report-id {
              type enumeration {
                enum "los" {
                  value 0;
                  description
                    "Set Loss of Signal reporting status";
                }
                enum "lof" {
                  value 1;
                  description
                    "Set OTU Loss of Frame reporting status";
                }
                enum "lom" {
                  value 2;
                  description
                    "Set Loss of Multiple Frame reporting status";
                }
                enum "iae" {
                  value 6;
                  description
                    "Set Incoming  Alignment Error reporting status";
                }
                enum "bdi" {
                  value 7;
                  description
                    "Set Backward Defect Indication reporting status";
                }
                enum "tim" {
                  value 8;
                  description
                    "Set Trace Identifier Mismatch reporting status";
                }
                enum "sf-ber" {
                  value 10;
                  description
                    "Set SM BER in excess of SF threshold reporting status";
                }
                enum "sd-ber" {
                  value 11;
                  description
                    "Set SM BER in excess of SD threshold reporting status";
                }
                enum "prefec-sd-ber" {
                  value 31;
                  description
                    "Set SM BER in excess of SD threshold reporting status";
                }
                enum "prefec-sf-ber" {
                  value 32;
                  description
                    "Set SM BER in excess of SF threshold reporting status";
                }
              }
              description
                "Configure OTU alarm reporting";
            }
            container disable {
              presence "Indicates a disable node is configured.";
              description
                "";
            }
          }
        }
        container overhead {
          description
            "Configure OTU overhead";
          container tti {
            description
              "Configure OTU Trail Trace Identifier buffer";
            container sent {
              description
                "Set transmit TTI";
              leaf ascii {
                type string {
                  length "1..64" {
                    description
                      "ASCII text (Max 64 characters)";
                  }
                }
                description
                  "Enter ASCII string";
              }
              leaf hex {
                type string {
                  length "1..128" {
                    description
                      "Hex nibbles (Max 128- The string length should be an even number)";
                  }
                }
                description
                  "Enter hex string- Length should be even number";
              }
              container otn-std {
                description
                  "Configure tti in otn standard defined fields";
                leaf sapi {
                  type string {
                    length "1..15" {
                      description
                        "Enter SAPI text (Max Length 15 Characters)";
                    }
                  }
                  description
                    "Enter Source Access Point Identifier field 1-15";
                }
                leaf dapi {
                  type string {
                    length "1..15" {
                      description
                        "Enter DAPI text (Max Length 15 Characters)";
                    }
                  }
                  description
                    "Enter Destination Access Point Identifier field 1-15";
                }
                leaf operator-specific {
                  type string {
                    length "1..32" {
                      description
                        "Enter Operator Specific text (Max Length 32 Characters)";
                    }
                  }
                  description
                    "Enter Operator Specific field";
                }
              }
            }
            container expected {
              description
                "Set expected TTI";
              leaf ascii {
                type string {
                  length "1..64" {
                    description
                      "ASCII text (Max 64 characters)";
                  }
                }
                description
                  "Enter ASCII string";
              }
              leaf hex {
                type string {
                  length "1..128" {
                    description
                      "Hex nibbles (Max 128- The string length should be an even number)";
                  }
                }
                description
                  "Enter hex string- Length should be even number";
              }
              container otn-std {
                description
                  "Configure tti in otn standard defined fields";
                leaf sapi {
                  type string {
                    length "1..15" {
                      description
                        "Enter SAPI text (Max Length 15 Characters)";
                    }
                  }
                  description
                    "Enter Source Access Point Identifier field 1-15";
                }
                leaf dapi {
                  type string {
                    length "1..15" {
                      description
                        "Enter DAPI text (Max Length 15 Characters)";
                    }
                  }
                  description
                    "Enter Destination Access Point Identifier field 1-15";
                }
                leaf operator-specific {
                  type string {
                    length "1..32" {
                      description
                        "Enter Operator Specific text (Max Length 32 Characters)";
                    }
                  }
                  description
                    "Enter Operator Specific field";
                }
              }
            }
          }
        }
        container threshold {
          description
            "Configure OTU threshold value";
          leaf sd-ber {
            type uint32 {
              range "1..9" {
                description
                  "Bit error rate (10 to the minus n) (default 6)";
              }
            }
            description
              "Set Signal Degrade BER threshold";
          }
          leaf sf-ber {
            type uint32 {
              range "1..9" {
                description
                  "Bit error rate (10 to the minus n) (default 3)";
              }
            }
            description
              "Set Signal Failure BER threshold";
          }
          leaf prefec-sd-ber {
            type uint32 {
              range "2..9" {
                description
                  "Bit error rate (10 to the minus n) (default 6)";
              }
            }
            description
              "Set PreFec Signal Degrate BER threshold";
          }
          leaf prefec-sf-ber {
            type uint32 {
              range "2..9" {
                description
                  "Bit error rate (10 to the minus n) (default 4)";
              }
            }
            description
              "Set PreFec Signal fail BER threshold";
          }
        }
      }
      container odu {
        description
          "Configure ODU parameters";
        container reports {
          description
            "Configure ODU alarm reporting";
          list report {
            key "report-id";
            description
              "Configure ODU alarm reporting";
            leaf report-id {
              type enumeration {
                enum "oci" {
                  value 14;
                  description
                    "Set Open Connection Indication reporting status";
                }
                enum "ais" {
                  value 15;
                  description
                    "Set Alarm Indication Signal reporting status";
                }
                enum "lck" {
                  value 16;
                  description
                    "Set Upstream Connection Locked reporting status";
                }
                enum "bdi" {
                  value 17;
                  description
                    "Set Backward Defect Indication reporting status";
                }
                enum "sf-ber" {
                  value 20;
                  description
                    "Set PM BER in excess of SF threshold reporting status";
                }
                enum "sd-ber" {
                  value 21;
                  description
                    "Set PM BER in excess of SD threshold reporting status";
                }
                enum "ptim" {
                  value 22;
                  description
                    "Set Payload Type Identifier Mismatch reporting status";
                }
                enum "tim" {
                  value 23;
                  description
                    "Set Trace Identifier Mismatch reporting status";
                }
              }
              description
                "Configure ODU alarm reporting";
            }
            container disable {
              presence "Indicates a disable node is configured.";
              description
                "";
            }
          }
        }
        container overhead {
          description
            "Configure ODU overhead";
          container tti {
            description
              "Configure ODU Trail Trace Identifier buffer";
            container sent {
              description
                "Set transmit TTI";
              leaf ascii {
                type string {
                  length "1..64" {
                    description
                      "ASCII text (Max 64 characters)";
                  }
                }
                description
                  "Enter ASCII string";
              }
              leaf hex {
                type string {
                  length "1..128" {
                    description
                      "Hex nibbles (Max 128- The string length should be an even number)";
                  }
                }
                description
                  "Enter hex string- Length should be even number";
              }
              container otn-std {
                description
                  "Configure tti in otn standard defined fields";
                leaf sapi {
                  type string {
                    length "1..15" {
                      description
                        "Enter SAPI text (Max Length 15 Characters)";
                    }
                  }
                  description
                    "Enter Source Access Point Identifier field 1-15";
                }
                leaf dapi {
                  type string {
                    length "1..15" {
                      description
                        "Enter DAPI text (Max Length 15 Characters)";
                    }
                  }
                  description
                    "Enter Destination Access Point Identifier field 1-15";
                }
                leaf operator-specific {
                  type string {
                    length "1..32" {
                      description
                        "Enter Operator Specific text (Max Length 32 Characters)";
                    }
                  }
                  description
                    "Enter Operator Specific field";
                }
              }
            }
            container expected {
              description
                "Set expected TTI";
              leaf ascii {
                type string {
                  length "1..64" {
                    description
                      "ASCII text (Max 64 characters)";
                  }
                }
                description
                  "Enter ASCII string";
              }
              leaf hex {
                type string {
                  length "1..128" {
                    description
                      "Hex nibbles (Max 128- The string length should be an even number)";
                  }
                }
                description
                  "Enter hex string- Length should be even number";
              }
              container otn-std {
                description
                  "Configure tti in otn standard defined fields";
                leaf sapi {
                  type string {
                    length "1..15" {
                      description
                        "Enter SAPI text (Max Length 15 Characters)";
                    }
                  }
                  description
                    "Enter Source Access Point Identifier field 1-15";
                }
                leaf dapi {
                  type string {
                    length "1..15" {
                      description
                        "Enter DAPI text (Max Length 15 Characters)";
                    }
                  }
                  description
                    "Enter Destination Access Point Identifier field 1-15";
                }
                leaf operator-specific {
                  type string {
                    length "1..32" {
                      description
                        "Enter Operator Specific text (Max Length 32 Characters)";
                    }
                  }
                  description
                    "Enter Operator Specific field";
                }
              }
            }
          }
        }
        container threshold {
          description
            "Configure ODU threshold value";
          leaf sd-ber {
            type uint32 {
              range "1..9" {
                description
                  "Bit error rate (10 to the minus n) (default 6)";
              }
            }
            description
              "Set Signal Degrade BER threshold";
          }
          leaf sf-ber {
            type uint32 {
              range "1..9" {
                description
                  "Bit error rate (10 to the minus n) (default 3)";
              }
            }
            description
              "Set Signal Failure BER threshold";
          }
        }
      }
    }
    container vtxp-monitor {
      presence "Indicates a vtxp-monitor node is configured.";
      description
        "Enable VTXP monitoring function";
    }
    container proactive {
      presence "Indicates a proactive node is configured.";
      description
        "Enable Proactive Protection Feature";
      container graceful-mode {
        presence "Indicates a graceful-mode node is configured.";
        description
          "Operate the Proactive Protection FSM in Graceful Mode, Do Not bring down the Interface";
      }
      container trigger {
        description
          "Configure trigger thresholds";
        leaf threshold {
          type uint32 {
            range "1..9" {
              description
                "Bit error rate coefficient (x of xE-y) (Trigger threshold cannot be > 1E-2)";
            }
          }
          must "../bit-error-rate-power";
          description
            "Set values x and y of xE-y";
        }
        leaf bit-error-rate-power {
          type uint32 {
            range "2..9" {
              description
                "Bit error rate power (y of xE-y) (Trigger threshold cannot be > 1E-2)";
            }
          }
          must "../threshold";
          description
            "Bit error rate power (y of xE-y) (Trigger threshold cannot be > 1E-2)";
        }
        leaf window {
          type uint32 {
            range "10..10000" {
              description
                "Integration window for FRR trigger in MS";
            }
          }
          description
            "Number of times threshold crossing is tested";
        }
      }
      container revert {
        description
          "Configure Revert thresholds";
        leaf threshold {
          type uint32 {
            range "1..9" {
              description
                "Bit error rate coefficient (x of xE-y) (Revert threshold cannot be > 1E-3)";
            }
          }
          must "../bit-error-rate-power";
          description
            "Set values x and y of xE-y";
        }
        leaf bit-error-rate-power {
          type uint32 {
            range "3..10" {
              description
                "Bit error rate power (y of xE-y) (Revert threshold cannot be > 1E-3)";
            }
          }
          must "../threshold";
          description
            "Bit error rate power (y of xE-y) (Revert threshold cannot be > 1E-3)";
        }
        leaf window {
          type uint32 {
            range "500..100000" {
              description
                "Integration window for FRR revert in MS";
            }
          }
          description
            "Number of times threshold crossing is tested";
        }
      }
      leaf event {
        type uint32 {
          range "1..50" {
            description
              "Number of Ports that will be given the event";
          }
        }
        must "../pp-event-number";
        description
          "Hidden command to trigger PP Event";
      }
      leaf pp-event-number {
        type uint32 {
          range "0..50" {
            description
              "PP Event Number";
          }
        }
        must "../event";
        must "../pp-event-value";
        description
          "PP Event Number";
      }
      leaf pp-event-value {
        type uint32 {
          range "0..255" {
            description
              "PP Event Value";
          }
        }
        must "../pp-event-number";
        description
          "PP Event Value";
      }
    }
    container log {
      description
        "Proactive log ";
      leaf signal {
        type xr:Cisco-ios-xr-string {
          length "1..32" {
            description
              "The string length file name";
          }
        }
        description
          "Enable Proactive signal log ";
      }
    }
    container network {
      description
        "Configure DWDM network information";
      container port {
        description
          "Configure the port ID for this DWDM port";
        leaf id {
          type string {
            length "1..64" {
              description
                "Enter a port ID (string, max length 64)";
            }
          }
          description
            "Configure the port ID for this DWDM port";
        }
      }
      container connection {
        description
          "Configure the connection ID for this DWDM port";
        leaf id {
          type string {
            length "1..64" {
              description
                "Enter a connection ID (string, max length 64)";
            }
          }
          description
            "Configure the connection ID for this DWDM port";
        }
      }
      container srlg {
        description
          "Submode to configure shared risks for the DWDM connection";
        container sets {
          description
            "Configure Network SRLG sets";
          list set {
            must "network-srlg-values";
            key "set-id";
            description
              "Configure Network SRLG sets";
            leaf set-id {
              type uint32 {
                range "1..17" {
                  description
                    "Set index";
                }
              }
              description
                "Configure Network SRLG sets";
            }
            leaf-list network-srlg-values {
              type uint32 {
                range "0..4294967294" {
                  description
                    "Network SRLG values (max 6 per set)";
                }
              }
              max-elements "6";
              description
                "Network SRLG values (max 6 per set)";
            }
          }
        }
      }
    }
  }

  augment "/a1:interfaces/a1:interface" {
    uses IF-BODY;
  }
  augment "/a1:interfaces/a1:interface-preconfigure" {
    uses IF-BODY;
  }
  augment "/a1:interfaces/a1:controller" {
    uses CONT-BODY;
  }
  augment "/a1:interfaces/a1:controller-preconfigure" {
    uses CONT-BODY;
  }
}
