module Cisco-IOS-XR-ipv4-bgp-cfg-ncs540-deviations {
  namespace "http://cisco.com/ns/yang/Cisco-IOS-XR-ipv4-bgp-cfg-ncs540-deviations";
  prefix ipv4-bgp-cfg-ncs540-dev;

  import Cisco-IOS-XR-ipv4-bgp-cfg {
    prefix ipv4-bgp-cfg;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations of ipv4 bgp
     for ncs540 platform on Ciso-IOS-XR device.
     
     Copyright (c) 2017, 2019-2022 by Cisco Systems, Inc.
     All rights reserved.";

  revision 2021-10-15 {
    description
      "Initial revision applicable to IOS-XR 7.6 and older releases";
    reference "RFC RFC 8407: 4.8";
  }

  deviation "/ipv4-bgp-cfg:bgp/ipv4-bgp-cfg:instance/ipv4-bgp-cfg:instance-as/ipv4-bgp-cfg:four-byte-as/ipv4-bgp-cfg:vrfs/ipv4-bgp-cfg:vrf/ipv4-bgp-cfg:vrf-global/ipv4-bgp-cfg:vrf-global-afs/ipv4-bgp-cfg:vrf-global-af/ipv4-bgp-cfg:ebgp/ipv4-bgp-cfg:paths-value" {
    deviate replace {
      type uint32 {
        range "2..64";
      }
    }
  }
  deviation "/ipv4-bgp-cfg:bgp/ipv4-bgp-cfg:instance/ipv4-bgp-cfg:instance-as/ipv4-bgp-cfg:four-byte-as/ipv4-bgp-cfg:vrfs/ipv4-bgp-cfg:vrf/ipv4-bgp-cfg:vrf-global/ipv4-bgp-cfg:vrf-global-afs/ipv4-bgp-cfg:vrf-global-af/ipv4-bgp-cfg:ibgp/ipv4-bgp-cfg:paths-value" {
    deviate replace {
      type uint32 {
        range "2..64";
      }
    }
  }
  deviation "/ipv4-bgp-cfg:bgp/ipv4-bgp-cfg:instance/ipv4-bgp-cfg:instance-as/ipv4-bgp-cfg:four-byte-as/ipv4-bgp-cfg:vrfs/ipv4-bgp-cfg:vrf/ipv4-bgp-cfg:vrf-global/ipv4-bgp-cfg:vrf-global-afs/ipv4-bgp-cfg:vrf-global-af/ipv4-bgp-cfg:eibgp/ipv4-bgp-cfg:paths-value" {
    deviate replace {
      type uint32 {
        range "2..64";
      }
    }
  }
}
