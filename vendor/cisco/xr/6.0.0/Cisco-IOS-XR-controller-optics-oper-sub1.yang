submodule Cisco-IOS-XR-controller-optics-oper-sub1 {

  belongs-to Cisco-IOS-XR-controller-optics-oper {
    prefix Cisco-IOS-XR-controller-optics-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR controller-optics package operational data.

     Copyright (c) 2013-2015 by Cisco Systems, Inc.
     All rights reserved.";

  revision "2015-11-09" {
    description
      "IOS XR 6.0 revision.";
  }

  typedef Optics-phy {
    type enumeration {
      enum not-set {
        value 0;
        description "Not set";
      }
      enum invalid {
        value 1;
        description "Invalid";
      }
      enum long-reach-four-lanes {
        value 2;
        description "Long reach 4 lanes";
      }
      enum short-reach-ten-lanes {
        value 3;
        description "Short reach 10 lanes";
      }
      enum short-reach-one-lane {
        value 4;
        description "Short reach 1 lane";
      }
      enum long-reach-one-lane {
        value 5;
        description "Long reach 1 lane";
      }
      enum short-reach-four-lanes {
        value 6;
        description "Short reach 4 lanes";
      }
      enum copper-four-lanes {
        value 7;
        description "Copper 4 lanes";
      }
      enum active-optical-cable {
        value 8;
        description "Active optical cable";
      }
      enum fourty-gig-e-long-reach-four-lanes {
        value 9;
        description "Long reach 4 lanes";
      }
      enum fourty-gig-e-short-reach-four-lanes {
        value 10;
        description "Short reach 4 lanes";
      }
      enum cwdm-four-lanes {
        value 11;
        description "CWDM 4 lanes";
      }
    }
    description "Optics phy type";
  }
  typedef Optics-form-factor {
    type enumeration {
      enum not-set {
        value 0;
        description "Not set";
      }
      enum invalid {
        value 1;
        description "Invalid";
      }
      enum cpak {
        value 2;
        description "CPAK";
      }
      enum cxp {
        value 3;
        description "CXP";
      }
      enum sfp-plus {
        value 4;
        description "SFP+";
      }
      enum qsfp {
        value 5;
        description "QSFP";
      }
      enum qsfp-plus {
        value 6;
        description "QSFP+";
      }
      enum qsfp28 {
        value 7;
        description "QSFP28";
      }
    }
    description "Optics form factor";
  }
  typedef Optics-controller-state {
    type enumeration {
      enum optics-state-up {
        value 0;
        description "Up";
      }
      enum optics-state-down {
        value 1;
        description "Down";
      }
      enum optics-state-admin-down {
        value 2;
        description "Administratively Down";
      }
    }
    description "Optics controller state";
  }
  typedef Optics-led-state {
    type enumeration {
      enum off {
        value 0;
        description "Off";
      }
      enum green-on {
        value 1;
        description "Green";
      }
      enum green-flashing {
        value 2;
        description "Green Flashing";
      }
      enum yellow-on {
        value 3;
        description "Yellow";
      }
      enum yellow-flashing {
        value 4;
        description "Yellow Flashing";
      }
      enum red-on {
        value 5;
        description "Red";
      }
      enum red-flashing {
        value 6;
        description "Red Flashing";
      }
    }
    description "Optics led state";
  }
  typedef Optics-laser-state {
    type enumeration {
      enum on {
        value 0;
        description "On";
      }
      enum off {
        value 1;
        description "Off";
      }
      enum unknown {
        value 2;
        description "Unknown";
      }
    }
    description "Optics laser state";
  }
  typedef Optics {
    type enumeration {
      enum optics-unknown {
        value 0;
        description "Unknow Optics Type";
      }
      enum optics-grey {
        value 1;
        description "Grey Optics";
      }
      enum optics-dwdm {
        value 2;
        description "DWDM Optics";
      }
      enum optics-cwdm {
        value 3;
        description "CWDM Optics";
      }
    }
    description "Optics";
  }
  typedef Optics-tas {
    type enumeration {
      enum tas-ui-oos {
        value 0;
        description "Out Of Service";
      }
      enum tas-ui-main {
        value 1;
        description "Maintenance";
      }
      enum tas-ui-is {
        value 2;
        description "In Service";
      }
      enum tas-ui-ains {
        value 3;
        description "Automatic In Service";
      }
    }
    description "Optics tas";
  }

  grouping OPTICS-ALARM-DETAIL {
    description " Optics Alarm Detail";
    leaf is-detected {
      xr:xr-xml-map "optics_ui:IsDetected";
      type boolean;
      description "Is defect detected?";
    }
    leaf counter {
      xr:xr-xml-map "optics_ui:Counter";
      type uint32;
      description "Alarm counter";
    }
  }

  grouping OPTICS-EDM-ALARM-INFO {
    description "Optics Alarm Information";

    container high-rx-power {
      description "High Rx Power";
      uses OPTICS-ALARM-DETAIL;
    }

    container low-rx-power {
      description "Low Rx Power";
      uses OPTICS-ALARM-DETAIL;
    }

    container high-tx-power {
      description "High Tx Power";
      uses OPTICS-ALARM-DETAIL;
    }

    container low-tx-power {
      description "Low Tx Power";
      uses OPTICS-ALARM-DETAIL;
    }

    container high-lbc {
      description "High laser bias current";
      uses OPTICS-ALARM-DETAIL;
    }

    container high-rx1-power {
      description "High Rx1 Power";
      uses OPTICS-ALARM-DETAIL;
    }

    container high-rx2-power {
      description "High Rx2 Power";
      uses OPTICS-ALARM-DETAIL;
    }

    container high-rx3-power {
      description "High Rx3 Power";
      uses OPTICS-ALARM-DETAIL;
    }

    container high-rx4-power {
      description "High Rx4 Power";
      uses OPTICS-ALARM-DETAIL;
    }

    container low-rx1-power {
      description "Low Rx1 Power";
      uses OPTICS-ALARM-DETAIL;
    }

    container low-rx2-power {
      description "Low Rx2 Power";
      uses OPTICS-ALARM-DETAIL;
    }

    container low-rx3-power {
      description "Low Rx3 Power";
      uses OPTICS-ALARM-DETAIL;
    }

    container low-rx4-power {
      description "Low Rx4 Power";
      uses OPTICS-ALARM-DETAIL;
    }

    container high-tx1-power {
      description "High Tx1 Power";
      uses OPTICS-ALARM-DETAIL;
    }

    container high-tx2-power {
      description "High Tx2 Power";
      uses OPTICS-ALARM-DETAIL;
    }

    container high-tx3-power {
      description "High Tx3 Power";
      uses OPTICS-ALARM-DETAIL;
    }

    container high-tx4-power {
      description "High Tx4 Power";
      uses OPTICS-ALARM-DETAIL;
    }

    container low-tx1-power {
      description "Low Tx1 Power";
      uses OPTICS-ALARM-DETAIL;
    }

    container low-tx2-power {
      description "Low Tx2 Power";
      uses OPTICS-ALARM-DETAIL;
    }

    container low-tx3-power {
      description "Low Tx3 Power";
      uses OPTICS-ALARM-DETAIL;
    }

    container low-tx4-power {
      description "Low Tx4 Power";
      uses OPTICS-ALARM-DETAIL;
    }

    container high-tx1lbc {
      description "High Tx1 laser bias current";
      uses OPTICS-ALARM-DETAIL;
    }

    container high-tx2lbc {
      description "High Tx2 laser bias current";
      uses OPTICS-ALARM-DETAIL;
    }

    container high-tx3lbc {
      description "High Tx3 laser bias current";
      uses OPTICS-ALARM-DETAIL;
    }

    container high-tx4lbc {
      description "High Tx4 laser bias current";
      uses OPTICS-ALARM-DETAIL;
    }

    container low-tx1lbc {
      description "Low Tx1 laser bias current";
      uses OPTICS-ALARM-DETAIL;
    }

    container low-tx2lbc {
      description "Low Tx2 laser bias current";
      uses OPTICS-ALARM-DETAIL;
    }

    container low-tx3lbc {
      description "Low Tx3 laser bias current";
      uses OPTICS-ALARM-DETAIL;
    }

    container low-tx4lbc {
      description "Low Tx4 laser bias current";
      uses OPTICS-ALARM-DETAIL;
    }

    container rx-los {
      description "RX LOS";
      uses OPTICS-ALARM-DETAIL;
    }

    container tx-los {
      description "TX LOS";
      uses OPTICS-ALARM-DETAIL;
    }

    container rx-lol {
      description "RX LOL";
      uses OPTICS-ALARM-DETAIL;
    }

    container tx-lol {
      description "TX LOL";
      uses OPTICS-ALARM-DETAIL;
    }

    container tx-fault {
      description "TX Fault";
      uses OPTICS-ALARM-DETAIL;
    }

    container hidgd {
      description "HI DGD";
      uses OPTICS-ALARM-DETAIL;
    }

    container oorcd {
      description "OOR CD";
      uses OPTICS-ALARM-DETAIL;
    }

    container osnr {
      description "OSNR";
      uses OPTICS-ALARM-DETAIL;
    }

    container wvlool {
      description "WVL OOL";
      uses OPTICS-ALARM-DETAIL;
    }

    container mea {
      description "MEA";
      uses OPTICS-ALARM-DETAIL;
    }

    container imp-removal {
      description "IMPROPER REM";
      uses OPTICS-ALARM-DETAIL;
    }
  }

  grouping OPTICS-EDM-LANE-DATA {
    description "Grey lane data";
    leaf lane-index {
      xr:xr-xml-map "optics_ui:LaneIndex";
      type uint32;
      description "The index number of the lane";
    }
    leaf laser-bias-current-percent {
      xr:xr-xml-map "optics_ui:LaserBiasCurrentPercent";
      type uint32;
      description "Laser Bias Current in units of 0.01%";
    }
    leaf laser-bias-current-milli-amps {
      xr:xr-xml-map "optics_ui:LaserBiasCurrentMilliAmps";
      type uint32;
      description "Laser Bias Current in units of 0.01mA";
    }
    leaf transmit-power {
      xr:xr-xml-map "optics_ui:TransmitPower";
      type int32;
      description "Transmit power in the unit of 0.01dBm";
    }
    leaf receive-power {
      xr:xr-xml-map "optics_ui:ReceivePower";
      type int32;
      description
        "Transponder receive power in the unit of 0.01dBm";
    }
  }

  grouping OPTICS-EDM-NETWORK-SRLG-INFO {
    description "Network SRLG Information";
    leaf-list network-srlg {
      xr:xr-xml-map "optics_ui:NetworkSrlg";
      type uint32;
      max-elements "102";
      description "Network Srlg";
    }
  }

  grouping OPTICS-EDM-INFO {
    description "optics transponder information";

    container network-srlg-info {
      description "Network SRLG information";
      uses OPTICS-EDM-NETWORK-SRLG-INFO;
    }

    container optics-alarm-info {
      description "Optics Alarm Information";
      uses OPTICS-EDM-ALARM-INFO;
    }
    leaf transport-admin-state {
      xr:xr-xml-map "optics_ui:TransportAdminState";
      type Optics-tas;
      description "Transport Admin State";
    }
    leaf optics-present {
      xr:xr-xml-map "optics_ui:OpticsPresent";
      type boolean;
      description "Is Optics Present?";
    }
    leaf optics-type {
      xr:xr-xml-map "optics_ui:OpticsType";
      type Optics;
      description "Optics type name";
    }
    leaf optics-module {
      xr:xr-xml-map "optics_ui:OpticsModule";
      type string;
      description "Optics module name";
    }
    leaf dwdm-carrier-band {
      xr:xr-xml-map "optics_ui:DWDMCarrierBand";
      type uint32;
      description "DWDM Carrier Band information";
    }
    leaf dwdm-carrier-channel {
      xr:xr-xml-map "optics_ui:DWDMCarrierChannel";
      type string;
      description "Current ITU DWDM Carrier channel number";
    }
    leaf dwdm-carrier-frequency {
      xr:xr-xml-map "optics_ui:DWDMCarrierFrequency";
      type string;
      description
        "DWDM Carrier frequency read from hw in the unit
        0.01THz";
    }
    leaf dwdm-carrier-wavelength {
      xr:xr-xml-map "optics_ui:DWDMCarrierWavelength";
      type string;
      description "Wavelength of color optics 0.001nm";
    }
    leaf grey-wavelength {
      xr:xr-xml-map "optics_ui:GreyWavelength";
      type uint32;
      description "Wavelength of grey optics 0.01nm";
    }
    leaf rx-low-threshold {
      xr:xr-xml-map "optics_ui:RxLowThreshold";
      type int32;
      description "Rx Low threshold value";
    }
    leaf rx-high-threshold {
      xr:xr-xml-map "optics_ui:RxHighThreshold";
      type int32;
      description "Rx High threshold value";
    }
    leaf lbc-high-threshold {
      xr:xr-xml-map "optics_ui:LBCHighThreshold";
      type int32;
      description "LBC High threshold value";
    }
    leaf tx-low-threshold {
      xr:xr-xml-map "optics_ui:TxLowThreshold";
      type int32;
      description "Tx Low threshold value";
    }
    leaf tx-high-threshold {
      xr:xr-xml-map "optics_ui:TxHighThreshold";
      type int32;
      description "Tx High threshold value";
    }
    leaf temp-low-threshold {
      xr:xr-xml-map "optics_ui:TempLowThreshold";
      type int32;
      description "Temp Low threshold value";
    }
    leaf temp-high-threshold {
      xr:xr-xml-map "optics_ui:TempHighThreshold";
      type int32;
      description "Temp High threshold value";
    }
    leaf volt-low-threshold {
      xr:xr-xml-map "optics_ui:VoltLowThreshold";
      type int32;
      description "Volt Low threshold value";
    }
    leaf volt-high-threshold {
      xr:xr-xml-map "optics_ui:VoltHighThreshold";
      type int32;
      description "Volt High threshold value";
    }
    leaf cd {
      xr:xr-xml-map "optics_ui:CD";
      type int32;
      description "Chromatic Dispersion ps/nm";
    }
    leaf cd-min {
      xr:xr-xml-map "optics_ui:CDMin";
      type int32;
      description "Chromatic Dispersion Min ps/nm";
    }
    leaf cd-max {
      xr:xr-xml-map "optics_ui:CDMax";
      type int32;
      description "Chromatic Dispersion Max ps/nm";
    }
    leaf cd-low-threshold {
      xr:xr-xml-map "optics_ui:CDLowThreshold";
      type int32;
      description "Chromatic Dispersion low threshold ps/nm";
    }
    leaf cd-high-threshold {
      xr:xr-xml-map "optics_ui:CDHighThreshold";
      type int32;
      description "Chromatic Dispersion high threshold ps/nm";
    }
    leaf osnr-low-threshold {
      xr:xr-xml-map "optics_ui:OSNRLowThreshold";
      type string;
      description "OSNR low threshold in 0.01 dB";
    }
    leaf dgd-high-threshold {
      xr:xr-xml-map "optics_ui:DGDHighThreshold";
      type string;
      description "DGD high threshold in 0.1 ps";
    }
    leaf polarization-mode-dispersion {
      xr:xr-xml-map "optics_ui:PolarizationModeDispersion";
      type string;
      description "Polarization Mode Dispersion 0.1ps";
    }
    leaf second-order-polarization-mode-dispersion {
      xr:xr-xml-map "optics_ui:SecondOrderPolarizationModeDispersio"+
        "n";
      type string;
      description
        "Second Order Polarization Mode Dispersion 0
        .1ps^2";
    }
    leaf optical-signal-to-noise-ratio {
      xr:xr-xml-map "optics_ui:OpticalSignalToNoiseRatio";
      type string;
      description "Optical Signal to Noise Ratio dB";
    }
    leaf polarization-dependent-loss {
      xr:xr-xml-map "optics_ui:PolarizationDependentLoss";
      type string;
      description "Polarization Dependent Loss dB";
    }
    leaf polarization-change-rate {
      xr:xr-xml-map "optics_ui:PolarizationChangeRate";
      type string;
      description "Polarization Change Rate rad/s";
    }
    leaf differential-group-delay {
      xr:xr-xml-map "optics_ui:DifferentialGroupDelay";
      type string;
      description "Differential Group Delay ps";
    }
    leaf phase-noise {
      xr:xr-xml-map "optics_ui:PhaseNoise";
      type string;
      description "Phase Noise dB";
    }
    leaf pm-enable {
      xr:xr-xml-map "optics_ui:PmEnable";
      type uint32;
      description "PmEable or Disable";
    }
    leaf laser-state {
      xr:xr-xml-map "optics_ui:LaserState";
      type Optics-laser-state;
      description "Showing laser state.Either ON or OFF or unknown";
    }
    leaf led-state {
      xr:xr-xml-map "optics_ui:LedState";
      type Optics-led-state;
      description "Showing Current Colour of led state";
    }
    leaf controller-state {
      xr:xr-xml-map "optics_ui:ControllerState";
      type Optics-controller-state;
      description
        "Optics controller state: Up, Down or
        Administratively Down";
    }
    leaf form-factor {
      xr:xr-xml-map "optics_ui:FormFactor";
      type Optics-form-factor;
      description "Optics form factor";
    }
    leaf phy-type {
      xr:xr-xml-map "optics_ui:PhyType";
      type Optics-phy;
      description "Optics physical type";
    }
    leaf cfg-tx-power {
      xr:xr-xml-map "optics_ui:CfgTXPower";
      type int32;
      description "Configured Tx power value";
    }
    leaf vendor-info {
      xr:xr-xml-map "optics_ui:Vendor_info";
      type string;
      description "Vendor Information";
    }
    leaf display-volt-temp {
      xr:xr-xml-map "optics_ui:DisplayVoltTemp";
      type boolean;
      description "Display Volt/Temp ?";
    }

    list lane-data {
      description "Lane information";
      uses OPTICS-EDM-LANE-DATA;
    }
  }

  grouping OPTICS-EDM-CHANNEL-WAVELENGTH-MAP-INFO {
    description "OPTICS EDM CHANNEL WAVELENGTH MAP INFO";
    leaf itu-chan-num {
      xr:xr-xml-map "optics_ui:ItuChanNum";
      type uint32;
      description "ITU channel number";
    }
    leaf g694-chan-num {
      xr:xr-xml-map "optics_ui:G694ChanNum";
      type int32;
      description "G694 channel number";
    }
    leaf frequency {
      xr:xr-xml-map "optics_ui:Frequency";
      type string {
        length "0..32";
      }
      description "Frequency";
    }
    leaf wavelength {
      xr:xr-xml-map "optics_ui:Wavelength";
      type string {
        length "0..32";
      }
      description "Wavelength";
    }
  }

  grouping OPTICS-EDM-WAVE-INFO {
    description "wavelength channel mapping information";
    leaf dwdm-carrier-band {
      xr:xr-xml-map "optics_ui:DwdmCarrierBand";
      type string {
        length "0..32";
      }
      description "DWDM carrier band";
    }
    leaf dwdm-carrier-min {
      xr:xr-xml-map "optics_ui:DwdmCarrierMin";
      type uint32;
      description "Lowest DWDM carrier supported";
    }
    leaf dwdm-carrier-max {
      xr:xr-xml-map "optics_ui:DwdmCarrierMax";
      type uint32;
      description "Highest DWDM carrier supported";
    }

    list dwdm-carrier-map-info {
      description "DWDM carrier mapping info";
      uses OPTICS-EDM-CHANNEL-WAVELENGTH-MAP-INFO;
    }
  }
}
