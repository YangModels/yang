module Cisco-IOS-XR-ncs1k-mxp-headless-oper {

  /*** NAMESPACE / PREFIX DEFINITION ***/

  namespace "http://cisco.com/ns/yang"+
    "/Cisco-IOS-XR-ncs1k-mxp-headless-oper";


  prefix "ncs1k-mxp-headless-oper";

  /*** LINKAGE (IMPORTS / INCLUDES) ***/

  import Cisco-IOS-XR-types { prefix "xr"; }

  include Cisco-IOS-XR-ncs1k-mxp-headless-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1k-mxp-headless package operational data.

     This module contains definitions
     for the following management objects:
       headless-func-data: Information related to headless
         functionality

     Copyright (c) 2013-2015 by Cisco Systems, Inc.
     All rights reserved.";

  revision "2015-11-09" {
    description
      "IOS XR 6.0 revision.";
  }


  container headless-func-data {
    xr:xr-xml-map "mxp_headless_oper:HeadlessFuncData";
    config false;
    description "Information related to headless functionality";

    container otn-port-names {
      xr:xr-xml-map "mxp_headless_oper:OtnStatistics";
      description
        "OTN Statistics collected during last headless
        operation";

      list otn-port-name {
        xr:xr-xml-map "mxp_headless_oper:OtnPortName";
        key "name";
        description "port Name";
        leaf name {
          xr:xr-xml-map "mxp_headless_oper:Name";
          type xr:Interface-name;
          description "Port name";
        }
        uses MXP-HEADLESS-OTN-CNT-INFO;
      }
    }

    container ethernet-port-names {
      xr:xr-xml-map "mxp_headless_oper:EtherStatistics";
      description
        "Ethernet Statistics collected during last
        headless operation";

      list ethernet-port-name {
        xr:xr-xml-map "mxp_headless_oper:EthernetPortName";
        key "name";
        description "Port Name";
        leaf name {
          xr:xr-xml-map "mxp_headless_oper:Name";
          type xr:Interface-name;
          description "Port name";
        }
        uses MXP-HEADLESS-ETHER-PRIM-INFO;
      }
    }
  }
}
