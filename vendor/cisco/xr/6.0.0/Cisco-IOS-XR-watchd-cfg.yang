module Cisco-IOS-XR-watchd-cfg {

  /*** NAMESPACE / PREFIX DEFINITION ***/

  namespace "http://cisco.com/ns/yang/Cisco-IOS-XR-watchd-cfg";


  prefix "watchd-cfg";

  /*** LINKAGE (IMPORTS / INCLUDES) ***/

  import Cisco-IOS-XR-types { prefix "xr"; }

  import Cisco-IOS-XR-config-mda-cfg { prefix "node"; }

  import Cisco-IOS-XR-config-mda-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR watchd package configuration.

     This module contains definitions
     for the following management objects:
       watchdog: Watchdog configuration commands
       watchd: watchd

     This YANG module augments the
       Cisco-IOS-XR-config-mda-cfg
       Cisco-IOS-XR-config-mda-cfg
     modules with configuration data.

     Copyright (c) 2013-2015 by Cisco Systems, Inc.
     All rights reserved.";

  revision "2015-11-09" {
    description
      "IOS XR 6.0 revision.";
  }

  revision "2015-10-12" {
    description
      "Descriptions updated.";
  }


  grouping NODE-CFG {
    description "active/preconfigured nodes configuration";

    container watchdog-node-threshold {
      xr:xr-xml-map "watchd_cfg:WatchdogNodeThreshold";
      description "watchdog node threshold";

      container memory-threshold {
        xr:xr-xml-map "watchd_cfg:MemoryThreshold";
        description "Memory thresholds";
        leaf minor {
          xr:xr-xml-map "watchd_cfg:minor";
          type uint32 {
            range "5..40";
          }
          description "Threshold, Range(5, 40)";
        }
        leaf severe {
          xr:xr-xml-map "watchd_cfg:severe";
          type uint32 {
            range "4..40";
          }
          description "Threshold, Range(4, minor)";
        }
        leaf critical {
          xr:xr-xml-map "watchd_cfg:critical";
          type uint32 {
            range "3..40";
          }
          description "Threshold, Range(3, severe)";
        }
      }
    }
  }

  container watchdog {
    xr:xr-xml-map "watchd_cfg:Watchdog";
    description "Watchdog configuration commands";

    container threshold-memory {
      xr:xr-xml-map "watchd_cfg:ThresholdMemory";
      description "Memory thresholds";
      leaf minor {
        xr:xr-xml-map "watchd_cfg:minor";
        type uint32 {
          range "5..40";
        }
        description "Threshold, Range (5, 40)";
      }
      leaf severe {
        xr:xr-xml-map "watchd_cfg:severe";
        type uint32 {
          range "4..40";
        }
        description "Threshold, Range (4, minor)";
      }
      leaf critical {
        xr:xr-xml-map "watchd_cfg:critical";
        type uint32 {
          range "3..40";
        }
        description "Threshold, Range (3, severe)";
      }
    }
    leaf overload-notification {
      xr:xr-xml-map "watchd_cfg:OverloadNotification";
      xr:xr-cli-map "overload notification disable ";
      type empty;
      description "Disable critical event notification";
    }
    leaf restart-deadlock-disable {
      xr:xr-xml-map "watchd_cfg:RestartDeadlockDisable";
      xr:xr-cli-map "restart deadlock disable ";
      type empty;
      description "Disable watchdog restart deadlock";
    }
    leaf restart-memoryhog-disable {
      xr:xr-xml-map "watchd_cfg:RestartMemoryhogDisable";
      xr:xr-cli-map "restart memory-hog disable ";
      type empty;
      description "Disable watchdog restart memory-hog";
    }
    leaf overload-throttle-timeout {
      xr:xr-xml-map "watchd_cfg:OverloadThrottleTimeout";
      xr:xr-cli-map "overload throttle-timeout <number> ";
      type uint32 {
        range "5..120";
      }
      units "second";
      description
        "Watchdog overload throttle timeout configuration";
    }
  }

  container watchd {
    xr:xr-xml-map "watchd_cfg_vmm:Watchd";
    description "watchd";
    leaf timeout {
      xr:xr-xml-map "watchd_cfg_vmm:Timeout";
      xr:xr-cli-map "watchd timeout <number> ";
      type uint32 {
        range "1..10";
      }
      units "second";
      description "Length of timeout in seconds";
    }
  }

  augment "/node:active-nodes/node:active-node" {
    uses NODE-CFG;
    description "This augment extends active nodes configuration";
  }

  augment "/node:preconfigured-nodes/node:preconfigured-node" {
    uses NODE-CFG;
    description
      "This augment extends preconfigured nodes
      configuration";
  }
}
