submodule Cisco-IOS-XR-wanphy-ui-oper-sub1 {

  belongs-to Cisco-IOS-XR-wanphy-ui-oper {
    prefix Cisco-IOS-XR-wanphy-ui-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR wanphy-ui package operational data.

     Copyright (c) 2013-2015 by Cisco Systems, Inc.
     All rights reserved.";

  revision "2015-11-09" {
    description
      "IOS XR 6.0 revision.";
  }

  typedef Wanphy-alarm-rep-status {
    type enumeration {
      enum disable {
        description "Alarm reporting is disable";
      }
      enum enable {
        description "Alarm reporting is enable";
      }
    }
    description "WANPHY Alarm Report Status";
  }
  typedef Wanphy-mode-info {
    type enumeration {
      enum lan {
        description "LAN mode";
      }
      enum wan {
        description "WAN mode";
      }
    }
    description "WANPHY Modes";
  }

  grouping WANPHY-EDM-INFO {
    description "WAN-PHY Information";
    leaf admin-mode {
      xr:xr-xml-map "wanphy_edm:AdminMode";
      type Wanphy-mode-info;
      description "Configuration Mode";
    }
    leaf port-state {
      xr:xr-xml-map "wanphy_edm:PortState";
      type uint32;
      description "Port State";
    }
    leaf section-lof {
      xr:xr-xml-map "wanphy_edm:SectionLOF";
      type uint32;
      description "Section LOF";
    }
    leaf section-los {
      xr:xr-xml-map "wanphy_edm:SectionLOS";
      type uint32;
      description "Section LOS";
    }
    leaf section-bip {
      xr:xr-xml-map "wanphy_edm:SectionBIP";
      type uint64;
      description "Section BIP(B1)";
    }
    leaf line-ais {
      xr:xr-xml-map "wanphy_edm:LineAIS";
      type uint32;
      description "Line AIS";
    }
    leaf line-rdi {
      xr:xr-xml-map "wanphy_edm:LineRDI";
      type uint32;
      description "Line RDI";
    }
    leaf line-febe {
      xr:xr-xml-map "wanphy_edm:LineFEBE";
      type uint64;
      description "Line FEBE";
    }
    leaf line-bip {
      xr:xr-xml-map "wanphy_edm:LineBIP";
      type uint64;
      description "Line BIP(B2) ";
    }
    leaf path-ais {
      xr:xr-xml-map "wanphy_edm:PathAIS";
      type uint32;
      description "Path AIS";
    }
    leaf path-rdi {
      xr:xr-xml-map "wanphy_edm:PathRDI";
      type uint32;
      description "Path RDI";
    }
    leaf path-febe {
      xr:xr-xml-map "wanphy_edm:PathFEBE";
      type uint64;
      description "Path FEBE";
    }
    leaf path-bip {
      xr:xr-xml-map "wanphy_edm:PathBIP";
      type uint64;
      description "Path BIP(B3)";
    }
    leaf path-lop {
      xr:xr-xml-map "wanphy_edm:PathLOP";
      type uint32;
      description "Path LOP";
    }
    leaf path-newptr {
      xr:xr-xml-map "wanphy_edm:PathNEWPTR";
      type uint32;
      description "Path NEWPTR";
    }
    leaf path-pse {
      xr:xr-xml-map "wanphy_edm:PathPSE";
      type uint32;
      description "Path PSE";
    }
    leaf path-nse {
      xr:xr-xml-map "wanphy_edm:PathNSE";
      type uint32;
      description "Path NSE";
    }
    leaf wis-alarms-ser {
      xr:xr-xml-map "wanphy_edm:WISAlarmsSER";
      type uint32;
      description "WIS Alarms SER";
    }
    leaf wis-alarms-felcdp {
      xr:xr-xml-map "wanphy_edm:WISAlarmsFELCDP";
      type uint32;
      description "WIS Alarms FELCDP";
    }
    leaf wis-alarms-feaisp {
      xr:xr-xml-map "wanphy_edm:WISAlarmsFEAISP";
      type uint32;
      description "WIS Alarms FEAISP";
    }
    leaf wis-alarms-wlos {
      xr:xr-xml-map "wanphy_edm:WISAlarmsWLOS";
      type uint32;
      description "WIS Alarms WLOS";
    }
    leaf wis-alarms-plcd {
      xr:xr-xml-map "wanphy_edm:WISAlarmsPLCD";
      type uint32;
      description "WIS Alarms PLCD";
    }
    leaf wis-alarms-lfebip {
      xr:xr-xml-map "wanphy_edm:WISAlarmsLFEBIP";
      type uint64;
      description "WIS Alarms LFEBIP";
    }
    leaf wis-alarms-pbec {
      xr:xr-xml-map "wanphy_edm:WISAlarmsPBEC";
      type uint64;
      description "WIS Alarms PBEC";
    }
    leaf wis-alarms-plmp {
      xr:xr-xml-map "wanphy_edm:WISAlarmsPLMP";
      type uint32;
      description "WIS Alarms PLMP";
    }
    leaf sf-ber-threshold {
      xr:xr-xml-map "wanphy_edm:SF_BERThreshold";
      type uint32;
      description "BER thresholds: SF. Value 'd' in 10e-%d";
    }
    leaf sd-ber-threshold {
      xr:xr-xml-map "wanphy_edm:SD_BERThreshold";
      type uint32;
      description "BER thresholds: SD. Value 'd' in 10e-%d";
    }
    leaf sf-ber-report {
      xr:xr-xml-map "wanphy_edm:SF_BERReport";
      type Wanphy-alarm-rep-status;
      description "SF_BER Report";
    }
    leaf sd-ber-report {
      xr:xr-xml-map "wanphy_edm:SD_BERReport";
      type Wanphy-alarm-rep-status;
      description "SD_BER Report";
    }
    leaf operational-mode {
      xr:xr-xml-map "wanphy_edm:OperationalMode";
      type Wanphy-mode-info;
      description "Operational Mode";
    }
    leaf remote-ip {
      xr:xr-xml-map "wanphy_edm:RemoteIP";
      type string;
      description "Remote IP Address";
    }
    leaf register-p-febe {
      xr:xr-xml-map "wanphy_edm:RegisterP_FEBE";
      type uint32;
      description "Register P_FEBE";
    }
    leaf register-l-fe-bip {
      xr:xr-xml-map "wanphy_edm:RegisterL_FE_BIP";
      type uint32;
      description "Register L_FE_BIP";
    }
    leaf register-l-bip {
      xr:xr-xml-map "wanphy_edm:RegisterL_BIP";
      type uint32;
      description "Register L_BIP";
    }
    leaf register-p-bec {
      xr:xr-xml-map "wanphy_edm:RegisterP_BEC";
      type uint32;
      description "Register P_BEC";
    }
    leaf register-s-bip {
      xr:xr-xml-map "wanphy_edm:RegisterS_BIP";
      type uint32;
      description "Register S_BIP";
    }
    leaf register-j1-rx0 {
      xr:xr-xml-map "wanphy_edm:RegisterJ1_Rx0";
      type uint32;
      description "Register J1-Rx0";
    }
    leaf register-j1-rx1 {
      xr:xr-xml-map "wanphy_edm:RegisterJ1_Rx1";
      type uint32;
      description "Register J1-Rx1";
    }
    leaf register-j1-rx2 {
      xr:xr-xml-map "wanphy_edm:RegisterJ1_Rx2";
      type uint32;
      description "Register J1-Rx2";
    }
    leaf register-j1-rx3 {
      xr:xr-xml-map "wanphy_edm:RegisterJ1_Rx3";
      type uint32;
      description "Register J1-Rx3";
    }
    leaf register-j1-rx4 {
      xr:xr-xml-map "wanphy_edm:RegisterJ1_Rx4";
      type uint32;
      description "Register J1-Rx4";
    }
    leaf register-j1-rx5 {
      xr:xr-xml-map "wanphy_edm:RegisterJ1_Rx5";
      type uint32;
      description "Register J1-Rx5";
    }
    leaf register-j1-rx6 {
      xr:xr-xml-map "wanphy_edm:RegisterJ1_Rx6";
      type uint32;
      description "Register J1-Rx6";
    }
    leaf register-j1-rx7 {
      xr:xr-xml-map "wanphy_edm:RegisterJ1_Rx7";
      type uint32;
      description "Register J1-Rx7";
    }
  }
}
