submodule Cisco-IOS-XR-cdp-oper-sub1 {

  belongs-to Cisco-IOS-XR-cdp-oper {
    prefix Cisco-IOS-XR-cdp-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR cdp package operational data.

     Copyright (c) 2013-2015 by Cisco Systems, Inc.
     All rights reserved.";

  revision "2015-01-07" {
    description
      "IOS XR 5.3.1 revision.";
  }

  typedef Im-state {
    type uint32;
    description "Im state";
  }
  typedef Cdp-duplex {
    type enumeration {
      enum cdp-dplx-none {
        value 0;
        description "cdp dplx none";
      }
      enum cdp-dplx-half {
        value 1;
        description "cdp dplx half";
      }
      enum cdp-dplx-full {
        value 2;
        description "cdp dplx full";
      }
    }
    description "Cdp duplex";
  }
  typedef In6-addr {
    type inet:ipv6-address;
    description "In6 addr";
  }
  typedef Cdp-l3-addr-protocol {
    type enumeration {
      enum ipv4 {
        description "IPv4";
      }
      enum ipv6 {
        description "IPv6";
      }
    }
    description "Cdp l3 addr protocol";
  }

  grouping CDP-INTERFACE {
    description
      "Information about an interface that CDP is
      running on";
    leaf interface-name-xr {
      xr:xr-xml-map "cdp:interface-name-xr";
      type xr:Interface-name;
      description "Interface";
    }
    leaf basecaps-state {
      xr:xr-xml-map "cdp:BasecapsState";
      type Im-state;
      description "Interface basecaps state";
    }
    leaf cdp-protocol-state {
      xr:xr-xml-map "cdp:CDPProtocolState";
      type Im-state;
      description "CDP protocol state";
    }
    leaf interface-encaps {
      xr:xr-xml-map "cdp:InterfaceEncaps";
      type string;
      description "Interface encapsulation";
    }
  }

  grouping CDP-STATS {
    description "CDP statistics";
    leaf received-packets {
      xr:xr-xml-map "cdp:ReceivedPackets";
      type uint32;
      description "Received packets";
    }
    leaf received-packets-v1 {
      xr:xr-xml-map "cdp:ReceivedPacketsV1";
      type uint32;
      description "Received v1 packets";
    }
    leaf received-packets-v2 {
      xr:xr-xml-map "cdp:ReceivedPacketsV2";
      type uint32;
      description "Received v2 packets";
    }
    leaf transmitted-packets {
      xr:xr-xml-map "cdp:TransmittedPackets";
      type uint32;
      description "Transmitted packets";
    }
    leaf transmitted-packets-v1 {
      xr:xr-xml-map "cdp:TransmittedPacketsV1";
      type uint32;
      description "Transmitted v1 packets";
    }
    leaf transmitted-packets-v2 {
      xr:xr-xml-map "cdp:TransmittedPacketsV2";
      type uint32;
      description "Transmitted v2 packets";
    }
    leaf header-errors {
      xr:xr-xml-map "cdp:HeaderErrors";
      type uint32;
      description "Header syntax errors";
    }
    leaf checksum-errors {
      xr:xr-xml-map "cdp:ChecksumErrors";
      type uint32;
      description "Checksum errors";
    }
    leaf encapsulation-errors {
      xr:xr-xml-map "cdp:EncapsulationErrors";
      type uint32;
      description "Transmission errors";
    }
    leaf bad-packet-errors {
      xr:xr-xml-map "cdp:BadPacketErrors";
      type uint32;
      description "Bad packet received and dropped";
    }
    leaf out-of-memory-errors {
      xr:xr-xml-map "cdp:OutOfMemoryErrors";
      type uint32;
      description "Out-of-memory conditions";
    }
    leaf truncated-packet-errors {
      xr:xr-xml-map "cdp:TruncatedPacketErrors";
      type uint32;
      description "Truncated messages";
    }
    leaf header-version-errors {
      xr:xr-xml-map "cdp:HeaderVersionErrors";
      type uint32;
      description "Can't handle receive version";
    }
    leaf open-file-errors {
      xr:xr-xml-map "cdp:OpenFileErrors";
      type uint32;
      description "Cannot open file";
    }
  }

  grouping CDP-PROTOCOL-HELLO-ENTRY {
    description "CDP Protocol Hello entry";

    list cdp-prot-hello-entry {
      description "cdp prot hello entry";
      leaf hello-message {
        type yang:hex-string;
        description "Protocol Hello msg";
      }
    }
  }

  grouping CDP-L3-ADDR {
    description "CDP L3 ADDR";
    leaf address-type {
      xr:xr-xml-map "cdp:AddressType";
      type Cdp-l3-addr-protocol;
      description "AddressType";
    }
    leaf ipv4-address {
      xr:xr-xml-map "cdp:IPv4Address";
      when "../address-type = 'ipv4'" {
        description "../AddressType = 'IPv4'";
      }
      type inet:ipv4-address;
      description "IPv4 address";
    }
    leaf ipv6-address {
      xr:xr-xml-map "cdp:IPv6Address";
      when "../address-type = 'ipv6'" {
        description "../AddressType = 'IPv6'";
      }
      type In6-addr;
      description "IPv6 address";
    }
  }

  grouping CDP-ADDRESS-ENTRY {
    description "CDP Address entry";

    list cdp-addr-entry {
      description "cdp addr entry";

      container address {
        description "Network layer address";
        uses CDP-L3-ADDR;
      }
    }
  }

  grouping CDP-NEIGHBOR-ENTRY-DETAILS {
    description "Detailed neighbor info";

    container network-addresses {
      description "List of network addresses ";
      uses CDP-ADDRESS-ENTRY;
    }

    container protocol-hello-list {
      description "List of protocol hello entries";
      uses CDP-PROTOCOL-HELLO-ENTRY;
    }
    leaf version {
      xr:xr-xml-map "cdp:Version";
      type string;
      description "Version TLV";
    }
    leaf vtp-domain {
      xr:xr-xml-map "cdp:VTPDomain";
      type string;
      description "VTP domain";
    }
    leaf native-vlan {
      xr:xr-xml-map "cdp:NativeVLAN";
      type uint32;
      description "Native VLAN";
    }
    leaf duplex {
      xr:xr-xml-map "cdp:Duplex";
      type Cdp-duplex;
      description "Duplex setting";
    }
    leaf system-name {
      xr:xr-xml-map "cdp:SystemName";
      type string;
      description "SysName";
    }
  }

  grouping CDP-NEIGHBOR {
    description "CDP neighbor info";

    list cdp-neighbor {
      description "cdp neighbor";

      container detail {
        description "Detailed neighbor info";
        uses CDP-NEIGHBOR-ENTRY-DETAILS;
      }
      leaf receiving-interface-name {
        type xr:Interface-name;
        description "Interface the neighbor entry was received on ";
      }
      leaf device-id {
        type string;
        description "Device identifier";
      }
      leaf port-id {
        type string;
        description "Outgoing port identifier";
      }
      leaf header-version {
        type uint8;
        description "Version number";
      }
      leaf hold-time {
        type uint16;
        description "Remaining hold time";
      }
      leaf capabilities {
        type string;
        description "Capabilities";
      }
      leaf platform {
        type string;
        description "Platform type";
      }
    }
  }
}
