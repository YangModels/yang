submodule Cisco-IOS-XR-man-xml-ttyagent-oper-sub1 {

  belongs-to Cisco-IOS-XR-man-xml-ttyagent-oper {
    prefix Cisco-IOS-XR-man-xml-ttyagent-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR man-xml-ttyagent package operational data.

     Copyright (c) 2013-2015 by Cisco Systems, Inc.
     All rights reserved.";

  revision "2015-10-29" {
    description
      "Descriptions updated.";
  }

  revision "2015-01-07" {
    description
      "IOS XR 5.3.1 revision.";
  }

  typedef Xr-xml-session-alarm-register {
    type enumeration {
      enum registered {
        value 1;
        description "Registered";
      }
      enum not-registered {
        value 2;
        description "NotRegistered";
      }
    }
    description "AlarmNotify";
  }
  typedef Xr-xml-session-state {
    type enumeration {
      enum idle {
        value 1;
        description "Idle";
      }
      enum busy {
        value 2;
        description "Busy";
      }
    }
    description "SessionState";
  }

  grouping XR-XML-SESSION-INFO {
    description "XML SESSION INFO";
    leaf username {
      xr:xr-xml-map "xml_agent:Username";
      type string;
      description "Username";
    }
    leaf state {
      xr:xr-xml-map "xml_agent:State";
      type Xr-xml-session-state;
      description "state of the session idle/busy";
    }
    leaf client-address {
      xr:xr-xml-map "xml_agent:ClientAddress";
      type string;
      description "ip address of the client";
    }
    leaf client-port {
      xr:xr-xml-map "xml_agent:ClientPort";
      type uint32;
      description "client's port";
    }
    leaf config-session-id {
      xr:xr-xml-map "xml_agent:ConfigSessionID";
      type string;
      description "Config session ID";
    }
    leaf admin-config-session-id {
      xr:xr-xml-map "xml_agent:AdminConfigSessionID";
      type string;
      description "Admin config session ID";
    }
    leaf alarm-notification {
      xr:xr-xml-map "xml_agent:AlarmNotification";
      type Xr-xml-session-alarm-register;
      description
        "is the session registered for alarm
        notifications";
    }
    leaf vrf-name {
      xr:xr-xml-map "xml_agent:VRFName";
      type string;
      description "VRF name ";
    }
    leaf start-time {
      xr:xr-xml-map "xml_agent:StartTime";
      type uint32;
      units "second";
      description
        "session start time in seconds since the Unix
        Epoch";
    }
    leaf elapsed-time {
      xr:xr-xml-map "xml_agent:ElapsedTime";
      type uint32;
      units "second";
      description
        " Elapsed time(seconds) since a session is
        created";
    }
    leaf last-state-change {
      xr:xr-xml-map "xml_agent:LastStateChange";
      type uint32;
      units "second";
      description
        "Time(seconds) since last session state change
        happened ";
    }
  }
}
