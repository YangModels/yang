module Cisco-IOS-XR-Ethernet-SPAN-cfg {

  /*** NAMESPACE / PREFIX DEFINITION ***/

  namespace "http://cisco.com/ns"+
    "/yang/Cisco-IOS-XR-Ethernet-SPAN-cfg";


  prefix "ethernet-span-cfg";

  /*** LINKAGE (IMPORTS / INCLUDES) ***/

  import ietf-inet-types { prefix "inet"; }

  import Cisco-IOS-XR-types { prefix "xr"; }

  import Cisco-IOS-XR-Ethernet-SPAN-datatypes { prefix "dt1"; }

  import Cisco-IOS-XR-ifmgr-cfg { prefix "a1"; }

  import Cisco-IOS-XR-l2vpn-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR Ethernet-SPAN package configuration.

     This module contains definitions
     for the following management objects:
       span-monitor-session: none

     This YANG module augments the
       Cisco-IOS-XR-ifmgr-cfg,
       Cisco-IOS-XR-l2vpn-cfg
     modules with configuration data.

     Copyright (c) 2013-2015 by Cisco Systems, Inc.
     All rights reserved.";

  revision "2015-11-09" {
    description
      "IOS XR 6.0 revision.";
  }

  typedef Span-traffic-direction {
    type enumeration {
      enum rx-only {
        value 1;
        description "Replicate only received (ingress) traffic";
      }
      enum tx-only {
        value 2;
        description "Replicate only transmitted (egress) traffic";
      }
    }
    description "Span traffic direction";
  }
  typedef Span-mirror-interval {
    type enumeration {
      enum 512 {
        value 1;
        description "Mirror 1 in every 512 packets";
      }
      enum 1k {
        value 2;
        description "Mirror 1 in every 1024 packets";
      }
      enum 2k {
        value 3;
        description "Mirror 1 in every 2048 packets";
      }
      enum 4k {
        value 4;
        description "Mirror 1 in every 4096 packets";
      }
      enum 8k {
        value 5;
        description "Mirror 1 in every 8192 packets";
      }
      enum 16k {
        value 6;
        description "Mirror 1 in every 16384 packets";
      }
    }
    description "Span mirror interval";
  }
  typedef Span-destination {
    type enumeration {
      enum interface {
        value 0;
        description "Destination Interface";
      }
      enum pseudowire {
        value 1;
        description "Destination Pseudowire";
      }
      enum ipv4-address {
        value 2;
        description "Destination next-hop IPv4 address";
      }
      enum ipv6-address {
        value 3;
        description "Destination next-hop IPv6 address";
      }
    }
    description "Span destination";
  }

  grouping MIRROR-INTERVAL {
    description
      "Common node of span-monitor-session,
      span-monitor-session";
    leaf mirror-interval {
      xr:xr-xml-map "ethernet-span_attach_cfg:MirrorInterval";
      type Span-mirror-interval;
      description "Specify the mirror interval";
    }
  }

  grouping MIRROR-FIRST {
    description
      "Common node of span-monitor-session,
      span-monitor-session";
    leaf mirror-first {
      xr:xr-xml-map "ethernet-span_attach_cfg:MirrorFirst";
      type uint32 {
        range "1..10000";
      }
      units "byte";
      description
        "Mirror a specified number of bytes from start of
        packet";
    }
  }

  grouping SPAN-MONITOR-SESSION-TABLE {
    description
      "Common node of ip-subscriber, ppp,
      subscriber-service";

    container span-monitor-sessions {
      xr:xr-xml-map "ethernet-span_dyn_tmpl_cfg:SPANMonitorSessionT"+
        "able";
      description "Monitor Session container for this template";

      list span-monitor-session {
        xr:xr-xml-map "ethernet-span_dyn_tmpl_cfg:SPANMonitorSessio"+
          "n";
        key "session-class";
        description
          "Configuration for a particular class of Monitor
          Session";
        leaf session-class {
          xr:xr-xml-map "ethernet-span_dyn_tmpl_cfg:SessionClass";
          type dt1:Span-session-class;
          description "Session Class";
        }
        uses MIRROR-FIRST;
        uses ATTACHMENT;
        uses MIRROR-INTERVAL;
        uses ACL;
      }
    }
  }

  grouping ETHERNET-SPAN-INTERFACE-CFG-SPAN-MONITOR-SESSION-TABLE {
    description
      "Common node of interface-configuration,
      l2-transport";

    container span-monitor-sessions {
      xr:xr-xml-map "ethernet-span_interface_cfg:SPANMonitorSession"+
        "Table";
      description
        "Monitor Session container for this source
        interface";

      list span-monitor-session {
        xr:xr-xml-map "ethernet-span_interface_cfg:SPANMonitorSessi"+
          "on";
        key "session-class";
        description
          "Configuration for a particular class of Monitor
          Session";
        leaf session-class {
          xr:xr-xml-map "ethernet-span_interface_cfg:SessionClass";
          type dt1:Span-session-class;
          description "Session Class";
        }
        uses MIRROR-FIRST;
        uses ATTACHMENT;
        uses MIRROR-INTERVAL;
        uses ACL;
      }
    }
  }

  grouping ACL {
    description
      "Common node of span-monitor-session,
      span-monitor-session";
    leaf acl {
      xr:xr-xml-map "ethernet-span_attach_cfg:ACL";
      type empty;
      description "Enable ACL matching for traffic mirroring";
    }
  }

  grouping ATTACHMENT {
    description
      "Common node of span-monitor-session,
      span-monitor-session";

    container attachment {
      xr:xr-xml-map "ethernet-span_attach_cfg:Attachment";
      presence "Indicates a attachment node is configured.";
      description "Attach the interface to a Monitor Session";
      leaf session-name {
        xr:xr-xml-map "ethernet-span_attach_cfg:SessionName";
        type dt1:Span-session-name;
        mandatory true;
        description "Session Name";
      }
      leaf direction {
        xr:xr-xml-map "ethernet-span_attach_cfg:Direction";
        type Span-traffic-direction;
        description
          "Specify the direction of traffic to replicate
          (optional)";
      }
      leaf port-level-enable {
        xr:xr-xml-map "ethernet-span_attach_cfg:PortLevelEnable";
        type empty;
        description "Enable port level traffic mirroring";
      }
    }
  }

  container span-monitor-session {
    xr:xr-xml-map "ethernet-span_cfg:SpanMonitorSession";
    description "none";

    container sessions {
      xr:xr-xml-map "ethernet-span_cfg:SessionTable";
      description "Monitor-session configuration commands";

      list session {
        xr:xr-xml-map "ethernet-span_cfg:Session";
        key "session";
        description
          "Configuration for a particular Monitor Session";

        container destination {
          xr:xr-xml-map "ethernet-span_cfg:Destination";
          description "Specify a destination";
          leaf destination-type {
            xr:xr-xml-map "ethernet-span_cfg:DestinationType";
            type Span-destination;
            description "Specify the type of destination";
          }
          leaf destination-interface-name {
            xr:xr-xml-map "ethernet-span_cfg:DestinationInterfaceNa"+
              "me";
            when "../destination-type = 'interface'" {
              description "../DestinationType = 0";
            }
            type xr:Interface-name;
            description "Specify the destination interface name";
          }
          leaf destination-ipv4-address {
            xr:xr-xml-map "ethernet-span_cfg:DestinationIPv4Address";
            when "../destination-type = 'ipv4-address'" {
              description "../DestinationType = 2";
            }
            type inet:ipv4-address-no-zone;
            description
              "Specify the destination next-hop IPv4 address";
          }
          leaf destination-ipv6-address {
            xr:xr-xml-map "ethernet-span_cfg:DestinationIPv6Address";
            when "../destination-type = 'ipv6-address'" {
              description "../DestinationType = 3";
            }
            type inet:ipv6-address-no-zone;
            description
              "Specify the destination next-hop IPv6 address";
          }
        }
        leaf class {
          xr:xr-xml-map "ethernet-span_cfg:Class";
          type dt1:Span-session-class;
          default "ethernet";
          description
            "Enable a Monitor Session.  Setting this item
            causes the Monitor Session to be created.";
        }
        leaf session {
          xr:xr-xml-map "ethernet-span_cfg:Session";
          type dt1:Span-session-name;
          description "Session Name";
        }
      }
    }
  }

  augment "/a1:interface-configurations/a1:interface-configuration"+
    "/a2:l2-transport" {
    description
      "This augment extends the configuration data of
      'Cisco-IOS-XR-l2vpn-cfg'";
    uses ETHERNET-SPAN-INTERFACE-CFG-SPAN-MONITOR-SESSION-TABLE;
  }

  augment "/a1:interface-configurations/a1:interface-configuration" {
    description
      "This augment extends the configuration data of
      'Cisco-IOS-XR-ifmgr-cfg'";
    uses ETHERNET-SPAN-INTERFACE-CFG-SPAN-MONITOR-SESSION-TABLE;
  }
}
