module Cisco-IOS-XR-nto-misc-oper {

  /*** NAMESPACE / PREFIX DEFINITION ***/

  namespace "http://cisco.com/ns/yang/Cisco-IOS-XR-nto-misc-oper";


  prefix "nto-misc-oper";

  /*** LINKAGE (IMPORTS / INCLUDES) ***/

  import Cisco-IOS-XR-types { prefix "xr"; }

  include Cisco-IOS-XR-nto-misc-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR nto-misc package operational data.

     This module contains definitions
     for the following management objects:
       memory-summary: Memory summary information

     Copyright (c) 2013-2015 by Cisco Systems, Inc.
     All rights reserved.";

  revision "2015-11-09" {
    description
      "IOS XR 6.0 revision.";
  }


  container memory-summary {
    xr:xr-xml-map "nto_misc_oper:MemorySummary";
    config false;
    description "Memory summary information";

    container nodes {
      xr:xr-xml-map "nto_misc_oper:NodeTable";
      description "List of nodes";

      list node {
        xr:xr-xml-map "nto_misc_oper:Node";
        key "node-name";
        description "Name of nodes";

        container summary {
          xr:xr-xml-map "nto_misc_oper:Summary";
          description
            "Memory summary information for a specific node";
          uses NODE-MEM-INFO;
        }
        leaf node-name {
          xr:xr-xml-map "nto_misc_oper:NodeName";
          type xr:Node-id;
          description "Node name";
        }
      }
    }
  }
}
