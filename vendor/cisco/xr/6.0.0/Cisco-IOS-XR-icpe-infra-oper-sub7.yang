submodule Cisco-IOS-XR-icpe-infra-oper-sub7 {

  belongs-to Cisco-IOS-XR-icpe-infra-oper {
    prefix Cisco-IOS-XR-icpe-infra-oper;
  }

  /*** LINKAGE (IMPORTS / INCLUDES) ***/

  import Cisco-IOS-XR-types { prefix "xr"; }

  include Cisco-IOS-XR-icpe-infra-oper-sub5 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2015 by Cisco Systems, Inc.
     All rights reserved.";

  revision "2015-11-09" {
    description
      "IOS XR 6.0 revision.";
  }


  grouping ICPE-INSTALL-STATUS-DETAIL {
    description "Detailed breakdown of install status";
    leaf satellite-range-xr {
      xr:xr-xml-map "icpe_install_data_gen:satellite-range-xr";
      type Xr-yang-string;
      description "Satellite range";
    }
    leaf operation-id {
      xr:xr-xml-map "icpe_install_data_gen:OperationID";
      type uint32;
      description "Operation ID";
    }
    leaf-list sats-not-initiated {
      xr:xr-xml-map "icpe_install_data_gen:SatsNotInitiated";
      type uint16;
      description "Sats not initiated";
    }
    leaf-list sats-transferring {
      xr:xr-xml-map "icpe_install_data_gen:SatsTransferring";
      type uint16;
      description "Sats transferring";
    }
    leaf-list sats-activating {
      xr:xr-xml-map "icpe_install_data_gen:SatsActivating";
      type uint16;
      description "Sats activating";
    }
    leaf-list sats-transfer-failed {
      xr:xr-xml-map "icpe_install_data_gen:SatsTransferFailed";
      type uint16;
      description "Sats transfer failed";
    }
    leaf-list sats-activate-failed {
      xr:xr-xml-map "icpe_install_data_gen:SatsActivateFailed";
      type uint16;
      description "Sats activate failed";
    }
    leaf-list sats-transfer-aborted {
      xr:xr-xml-map "icpe_install_data_gen:SatsTransferAborted";
      type uint16;
      description "Sats transfer aborted";
    }
    leaf-list sats-activate-aborted {
      xr:xr-xml-map "icpe_install_data_gen:SatsActivateAborted";
      type uint16;
      description "Sats activate aborted";
    }
    leaf-list sats-no-operation {
      xr:xr-xml-map "icpe_install_data_gen:SatsNoOperation";
      type uint16;
      description "Sats no operation";
    }
    leaf-list sats-completed {
      xr:xr-xml-map "icpe_install_data_gen:SatsCompleted";
      type uint16;
      description "Sats completed";
    }
  }
}
