submodule Cisco-IOS-XR-asr9k-netflow-oper-sub2 {

  belongs-to Cisco-IOS-XR-asr9k-netflow-oper {
    prefix Cisco-IOS-XR-asr9k-netflow-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-netflow package operational data.

     Copyright (c) 2013-2015 by Cisco Systems, Inc.
     All rights reserved.";

  revision "2015-11-09" {
    description
      "IOS XR 6.0 revision.";
  }


  grouping NF-PRODUCER-STATS {
    description "Netflow Platform Producer Process statistics";
    leaf ipv4-ingress-flows {
      xr:xr-xml-map "netflow_producer_types:IPv4IngressFlows";
      type uint64;
      description "IPv4 ingress flows";
    }
    leaf ipv4-egress-flows {
      xr:xr-xml-map "netflow_producer_types:IPv4EgressFlows";
      type uint64;
      description "IPv4 egress flows";
    }
    leaf ipv6-ingress-flows {
      xr:xr-xml-map "netflow_producer_types:IPv6IngressFlows";
      type uint64;
      description "IPv6 ingress flows";
    }
    leaf ipv6-egress-flows {
      xr:xr-xml-map "netflow_producer_types:IPv6EgressFlows";
      type uint64;
      description "IPv6 egress flows";
    }
    leaf mpls-ingress-flows {
      xr:xr-xml-map "netflow_producer_types:MPLSIngressFlows";
      type uint64;
      description "MPLS ingress flows";
    }
    leaf mpls-egress-flows {
      xr:xr-xml-map "netflow_producer_types:MPLSEgressFlows";
      type uint64;
      description "MPLS egress flows";
    }
    leaf drops-no-space {
      xr:xr-xml-map "netflow_producer_types:DropsNoSpace";
      type uint64;
      description "Drops (no space)";
    }
    leaf drops-others {
      xr:xr-xml-map "netflow_producer_types:DropsOthers";
      type uint64;
      description "Drops (others)";
    }
    leaf unknown-ingress-flows {
      xr:xr-xml-map "netflow_producer_types:UnknownIngressFlows";
      type uint64;
      description "Unknown ingress flows";
    }
    leaf unknown-egress-flows {
      xr:xr-xml-map "netflow_producer_types:UnknownEgressFlows";
      type uint64;
      description "Unknown egress flows";
    }
    leaf waiting-servers {
      xr:xr-xml-map "netflow_producer_types:WaitingServers";
      type uint64;
      description "Number of waiting servers";
    }
    leaf spp-rx-counts {
      xr:xr-xml-map "netflow_producer_types:SppRxCounts";
      type uint64;
      description "Number of Rxed SPP Packets";
    }
    leaf flow-packet-counts {
      xr:xr-xml-map "netflow_producer_types:FlowPacketCounts";
      type uint64;
      description "Number of Rxed Flow Packets";
    }
    leaf last-cleared {
      xr:xr-xml-map "netflow_producer_types:LastCleared";
      type string;
      description
        "Last time Statistics cleared in 'Mon Jan 1 12:00
        :00 2xxx' format";
    }
  }
}
