submodule Cisco-IOS-XR-dnx-netflow-oper-sub5 {

  belongs-to Cisco-IOS-XR-dnx-netflow-oper {
    prefix Cisco-IOS-XR-dnx-netflow-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-netflow package operational data.

     Copyright (c) 2013-2015 by Cisco Systems, Inc.
     All rights reserved.";

  revision "2015-11-09" {
    description
      "IOS XR 6.0 revision.";
  }


  grouping NFMGR-EXPORTER-NAME {
    description "Exporter name";
    leaf name {
      xr:xr-xml-map "netflow_monitor_types:Name";
      type string;
      description "Exporter name";
    }
  }

  grouping NFMGR-FMM-EDM-INFO {
    description "Netflow flow monitor data";
    leaf id {
      xr:xr-xml-map "netflow_monitor_types:ID";
      type uint32;
      description "Unique ID in the global flow monitor ID space";
    }
    leaf name {
      xr:xr-xml-map "netflow_monitor_types:Name";
      type string;
      description "Name of the flow monitor map";
    }
    leaf record-map {
      xr:xr-xml-map "netflow_monitor_types:RecordMap";
      type string;
      description "Name of the flow record map";
    }
    leaf cache-aging-mode {
      xr:xr-xml-map "netflow_monitor_types:CacheAgingMode";
      type string;
      description "Aging mode for flow cache";
    }
    leaf number-of-labels {
      xr:xr-xml-map "netflow_monitor_types:NumberOfLabels";
      type uint32;
      description "Number of MPLS labels in key";
    }
    leaf cache-max-entry {
      xr:xr-xml-map "netflow_monitor_types:CacheMaxEntry";
      type uint32;
      description "Max num of entries in flow cache";
    }
    leaf cache-active-timeout {
      xr:xr-xml-map "netflow_monitor_types:CacheActiveTimeout";
      type uint32;
      units "second";
      description "Cache active flow timeout in seconds";
    }
    leaf cache-inactive-timeout {
      xr:xr-xml-map "netflow_monitor_types:CacheInactiveTimeout";
      type uint32;
      units "second";
      description "Cache inactive flow timeout in seconds";
    }
    leaf cache-update-timeout {
      xr:xr-xml-map "netflow_monitor_types:CacheUpdateTimeout";
      type uint32;
      units "second";
      description "Cache update timeout in seconds";
    }
    leaf cache-timeout-rate-limit {
      xr:xr-xml-map "netflow_monitor_types:CacheTimeoutRateLimit";
      type uint32;
      description "Maximum number of entries to age each second";
    }
    leaf options {
      xr:xr-xml-map "netflow_monitor_types:Options";
      type uint32;
      description "Options applied to the flow monitor";
    }

    list exporter {
      max-elements "8";
      description
        "Name of the flow exporters used by the flow
        monitor";
      uses NFMGR-EXPORTER-NAME;
    }
  }
}
