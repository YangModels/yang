module Cisco-IOS-XR-ha-eem-oper {

  /*** NAMESPACE / PREFIX DEFINITION ***/

  namespace "http://cisco.com/ns/yang/Cisco-IOS-XR-ha-eem-oper";


  prefix "ha-eem-oper";

  /*** LINKAGE (IMPORTS / INCLUDES) ***/

  import Cisco-IOS-XR-types { prefix "xr"; }

  include Cisco-IOS-XR-ha-eem-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ha-eem package operational data.

     This module contains definitions
     for the following management objects:
       system-monitoring: Processes operational data

     Copyright (c) 2013-2015 by Cisco Systems, Inc.
     All rights reserved.";

  revision "2015-01-07" {
    description
      "IOS XR 5.3.1 revision.";
  }


  container system-monitoring {
    xr:xr-xml-map "ha_eem_oper:SystemMonitoring";
    config false;
    description "Processes operational data";

    list cpu-utilization {
      xr:xr-xml-map "ha_eem_oper:CPUUtilization";
      key "node-name";
      description "Processes CPU utilization information";
      leaf node-name {
        xr:xr-xml-map "ha_eem_oper:NodeName";
        type xr:Node-id;
        description "Node name";
      }
      uses NODE-CPU-UTIL;
    }
  }
}
