submodule Cisco-IOS-XR-ip-rib-ipv4-oper-sub1 {

  belongs-to Cisco-IOS-XR-ip-rib-ipv4-oper {
    prefix Cisco-IOS-XR-ip-rib-ipv4-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rib-ipv4 package operational data.

     Copyright (c) 2013-2015 by Cisco Systems, Inc.
     All rights reserved.";

  revision "2015-11-09" {
    description
      "IOS XR 6.0 revision.";
  }

  typedef Ipv4-rib-edm-addr {
    type inet:ipv4-address;
    description "Ipv4 rib edm addr";
  }

  grouping RIB-EDM-ROUTE-COUNT {
    description "Specifics of route count";
    leaf active-routes-count {
      xr:xr-xml-map "rib_edm:ActiveRoutesCount";
      type uint32;
      description "Number of active routes";
    }
    leaf num-backup-routes {
      xr:xr-xml-map "rib_edm:num_backup_routes";
      type uint32;
      description "Number of backup (inactive) routes";
    }
    leaf num-active-paths {
      xr:xr-xml-map "rib_edm:num_active_paths";
      type uint32;
      description "Number of paths to active routes";
    }
    leaf num-backup-paths {
      xr:xr-xml-map "rib_edm:num_backup_paths";
      type uint32;
      description "Number of paths to backup routes";
    }
  }

  grouping RIB-EDM-PROTO-ROUTE-SUMM-DETAIL {
    description "Details of Protocol route types";

    container proto-route-count {
      description "Count for proto. instance";
      uses RIB-EDM-ROUTE-COUNT;
    }

    container rtype-none {
      description "No route type";
      uses RIB-EDM-ROUTE-COUNT;
    }

    container rtype-other {
      description "Unknown route type";
      uses RIB-EDM-ROUTE-COUNT;
    }

    container rtype-ospf-intra {
      description "OSPF route within an area";
      uses RIB-EDM-ROUTE-COUNT;
    }

    container rtype-ospf-inter {
      description "OSPF route across diff. areas";
      uses RIB-EDM-ROUTE-COUNT;
    }

    container rtype-ospf-extern1 {
      description "OSPF external route of type 1";
      uses RIB-EDM-ROUTE-COUNT;
    }

    container rtype-ospf-extern2 {
      description "OSPF external route of type 2";
      uses RIB-EDM-ROUTE-COUNT;
    }

    container rtype-isis-sum {
      description "IS-IS summary route";
      uses RIB-EDM-ROUTE-COUNT;
    }

    container rtype-isis-l1 {
      description "IS-IS level 1 route";
      uses RIB-EDM-ROUTE-COUNT;
    }

    container rtype-isis-l2 {
      description "IS-IS level 2 route";
      uses RIB-EDM-ROUTE-COUNT;
    }

    container rtype-isis-l1-ia {
      description "IS-IS level1 inter-area route";
      uses RIB-EDM-ROUTE-COUNT;
    }

    container rtype-bgp-int {
      description "iBGP route";
      uses RIB-EDM-ROUTE-COUNT;
    }

    container rtype-bgp-ext {
      description "eBGP route";
      uses RIB-EDM-ROUTE-COUNT;
    }

    container rtype-bgp-loc {
      description "BGP local route";
      uses RIB-EDM-ROUTE-COUNT;
    }

    container rtype-ospf-nssa1 {
      description "OSPF NSSA ext. route type 1";
      uses RIB-EDM-ROUTE-COUNT;
    }

    container rtype-ospf-nssa2 {
      description "OSPF NSSA ext. route type 2";
      uses RIB-EDM-ROUTE-COUNT;
    }

    container rtype-igrp2-int {
      description "EIGRP internal route";
      uses RIB-EDM-ROUTE-COUNT;
    }

    container rtype-igrp2-ext {
      description "EIGRP external route";
      uses RIB-EDM-ROUTE-COUNT;
    }
    leaf name {
      xr:xr-xml-map "rib_edm:name";
      type string;
      description "Proto name";
    }
    leaf instance {
      xr:xr-xml-map "rib_edm:Instance";
      type string;
      description "Instance";
    }
  }

  grouping IPV4-RIB-EDM-ADVERT {
    description "Route advertisement information";

    list ipv4-rib-edm-advert {
      description "ipv4 rib edm advert";
      leaf protocol-id {
        type uint32;
        description "Protocol advertising the route";
      }
      leaf client-id {
        type uint32;
        description "  Client advertising the route";
      }
      leaf number-of-extended-communities {
        type uint32;
        description "Number of extended communities";
      }
      leaf extended-communities {
        type yang:hex-string;
        description "Extended communities";
      }
      leaf protocol-opaque-flags {
        type uint8;
        description "OSPF area-id flags";
      }
      leaf protocol-opaque {
        type uint32;
        description "OSPF area-id";
      }
      leaf code {
        type int8;
        description "Protocol code";
      }
      leaf instance-name {
        type string {
          length "0..41";
        }
        description "Instance name";
      }
    }
  }

  grouping IPV4-RIB-EDM-PROTO {
    description "Information of a rib protocol";
    leaf protocol-names {
      xr:xr-xml-map "rib_edm:ProtocolNames";
      type string;
      description "Name";
    }
    leaf instance {
      xr:xr-xml-map "rib_edm:Instance";
      type string;
      description "Instance";
    }
    leaf version {
      xr:xr-xml-map "rib_edm:Version";
      type uint32;
      description "Proto version";
    }
    leaf redistribution-client-count {
      xr:xr-xml-map "rib_edm:RedistributionClientCount";
      type uint32;
      description "Number of redist clients";
    }
    leaf protocol-clients-count {
      xr:xr-xml-map "rib_edm:ProtocolClientsCount";
      type uint32;
      description "Number of proto clients";
    }
    leaf routes-counts {
      xr:xr-xml-map "rib_edm:RoutesCounts";
      type uint32;
      description
        "Number of routes (including active, backup and
        deleted), where, number of backup routes =
        RoutesCounts - ActiveRoutesCount -
        DeletedRoutesCount ";
    }
    leaf active-routes-count {
      xr:xr-xml-map "rib_edm:ActiveRoutesCount";
      type uint32;
      description "Number of active routes (not deleted)";
    }
    leaf deleted-routes-count {
      xr:xr-xml-map "rib_edm:DeletedRoutesCount";
      type uint32;
      description "Number of deleted routes";
    }
    leaf paths-count {
      xr:xr-xml-map "rib_edm:PathsCount";
      type uint32;
      description "Number of paths for all routes";
    }
    leaf protocol-route-memory {
      xr:xr-xml-map "rib_edm:ProtocolRouteMemory";
      type uint32;
      units "byte";
      description "Memory for proto's routes and paths in bytes";
    }
  }

  grouping RIB-EDM-OPAQUE-OBJ {
    description "Informaton of an opaque data";
    leaf key {
      xr:xr-xml-map "rib_edm:key";
      type yang:hex-string;
      description "key";
    }
    leaf data {
      xr:xr-xml-map "rib_edm:data";
      type yang:hex-string;
      description "data";
    }
  }

  grouping IPV4-RIB-EDM-PATH {
    description "Information of a rib path";

    list ipv4-rib-edm-path {
      description "ipv4 rib edm path";
      leaf address {
        type Ipv4-rib-edm-addr;
        description "Nexthop";
      }
      leaf information-source {
        type Ipv4-rib-edm-addr;
        description "Infosource";
      }
      leaf v6-nexthop {
        type inet:ipv6-address;
        description "V6 nexthop";
      }
      leaf interface-name {
        type xr:Interface-name;
        description "Interface Name";
      }
      leaf metric {
        type uint32;
        description "Metrics";
      }
      leaf load-metric {
        type uint32;
        description "Load Metrics";
      }
      leaf flags64 {
        type uint64;
        description "Flags extended to 64 bits";
      }
      leaf flags {
        type uint16;
        description "Flags";
      }
      leaf private-flags {
        type uint16;
        description "Private Flags";
      }
      leaf looped {
        type boolean;
        description "Looping path";
      }
      leaf next-hop-table-id {
        type uint32;
        description "Nexthop tableid";
      }
      leaf next-hop-vrf-name {
        type string;
        description "VRF Name of the nh table";
      }
      leaf next-hop-table-name {
        type string;
        description "NH table name";
      }
      leaf next-hop-afi {
        type uint32;
        description "NH afi";
      }
      leaf next-hop-safi {
        type uint32;
        description "NH safi";
      }
      leaf route-label {
        type uint32;
        description "Label associated with this path";
      }
      leaf tunnel-id {
        type uint32;
        description "Tunnel ID associated with this path";
      }
      leaf pathid {
        type uint32;
        description "Path id of this path";
      }
      leaf backup-pathid {
        type uint32;
        description "Path id of this path's backup";
      }
      leaf ref-cnt-of-backup {
        type uint32;
        description "Refcnt of backup";
      }
      leaf number-of-extended-communities {
        type uint32;
        description "Number of extended communities";
      }
      leaf extended-communities {
        type yang:hex-string;
        description "Extended communities";
      }
      leaf mvpn-present {
        type boolean;
        description "MVPN attribute present";
      }
      leaf mvpn-attribute {
        type yang:hex-string;
        description "MVPN attribute";
      }
      leaf path-rt-present {
        type boolean;
        description "Path RT present";
      }
      leaf path-rt-attribute {
        type yang:hex-string;
        description "PATHRTAttribute";
      }
      leaf vrf-import-rt-present {
        type boolean;
        description "VRFIMPORTRTPresent";
      }
      leaf vrf-import-rt-attribute {
        type yang:hex-string;
        description "VRFIMPORTRTAttribute";
      }
      leaf source-asrt-present {
        type boolean;
        description "SOURCEASRTPresent";
      }
      leaf source-asrt-attribute {
        type yang:hex-string;
        description "SOURCEASRTAttribute";
      }
      leaf source-rd-present {
        type boolean;
        description "SOURCERDPresent";
      }
      leaf source-rd-attribute {
        type yang:hex-string;
        description "SOURCERDAttribute";
      }
      leaf segmented-nexthop-present {
        type boolean;
        description "SegmentedNexthopPresent";
      }
      leaf segmented-nexthop-attribute {
        type yang:hex-string;
        description "SegmentedNexthopAttribute";
      }
      leaf next-hop-id {
        type uint32;
        description "NHID associated with this path";
      }
      leaf next-hop-id-refcount {
        type uint32;
        description "NHID references";
      }
      leaf ospf-area-id {
        type uint32;
        description "OSPF area associated with the path";
      }
      leaf has-labelstk {
        type boolean;
        description "Path has a label stack";
      }
      leaf num-labels {
        type uint8;
        description "Number of labels in stack";
      }
      leaf binding-label {
        type uint32;
        description "binding Label for this path";
      }
      leaf nhid-feid {
        type uint64;
        description "Fib nhid encap id";
      }
      leaf mpls-feid {
        type uint64;
        description "Fib mpls encap id";
      }
      leaf-list remote-backup-addr {
        type Ipv4-rib-edm-addr;
        max-elements "2";
        description "Remote backup node address";
      }
      leaf-list labelstk {
        type uint32;
        max-elements "3";
        description "Labels for this path";
      }
    }
  }

  grouping IPV4-RIB-EDM-ROUTE {
    description
      "Information of a rib route head and rib proto
      route";

    container route-path {
      description "Path(s) of the route";
      uses IPV4-RIB-EDM-PATH;
    }
    leaf prefix {
      xr:xr-xml-map "rib_edm:Prefix";
      type Ipv4-rib-edm-addr;
      description "Route prefix";
    }
    leaf prefix-length-xr {
      xr:xr-xml-map "rib_edm:prefix-length-xr";
      type uint8;
      description "Length of prefix";
    }
    leaf route-version {
      xr:xr-xml-map "rib_edm:RouteVersion";
      type uint32;
      description "Route version";
    }
    leaf protocol-id {
      xr:xr-xml-map "rib_edm:ProtocolID";
      type uint32;
      description "Protocol advertising the route";
    }
    leaf protocol-name {
      xr:xr-xml-map "rib_edm:ProtocolName";
      type string;
      description " Name of Protocol";
    }
    leaf instance {
      xr:xr-xml-map "rib_edm:Instance";
      type string;
      description "Instance name";
    }
    leaf client-id {
      xr:xr-xml-map "rib_edm:ClientID";
      type uint32;
      description "Client adding the route to RIB";
    }
    leaf route-type {
      xr:xr-xml-map "rib_edm:RouteType";
      type uint16;
      description "Route type";
    }
    leaf priority {
      xr:xr-xml-map "rib_edm:Priority";
      type uint8;
      description "Route priority";
    }
    leaf svd-type {
      xr:xr-xml-map "rib_edm:SVDType";
      type uint8;
      description "SVD Type of route";
    }
    leaf flags {
      xr:xr-xml-map "rib_edm:Flags";
      type uint32;
      description "Route flags";
    }
    leaf tag {
      xr:xr-xml-map "rib_edm:Tag";
      type uint32;
      description "Opaque proto specific info";
    }
    leaf distance {
      xr:xr-xml-map "rib_edm:Distance";
      type uint32;
      description "Distance of the route";
    }
    leaf diversion-distance {
      xr:xr-xml-map "rib_edm:DiversionDistance";
      type uint32;
      description "Diversion distance of the route";
    }
    leaf metric {
      xr:xr-xml-map "rib_edm:Metric";
      type uint32;
      description "Route metric";
    }
    leaf paths-count {
      xr:xr-xml-map "rib_edm:PathsCount";
      type uint32;
      description "Number of paths";
    }
    leaf attribute-identity {
      xr:xr-xml-map "rib_edm:AttributeIdentity";
      type uint32;
      description "BGP Attribute ID";
    }
    leaf traffic-index {
      xr:xr-xml-map "rib_edm:TrafficIndex";
      type uint8;
      description "BGP Traffic Index";
    }
    leaf route-precedence {
      xr:xr-xml-map "rib_edm:RoutePrecedence";
      type uint8;
      description "Route ip precedence";
    }
    leaf qos-group {
      xr:xr-xml-map "rib_edm:QosGroup";
      type uint8;
      description "Route qos group";
    }
    leaf flow-tag {
      xr:xr-xml-map "rib_edm:FlowTag";
      type uint8;
      description "Flow tag";
    }
    leaf fwd-class {
      xr:xr-xml-map "rib_edm:FwdClass";
      type uint8;
      description "Forward Class";
    }
    leaf pic-count {
      xr:xr-xml-map "rib_edm:PICCount";
      type uint8;
      description "Number of pic paths in this route";
    }
    leaf active {
      xr:xr-xml-map "rib_edm:Active";
      type boolean;
      description "Is the route active or backup";
    }
    leaf diversion {
      xr:xr-xml-map "rib_edm:Diversion";
      type boolean;
      description "Route has a diversion path";
    }
    leaf diversion-proto-name {
      xr:xr-xml-map "rib_edm:DiversionProtoName";
      type string;
      description "Diversion route protocol name";
    }
    leaf route-age {
      xr:xr-xml-map "rib_edm:RouteAge";
      type uint32;
      units "second";
      description "Age of route (seconds)";
    }
    leaf route-label {
      xr:xr-xml-map "rib_edm:RouteLabel";
      type uint32;
      description "Local label of the route";
    }
    leaf version {
      xr:xr-xml-map "rib_edm:Version";
      type uint32;
      description "Route Version";
    }
    leaf tbl-version {
      xr:xr-xml-map "rib_edm:TblVersion";
      type uint64;
      description "Table Version";
    }
    leaf route-modify-time {
      xr:xr-xml-map "rib_edm:RouteModifyTime";
      type uint64;
      units "nanosecond";
      description "Route modification time(nanoseconds)";
    }
  }
}
