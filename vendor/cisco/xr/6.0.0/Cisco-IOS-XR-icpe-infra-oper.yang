module Cisco-IOS-XR-icpe-infra-oper {

  /*** NAMESPACE / PREFIX DEFINITION ***/

  namespace "http://cisco.com/ns/yang/Cisco-IOS-XR-icpe-infra-oper";


  prefix "icpe-infra-oper";

  /*** LINKAGE (IMPORTS / INCLUDES) ***/

  import Cisco-IOS-XR-types { prefix "xr"; }

  include Cisco-IOS-XR-icpe-infra-oper-sub7 {
    revision-date 2015-11-09;
  }

  include Cisco-IOS-XR-icpe-infra-oper-sub6 {
    revision-date 2015-11-09;
  }

  include Cisco-IOS-XR-icpe-infra-oper-sub5 {
    revision-date 2015-11-09;
  }

  include Cisco-IOS-XR-icpe-infra-oper-sub4 {
    revision-date 2015-11-09;
  }

  include Cisco-IOS-XR-icpe-infra-oper-sub3 {
    revision-date 2015-11-09;
  }

  include Cisco-IOS-XR-icpe-infra-oper-sub2 {
    revision-date 2015-11-09;
  }

  include Cisco-IOS-XR-icpe-infra-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR icpe-infra package operational data.

     This module contains definitions
     for the following management objects:
       nv-satellite: Satellite operational information

     Copyright (c) 2013-2015 by Cisco Systems, Inc.
     All rights reserved.";

  revision "2015-11-09" {
    description
      "IOS XR 6.0 revision.";
  }


  container nv-satellite {
    xr:xr-xml-map "icpe_sat_oper_yang_gen:nVSatellite";
    config false;
    description "Satellite operational information";

    container install-statuses {
      xr:xr-xml-map "icpe_install_yang_gen:InstallStatusTable";
      description "Detailed breakdown of install status table";

      list install-status {
        xr:xr-xml-map "icpe_install_yang_gen:InstallStatus";
        key "satellite-range";
        description "Detailed breakdown of install status";
        leaf satellite-range {
          xr:xr-xml-map "icpe_install_yang_gen:SatelliteRange";
          type xr:Cisco-ios-xr-string;
          description "Satellite range";
        }
        uses ICPE-INSTALL-STATUS-DETAIL;
      }
    }

    container sdacp-redundancies {
      xr:xr-xml-map "icpe_redundancy_oper_yang_gen:SDACPRedundancyT"+
        "able";
      description
        "nV Satellite Redundancy Protocol Information
        table";

      list sdacp-redundancy {
        xr:xr-xml-map "icpe_redundancy_oper_yang_gen:SDACPRedundanc"+
          "y";
        key "iccp-group";
        description "nV Satellite Redundancy Protocol Information";
        leaf iccp-group {
          xr:xr-xml-map "icpe_redundancy_oper_yang_gen:ICCPGroup";
          type uint32 {
            range "0..4294967295";
          }
          description "ICCP group";
        }
        uses ICPE-REDUNDANCY-SESSION;
      }
    }

    container satellite-statuses {
      xr:xr-xml-map "icpe_oper_yang_gen:SatelliteStatusTable";
      description "Satellite status information table";

      list satellite-status {
        xr:xr-xml-map "icpe_oper_yang_gen:SatelliteStatus";
        key "satellite-id";
        description "Satellite status information";
        leaf satellite-id {
          xr:xr-xml-map "icpe_oper_yang_gen:SatelliteID";
          type uint32 {
            range "0..4294967295";
          }
          description "Satellite ID";
        }
        uses ICPE-OPER-SAT-STATUS;
      }
    }

    container satellite-topologies {
      xr:xr-xml-map "icpe_topo_oper_yang_gen:SatelliteTopologyTable";
      description "Satellite Topology Information table";

      list satellite-topology {
        xr:xr-xml-map "icpe_topo_oper_yang_gen:SatelliteTopology";
        key "interface-name";
        description "Satellite Topology Information";
        leaf interface-name {
          xr:xr-xml-map "icpe_topo_oper_yang_gen:InterfaceName";
          type xr:Cisco-ios-xr-string;
          description "Interface name";
        }
        uses ICPE-OPER-TOPO-CSFL-TYPE;
      }
    }

    container install-progresses {
      xr:xr-xml-map "icpe_install_progress_yang_gen:InstallProgress"+
        "Table";
      description "Current percentage of install table";

      list install-progress {
        xr:xr-xml-map "icpe_install_progress_yang_gen:InstallProgre"+
          "ss";
        key "progress-percentage";
        description "Current percentage of install";
        leaf progress-percentage {
          xr:xr-xml-map "icpe_install_progress_yang_gen:ProgressPer"+
            "centage";
          type uint32 {
            range "0..2147483647";
          }
          units "percentage";
          description "Progress percentage";
        }
        uses ICPE-INSTALL-PROGRESS;
      }
    }

    container reload-statuses {
      xr:xr-xml-map "icpe_reload_yang_gen:ReloadStatusTable";
      description "Detailed breakdown of reload status table";

      list reload-status {
        xr:xr-xml-map "icpe_reload_yang_gen:ReloadStatus";
        key "satellite-range";
        description "Detailed breakdown of reload status";
        leaf satellite-range {
          xr:xr-xml-map "icpe_reload_yang_gen:SatelliteRange";
          type xr:Cisco-ios-xr-string;
          description "Satellite range";
        }
        uses ICPE-RELOAD-STATUS-DETAIL;
      }
    }

    container install-op-statuses {
      xr:xr-xml-map "icpe_install_op_oper_yang_gen:InstallOpStatusT"+
        "able";
      description "Detailed breakdown of install status table";

      list install-op-status {
        xr:xr-xml-map "icpe_install_op_oper_yang_gen:InstallOpStatu"+
          "s";
        key "operation-id";
        description "Detailed breakdown of install status";
        leaf operation-id {
          xr:xr-xml-map "icpe_install_op_oper_yang_gen:OperationID";
          type uint32 {
            range "0..4294967295";
          }
          description "Operation ID";
        }
        uses ICPE-INSTALL-OP-STATUS-DETAIL;
      }
    }
  }
}
