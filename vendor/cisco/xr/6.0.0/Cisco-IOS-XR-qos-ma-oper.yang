module Cisco-IOS-XR-qos-ma-oper {

  /*** NAMESPACE / PREFIX DEFINITION ***/

  namespace "http://cisco.com/ns/yang/Cisco-IOS-XR-qos-ma-oper";


  prefix "qos-ma-oper";

  /*** LINKAGE (IMPORTS / INCLUDES) ***/

  import Cisco-IOS-XR-types { prefix "xr"; }

  include Cisco-IOS-XR-qos-ma-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR qos-ma package operational data.

     This module contains definitions
     for the following management objects:
       qos: QoS operational data

     Copyright (c) 2013-2015 by Cisco Systems, Inc.
     All rights reserved.";

  revision "2015-01-07" {
    description
      "IOS XR 5.3.1 revision.";
  }


  grouping INPUT {
    description
      "Common node of member-interface,
      nv-satellite-interface";

    container input {
      xr:xr-xml-map "qos_ma_nv_status_oper:Input";
      description
        "A piece of QoS policy-map operational data for
        an interface";
      uses STATUS;
    }
  }

  grouping STATUS {
    description
      "Common node of input, output,
      nv-satellite-interface";

    container status {
      xr:xr-xml-map "qos_ma_nv_status_oper:Status";
      description
        "Policy-map status operational data for an
        interface";
      uses QOS-MA-SAT-IF-EDM-INFO-XML;
    }
  }

  grouping INTERFACE-TABLE {
    description "Common node of qos, policy-map";

    container interface-table {
      xr:xr-xml-map "qos_ma_oper:InterfaceTable";
      description "Operational data for all interfaces";
    }
  }

  grouping OUTPUT {
    description
      "Common node of member-interface,
      nv-satellite-interface";

    container output {
      xr:xr-xml-map "qos_ma_nv_status_oper:Output";
      description
        "A piece of QoS policy-map operational data for
        an interface";
      uses STATUS;
    }
  }

  container qos {
    xr:xr-xml-map "qos_ma_oper:QOS";
    config false;
    description "QoS operational data";

    container nv-interface-table {
      xr:xr-xml-map "qos_ma_oper:nVInterfaceTable";
      description "Operational data for satellite interfaces";
    }

    container nv-satellite {
      xr:xr-xml-map "qos_ma_oper:nVSatellite";
      description "Satellite table";

      container nv-satellite-statistics {
        xr:xr-xml-map "qos_ma_oper:nVSatelliteStatistics";
        description "Satellite statistics based on Satellite ID";

        container nv-satellite-ids {
          xr:xr-xml-map "qos_ma_oper:nVSatelliteIDTable";
          description "Satellite ID table";

          list nv-satellite-id {
            xr:xr-xml-map "qos_ma_oper:nVSatelliteID";
            key "satellite-id";
            description "Satellite ID information";
            leaf satellite-id {
              xr:xr-xml-map "qos_ma_oper:SatelliteID";
              type int32;
              description "Satellite ID";
            }
          }
        }
      }

      container nv-satellite-status {
        xr:xr-xml-map "qos_ma_nv_status_oper:nVSatelliteStatus";
        description
          "Satellite QOS offload status based on Satellite
          ID";

        container nv-satellite-ids {
          xr:xr-xml-map "qos_ma_nv_status_oper:nVSatelliteIDTable";
          description "Satellite ID table";

          list nv-satellite-id {
            xr:xr-xml-map "qos_ma_nv_status_oper:nVSatelliteID";
            key "satellite-id";
            description "Satellite ID information";

            container nv-satellite-interfaces {
              xr:xr-xml-map "qos_ma_nv_status_oper:nVSatelliteInter"+
                "faceTable";
              description
                "QOS offload status of satellite interface of
                a particular satellite";

              list nv-satellite-interface {
                xr:xr-xml-map "qos_ma_nv_status_oper:nVSatelliteInt"+
                  "erface";
                key "interface-name";
                description
                  "QOS offload status for a particular
                  satellite interface";

                container member-interfaces {
                  xr:xr-xml-map "qos_ma_nv_status_oper:MemberInterf"+
                    "aceTable";
                  description "Satellite member interface table";

                  list member-interface {
                    xr:xr-xml-map "qos_ma_nv_status_oper:MemberInte"+
                      "rface";
                    key "interface-name";
                    description
                      "Satellite member interface statistics";
                    leaf interface-name {
                      xr:xr-xml-map "qos_ma_nv_status_oper:Interfac"+
                        "eName";
                      type xr:Interface-name;
                      description "Name of member interface";
                    }
                    uses INPUT;
                    uses OUTPUT;
                  }
                }
                leaf interface-name {
                  xr:xr-xml-map "qos_ma_nv_status_oper:InterfaceNam"+
                    "e";
                  type xr:Interface-name;
                  description "Name of the interface";
                }
                uses INPUT;
                uses STATUS;
                uses OUTPUT;
              }
            }
            leaf satellite-id {
              xr:xr-xml-map "qos_ma_nv_status_oper:SatelliteID";
              type int32;
              description "Satellite ID";
            }
          }
        }
      }
    }

    container nodes {
      xr:xr-xml-map "qos_ma_oper:NodeTable";
      description "Node-specific QoS operational data";

      list node {
        xr:xr-xml-map "qos_ma_oper:Node";
        key "node-name";
        description "QoS operational data for a particular node";

        container policy-map {
          xr:xr-xml-map "qos_ma_oper:PolicyMap";
          description "Operational data for policymaps";
          uses INTERFACE-TABLE;
        }
        leaf node-name {
          xr:xr-xml-map "qos_ma_oper:NodeName";
          type xr:Node-id;
          description "The node";
        }
      }
    }

    container qos-global {
      xr:xr-xml-map "qos_ma_oper:QOSGlobal";
      description "For global registrations";

      container vo-q {
        xr:xr-xml-map "qos_ma_oper:VoQ";
        description "For VoQ operational data";

        container vo-q-statistics {
          xr:xr-xml-map "qos_ma_oper:VoQStatistics";
          description "For VoQ statistics";

          container vo-q-table {
            xr:xr-xml-map "qos_ma_oper:VoQTable";
            description "VoQ interface";
          }
        }
      }
    }
    uses INTERFACE-TABLE;
  }
}
