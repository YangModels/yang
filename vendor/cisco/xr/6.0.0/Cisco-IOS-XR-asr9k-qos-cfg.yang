module Cisco-IOS-XR-asr9k-qos-cfg {

  /*** NAMESPACE / PREFIX DEFINITION ***/

  namespace "http://cisco.com/ns/yang/Cisco-IOS-XR-asr9k-qos-cfg";


  prefix "asr9k-qos-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-qos package configuration.

     This module contains definitions
     for the following management objects:
       qos: Global QOS configuration.

     Copyright (c) 2013-2015 by Cisco Systems, Inc.
     All rights reserved.";

  revision "2015-11-09" {
    description
      "IOS XR 6.0 revision.";
  }

  typedef Qosl2-data-link {
    type enumeration {
      enum aal5 {
        value 0;
        description "ATM adaption layer AAL5";
      }
    }
    description "Qosl2 data link";
  }
  typedef Qosl2-encap {
    type enumeration {
      enum snap-pppoa {
        value 1;
        description
          "snap-pppoa encap used between the DSLAM and CPE";
      }
      enum mux-pppoa {
        value 2;
        description
          "mux-pppoa encap used between the DSLAM and CPE";
      }
      enum snap1483-routed {
        value 3;
        description
          "snap-1483routed encap used between the DSLAM
          and CPE";
      }
      enum mux1483-routed {
        value 4;
        description
          "mux-1483routed encap used between the DSLAM and
          CPE";
      }
      enum snap-rbe {
        value 5;
        description "snap-rbe encap used between the DSLAM and CPE";
      }
      enum snap-dot1qrbe {
        value 6;
        description
          "snap-dot1q-rbe encap used between the DSLAM and
          CPE";
      }
      enum mux-rbe {
        value 7;
        description "mux-rbe encap used between the DSLAM and CPE";
      }
      enum mux-dot1qrbe {
        value 8;
        description
          "mux-dot1q-rbe encap used between the DSLAM and
          CPE";
      }
    }
    description "Qosl2 encap";
  }
  typedef Qos-field-not-supported {
    type enumeration {
      enum not-supported {
        value 0;
        description "Dummy data type leave unspecified";
      }
    }
    description "Qos field not supported";
  }
  typedef Qos-policy-account {
    type enumeration {
      enum no-preference {
        value 0;
        description "No account turn off preference";
      }
      enum layer2 {
        value 1;
        description "Turn on layer 2 accounting";
      }
      enum no-layer2 {
        value 2;
        description "Turn off layer 2 accounting";
      }
      enum user-defined {
        value 4;
        description "User defined accounting";
      }
      enum layer1 {
        value 8;
        description "Turn on layer 1 accounting";
      }
    }
    description "Qos policy account";
  }

  grouping QOS {
    description
      "Common node of interface-configuration, cac, pvp,
      pac, pvc, pvc-mode, nv-satellite-access,
      nv-satellite-fabric-link, satellites";

    container qos {
      xr:xr-xml-map "qos_viking_interface_cfg:QOS";
      description "Interface QOS configuration";

      container l2-overhead {
        xr:xr-xml-map "qos_viking_interface_cfg:L2Overhead";
        description "Layer 2 overhead accounting";

        container account {
          xr:xr-xml-map "qos_viking_interface_cfg:Account";
          description "Access Loop Encapsulation";
          leaf data-link-type {
            xr:xr-xml-map "qos_viking_interface_cfg:DataLinkType";
            type Qosl2-data-link;
            description "Data link type";
          }
          leaf encap-type {
            xr:xr-xml-map "qos_viking_interface_cfg:EncapType";
            type Qosl2-encap;
            description "Encap used between the DSLAM and CPE";
          }
          leaf atm-cell-tax {
            xr:xr-xml-map "qos_viking_interface_cfg:ATMCellTax";
            type boolean;
            description
              "ATM cell tax to be included for overhead
              calculation";
          }
          leaf l2-user-defined {
            xr:xr-xml-map "qos_viking_interface_cfg:L2UserDefined";
            type int32 {
              range "-63..63";
            }
            description "User specified value ";
          }
        }
        leaf iwf {
          xr:xr-xml-map "qos_viking_interface_cfg:IWF";
          type empty;
          description "Enable IWF for L2 overhead accounting";
        }
      }

      container output {
        xr:xr-xml-map "qos_viking_interface_cfg:Output";
        description "Egress service policy";
        uses SERVICE-POLICY;
      }

      container input {
        xr:xr-xml-map "qos_viking_interface_cfg:Input";
        description "Ingress service policy";
        uses SERVICE-POLICY;
      }
      leaf minimum-bandwidth {
        xr:xr-xml-map "qos_viking_interface_cfg:MinimumBandwidth";
        type uint32 {
          range "1..4294967295";
        }
        description "Minimum bandwidth guaranteed for a subscriber";
      }
      leaf actual-rate-down {
        xr:xr-xml-map "qos_viking_interface_cfg:ActualRateDown";
        type uint32 {
          range "1..4294967295";
        }
        description "Minimum bandwidth guaranteed for a subscriber";
      }
      leaf actual-rate-up {
        xr:xr-xml-map "qos_viking_interface_cfg:ActualRateUp";
        type uint32 {
          range "1..4294967295";
        }
        description "Minimum bandwidth guaranteed for a subscriber";
      }
    }
  }

  grouping SERVICE-POLICY {
    description "Common node of input, output";

    list service-policy {
      xr:xr-xml-map "qos_viking_interface_cfg:ServicePolicy";
      key "service-policy-name";
      description "Service policy details";
      leaf service-policy-name {
        xr:xr-xml-map "qos_viking_interface_cfg:ServicePolicyName";
        type string {
          length "0..64";
        }
        description "Name of policy-map";
      }
      leaf account-type {
        xr:xr-xml-map "qos_viking_interface_cfg:AccountType";
        type Qos-policy-account;
        description "Turn off L2 or L3 accounting.";
      }
      leaf l1-user-defined {
        xr:xr-xml-map "qos_viking_interface_cfg:L1UserDefined";
        type int32 {
          range "-63..63";
        }
        description "User specified value";
      }
      leaf spi-name {
        xr:xr-xml-map "qos_viking_interface_cfg:SPIName";
        type string;
        description "Name of the SPI";
      }
      leaf policy-merge {
        xr:xr-xml-map "qos_viking_interface_cfg:PolicyMerge";
        type Qos-field-not-supported;
        description "Not supported (Leave unspecified).";
      }
      leaf subscriber-parent-policy {
        xr:xr-xml-map "qos_viking_interface_cfg:SubscriberParentPol"+
          "icy";
        type boolean;
        description "TRUE if service-policy applied on svlan.";
      }
      leaf resource-id {
        xr:xr-xml-map "qos_viking_interface_cfg:ResourceID";
        type uint32 {
          range "0..3";
        }
        description "Resource ID value";
      }
      leaf service-fragment-parent-policy {
        xr:xr-xml-map "qos_viking_interface_cfg:ServiceFragmentPare"+
          "ntPolicy";
        type boolean;
        description
          "TRUE if service-policy applied is a
          service-fragment policy).";
      }
    }
  }

  container qos {
    xr:xr-xml-map "qos_viking_qfab_cfg:QOS";
    description "Global QOS configuration.";
    leaf fabric-service-policy {
      xr:xr-xml-map "qos_viking_qfab_cfg:FabricServicePolicy";
      type xr:Cisco-ios-xr-string {
        length "0..63";
      }
      description "Name of the fabric service policy";
    }
  }
}
