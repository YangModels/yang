module Cisco-IOS-XR-ipv4-io-oper {

  /*** NAMESPACE / PREFIX DEFINITION ***/

  namespace "http://cisco.com/ns/yang/Cisco-IOS-XR-ipv4-io-oper";


  prefix "ipv4-io-oper";

  /*** LINKAGE (IMPORTS / INCLUDES) ***/

  import Cisco-IOS-XR-types { prefix "xr"; }

  include Cisco-IOS-XR-ipv4-io-oper-sub2 {
    revision-date 2015-01-07;
  }

  include Cisco-IOS-XR-ipv4-io-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-io package operational data.

     This module contains definitions
     for the following management objects:
       ipv4-network: IPv4 network operational data

     Copyright (c) 2013-2015 by Cisco Systems, Inc.
     All rights reserved.";

  revision "2015-01-07" {
    description
      "IOS XR 5.3.1 revision.";
  }


  container ipv4-network {
    xr:xr-xml-map "ipv4_io_oper:IPV4Network";
    config false;
    description "IPv4 network operational data";

    container nodes {
      xr:xr-xml-map "ipv4_io_oper:NodeTable";
      description "Node-specific IPv4 network operational data";

      list node {
        xr:xr-xml-map "ipv4_io_oper:Node";
        key "node-name";
        description
          "IPv4 network operational data for a particular
          node";

        container interface-data {
          xr:xr-xml-map "ipv4_io_oper:InterfaceData";
          description "IPv4 network operational interface data";

          container vrfs {
            xr:xr-xml-map "ipv4_io_oper:VRFTable";
            description
              "VRF specific IPv4 network operational
              interface data";

            list vrf {
              xr:xr-xml-map "ipv4_io_oper:VRF";
              key "vrf-name";
              description "VRF name of an interface belong to";

              container briefs {
                xr:xr-xml-map "ipv4_io_oper:BriefTable";
                description
                  "Brief interface IPv4 network operational
                  data for a node";

                list brief {
                  xr:xr-xml-map "ipv4_io_oper:Brief";
                  key "interface-name";
                  description
                    "Brief interface IPv4 network operational
                    data for an interface";
                  leaf interface-name {
                    xr:xr-xml-map "ipv4_io_oper:InterfaceName";
                    type xr:Interface-name;
                    description "The name of the interface";
                  }
                  uses IPV4-IF-BRIEF;
                }
              }

              container details {
                xr:xr-xml-map "ipv4_io_oper:DetailTable";
                description
                  "Detail interface IPv4 network operational
                  data for a node";

                list detail {
                  xr:xr-xml-map "ipv4_io_oper:Detail";
                  key "interface-name";
                  description
                    "Detail interface IPv4 network operational
                    data for an interface";
                  leaf interface-name {
                    xr:xr-xml-map "ipv4_io_oper:InterfaceName";
                    type xr:Interface-name;
                    description "The name of the interface";
                  }
                  uses IPV4-IF-DETAIL;
                }
              }
              leaf vrf-name {
                xr:xr-xml-map "ipv4_io_oper:VRFName";
                type xr:Cisco-ios-xr-string;
                description "The VRF name";
              }
            }
          }

          container summary {
            xr:xr-xml-map "ipv4_io_oper:Summary";
            description
              "Summary of IPv4 network operational interface
              data on a node";
            uses IPV4-IF-SUMMARY;
          }
        }

        container statistics {
          xr:xr-xml-map "ipv4_io_oper:Statistics";
          description
            "Statistical IPv4 network operational data for
            a node";

          container traffic {
            xr:xr-xml-map "ipv4_io_oper:Traffic";
            description "Traffic statistics for a node";
            uses IP-TRAFFIC;
          }
        }
        leaf node-name {
          xr:xr-xml-map "ipv4_io_oper:NodeName";
          type xr:Node-id;
          description "The node name";
        }
      }
    }
  }
}
