submodule Cisco-IOS-XR-qos-ma-oper-sub1 {

  belongs-to Cisco-IOS-XR-qos-ma-oper {
    prefix Cisco-IOS-XR-qos-ma-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR qos-ma package operational data.

     Copyright (c) 2013-2015 by Cisco Systems, Inc.
     All rights reserved.";

  revision "2015-01-07" {
    description
      "IOS XR 5.3.1 revision.";
  }

  typedef Qos-caps-operation-enum {
    type enumeration {
      enum add {
        value 0;
        description "Add";
      }
      enum remove {
        value 1;
        description "Remove";
      }
      enum replace {
        value 2;
        description "Replace";
      }
      enum modify {
        value 3;
        description "Modify";
      }
      enum unknown {
        value 4;
        description "Unknown";
      }
    }
    description "Satellite QOS offload operation";
  }
  typedef Qos-ma-sat-caps-type-enum {
    type enumeration {
      enum input {
        value 0;
        description "Input";
      }
      enum output {
        value 1;
        description "Output";
      }
      enum unknown {
        value 2;
        description "Unknown";
      }
    }
    description "Satellite capsulation information";
  }
  typedef String-arr {
    type string;
    description "String arr";
  }

  grouping QOS-MA-SAT-IF-EDM-INFO-XML {
    description "QoS offload information on Satellite interface";
    leaf policy-name {
      xr:xr-xml-map "qos_ma_intf:PolicyName";
      type String-arr;
      description "Service policy name";
    }
    leaf direction {
      xr:xr-xml-map "qos_ma_intf:Direction";
      type Qos-ma-sat-caps-type-enum;
      description "Satellite caps type";
    }
    leaf last-operation {
      xr:xr-xml-map "qos_ma_intf:LastOperation";
      type Qos-caps-operation-enum;
      description "Previous caps operation";
    }
    leaf status {
      xr:xr-xml-map "qos_ma_intf:Status";
      type String-arr;
      description "Status of offload";
    }
    leaf error-message {
      xr:xr-xml-map "qos_ma_intf:ErrorMessage";
      type String-arr;
      description "Error message";
    }
  }
}
