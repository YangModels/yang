module Cisco-IOS-XR-snmp-agent-cfg {

  /*** NAMESPACE / PREFIX DEFINITION ***/

  namespace "http://cisco.com/ns/yang/Cisco-IOS-XR-snmp-agent-cfg";


  prefix "snmp-agent-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-agent package configuration.

     This module contains definitions
     for the following management objects:
       snmp: The heirarchy point for all the SNMP configurations
       mib: mib

     Copyright (c) 2013-2015 by Cisco Systems, Inc.
     All rights reserved.";

  revision "2015-05-14" {
    description
      "IOS XR 5.3.2 revision.";
  }

  revision "2015-01-07" {
    description
      "IOS XR 5.3.1 revision.";
  }

  typedef Snmp-tos {
    type enumeration {
      enum precedence {
        value 0;
        description "SNMP TOS type Precedence";
      }
      enum dscp {
        value 1;
        description "SNMP TOS type DSCP";
      }
    }
    description "Snmp tos";
  }
  typedef Snmp-hash-algorithm {
    type enumeration {
      enum none {
        value 0;
        description "No authentication required";
      }
      enum md5 {
        value 1;
        description "Standard Message Digest algorithm";
      }
      enum sha {
        value 2;
        description "SHA algorithm";
      }
    }
    description "Snmp hash algorithm";
  }
  typedef Snmp-priv-algorithm {
    type enumeration {
      enum none {
        value 0;
        description "No Privacy";
      }
      enum des {
        value 1;
        description "Des algorithm";
      }
      enum 3des {
        value 2;
        description "3des algorithm";
      }
      enum aes128 {
        value 3;
        description "aes128 algorithm";
      }
      enum aes192 {
        value 4;
        description "aes192 algorithm";
      }
      enum aes256 {
        value 5;
        description "aes256 algorithm";
      }
    }
    description "Snmp priv algorithm";
  }
  typedef Snmp-owner-access {
    type enumeration {
      enum sdr-owner {
        value 0;
        description "Secure Domain Router Owner permissions";
      }
      enum system-owner {
        value 1;
        description "System owner permissions";
      }
    }
    description "Snmp owner access";
  }
  typedef Snmp-bulkstat-schema {
    type enumeration {
      enum exact-interface {
        value 1;
        description "Exact Interface";
      }
      enum exact-oid {
        value 2;
        description "Exact OID";
      }
      enum wild-interface {
        value 3;
        description "Wild Interface";
      }
      enum wild-oid {
        value 4;
        description "Wild OID";
      }
      enum range-oid {
        value 5;
        description "Range of OID";
      }
      enum repeat-oid {
        value 6;
        description "Repeated the instance";
      }
    }
    description "Snmp bulkstat schema";
  }
  typedef Snmpacl {
    type enumeration {
      enum ipv4 {
        value 1;
        description "Ipv4 Access-list";
      }
      enum ipv6 {
        value 2;
        description "Ipv6 Access-list";
      }
    }
    description "Snmpacl";
  }
  typedef Snmp-dscp-value {
    type union {
      type enumeration {
        enum default {
          value 0;
          description "Applicable to DSCP: bits 000000";
        }
        enum af11 {
          value 10;
          description "Applicable to DSCP: bits 001010";
        }
        enum af12 {
          value 12;
          description "Applicable to DSCP: bits 001100";
        }
        enum af13 {
          value 14;
          description "Applicable to DSCP: bits 001110";
        }
        enum af21 {
          value 18;
          description "Applicable to DSCP: bits 010010";
        }
        enum af22 {
          value 20;
          description "Applicable to DSCP: bits 010100";
        }
        enum af23 {
          value 22;
          description "Applicable to DSCP: bits 010110";
        }
        enum af31 {
          value 26;
          description "Applicable to DSCP: bits 011010";
        }
        enum af32 {
          value 28;
          description "Applicable to DSCP: bits 011100";
        }
        enum af33 {
          value 30;
          description "Applicable to DSCP: bits 011110";
        }
        enum af41 {
          value 34;
          description "Applicable to DSCP: bits 100010";
        }
        enum af42 {
          value 36;
          description "Applicable to DSCP: bits 100100";
        }
        enum af43 {
          value 38;
          description "Applicable to DSCP: bits 100110";
        }
        enum ef {
          value 46;
          description "Applicable to DSCP: bits 101110";
        }
        enum cs1 {
          value 8;
          description "Applicable to DSCP: bits 001000";
        }
        enum cs2 {
          value 16;
          description "Applicable to DSCP: bits 010000";
        }
        enum cs3 {
          value 24;
          description "Applicable to DSCP: bits 011000";
        }
        enum cs4 {
          value 32;
          description "Applicable to DSCP: bits 100000";
        }
        enum cs5 {
          value 40;
          description "Applicable to DSCP: bits 101000";
        }
        enum cs6 {
          value 48;
          description "Applicable to DSCP: bits 110000";
        }
        enum cs7 {
          value 56;
          description "Applicable to DSCP: bits 111000";
        }
      }
      type uint32 {
        range "0..63";
      }
    }
    description "Snmp dscp value";
  }
  typedef Snmp-precedence-value1 {
    type union {
      type enumeration {
        enum routine {
          value 0;
          description "Applicable to Precedence: value 0";
        }
        enum priority {
          value 1;
          description "Applicable to Precedence: value 1";
        }
        enum immediate {
          value 2;
          description "Applicable to Precedence: value 2";
        }
        enum flash {
          value 3;
          description "Applicable to Precedence: value 3";
        }
        enum flash-override {
          value 4;
          description "Applicable to Precedence: value 4";
        }
        enum critical {
          value 5;
          description "Applicable to Precedence: value 5";
        }
        enum internet {
          value 6;
          description "Applicable to Precedence: value 6";
        }
        enum network {
          value 7;
          description "Applicable to Precedence: value 7";
        }
      }
      type uint32 {
        range "0..7";
      }
    }
    description "Snmp precedence value1";
  }
  typedef Snmp-security-model {
    type enumeration {
      enum no-authentication {
        value 0;
        description "No Authentication required";
      }
      enum authentication {
        value 1;
        description
          "Authentication password alone required for
          access";
      }
      enum privacy {
        value 2;
        description
          "Authentication and privacy password required
          for access";
      }
    }
    description "Snmp security model";
  }
  typedef Snmp-mib-view-inclusion {
    type enumeration {
      enum included {
        value 1;
        description "MIB View to be included";
      }
      enum excluded {
        value 2;
        description "MIB View to be excluded";
      }
    }
    description "Snmp mib view inclusion";
  }
  typedef Snmp-bulkstat-file-format {
    type enumeration {
      enum schema-ascii {
        value 1;
        description "Tranfer file in schema Ascii format";
      }
      enum bulk-ascii {
        value 2;
        description "Tranfer file in Bulk Ascii format";
      }
      enum bulk-binary {
        value 3;
        description "Tranfer file in Bulk binary format";
      }
    }
    description "Snmp bulkstat file format";
  }
  typedef Snmp-access-level {
    type enumeration {
      enum read-only {
        value 0;
        description "Read Only Access for a community string";
      }
      enum read-write {
        value 1;
        description "Read Write Access for a community string";
      }
    }
    description "Snmp access level";
  }
  typedef Snmp-context {
    type enumeration {
      enum vrf {
        value 1;
        description "VRF feature";
      }
      enum bridge {
        value 4;
        description "BRIDGE feature";
      }
      enum ospf {
        value 5;
        description "OSPF feature";
      }
      enum ospfv3 {
        value 6;
        description "OSPFv3 feature";
      }
    }
    description "Snmp context";
  }
  typedef Group-snmp-version {
    type enumeration {
      enum v1 {
        value 0;
        description "SNMP version 1";
      }
      enum v2c {
        value 1;
        description "SNMP version 2";
      }
      enum v3 {
        value 2;
        description "SNMP version 3";
      }
    }
    description "Group snmp version";
  }
  typedef User-snmp-version {
    type enumeration {
      enum v1 {
        value 1;
        description "SNMP version 1";
      }
      enum v2c {
        value 2;
        description "SNMP version 2";
      }
      enum v3 {
        value 3;
        description "SNMP version 3";
      }
    }
    description "User snmp version";
  }

  grouping APPLIED-TO {
    description "Common node of rule, rule-set";

    container applied-to {
      xr:xr-xml-map "snmp_corr_cfg:AppliedTo";
      description "Applied to the Rule or Ruleset";

      container hosts {
        xr:xr-xml-map "snmp_corr_cfg:HostTable";
        description "Table of configured hosts to apply rules to";

        list host {
          xr:xr-xml-map "snmp_corr_cfg:Host";
          key "ip-address port";
          description "A destination host";
          leaf ip-address {
            xr:xr-xml-map "snmp_corr_cfg:IPAddress";
            type inet:ip-address-no-zone;
            description "IP address";
          }
          leaf port {
            xr:xr-xml-map "snmp_corr_cfg:Port";
            type xr:Cisco-ios-xr-port-number;
            description "Port (specify 162 for default)";
          }
        }
      }
      leaf all {
        xr:xr-xml-map "snmp_corr_cfg:All";
        type empty;
        description "Apply to all of the device";
      }
    }
  }

  grouping CONTEXT-TABLE {
    description "Common node of snmp, vrf";

    container contexts {
      xr:xr-xml-map "snmp_cfg:ContextTable";
      description "List of Context Names";

      list context {
        xr:xr-xml-map "snmp_cfg:Context";
        xr:xr-cli-map "vrf <string> context <string> ";
        xr:xr-cli-map "context <string> ";
        key "context-name";
        description "Context Name";
        leaf context-name {
          xr:xr-xml-map "snmp_cfg:ContextName";
          type xr:Cisco-ios-xr-string;
          description "Context Name";
        }
      }
    }
  }

  grouping VAR-BIND-TABLE {
    description "Common node of root-cause, non-root-cause";

    container var-binds {
      xr:xr-xml-map "snmp_corr_cfg:VarBindTable";
      description "Varbinds to match";

      list var-bind {
        xr:xr-xml-map "snmp_corr_cfg:VarBind";
        key "oid";
        description "Varbind match conditions";

        container match {
          xr:xr-xml-map "snmp_corr_cfg:Match";
          description "VarBind match conditions";
          leaf value {
            xr:xr-xml-map "snmp_corr_cfg:Value";
            type string;
            description "Regular Expression to match value";
          }
          leaf index {
            xr:xr-xml-map "snmp_corr_cfg:Index";
            type string;
            description "Regular Expression to match index";
          }
        }
        leaf oid {
          xr:xr-xml-map "snmp_corr_cfg:OID";
          type string;
          description "OID of varbind (dotted decimal)";
        }
      }
    }
  }

  grouping TRAP-HOST-TABLE {
    description "Common node of snmp, vrf";

    container trap-hosts {
      xr:xr-xml-map "snmp_cfg:TrapHostTable";
      description "Specify hosts to receive SNMP notifications";

      list trap-host {
        xr:xr-xml-map "snmp_cfg:TrapHost";
        key "ip-address";
        description "Specify hosts to receive SNMP notifications";

        container encrypted-user-communities {
          xr:xr-xml-map "snmp_cfg:EncryptedUserCommunityTable";
          description
            "Container class for defining Clear/encrypt
            communities for a trap host";

          list encrypted-user-community {
            xr:xr-xml-map "snmp_cfg:EncryptedUserCommunity";
            key "community-name";
            description
              "Clear/Encrypt Community name associated with
              a trap host";
            leaf community-name {
              xr:xr-xml-map "snmp_cfg:CommunityName";
              type xr:Cisco-ios-xr-string;
              description
                "SNMPv1/v2c community string or SNMPv3 user";
            }
            leaf port {
              xr:xr-xml-map "snmp_cfg:Port";
              type xr:Cisco-ios-xr-port-number;
              description "UDP port number";
            }
            leaf version {
              xr:xr-xml-map "snmp_cfg:Version";
              type string;
              mandatory true;
              description "SNMP Version to be used v1/v2c/v3";
            }
            leaf security-level {
              xr:xr-xml-map "snmp_cfg:SecurityLevel";
              type Snmp-security-model;
              description
                "Security level to be used noauth/auth/priv";
            }
            leaf basic-trap-types {
              xr:xr-xml-map "snmp_cfg:BasicTrapTypes";
              type int32;
              mandatory true;
              description
                "Number to signify the feature traps that
                needs to be setBasicTrapTypes is used for
                all traps except copy-completeSet this value
                to an integer corresponding to the trapBGP
                8192, CONFIG 4096,SYSLOG 131072,SNMP_TRAP
                1COPY_COMPLETE_TRAP 64To provide a
                combination of trap Add the respective
                numbersValue must be set to 0 for all traps";
            }
            leaf advanced-trap-types1 {
              xr:xr-xml-map "snmp_cfg:AdvancedTrapTypes1";
              type int32;
              mandatory true;
              description
                "Number to signify the feature traps that
                needs to be setUse this for providing
                copy-complete trapValue must be set to 0 if
                not used";
            }
            leaf advanced-trap-types2 {
              xr:xr-xml-map "snmp_cfg:AdvancedTrapTypes2";
              type int32;
              mandatory true;
              description
                "Number to signify the feature traps that
                needs to be setvalue should always to set as
                0";
            }
          }
        }

        container inform-host {
          xr:xr-xml-map "snmp_cfg:InformHost";
          description
            "Container class for defining notification type
            for a Inform host";

          container inform-user-communities {
            xr:xr-xml-map "snmp_cfg:InformUserCommunityTable";
            description
              "Container class for defining communities for
              a inform host";

            list inform-user-community {
              xr:xr-xml-map "snmp_cfg:InformUserCommunity";
              key "community-name";
              description
                "Unencrpted Community name associated with a
                inform host";
              leaf community-name {
                xr:xr-xml-map "snmp_cfg:CommunityName";
                type xr:Cisco-ios-xr-string {
                  length "0..128";
                }
                description
                  "SNMPv2c community string or SNMPv3 user";
              }
              leaf port {
                xr:xr-xml-map "snmp_cfg:Port";
                type xr:Cisco-ios-xr-port-number;
                description "UDP port number";
              }
              leaf version {
                xr:xr-xml-map "snmp_cfg:Version";
                type string;
                mandatory true;
                description "SNMP Version to be used v2c/v3";
              }
              leaf security-level {
                xr:xr-xml-map "snmp_cfg:SecurityLevel";
                type Snmp-security-model;
                description
                  "Security level to be used noauth/auth/priv";
              }
              leaf basic-trap-types {
                xr:xr-xml-map "snmp_cfg:BasicTrapTypes";
                type int32;
                mandatory true;
                description
                  "Number to signify the feature traps that
                  needs to be setBasicTrapTypes is used for
                  all traps except copy-completeSet this
                  value to an integer corresponding to the
                  trapBGP 8192, CONFIG 4096,SYSLOG 131072
                  ,SNMP_TRAP 1COPY_COMPLETE_TRAP 64To provide
                  a combination of trap Add the respective
                  numbersValue must be set to 0 for all traps";
              }
              leaf advanced-trap-types1 {
                xr:xr-xml-map "snmp_cfg:AdvancedTrapTypes1";
                type int32;
                mandatory true;
                description
                  "Number to signify the feature traps that
                  needs to be setUse this for providing
                  copy-complete trapValue must be set to 0 if
                  not used";
              }
              leaf advanced-trap-types2 {
                xr:xr-xml-map "snmp_cfg:AdvancedTrapTypes2";
                type int32;
                mandatory true;
                description
                  "Number to signify the feature traps that
                  needs to be setvalue should always to set
                  as 0";
              }
            }
          }

          container inform-encrypted-user-communities {
            xr:xr-xml-map "snmp_cfg:InformEncryptedUserCommunityTab"+
              "le";
            description
              "Container class for defining Clear/encrypt
              communities for a inform host";

            list inform-encrypted-user-community {
              xr:xr-xml-map "snmp_cfg:InformEncryptedUserCommunity";
              key "community-name";
              description
                "Clear/Encrypt Community name associated with
                a inform host";
              leaf community-name {
                xr:xr-xml-map "snmp_cfg:CommunityName";
                type xr:Cisco-ios-xr-string;
                description
                  "SNMPv2c community string or SNMPv3 user";
              }
              leaf port {
                xr:xr-xml-map "snmp_cfg:Port";
                type xr:Cisco-ios-xr-port-number;
                description "UDP port number";
              }
              leaf version {
                xr:xr-xml-map "snmp_cfg:Version";
                type string;
                mandatory true;
                description "SNMP Version to be used v2c/v3";
              }
              leaf security-level {
                xr:xr-xml-map "snmp_cfg:SecurityLevel";
                type Snmp-security-model;
                description
                  "Security level to be used noauth/auth/priv";
              }
              leaf basic-trap-types {
                xr:xr-xml-map "snmp_cfg:BasicTrapTypes";
                type int32;
                mandatory true;
                description
                  "Number to signify the feature traps that
                  needs to be setBasicTrapTypes is used for
                  all traps except copy-completeSet this
                  value to an integer corresponding to the
                  trapBGP 8192, CONFIG 4096,SYSLOG 131072
                  ,SNMP_TRAP 1COPY_COMPLETE_TRAP 64To provide
                  a combination of trap Add the respective
                  numbersValue must be set to 0 for all traps";
              }
              leaf advanced-trap-types1 {
                xr:xr-xml-map "snmp_cfg:AdvancedTrapTypes1";
                type int32;
                mandatory true;
                description
                  "Number to signify the feature traps that
                  needs to be setUse this for providing
                  copy-complete trapValue must be set to 0 if
                  not used";
              }
              leaf advanced-trap-types2 {
                xr:xr-xml-map "snmp_cfg:AdvancedTrapTypes2";
                type int32;
                mandatory true;
                description
                  "Number to signify the feature traps that
                  needs to be setvalue should always to set
                  as 0";
              }
            }
          }
        }

        container default-user-communities {
          xr:xr-xml-map "snmp_cfg:DefaultUserCommunityTable";
          description
            "Container class for defining communities for a
            trap host";

          list default-user-community {
            xr:xr-xml-map "snmp_cfg:DefaultUserCommunity";
            key "community-name";
            description
              "Unencrpted Community name associated with a
              trap host";
            leaf community-name {
              xr:xr-xml-map "snmp_cfg:CommunityName";
              type xr:Cisco-ios-xr-string {
                length "0..128";
              }
              description
                "SNMPv1/v2c community string or SNMPv3 user";
            }
            leaf port {
              xr:xr-xml-map "snmp_cfg:Port";
              type xr:Cisco-ios-xr-port-number;
              description "UDP port number";
            }
            leaf version {
              xr:xr-xml-map "snmp_cfg:Version";
              type string;
              mandatory true;
              description "SNMP Version to be used v1/v2c/v3";
            }
            leaf security-level {
              xr:xr-xml-map "snmp_cfg:SecurityLevel";
              type Snmp-security-model;
              description
                "Security level to be used noauth/auth/priv";
            }
            leaf basic-trap-types {
              xr:xr-xml-map "snmp_cfg:BasicTrapTypes";
              type int32;
              mandatory true;
              description
                "Number to signify the feature traps that
                needs to be setBasicTrapTypes is used for
                all traps except copy-completeSet this value
                to an integer corresponding to the trapBGP
                8192, CONFIG 4096,SYSLOG 131072,SNMP_TRAP
                1COPY_COMPLETE_TRAP 64To provide a
                combination of trap Add the respective
                numbersValue must be set to 0 for all traps";
            }
            leaf advanced-trap-types1 {
              xr:xr-xml-map "snmp_cfg:AdvancedTrapTypes1";
              type int32;
              mandatory true;
              description
                "Number to signify the feature traps that
                needs to be setUse this for providing
                copy-complete trapValue must be set to 0 if
                not used";
            }
            leaf advanced-trap-types2 {
              xr:xr-xml-map "snmp_cfg:AdvancedTrapTypes2";
              type int32;
              mandatory true;
              description
                "Number to signify the feature traps that
                needs to be setvalue should always to set as
                0";
            }
          }
        }
        leaf ip-address {
          xr:xr-xml-map "snmp_cfg:IPAddress";
          type inet:ip-address-no-zone;
          description "IP address of SNMP notification host";
        }
      }
    }
  }

  grouping CONTEXT-MAPPING-TABLE {
    description "Common node of snmp, vrf";

    container context-mappings {
      xr:xr-xml-map "snmp_cfg:ContextMappingTable";
      description "List of context names";

      list context-mapping {
        xr:xr-xml-map "snmp_cfg:ContextMapping";
        xr:xr-cli-map "context mapping <string> [feature <enum> (in"+
          "stance <string>)|(vrf <string>)|(topology <string>)] ";
        key "context-mapping-name";
        description "Context mapping name";
        leaf context-mapping-name {
          xr:xr-xml-map "snmp_cfg:ContextMappingName";
          type xr:Cisco-ios-xr-string;
          description "Context mapping name";
        }
        leaf context {
          xr:xr-xml-map "snmp_cfg:Context";
          type Snmp-context;
          description "SNMP context feature type";
        }
        leaf instance-name {
          xr:xr-xml-map "snmp_cfg:InstanceName";
          type string;
          description "OSPF protocol instance";
        }
        leaf vrf-name {
          xr:xr-xml-map "snmp_cfg:VRFName";
          type string;
          description "VRF name associated with the context";
        }
        leaf topology-name {
          xr:xr-xml-map "snmp_cfg:TopologyName";
          type string;
          description "Topology name associated with the context";
        }
      }
    }
  }

  container snmp {
    xr:xr-xml-map "snmp_cfg:SNMP";
    description
      "The heirarchy point for all the SNMP
      configurations";

    container encrypted-community-maps {
      xr:xr-xml-map "snmp_cfg:EncryptedCommunityMapTable";
      description
        "Container class to hold clear/encrypted
        communitie maps";

      list encrypted-community-map {
        xr:xr-xml-map "snmp_cfg:EncryptedCommunityMap";
        key "community-name";
        description "Clear/encrypted SNMP community map";
        leaf community-name {
          xr:xr-xml-map "snmp_cfg:CommunityName";
          type xr:Cisco-ios-xr-string;
          description "SNMP community map";
        }
        leaf context {
          xr:xr-xml-map "snmp_cfg:Context";
          type string;
          description "SNMP Context Name ";
        }
        leaf security {
          xr:xr-xml-map "snmp_cfg:Security";
          type string;
          description "SNMP Security Name ";
        }
        leaf target-list {
          xr:xr-xml-map "snmp_cfg:TargetList";
          type string;
          description "target list name ";
        }
      }
    }

    container views {
      xr:xr-xml-map "snmp_cfg:ViewTable";
      description "Class to configure a SNMPv2 MIB view";

      list view {
        xr:xr-xml-map "snmp_cfg:View";
        xr:xr-cli-map "view <string> <string> (included)|(excluded)"+
          " ";
        key "view-name family";
        description "Name of the view";
        leaf view-name {
          xr:xr-xml-map "snmp_cfg:ViewName";
          type xr:Cisco-ios-xr-string;
          description "Name of the view";
        }
        leaf family {
          xr:xr-xml-map "snmp_cfg:Family";
          type string;
          description "MIB view family name";
        }
        leaf view-inclusion {
          xr:xr-xml-map "snmp_cfg:ViewInclusion";
          type Snmp-mib-view-inclusion;
          mandatory true;
          description "MIB view to be included or excluded";
        }
      }
    }

    container logging {
      xr:xr-xml-map "snmp_cfg:Logging";
      description "SNMP logging";

      container threshold {
        xr:xr-xml-map "snmp_cfg:Threshold";
        description "SNMP logging threshold";
        leaf oid-processing {
          xr:xr-xml-map "snmp_cfg:OIDProcessing";
          xr:xr-cli-map "logging threshold oid-processing <number> ";
          type uint32 {
            range "0..20000";
          }
          default "500";
          description "Threshold in ms";
        }
        leaf pdu-processing {
          xr:xr-xml-map "snmp_cfg:PDUProcessing";
          xr:xr-cli-map "logging threshold pdu-processing <number> ";
          type uint32 {
            range "0..20000";
          }
          default "20000";
          description "Threshold in ms";
        }
      }
    }

    container administration {
      xr:xr-xml-map "snmp_cfg:Administration";
      description "Container class for SNMP administration";

      container default-communities {
        xr:xr-xml-map "snmp_cfg:DefaultCommunityTable";
        description
          "Container class to hold unencrpted communities";

        list default-community {
          xr:xr-xml-map "snmp_cfg:DefaultCommunity";
          key "community-name";
          description
            "Unencrpted SNMP community string and access
            priviledges";
          leaf community-name {
            xr:xr-xml-map "snmp_cfg:CommunityName";
            type string {
              length "0..128";
            }
            description "SNMP community string";
          }
          leaf priviledge {
            xr:xr-xml-map "snmp_cfg:Priviledge";
            type Snmp-access-level;
            description "Read/Write Access";
          }
          leaf view-name {
            xr:xr-xml-map "snmp_cfg:ViewName";
            type string;
            description
              "MIB view to which the community has access";
          }
          leaf v4acl-type {
            xr:xr-xml-map "snmp_cfg:V4ACLType";
            type Snmpacl;
            description "Access-list type";
          }
          leaf v4-access-list {
            xr:xr-xml-map "snmp_cfg:V4AccessList";
            type string;
            description "Ipv4 Access-list name";
          }
          leaf v6acl-type {
            xr:xr-xml-map "snmp_cfg:V6ACLType";
            type Snmpacl;
            description "Access-list type";
          }
          leaf v6-access-list {
            xr:xr-xml-map "snmp_cfg:V6AccessList";
            type string;
            description "Ipv6 Access-list name";
          }
          leaf owner {
            xr:xr-xml-map "snmp_cfg:Owner";
            type Snmp-owner-access;
            description "Logical Router or System owner access";
          }
        }
      }

      container encrypted-communities {
        xr:xr-xml-map "snmp_cfg:EncryptedCommunityTable";
        description
          "Container class to hold clear/encrypted
          communities";

        list encrypted-community {
          xr:xr-xml-map "snmp_cfg:EncryptedCommunity";
          key "community-name";
          description
            "Clear/encrypted SNMP community string and
            access priviledges";
          leaf community-name {
            xr:xr-xml-map "snmp_cfg:CommunityName";
            type xr:Cisco-ios-xr-string;
            description "SNMP community string";
          }
          leaf priviledge {
            xr:xr-xml-map "snmp_cfg:Priviledge";
            type Snmp-access-level;
            description "Read/Write Access";
          }
          leaf view-name {
            xr:xr-xml-map "snmp_cfg:ViewName";
            type string;
            description
              "MIB view to which the community has access";
          }
          leaf v4acl-type {
            xr:xr-xml-map "snmp_cfg:V4ACLType";
            type Snmpacl;
            description "Access-list type";
          }
          leaf v4-access-list {
            xr:xr-xml-map "snmp_cfg:V4AccessList";
            type string;
            description "Ipv4 Access-list name";
          }
          leaf v6acl-type {
            xr:xr-xml-map "snmp_cfg:V6ACLType";
            type Snmpacl;
            description "Access-list type";
          }
          leaf v6-access-list {
            xr:xr-xml-map "snmp_cfg:V6AccessList";
            type string;
            description "Ipv6 Access-list name";
          }
          leaf owner {
            xr:xr-xml-map "snmp_cfg:Owner";
            type Snmp-owner-access;
            description "Logical Router or System owner access";
          }
        }
      }
    }

    container agent {
      xr:xr-xml-map "snmp_cfg:Agent";
      description
        "The heirarchy point for SNMP Agent
        configurations";

      container engine-id {
        xr:xr-xml-map "snmp_cfg:EngineID";
        description "SNMPv3 engineID";

        container remotes {
          xr:xr-xml-map "snmp_cfg:RemoteTable";
          description "SNMPv3 remote SNMP Entity";

          list remote {
            xr:xr-xml-map "snmp_cfg:Remote";
            xr:xr-cli-map "engineID remote <IPv4"+
              "/IPv6 address> <string> [udp-port <number>] ";
            key "remote-address";
            description "engineID of the remote agent";
            leaf remote-address {
              xr:xr-xml-map "snmp_cfg:RemoteAddress";
              type inet:ip-address-no-zone;
              description "IP address of remote SNMP entity";
            }
            leaf remote-engine-id {
              xr:xr-xml-map "snmp_cfg:RemoteEngineID";
              type string;
              description "engine ID octet string";
            }
            leaf port {
              xr:xr-xml-map "snmp_cfg:Port";
              type xr:Cisco-ios-xr-port-number;
              description "UDP port number";
            }
          }
        }
        leaf local {
          xr:xr-xml-map "snmp_cfg:Local";
          xr:xr-cli-map "engineID local <string> ";
          type string;
          description "engine ID octet string";
        }
      }
    }

    container trap {
      xr:xr-xml-map "snmp_cfg:Trap";
      description "Class to hold trap configurations";
      leaf timeout {
        xr:xr-xml-map "snmp_cfg:Timeout";
        xr:xr-cli-map "trap-timeout <number> ";
        type uint32 {
          range "1..1000";
        }
        description "Timeout";
      }
      leaf throttle-time {
        xr:xr-xml-map "snmp_cfg:ThrottleTime";
        xr:xr-cli-map "throttle-time <number> ";
        type uint32 {
          range "10..500";
        }
        units "millisecond";
        description "Time in msec (default 250 msecs)";
      }
      leaf queue-length {
        xr:xr-xml-map "snmp_cfg:QueueLength";
        xr:xr-cli-map "queue-length <number> ";
        type uint32 {
          range "1..5000";
        }
        description "Queue length";
      }
    }

    container ipv6 {
      xr:xr-xml-map "snmp_cfg:IPv6";
      description "SNMP TOS bit for outgoing packets";

      container tos {
        xr:xr-xml-map "snmp_cfg:TOS";
        description "Type of TOS";
        leaf type {
          xr:xr-xml-map "snmp_cfg:Type";
          type Snmp-tos;
          description "SNMP TOS type DSCP or Precedence";
        }
        leaf precedence {
          xr:xr-xml-map "snmp_cfg:Precedence";
          when "../type = 'precedence'" {
            description "../Type = Precedence";
          }
          type Snmp-precedence-value1;
          description "SNMP Precedence value";
        }
        leaf dscp {
          xr:xr-xml-map "snmp_cfg:DSCP";
          when "../type = 'dscp'" {
            description "../Type = DSCP";
          }
          type Snmp-dscp-value;
          description "SNMP DSCP value";
        }
      }
    }

    container ipv4 {
      xr:xr-xml-map "snmp_cfg:IPv4";
      description "SNMP TOS bit for outgoing packets";

      container tos {
        xr:xr-xml-map "snmp_cfg:TOS";
        description "Type of TOS";
        leaf type {
          xr:xr-xml-map "snmp_cfg:Type";
          type Snmp-tos;
          description "SNMP TOS type DSCP or Precedence";
        }
        leaf precedence {
          xr:xr-xml-map "snmp_cfg:Precedence";
          when "../type = 'precedence'" {
            description "../Type = Precedence";
          }
          type Snmp-precedence-value1;
          description "SNMP Precedence value";
        }
        leaf dscp {
          xr:xr-xml-map "snmp_cfg:DSCP";
          when "../type = 'dscp'" {
            description "../Type = DSCP";
          }
          type Snmp-dscp-value;
          description "SNMP DSCP value";
        }
      }
    }

    container system {
      xr:xr-xml-map "snmp_cfg:System";
      description "container to hold system information";
      leaf chassis-id {
        xr:xr-xml-map "snmp_cfg:ChassisID";
        xr:xr-cli-map "chassis-id <text> ";
        type string {
          length "0..255";
        }
        description "Chassis ID";
      }
      leaf location {
        xr:xr-xml-map "snmp_cfg:Location";
        xr:xr-cli-map "location <text> ";
        type string {
          length "0..255";
        }
        description "The physical location of this node";
      }
      leaf contact {
        xr:xr-xml-map "snmp_cfg:Contact";
        xr:xr-cli-map "contact <text> ";
        type string {
          length "0..255";
        }
        description
          "identification of the contact person for this
          managed node";
      }
    }

    container target {
      xr:xr-xml-map "snmp_cfg:Target";
      description "SNMP target configurations";

      container targets {
        xr:xr-xml-map "snmp_cfg:TargetListTable";
        description "List of targets";

        list target {
          xr:xr-xml-map "snmp_cfg:TargetList";
          key "target-list-name";
          description "Name of the target list";

          container vrf-names {
            xr:xr-xml-map "snmp_cfg:VRFNameTable";
            description "List of VRF Name for a target list";

            list vrf-name {
              xr:xr-xml-map "snmp_cfg:VRFName";
              xr:xr-cli-map "target list <string> vrf <string> ";
              key "name";
              description "VRF name of the target";
              leaf name {
                xr:xr-xml-map "snmp_cfg:Name";
                type xr:Cisco-ios-xr-string;
                description "VRF Name";
              }
            }
          }

          container target-addresses {
            xr:xr-xml-map "snmp_cfg:TargetAddressTable";
            description "SNMP Target address configurations";

            list target-address {
              xr:xr-xml-map "snmp_cfg:TargetAddress";
              xr:xr-cli-map "target list <string> host <IPv4"+
                "/IPv6 address> ";
              key "ip-address";
              description
                "IP Address to be configured for the Target";
              leaf ip-address {
                xr:xr-xml-map "snmp_cfg:IPAddress";
                type inet:ip-address-no-zone;
                description "IPv4/Ipv6 address";
              }
            }
          }
          leaf target-list-name {
            xr:xr-xml-map "snmp_cfg:TargetListName";
            type xr:Cisco-ios-xr-string;
            description "Name of the target list";
          }
        }
      }
    }

    container notification {
      xr:xr-xml-map "snmp_cfg:Notification";
      description "Enable SNMP notifications";

      container snmp {
        xr:xr-xml-map "snmpmib_cfg:SNMP";
        description "SNMP notification configuration";
        leaf authentication {
          xr:xr-xml-map "snmpmib_cfg:Authentication";
          xr:xr-cli-map "authentication ";
          type empty;
          description "Enable authentication notification";
        }
        leaf cold-start {
          xr:xr-xml-map "snmpmib_cfg:ColdStart";
          xr:xr-cli-map "coldstart ";
          type empty;
          description "Enable cold start notification";
        }
        leaf warm-start {
          xr:xr-xml-map "snmpmib_cfg:WarmStart";
          xr:xr-cli-map "warmstart ";
          type empty;
          description "Enable warm start notification";
        }
        leaf enable {
          xr:xr-xml-map "snmpmib_cfg:Enable";
          xr:xr-cli-map "traps snmp ";
          type empty;
          description "Enable SNMP notifications";
        }
      }
    }

    container correlator {
      xr:xr-xml-map "snmp_corr_cfg:Correlator";
      description "Configure properties of the trap correlator";

      container rules {
        xr:xr-xml-map "snmp_corr_cfg:RuleTable";
        description "Table of configured rules";

        list rule {
          xr:xr-xml-map "snmp_corr_cfg:Rule";
          key "name";
          description "Rule name";

          container non-stateful {
            xr:xr-xml-map "snmp_corr_cfg:NonStateful";
            presence "Indicates a non-stateful node is configured.";
            description "The Non-Stateful Rule Type";

            container root-causes {
              xr:xr-xml-map "snmp_corr_cfg:RootCauseTable";
              description
                "Table of configured rootcause (only one
                entry allowed)";

              list root-cause {
                xr:xr-xml-map "snmp_corr_cfg:RootCause";
                key "oid";
                description
                  "The rootcause - maximum of one can be
                  configured per rule";
                leaf created {
                  xr:xr-xml-map "snmp_corr_cfg:Created";
                  type empty;
                  description "Create rootcause";
                }
                leaf oid {
                  xr:xr-xml-map "snmp_corr_cfg:OID";
                  type string;
                  description
                    "OID of rootcause trap (dotted decimal)";
                }
                uses VAR-BIND-TABLE;
              }
            }

            container non-root-causes {
              xr:xr-xml-map "snmp_corr_cfg:NonRootCauseTable";
              description "Table of configured non-rootcause";

              list non-root-cause {
                xr:xr-xml-map "snmp_corr_cfg:NonRootCause";
                key "oid";
                description "A non-rootcause";
                leaf created {
                  xr:xr-xml-map "snmp_corr_cfg:Created";
                  type empty;
                  description "Create nonrootcause";
                }
                leaf oid {
                  xr:xr-xml-map "snmp_corr_cfg:OID";
                  type string;
                  description
                    "OID of nonrootcause trap (dotted decimal)";
                }
                uses VAR-BIND-TABLE;
              }
            }
            leaf timeout {
              xr:xr-xml-map "snmp_corr_cfg:Timeout";
              type uint32 {
                range "1..600000";
              }
              units "millisecond";
              description "Timeout (ms)";
            }
          }
          leaf name {
            xr:xr-xml-map "snmp_corr_cfg:Name";
            type string {
              length "0..32";
            }
            description "Rule name";
          }
          uses APPLIED-TO;
        }
      }

      container rule-sets {
        xr:xr-xml-map "snmp_corr_cfg:RulesetTable";
        description "Table of configured rulesets";

        list rule-set {
          xr:xr-xml-map "snmp_corr_cfg:Ruleset";
          key "name";
          description "Ruleset name";

          container rulenames {
            xr:xr-xml-map "snmp_corr_cfg:RulenameTable";
            description "Table of configured rulenames";

            list rulename {
              xr:xr-xml-map "snmp_corr_cfg:Rulename";
              xr:xr-cli-map "ruleset <string> rulename <string> ";
              key "rulename";
              description "A rulename";
              leaf rulename {
                xr:xr-xml-map "snmp_corr_cfg:Rulename";
                type string {
                  length "0..32";
                }
                description "Rule name";
              }
            }
          }
          leaf name {
            xr:xr-xml-map "snmp_corr_cfg:Name";
            type string {
              length "0..32";
            }
            description "Ruleset name";
          }
          uses APPLIED-TO;
        }
      }
      leaf buffer-size {
        xr:xr-xml-map "snmp_corr_cfg:BufferSize";
        xr:xr-cli-map "buffer-size <number> ";
        type uint32 {
          range "1024..52428800";
        }
        description "Size of the correlator buffer";
      }
    }

    container bulk-stats {
      xr:xr-xml-map "snmp_bulkstat_cfg:BulkStats";
      description "SNMP bulk stats configuration commands";

      container schemas {
        xr:xr-xml-map "snmp_bulkstat_cfg:SchemaTable";
        description "Configure schema definition";

        list schema {
          xr:xr-xml-map "snmp_bulkstat_cfg:Schema";
          key "schema-name";
          description "The name of the Schema";

          container instance {
            xr:xr-xml-map "snmp_bulkstat_cfg:Instance";
            presence "Indicates a instance node is configured.";
            description "Object instance information";
            leaf type {
              xr:xr-xml-map "snmp_bulkstat_cfg:Type";
              type Snmp-bulkstat-schema;
              mandatory true;
              description "Type of the instance";
            }
            leaf instance {
              xr:xr-xml-map "snmp_bulkstat_cfg:Instance";
              type xr:Interface-name;
              description "Instance of the schema";
            }
            leaf start {
              xr:xr-xml-map "snmp_bulkstat_cfg:Start";
              type string;
              mandatory true;
              description "Start Instance OID for repetition";
            }
            leaf end {
              xr:xr-xml-map "snmp_bulkstat_cfg:End";
              type string;
              mandatory true;
              description "End Instance OID for repetition";
            }
            leaf max {
              xr:xr-xml-map "snmp_bulkstat_cfg:Max";
              type int32;
              mandatory true;
              description "Max value of Instance repetition";
            }
            leaf sub-interface {
              xr:xr-xml-map "snmp_bulkstat_cfg:SubInterface";
              type boolean;
              mandatory true;
              description "Include all the subinterface";
            }
          }
          leaf type {
            xr:xr-xml-map "snmp_bulkstat_cfg:Type";
            type empty;
            description "Configure schema name";
          }
          leaf schema-object-list {
            xr:xr-xml-map "snmp_bulkstat_cfg:SchemaObjectList";
            xr:xr-cli-map "schema <string> object-list <string> ";
            type xr:Cisco-ios-xr-string {
              length "0..32";
            }
            description "Name of an object List";
          }
          leaf poll-interval {
            xr:xr-xml-map "snmp_bulkstat_cfg:PollInterval";
            xr:xr-cli-map "schema <string> poll-interval <number> ";
            type uint32 {
              range "1..20000";
            }
            units "minute";
            description
              "Periodicity for polling of objects in this
              schema in minutes";
          }
          leaf schema-name {
            xr:xr-xml-map "snmp_bulkstat_cfg:SchemaName";
            type xr:Cisco-ios-xr-string {
              length "0..32";
            }
            description "The name of the schema";
          }
        }
      }

      container objects {
        xr:xr-xml-map "snmp_bulkstat_cfg:ObjectListTable";
        description "Configure an Object List ";

        list object {
          xr:xr-xml-map "snmp_bulkstat_cfg:ObjectList";
          key "object-list-name";
          description "Name of the object List";

          container objects {
            xr:xr-xml-map "snmp_bulkstat_cfg:ObjectTable";
            description "Configure an object List";

            list object {
              xr:xr-xml-map "snmp_bulkstat_cfg:Object";
              xr:xr-cli-map "object-list <string> add <string> ";
              key "oid";
              description "Object name or OID";
              leaf oid {
                xr:xr-xml-map "snmp_bulkstat_cfg:OID";
                type string;
                description "Object name or OID ";
              }
            }
          }
          leaf type {
            xr:xr-xml-map "snmp_bulkstat_cfg:Type";
            type empty;
            description "Configure object list name";
          }
          leaf object-list-name {
            xr:xr-xml-map "snmp_bulkstat_cfg:ObjectListName";
            type xr:Cisco-ios-xr-string {
              length "0..32";
            }
            description "Name of the object List";
          }
        }
      }

      container transfers {
        xr:xr-xml-map "snmp_bulkstat_cfg:TransferTable";
        description
          "Periodicity for the transfer of bulk data in
          minutes";

        list transfer {
          xr:xr-xml-map "snmp_bulkstat_cfg:Transfer";
          key "transfer-name";
          description "Name of bulk transfer";

          container transfer-schemas {
            xr:xr-xml-map "snmp_bulkstat_cfg:TransferSchemaTable";
            description
              "Schema that contains objects to be collected";

            list transfer-schema {
              xr:xr-xml-map "snmp_bulkstat_cfg:TransferSchema";
              xr:xr-cli-map "transfer-id <string> schema <string> ";
              key "schema-name";
              description
                "Schema that contains objects to be collected";
              leaf schema-name {
                xr:xr-xml-map "snmp_bulkstat_cfg:SchemaName";
                type xr:Cisco-ios-xr-string {
                  length "0..32";
                }
                description
                  "Schema that contains objects to be
                  collected";
              }
            }
          }
          leaf secondary {
            xr:xr-xml-map "snmp_bulkstat_cfg:Secondary";
            xr:xr-cli-map "transfer-id <string> url secondary <stri"+
              "ng> ";
            type string;
            description
              "FTP or rcp or TFTP can be used for file
              transfer";
          }
          leaf type {
            xr:xr-xml-map "snmp_bulkstat_cfg:Type";
            type empty;
            description "Configure transfer list name";
          }
          leaf buffer-size {
            xr:xr-xml-map "snmp_bulkstat_cfg:BufferSize";
            xr:xr-cli-map "transfer-id <string> buffer-size <number"+
              "> ";
            type uint32 {
              range "1024..2147483647";
            }
            units "byte";
            description "Bulkstat data file maximum size in bytes";
          }
          leaf retain {
            xr:xr-xml-map "snmp_bulkstat_cfg:Retain";
            xr:xr-cli-map "transfer-id <string> retain <number> ";
            type uint32 {
              range "0..20000";
            }
            units "minute";
            description "Retention period in minutes";
          }
          leaf format {
            xr:xr-xml-map "snmp_bulkstat_cfg:Format";
            xr:xr-cli-map "transfer-id <string> format (bulkBinary)"+
              "|(bulkASCII)|(schemaASCII) ";
            type Snmp-bulkstat-file-format;
            description "File format";
          }
          leaf retry {
            xr:xr-xml-map "snmp_bulkstat_cfg:Retry";
            xr:xr-cli-map "transfer-id <string> retry <number> ";
            type uint32 {
              range "0..100";
            }
            description "Number of transmission retries";
          }
          leaf enable {
            xr:xr-xml-map "snmp_bulkstat_cfg:Enable";
            xr:xr-cli-map "transfer-id <string> enable ";
            type empty;
            description
              "Start Data Collection for this Configuration";
          }
          leaf primary {
            xr:xr-xml-map "snmp_bulkstat_cfg:Primary";
            xr:xr-cli-map "transfer-id <string> url primary <string"+
              "> ";
            type string;
            description
              "FTP or rcp or TFTP can be used for file
              transfer";
          }
          leaf interval {
            xr:xr-xml-map "snmp_bulkstat_cfg:Interval";
            xr:xr-cli-map "transfer-id <string> transfer-interval <"+
              "number> ";
            type int32;
            units "minute";
            description "Periodicity of the transfer";
          }
          leaf transfer-name {
            xr:xr-xml-map "snmp_bulkstat_cfg:TransferName";
            type xr:Cisco-ios-xr-string {
              length "0..32";
            }
            description "Name of bulk transfer";
          }
        }
      }
      leaf memory {
        xr:xr-xml-map "snmp_bulkstat_cfg:Memory";
        xr:xr-cli-map "mib bulkstat max-procmem-size <number> ";
        type uint32 {
          range "100..200000";
        }
        units "kilobyte";
        description "per process memory limit in kilo bytes";
      }
    }

    container default-community-maps {
      xr:xr-xml-map "snmp_cfg:DefaultCommunityMapTable";
      description
        "Container class to hold unencrpted community map";

      list default-community-map {
        xr:xr-xml-map "snmp_cfg:DefaultCommunityMap";
        key "community-name";
        description "Unencrpted SNMP community map name ";
        leaf community-name {
          xr:xr-xml-map "snmp_cfg:CommunityName";
          type xr:Cisco-ios-xr-string {
            length "0..128";
          }
          description "SNMP community map";
        }
        leaf context {
          xr:xr-xml-map "snmp_cfg:Context";
          type string;
          description "SNMP Context Name ";
        }
        leaf security {
          xr:xr-xml-map "snmp_cfg:Security";
          type string;
          description "SNMP Security Name ";
        }
        leaf target-list {
          xr:xr-xml-map "snmp_cfg:TargetList";
          type string;
          description "target list name ";
        }
      }
    }

    container overload-control {
      xr:xr-xml-map "snmp_cfg:OverloadControl";
      presence "Indicates a overload-control node is configured.";
      description
        "Set overload control params for handling
        incoming messages";
      leaf drop-time {
        xr:xr-xml-map "snmp_cfg:DropTime";
        type uint32 {
          range "0..300";
        }
        units "second";
        mandatory true;
        description
          "Drop time in seconds for incoming queue
          (default 1 sec)";
      }
      leaf throttle-rate {
        xr:xr-xml-map "snmp_cfg:ThrottleRate";
        type uint32 {
          range "0..1000";
        }
        units "millisecond";
        mandatory true;
        description
          "Throttle time in milliseconds for incoming
          queue (default 500 msec)";
      }
    }

    container timeouts {
      xr:xr-xml-map "snmp_cfg:Timeouts";
      description "SNMP timeouts";
      leaf duplicates {
        xr:xr-xml-map "snmp_cfg:Duplicates";
        xr:xr-cli-map "timeouts duplicate <number> ";
        type uint32 {
          range "0..20";
        }
        units "second";
        default "1";
        description "timeout in secs";
      }
      leaf in-qdrop {
        xr:xr-xml-map "snmp_cfg:InQdrop";
        xr:xr-cli-map "timeouts inQdrop <number> ";
        type uint32 {
          range "0..20";
        }
        units "second";
        default "10";
        description "timeout in secs";
      }
      leaf subagent {
        xr:xr-xml-map "snmp_cfg:Subagent";
        xr:xr-cli-map "timeouts subagent <number> ";
        type uint32 {
          range "1..20";
        }
        units "second";
        default "10";
        description "timeout in secs";
      }
      leaf pdu-stats {
        xr:xr-xml-map "snmp_cfg:PDUStats";
        xr:xr-cli-map "timeouts pdu stats <number> ";
        type uint32 {
          range "1..10";
        }
        units "second";
        default "2";
        description "timeout in secs";
      }
    }

    container users {
      xr:xr-xml-map "snmp_cfg:UserTable";
      description "Define a user who can access the SNMP engine";

      list user {
        xr:xr-xml-map "snmp_cfg:User";
        xr:xr-cli-map "user <string> <string> [remote <IPv4"+
          "/IPv6 address> [udp-port <number>]] (v1)|(v2c)|(v3 [auth"+
          " (md5)|(sha) ([0] <string>)|(clear)|((7)|(encrypted) <st"+
          "ring>)|(<string>) [priv (des56)|(3des)|(aes (128)|(192)|"+
          "(256)) ([0] <string>)|(clear)|((7)|(encrypted) <string>)"+
          "|(<string>)]])] [IPv4 <string> [IPv6 <string>]|IPv6 <str"+
          "ing> [IPv4 <string>]|<string>] [SDROwner|LROwner|SystemO"+
          "wner] ";
        key "user-name";
        description "Name of the user";
        leaf user-name {
          xr:xr-xml-map "snmp_cfg:UserName";
          type string;
          description "Name of the user";
        }
        leaf group-name {
          xr:xr-xml-map "snmp_cfg:GroupName";
          type string;
          mandatory true;
          description "Group to which the user belongs";
        }
        leaf version {
          xr:xr-xml-map "snmp_cfg:Version";
          type User-snmp-version;
          mandatory true;
          description "SNMP version to be used. v1,v2c or v3";
        }
        leaf authentication-password-configured {
          xr:xr-xml-map "snmp_cfg:AuthenticationPasswordConfigured";
          type empty;
          description
            "Flag to indicate that authentication password
            is configred for version 3";
        }
        leaf algorithm {
          xr:xr-xml-map "snmp_cfg:Algorithm";
          type Snmp-hash-algorithm;
          description "The algorithm used md5 or sha";
        }
        leaf authentication-password {
          xr:xr-xml-map "snmp_cfg:AuthenticationPassword";
          type xr:Proprietary-password;
          description "The authentication password";
        }
        leaf privacy-password-configured {
          xr:xr-xml-map "snmp_cfg:PrivacyPasswordConfigured";
          type empty;
          description
            "Flag to indicate that the privacy password is
            configured for version 3";
        }
        leaf priv-algorithm {
          xr:xr-xml-map "snmp_cfg:Priv_Algorithm";
          type Snmp-priv-algorithm;
          description
            "The algorithm used des56 or aes128 or aes192or
            aes256 or 3des";
        }
        leaf privacy-password {
          xr:xr-xml-map "snmp_cfg:PrivacyPassword";
          type xr:Proprietary-password;
          description "The privacy password";
        }
        leaf v4acl-type {
          xr:xr-xml-map "snmp_cfg:V4ACLType";
          type Snmpacl;
          description "Access-list type";
        }
        leaf v4-access-list {
          xr:xr-xml-map "snmp_cfg:V4AccessList";
          type string;
          description "Ipv4 Access-list name";
        }
        leaf v6acl-type {
          xr:xr-xml-map "snmp_cfg:V6ACLType";
          type Snmpacl;
          description "Access-list type";
        }
        leaf v6-access-list {
          xr:xr-xml-map "snmp_cfg:V6AccessList";
          type string;
          description "Ipv6 Access-list name";
        }
        leaf owner {
          xr:xr-xml-map "snmp_cfg:Owner";
          type Snmp-owner-access;
          description
            "The system access either SDROwner or
            SystemOwner";
        }
        leaf remote-address {
          xr:xr-xml-map "snmp_cfg:RemoteAddress";
          type inet:ip-address-no-zone;
          description "IP address of remote SNMP entity";
        }
        leaf port {
          xr:xr-xml-map "snmp_cfg:Port";
          type xr:Cisco-ios-xr-port-number;
          description "UDP port number";
        }
      }
    }

    container vrfs {
      xr:xr-xml-map "snmp_cfg:VRFTable";
      description "SNMP VRF configuration commands";

      list vrf {
        xr:xr-xml-map "snmp_cfg:VRF";
        key "name";
        description "VRF name";
        leaf name {
          xr:xr-xml-map "snmp_cfg:Name";
          type xr:Cisco-ios-xr-string;
          description "VRF name";
        }
        uses TRAP-HOST-TABLE;
        uses CONTEXT-TABLE;
        uses CONTEXT-MAPPING-TABLE;
      }
    }

    container groups {
      xr:xr-xml-map "snmp_cfg:GroupTable";
      description "Define a User Security Model group";

      list group {
        xr:xr-xml-map "snmp_cfg:Group";
        xr:xr-cli-map "group <string> <enum> [notify <string>|read "+
          "<string>|write <string>|context <string>] [IPv4 <string>"+
          " [IPv6 <string>]|IPv6 <string> [IPv4 <string>]|<string>]"+
          " ";
        key "name";
        description "Name of the group";
        leaf name {
          xr:xr-xml-map "snmp_cfg:Name";
          type xr:Cisco-ios-xr-string {
            length "0..128";
          }
          description "Name of the group";
        }
        leaf snmp-version {
          xr:xr-xml-map "snmp_cfg:SNMPVersion";
          type Group-snmp-version;
          mandatory true;
          description "snmp version";
        }
        leaf security-model {
          xr:xr-xml-map "snmp_cfg:SecurityModel";
          type Snmp-security-model;
          description
            "security model like auth/noAuth/Priv
            applicable for v3";
        }
        leaf notify-view {
          xr:xr-xml-map "snmp_cfg:NotifyView";
          type string;
          description "notify view name";
        }
        leaf read-view {
          xr:xr-xml-map "snmp_cfg:ReadView";
          type string;
          description "read view name";
        }
        leaf write-view {
          xr:xr-xml-map "snmp_cfg:WriteView";
          type string;
          description "write view name";
        }
        leaf v4acl-type {
          xr:xr-xml-map "snmp_cfg:V4ACLType";
          type Snmpacl;
          description "Access-list type";
        }
        leaf v4-access-list {
          xr:xr-xml-map "snmp_cfg:V4AccessList";
          type string;
          description "Ipv4 Access-list name";
        }
        leaf v6acl-type {
          xr:xr-xml-map "snmp_cfg:V6ACLType";
          type Snmpacl;
          description "Access-list type";
        }
        leaf v6-access-list {
          xr:xr-xml-map "snmp_cfg:V6AccessList";
          type string;
          description "Ipv6 Access-list name";
        }
        leaf context-name {
          xr:xr-xml-map "snmp_cfg:ContextName";
          type string;
          description "Context name";
        }
      }
    }
    leaf inform-retries {
      xr:xr-xml-map "snmp_cfg:InformRetries";
      xr:xr-cli-map "inform retries <number> ";
      type uint32 {
        range "0..100";
      }
      description
        "Number of times to retry an Inform request
        (default 3)";
    }
    leaf trap-port {
      xr:xr-xml-map "snmp_cfg:TrapPort";
      xr:xr-cli-map "trap-source port <number> ";
      type uint32 {
        range "1024..65535";
      }
      description "UDP port number";
    }
    leaf oid-poll-stats {
      xr:xr-xml-map "snmp_cfg:OIDPollStats";
      xr:xr-cli-map "oid-poll-stats ";
      type empty;
      description "Enable Poll OID statistics";
    }
    leaf trap-source {
      xr:xr-xml-map "snmp_cfg:TrapSource";
      xr:xr-cli-map "trap-source <interface> ";
      type xr:Interface-name;
      description "Interface name";
    }
    leaf vrf-authentication-trap-disable {
      xr:xr-xml-map "snmp_cfg:VRFAuthenticationTrapDisable";
      xr:xr-cli-map "authentication vrf disable ";
      type empty;
      description
        "Disable authentication traps for packets on a
        vrf";
    }
    leaf inform-timeout {
      xr:xr-xml-map "snmp_cfg:InformTimeout";
      xr:xr-cli-map "inform timeout <number> ";
      type uint32 {
        range "1..42949671";
      }
      units "second";
      description
        "Timeout value in seconds for Inform request
        (default 15 sec)";
    }
    leaf packet-size {
      xr:xr-xml-map "snmp_cfg:PacketSize";
      xr:xr-cli-map "packetsize <number> ";
      type uint32 {
        range "484..65500";
      }
      description "Packet size";
    }
    leaf throttle-time {
      xr:xr-xml-map "snmp_cfg:ThrottleTime";
      xr:xr-cli-map "throttle-time <number> ";
      type uint32 {
        range "50..1000";
      }
      description
        "Throttle time for incoming queue (default 0
        msec)";
    }
    leaf inform-pending {
      xr:xr-xml-map "snmp_cfg:InformPending";
      xr:xr-cli-map "inform pending <number> ";
      type uint32 {
        range "0..4294967295";
      }
      description
        "Max nmber of informs to hold in queue, (default
        25)";
    }
    uses TRAP-HOST-TABLE;
    uses CONTEXT-TABLE;
    uses CONTEXT-MAPPING-TABLE;
  }

  container mib {
    xr:xr-xml-map "snmp_cfg:MIB";
    description "mib";
  }
}
