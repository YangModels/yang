module Cisco-IOS-XR-um-if-encap-ambiguous-cfg {
  namespace "http://cisco.com/ns/yang/Cisco-IOS-XR-um-if-encap-ambiguous-cfg";
  prefix um-if-encap-ambiguous-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-encap-ambiguous package configuration.
     
     This YANG module augments the
     modules with configuration data.
     
     Copyright (c) 2020-2022 by Cisco Systems, Inc.
     All rights reserved.";

  revision 2021-12-10 {
    description
      "Updated must checks for dot1q/vlan-id and dot1ad/vlan-id";
    semver:module-version "1.1.0";
  }
  revision 2020-07-17 {
    description
      "Initial release";
    semver:module-version "1.0.0";
  }

  grouping IF-BODY {
    container encapsulation {
      when "(../a1:interface-name[starts-with(text(),'FastEthernet')] or ../a1:interface-name[starts-with(text(),'GigabitEthernet')] or ../a1:interface-name[starts-with(text(),'TenGigE')] or ../a1:interface-name[starts-with(text(),'FortyGigE')] or ../a1:interface-name[starts-with(text(),'HundredGigE')] or ../a1:interface-name[starts-with(text(),'TwoHundredGigE')] or ../a1:interface-name[starts-with(text(),'FourHundredGigE')] or ../a1:interface-name[starts-with(text(),'EightHundredGigE')] or ../a1:interface-name[starts-with(text(),'TwentyFiveGigE')] or ../a1:interface-name[starts-with(text(),'FiftyGigE')])and ../a1:interface-name[contains(text(),'.')]and not(../a1:sub-interface-type/a1:l2transport)" {
        tailf:dependency "../a1:interface-name";
      }
      description
        "Specify which packets will be matched by this sub-interface";
      container ambiguous {
        description
          "Ambiguous L3 VLAN configuration";
        container dot1q {
          description
            "IEEE 802.1Q VLAN-tagged packets";
          leaf vlan-id {
            type uint32 {
              range "1..4094" {
                description
                  "Single VLAN id";
              }
            }
            must "not(../any) and (../end-vlan-id or ../vlan-id-2 or ../second-dot1q/vlan-id or ../second-dot1q/any)";
            description
              "Single VLAN id or start of VLAN range";
          }
          container any {
            must "not(../vlan-id)";
            presence "Indicates a any node is configured.";
            description
              "Match any VLAN id";
          }
          leaf end-vlan-id {
            type uint32 {
              range "1..4094" {
                description
                  "End of VLAN range";
              }
            }
            must "../vlan-id";
            description
              "End of VLAN range";
          }
          leaf vlan-id-2 {
            type uint32 {
              range "1..4094" {
                description
                  "Single VLAN id";
              }
            }
            must "../vlan-id";
            description
              "Single VLAN id or start of VLAN range";
          }
          leaf end-vlan-id-2 {
            type uint32 {
              range "1..4094" {
                description
                  "End of VLAN range";
              }
            }
            must "../vlan-id-2";
            description
              "End of VLAN range";
          }
          leaf vlan-id-3 {
            type uint32 {
              range "1..4094" {
                description
                  "Single VLAN id";
              }
            }
            must "../vlan-id-2";
            description
              "Single VLAN id or start of VLAN range";
          }
          leaf end-vlan-id-3 {
            type uint32 {
              range "1..4094" {
                description
                  "End of VLAN range";
              }
            }
            must "../vlan-id-3";
            description
              "End of VLAN range";
          }
          leaf vlan-id-4 {
            type uint32 {
              range "1..4094" {
                description
                  "Single VLAN id";
              }
            }
            must "../vlan-id-3";
            description
              "Single VLAN id or start of VLAN range";
          }
          leaf end-vlan-id-4 {
            type uint32 {
              range "1..4094" {
                description
                  "End of VLAN range";
              }
            }
            must "../vlan-id-4";
            description
              "End of VLAN range";
          }
          leaf vlan-id-5 {
            type uint32 {
              range "1..4094" {
                description
                  "Single VLAN id";
              }
            }
            must "../vlan-id-4";
            description
              "Single VLAN id or start of VLAN range";
          }
          leaf end-vlan-id-5 {
            type uint32 {
              range "1..4094" {
                description
                  "End of VLAN range";
              }
            }
            must "../vlan-id-5";
            description
              "End of VLAN range";
          }
          leaf vlan-id-6 {
            type uint32 {
              range "1..4094" {
                description
                  "Single VLAN id";
              }
            }
            must "../vlan-id-5";
            description
              "Single VLAN id or start of VLAN range";
          }
          leaf end-vlan-id-6 {
            type uint32 {
              range "1..4094" {
                description
                  "End of VLAN range";
              }
            }
            must "../vlan-id-6";
            description
              "End of VLAN range";
          }
          leaf vlan-id-7 {
            type uint32 {
              range "1..4094" {
                description
                  "Single VLAN id";
              }
            }
            must "../vlan-id-6";
            description
              "Single VLAN id or start of VLAN range";
          }
          leaf end-vlan-id-7 {
            type uint32 {
              range "1..4094" {
                description
                  "End of VLAN range";
              }
            }
            must "../vlan-id-7";
            description
              "End of VLAN range";
          }
          leaf vlan-id-8 {
            type uint32 {
              range "1..4094" {
                description
                  "Single VLAN id";
              }
            }
            must "../vlan-id-7";
            description
              "Single VLAN id or start of VLAN range";
          }
          leaf end-vlan-id-8 {
            type uint32 {
              range "1..4094" {
                description
                  "End of VLAN range";
              }
            }
            must "../vlan-id-8";
            description
              "End of VLAN range";
          }
          leaf vlan-id-9 {
            type uint32 {
              range "1..4094" {
                description
                  "Single VLAN id";
              }
            }
            must "../vlan-id-8";
            description
              "Single VLAN id or start of VLAN range";
          }
          leaf end-vlan-id-9 {
            type uint32 {
              range "1..4094" {
                description
                  "End of VLAN range";
              }
            }
            must "../vlan-id-9";
            description
              "End of VLAN range";
          }
          container second-dot1q {
            description
              "IEEE 802.1Q VLAN-tagged packets";
            leaf vlan-id {
              type uint32 {
                range "1..4094" {
                  description
                    "Single VLAN id";
                }
              }
              must "../../any and not(../any)";
              description
                "Single VLAN id";
            }
            container any {
              must "not(../vlan-id)";
              presence "Indicates a any node is configured.";
              description
                "Match any VLAN id";
            }
          }
        }
        container dot1ad {
          description
            "IEEE 802.1ad VLAN-tagged packets";
          leaf vlan-id {
            type uint32 {
              range "1..4094" {
                description
                  "Single VLAN id";
              }
            }
            must "not(../any) and (../end-vlan-id or ../vlan-id-2)";
            description
              "Single VLAN id or start of VLAN range";
          }
          container any {
            must "not(../vlan-id)";
            presence "Indicates a any node is configured.";
            description
              "Match any VLAN id";
          }
          leaf end-vlan-id {
            type uint32 {
              range "1..4094" {
                description
                  "End of VLAN range";
              }
            }
            must "../vlan-id";
            description
              "End of VLAN range";
          }
          leaf vlan-id-2 {
            type uint32 {
              range "1..4094" {
                description
                  "Single VLAN id";
              }
            }
            must "../vlan-id";
            description
              "Single VLAN id or start of VLAN range";
          }
          leaf end-vlan-id-2 {
            type uint32 {
              range "1..4094" {
                description
                  "End of VLAN range";
              }
            }
            must "../vlan-id-2";
            description
              "End of VLAN range";
          }
          leaf vlan-id-3 {
            type uint32 {
              range "1..4094" {
                description
                  "Single VLAN id";
              }
            }
            must "../vlan-id-2";
            description
              "Single VLAN id or start of VLAN range";
          }
          leaf end-vlan-id-3 {
            type uint32 {
              range "1..4094" {
                description
                  "End of VLAN range";
              }
            }
            must "../vlan-id-3";
            description
              "End of VLAN range";
          }
          leaf vlan-id-4 {
            type uint32 {
              range "1..4094" {
                description
                  "Single VLAN id";
              }
            }
            must "../vlan-id-3";
            description
              "Single VLAN id or start of VLAN range";
          }
          leaf end-vlan-id-4 {
            type uint32 {
              range "1..4094" {
                description
                  "End of VLAN range";
              }
            }
            must "../vlan-id-4";
            description
              "End of VLAN range";
          }
          leaf vlan-id-5 {
            type uint32 {
              range "1..4094" {
                description
                  "Single VLAN id";
              }
            }
            must "../vlan-id-4";
            description
              "Single VLAN id or start of VLAN range";
          }
          leaf end-vlan-id-5 {
            type uint32 {
              range "1..4094" {
                description
                  "End of VLAN range";
              }
            }
            must "../vlan-id-5";
            description
              "End of VLAN range";
          }
          leaf vlan-id-6 {
            type uint32 {
              range "1..4094" {
                description
                  "Single VLAN id";
              }
            }
            must "../vlan-id-5";
            description
              "Single VLAN id or start of VLAN range";
          }
          leaf end-vlan-id-6 {
            type uint32 {
              range "1..4094" {
                description
                  "End of VLAN range";
              }
            }
            must "../vlan-id-6";
            description
              "End of VLAN range";
          }
          leaf vlan-id-7 {
            type uint32 {
              range "1..4094" {
                description
                  "Single VLAN id";
              }
            }
            must "../vlan-id-6";
            description
              "Single VLAN id or start of VLAN range";
          }
          leaf end-vlan-id-7 {
            type uint32 {
              range "1..4094" {
                description
                  "End of VLAN range";
              }
            }
            must "../vlan-id-7";
            description
              "End of VLAN range";
          }
          leaf vlan-id-8 {
            type uint32 {
              range "1..4094" {
                description
                  "Single VLAN id";
              }
            }
            must "../vlan-id-7";
            description
              "Single VLAN id or start of VLAN range";
          }
          leaf end-vlan-id-8 {
            type uint32 {
              range "1..4094" {
                description
                  "End of VLAN range";
              }
            }
            must "../vlan-id-8";
            description
              "End of VLAN range";
          }
          leaf vlan-id-9 {
            type uint32 {
              range "1..4094" {
                description
                  "Single VLAN id";
              }
            }
            must "../vlan-id-8";
            description
              "Single VLAN id or start of VLAN range";
          }
          leaf end-vlan-id-9 {
            type uint32 {
              range "1..4094" {
                description
                  "End of VLAN range";
              }
            }
            must "../vlan-id-9";
            description
              "End of VLAN range";
          }
          container dot1q {
            description
              "IEEE 802.1Q VLAN-tagged packets";
            leaf vlan-id {
              type uint32 {
                range "1..4094" {
                  description
                    "Single VLAN id";
                }
              }
              must "../../any and not(../any)";
              description
                "Single VLAN id";
            }
            container any {
              must "not(../vlan-id)";
              presence "Indicates a any node is configured.";
              description
                "Match any VLAN id";
            }
          }
        }
      }
    }
  }

  augment "/a1:interfaces/a1:interface" {
    uses IF-BODY;
  }
  augment "/a1:interfaces/a1:interface-preconfigure" {
    uses IF-BODY;
  }
}
