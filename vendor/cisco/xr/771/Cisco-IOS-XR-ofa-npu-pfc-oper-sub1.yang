submodule Cisco-IOS-XR-ofa-npu-pfc-oper-sub1 {
  belongs-to Cisco-IOS-XR-ofa-npu-pfc-oper {
    prefix Cisco-IOS-XR-ofa-npu-pfc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-npu-pfc package operational data.
     
     Copyright (c) 2013-2021 by Cisco Systems, Inc.
     All rights reserved.";

  revision 2021-08-19 {
    description
      "Create the initial priority-flow-control oper yang model.";
    semver:module-version "1.0.0";
  }
  revision 2019-04-05 {
    description
      "Establish semantic version baseline.";
  }
  revision 2015-11-09 {
    description
      "IOS XR 6.0 revision.";
  }

  grouping OFA-PFC-TC-CFG {
    description
      "OFA PFC TC CFG";
    leaf in-use {
      type boolean;
      description
        "Flag to indicate if PFC is configured for the tc";
    }
    leaf pause-threshold {
      type uint32;
      description
        "Pause-threshold configured";
    }
    leaf tc-headroom {
      type uint32;
      description
        "Headroom configured";
    }
    leaf tc-ecn {
      type uint32;
      description
        "ECN configured";
    }
  }

  grouping OFA-PFC-CFG {
    description
      "OFA PFC CFG";
    leaf in-use {
      type boolean;
      description
        "Flag to indicate if PFC is configured for the
         line-card";
    }
    leaf pfc-mode {
      type uint8;
      description
        "PFC Mode";
    }
    list tc-cfg {
      max-elements "8";
      description
        "Keeps a record of the PFC configuration for the
         line-card";
      uses OFA-PFC-TC-CFG;
    }
  }
}
