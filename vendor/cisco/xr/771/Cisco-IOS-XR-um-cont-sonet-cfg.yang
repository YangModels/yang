module Cisco-IOS-XR-um-cont-sonet-cfg {
  namespace "http://cisco.com/ns/yang/Cisco-IOS-XR-um-cont-sonet-cfg";
  prefix um-cont-sonet-cfg;

  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-sonet package configuration.
     
     This YANG module augments the
     modules with configuration data.
     
     Copyright (c) 2021-2022 by Cisco Systems, Inc.
     All rights reserved.";

  revision 2022-06-01 {
    description
      "Adjusted controller augmentation hierarchy";
    semver:module-version "1.0.0";
  }
  revision 2021-03-03 {
    description
      "Initial release";
    semver:module-version "1.0.0";
  }

  grouping CONT-BODY {
    container ais-shut {
      presence "Indicates a ais-shut node is configured.";
      description
        "Enable sending SONET/SDH LAIS when shutdown";
    }
    container ais-pwfault {
      presence "Indicates a ais-pwfault node is configured.";
      description
        "Enable sending SONET/SDH LAIS for L2Port when PW fails";
    }
    container clock {
      description
        "Configure SONET/SDH port clock";
      leaf source {
        type enumeration {
          enum "internal" {
            value 0;
            description
              "Select internal clock";
          }
          enum "line" {
            value 1;
            description
              "Select clock recovered from line (default)";
          }
        }
        description
          "Configure SONET/SDH port TX clock source";
      }
    }
    leaf framing {
      type enumeration {
        enum "sonet" {
          value 0;
          description
            "Select SONET framing (default)";
        }
        enum "sdh" {
          value 1;
          description
            "Select SDH framing";
        }
      }
      description
        "Configure SONET/SDH framing";
    }
    container loopback {
      description
        "Configure SONET/SDH controller loopback mode";
      container internal {
        must "not(../line)";
        presence "Indicates a internal node is configured.";
        description
          "Select local (terminal) loopback";
      }
      container line {
        must "not(../internal)";
        presence "Indicates a line node is configured.";
        description
          "Select network (facility) loopback";
      }
    }
    container down-when-looped {
      presence "Indicates a down-when-looped node is configured.";
      description
        "Configure SONET/SDH controller into down-when-looped mode";
    }
    container s1byte {
      description
        "Configure SONET/SDH controller to s1byte ignore mode";
      container ignore {
        presence "Indicates a ignore node is configured.";
        description
          "Ignore S1 byte";
      }
    }
    container overhead {
      description
        "Configure SONET/SDH SOH/LOH byte/bit values";
      leaf j0 {
        type uint32 {
          range "0..255" {
            description
              "J0/C1 byte value (default 0x01)";
          }
        }
        description
          "Specify STS identifier (J0/C1) byte";
      }
      leaf s1s0 {
        type uint32 {
          range "0..3" {
            description
              "s1 & s0 bits value (default 0x0)";
          }
        }
        description
          "Specify bits s1 and s0 of H1 byte";
      }
    }
    container report {
      description
        "Configure SONET/SDH section/line alarm reporting";
      container b1-tca {
        description
          "Set B1 BER Threshold Crossing Alert (TCA) reporting status";
        container disable {
          presence "Indicates a disable node is configured.";
          description
            "";
        }
      }
      container b2-tca {
        description
          "Set B2 BER Threshold Crossing Alert (TCA) reporting status";
        container disable {
          presence "Indicates a disable node is configured.";
          description
            "";
        }
      }
      container lais {
        presence "Indicates a lais node is configured.";
        description
          "Set Line Alarm Indication Signal reporting status";
      }
      container lrdi {
        presence "Indicates a lrdi node is configured.";
        description
          "Set Line Remote Defect Indication reporting status";
      }
      container sd-ber {
        presence "Indicates a sd-ber node is configured.";
        description
          "Set LBIP BER in excess of SD threshold reporting status";
      }
      container sf-ber {
        description
          "Set LBIP BER in excess of SF threshold reporting status";
        container disable {
          presence "Indicates a disable node is configured.";
          description
            "";
        }
      }
      container slof {
        description
          "Set Section Loss of Frame reporting status";
        container disable {
          presence "Indicates a disable node is configured.";
          description
            "";
        }
      }
      container slos {
        description
          "Set Section Loss of Signal reporting status";
        container disable {
          presence "Indicates a disable node is configured.";
          description
            "";
        }
      }
    }
    container threshold {
      description
        "Configure SONET/SDH section/line BER threshold values";
      leaf b1-tca {
        type uint32 {
          range "3..9" {
            description
              "Bit error rate (10 to the minus n) (default 6)";
          }
        }
        description
          "Set B1 BER Threshold Crossing Alert (TCA) threshold";
      }
      leaf b2-tca {
        type uint32 {
          range "3..9" {
            description
              "Bit error rate (10 to the minus n) (default 6)";
          }
        }
        description
          "Set B2 BER Threshold Crossing Alert (TCA) threshold";
      }
      leaf sd-ber {
        type uint32 {
          range "3..9" {
            description
              "Bit error rate (10 to the minus n) (default 6)";
          }
        }
        description
          "Set Signal Degrade BER threshold";
      }
      leaf sf-ber {
        type uint32 {
          range "3..9" {
            description
              "Bit error rate (10 to the minus n) (default 3)";
          }
        }
        description
          "Set Signal Fail BER threshold";
      }
    }
    container line {
      description
        "Configure SONET/SDH line parameters";
      container delay {
        description
          "alarm soaking";
        leaf trigger {
          type uint32 {
            range "0..60000" {
              description
                "Time in msec to soak before declaring the alarm (Default No Delay)";
            }
          }
          description
            "trigger time";
        }
        leaf clear {
          type uint32 {
            range "1000..180000" {
              description
                "Time in msec to soak before clearing the alarm (Default 10 seconds)";
            }
          }
          description
            "clear time";
        }
      }
      container down {
        description
          "Set Line Down";
        container sd-ber {
          presence "Indicates a sd-ber node is configured.";
          description
            "With Presence of SD BER";
        }
      }
    }
    container path {
      presence "Indicates a path node is configured.";
      description
        "Configure SONET/SDH path parameters";
      container delay {
        description
          "alarm soaking";
        leaf trigger {
          type uint32 {
            range "0..60000" {
              description
                "Time in msec to soak before declaring the alarm (Default No Delay)";
            }
          }
          description
            "trigger time";
        }
        leaf clear {
          type uint32 {
            range "1000..180000" {
              description
                "Time in msec to soak before clearing the alarm (Default 10 seconds)";
            }
          }
          description
            "clear time";
        }
      }
      container b3-ber-prdi {
        presence "Indicates a b3-ber-prdi node is configured.";
        description
          "Enable sending PRDI when configured";
      }
      container path-down-pplm {
        description
          "Set PPLM sonet path action";
        container disable {
          presence "Indicates a disable node is configured.";
          description
            "";
        }
      }
      container ais-shut {
        presence "Indicates a ais-shut node is configured.";
        description
          "Enable sending SONET/SDH PAIS when shutdown";
      }
      container overhead {
        description
          "Configure SONET/SDH POH byte/bit values";
        leaf c2 {
          type uint32 {
            range "0..255" {
              description
                "C2 byte value (default 0xCF)";
            }
          }
          description
            "Specify STS SPE content (C2) byte";
        }
        leaf j1 {
          type string {
            length "1..62" {
              description
                "ASCII text (max 62 characters)";
            }
          }
          description
            "Configure SONET/SDH path trace (J1) transmit buffer";
        }
        leaf expected-trace {
          type string {
            length "1..62" {
              description
                "ASCII text (max 62 characters)";
            }
          }
          description
            "Configure SONET/SDH expected path trace";
        }
      }
      container report {
        description
          "Configure SONET/SDH path alarm reporting";
        container b3-tca {
          description
            "Set B3 BER Threshold Crossing Alert (TCA) reporting status";
          container disable {
            presence "Indicates a disable node is configured.";
            description
              "";
          }
        }
        container pais {
          presence "Indicates a pais node is configured.";
          description
            "Set Path Alarm Indication Signal reporting status";
        }
        container plop {
          description
            "Set Path Loss of Pointer reporting status";
          container disable {
            presence "Indicates a disable node is configured.";
            description
              "";
          }
        }
        container prdi {
          presence "Indicates a prdi node is configured.";
          description
            "Set Path Remote Defect Indication reporting status";
        }
        container pplm {
          presence "Indicates a pplm node is configured.";
          description
            "Set Path Payload Mismatch Defect reporting status";
        }
        container ptim {
          presence "Indicates a ptim node is configured.";
          description
            "Set Path Trace Identity Mismatch Defect reporting status";
        }
        container puneq {
          presence "Indicates a puneq node is configured.";
          description
            "Set Path Unequipped Defect Indication reporting status";
        }
      }
      container scrambling {
        description
          "Configure SONET/SDH SPE scrambling";
        container disable {
          presence "Indicates a disable node is configured.";
          description
            "";
        }
      }
      container threshold {
        description
          "Configure SONET/SDH path BER threshold values";
        leaf b3-tca {
          type uint32 {
            range "3..9" {
              description
                "Bit error rate (10 to the minus n) (default 6)";
            }
          }
          description
            "Set B3 BER Threshold Crossing Alert (TCA) threshold";
        }
      }
      container disable {
        description
          "Configure SONET controller's state on detecting PATH alarms";
        container alarm-down {
          presence "Indicates a alarm-down node is configured.";
          description
            "Do not bring controller state to down on any path alarm";
        }
      }
      container uneq-shut {
        presence "Indicates a uneq-shut node is configured.";
        description
          "Configure sending SONET/SDH UNEQuipped when shutdown";
      }
    }
    container stses {
      description
        "Configure SONET path parameters";
      list sts {
        key "path-range";
        description
          "Configure SONET path parameters";
        leaf path-range {
          type uint32 {
            range "1..48" {
              description
                "Possible range is 1-3 for OC3, 1-12 for OC12 ..";
            }
          }
          description
            "Configure SONET path parameters";
        }
        leaf mode {
          type enumeration {
            enum "atm" {
              value 13;
              description
                "clear channel carrying atm";
            }
            enum "pos-scramble" {
              value 11;
              description
                "clear channel carrying POS scramble";
            }
            enum "pos-unscramble" {
              value 12;
              description
                "clear channel carrying POS unscramble";
            }
            enum "t3" {
              value 9;
              description
                "sonet path carrying T3";
            }
            enum "vt15" {
              value 6;
              description
                "sonet path carrying VT15";
            }
            enum "vt15-t1" {
              value 7;
              description
                "sonet path carrying VT15 T1";
            }
            enum "vt2" {
              value 8;
              description
                "sonet path carrying VT2";
            }
          }
          description
            "Configure mode for the path";
        }
        leaf width {
          type uint32 {
            range "1..768" {
              description
                "Valid width(1,3,12,48..), natural sts boundaries(1,4,7,10,13..)";
            }
          }
          description
            "Configure width for the path";
        }
        container report {
          description
            "Configure SONET/SDH path alarm reporting";
          container b3-tca {
            description
              "Set B3 BER Threshold Crossing Alert (TCA) reporting status";
            container disable {
              presence "Indicates a disable node is configured.";
              description
                "";
            }
          }
          container pais {
            presence "Indicates a pais node is configured.";
            description
              "Set Path Alarm Indication Signal reporting status";
          }
          container plop {
            description
              "Set Path Loss of Pointer reporting status";
            container disable {
              presence "Indicates a disable node is configured.";
              description
                "";
            }
          }
          container prdi {
            presence "Indicates a prdi node is configured.";
            description
              "Set Path Remote Defect Indication reporting status";
          }
          container puneq {
            presence "Indicates a puneq node is configured.";
            description
              "Set Path Unequipped Defect Indication reporting status";
          }
        }
        container threshold {
          description
            "Configure SONET path BER threshold values";
          leaf b3-tca {
            type uint32 {
              range "3..9" {
                description
                  "Bit error rate (10 to the minus n) (default 6)";
              }
            }
            description
              "Set B3 BER Threshold Crossing Alert (TCA) threshold";
          }
        }
        container overhead {
          description
            "Configure SONET/SDH POH byte/bit values";
          leaf c2 {
            type uint32 {
              range "0..255" {
                description
                  "C2 byte value (default 0xCF)";
              }
            }
            description
              "Specify STS SPE content (C2) byte";
          }
          leaf j1 {
            type string {
              length "1..62" {
                description
                  "ASCII text (max 62 characters)";
              }
            }
            description
              "Configure SONET/SDH path trace (J1) buffer";
          }
        }
        container delay {
          description
            "alarm soaking";
          leaf trigger {
            type uint32 {
              range "0..60000" {
                description
                  "Time in msec to soak before declaring the alarm(Non-intelligent SPA 0-511 msec; Intelligent SPA 0-60000 msec)";
              }
            }
            description
              "trigger time";
          }
          leaf clear {
            type uint32 {
              range "1000..180000" {
                description
                  "Time in msec to soak before clearing the alarm(Non-intelligent SPA(Not Supported); Intelligent SPA 1000-180000 msec)";
              }
            }
            description
              "clear time";
          }
        }
      }
    }
    container aus {
      description
        "Configure SDH path parameters";
      list au {
        key "path-range";
        description
          "Configure SDH path parameters";
        leaf path-range {
          type uint32 {
            range "1..48" {
              description
                "au3 or au4 path range";
            }
          }
          description
            "Configure SDH path parameters";
        }
        leaf mode {
          type enumeration {
            enum "atm" {
              value 13;
              description
                "clear channel carrying atm";
            }
            enum "pos-scramble" {
              value 11;
              description
                "clear channel carrying POS scramble";
            }
            enum "pos-unscramble" {
              value 12;
              description
                "clear channel carrying POS unscramble";
            }
            enum "c11" {
              value 4;
              description
                "au3 path carrying c11";
            }
            enum "c11-t1" {
              value 5;
              description
                "au3 path carrying c11 t1";
            }
            enum "c12" {
              value 2;
              description
                "au3 path carrying c12";
            }
            enum "c12-e1" {
              value 3;
              description
                "au3 path carrying c12 e1";
            }
            enum "e3" {
              value 10;
              description
                "au3 path carrying E3";
            }
            enum "t3" {
              value 9;
              description
                "au3 path carrying T3";
            }
            enum "tug3" {
              value 14;
              description
                "au4 path carries TUG3";
            }
          }
          description
            "Configure mode for the au path";
        }
        leaf width {
          type uint32 {
            range "1..768" {
              description
                "Valid width(1,3,12,48..), natural au boundaries(1,4,7,10,13..)";
            }
          }
          description
            "Configure width for the path";
        }
        container report {
          description
            "Configure SONET/SDH path alarm reporting";
          container b3-tca {
            description
              "Set B3 BER Threshold Crossing Alert (TCA) reporting status";
            container disable {
              presence "Indicates a disable node is configured.";
              description
                "";
            }
          }
          container pais {
            presence "Indicates a pais node is configured.";
            description
              "Set Path Alarm Indication Signal reporting status";
          }
          container plop {
            description
              "Set Path Loss of Pointer reporting status";
            container disable {
              presence "Indicates a disable node is configured.";
              description
                "";
            }
          }
          container prdi {
            presence "Indicates a prdi node is configured.";
            description
              "Set Path Remote Defect Indication reporting status";
          }
          container puneq {
            presence "Indicates a puneq node is configured.";
            description
              "Set Path Unequipped Defect Indication reporting status";
          }
        }
        container threshold {
          description
            "Configure SDH path BER threshold values";
          leaf b3-tca {
            type uint32 {
              range "3..9" {
                description
                  "Bit error rate (10 to the minus n) (default 6)";
              }
            }
            description
              "Set B3 BER Threshold Crossing Alert (TCA) threshold";
          }
        }
        container overhead {
          description
            "Configure SONET/SDH POH byte/bit values";
          leaf c2 {
            type uint32 {
              range "0..255" {
                description
                  "C2 byte value (default 0xCF)";
              }
            }
            description
              "Specify STS SPE content (C2) byte";
          }
          leaf j1 {
            type string {
              length "1..62" {
                description
                  "ASCII text (max 62 characters)";
              }
            }
            description
              "Configure SONET/SDH path trace (J1) buffer";
          }
        }
        container delay {
          description
            "alarm soaking";
          leaf trigger {
            type uint32 {
              range "0..60000" {
                description
                  "Time in msec to soak before declaring the alarm(Non-intelligent SPA 0-511 msec; Intelligent SPA 0-60000 msec)";
              }
            }
            description
              "trigger time";
          }
          leaf clear {
            type uint32 {
              range "1000..180000" {
                description
                  "Time in msec to soak before clearing the alarm(Non-intelligent SPA(Not Supported); Intelligent SPA 1000-180000 msec)";
              }
            }
            description
              "clear time";
          }
        }
        container tug3s {
          description
            "Configure tug3 path parameters";
          list tug3 {
            key "number-range";
            description
              "Configure tug3 path parameters";
            leaf number-range {
              type uint32 {
                range "1..3" {
                  description
                    "tug3 number range";
                }
              }
              description
                "Configure tug3 path parameters";
            }
            leaf mode {
              type enumeration {
                enum "c12" {
                  value 2;
                  description
                    "tug3 path carrying TU-12";
                }
                enum "c12-e1" {
                  value 3;
                  description
                    "tug3 path carrying TU-12 to e1";
                }
                enum "c11" {
                  value 4;
                  description
                    "tug3 path carrying TU-11";
                }
                enum "c11-t1" {
                  value 5;
                  description
                    "tug3 path carrying TU-11 to t1";
                }
                enum "t3" {
                  value 9;
                  description
                    "au3 or all tug3 path carrying T3";
                }
                enum "e3" {
                  value 10;
                  description
                    "au3 or all tug3 path carrying E3";
                }
              }
              description
                "Configure mode for the tug3 path";
            }
          }
        }
      }
    }
  }

  augment "/a1:controllers/a1:controller" {
    uses CONT-BODY;
  }
  augment "/a1:controllers/a1:controller-preconfigure" {
    uses CONT-BODY;
  }
}
