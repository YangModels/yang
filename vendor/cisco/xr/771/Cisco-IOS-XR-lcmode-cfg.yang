module Cisco-IOS-XR-lcmode-cfg {
  namespace "http://cisco.com/ns/yang/Cisco-IOS-XR-lcmode-cfg";
  prefix lcmode-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lcmode package configuration.
     
     This module contains definitions
     for the following management objects:
       lcmode-oc: LC MODE OC configuration
       lcmode-cli: LC MODE CLI configuration
     
     Copyright (c) 2013-2021 by Cisco Systems, Inc.
     All rights reserved.";

  revision 2021-06-28 {
    description
      "LCMODE for OTUCn-REGEN added";
    semver:module-version "2.0.0";
  }
  revision 2019-04-05 {
    description
      "Establish semantic version baseline.";
    semver:module-version "1.0.0";
  }
  revision 2015-11-09 {
    description
      "IOS XR 6.0 revision.";
  }

  typedef Lc-mode {
    type enumeration {
      enum "10g-grey-mxp" {
        value 1;
        description
          "LCMODE for 10G GREY MXP with QSFP28 Trunk";
      }
      enum "100g-txp" {
        value 2;
        description
          "LCMODE for 100G TXP";
      }
      enum "4x100g-mxp-400g-txp" {
        value 3;
        description
          "LCMODE for 100G MXP and 400G TXP with CFP2 DCO
           Trunk";
      }
      enum "40x10g-4x100g-mxp" {
        value 4;
        description
          "LCMODE for 10G/100G MXP With CFP2 DCO Trunk";
      }
      enum "4x100ge-mxp-dd" {
        value 5;
        description
          "LCMODE for 100GE MXP with QSFP-DD-ZR Trunk";
      }
      enum "400ge-txp-dd" {
        value 6;
        description
          "LCMODE for 400GE TXP with QSFP-DD-ZR Trunk";
      }
      enum "fc-mxp" {
        value 7;
        description
          "LCMODE for 24x16G FC and 12x32G FC MXP with
           CFP2 Trunk";
      }
      enum "otu-cn-regen" {
        value 8;
        description
          "LCMODE for OTUCn (n = 1,2,3,4) Regen";
      }
    }
    description
      "Lc mode";
  }

  container lcmode-oc {
    description
      "LC MODE OC configuration";
    list slot-info-oc {
      key "lc-slot";
      description
        "location of LC";
      leaf lcmode-type-oc {
        type Lc-mode;
        description
          "LCMODE config type";
      }
      leaf lc-slot {
        type xr:Cisco-ios-xr-string;
        description
          "LC location";
      }
    }
  }
  container lcmode-cli {
    description
      "LC MODE CLI configuration";
    list slot-info-cli {
      key "lc-slot";
      description
        "location of LC";
      leaf lcmode-type-cli {
        type Lc-mode;
        description
          "LCMODE config type";
      }
      leaf lc-slot {
        type xr:Cisco-ios-xr-string;
        description
          "LC location";
      }
    }
  }
}
