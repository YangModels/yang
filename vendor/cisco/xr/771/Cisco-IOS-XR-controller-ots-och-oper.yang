module Cisco-IOS-XR-controller-ots-och-oper {
  namespace "http://cisco.com/ns/yang/Cisco-IOS-XR-controller-ots-och-oper";
  prefix controller-ots-och-oper;

  import Cisco-IOS-XR-types {
    prefix xr;
  }
  import cisco-semver {
    prefix semver;
  }
  include Cisco-IOS-XR-controller-ots-och-oper-sub1 {
    revision-date 2022-03-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-ots-och package operational data.
     
     This module contains definitions
     for the following management objects:
       ots-och-oper: Optics operational data
     
     Copyright (c) 2013-2022 by Cisco Systems, Inc.
     All rights reserved.";

  revision 2022-03-07 {
    description
      "Removed Low-Tx-PWR information from ots_ui.bag";
    semver:module-version "1.0.0";
  }
  revision 2020-07-09 {
    description
      "New Oper Model Added for Ots-Och Controller";
  }
  revision 2019-04-05 {
    description
      "Establish semantic version baseline.";
  }
  revision 2015-11-09 {
    description
      "IOS XR 6.0 revision.";
  }

  container ots-och-oper {
    config false;
    description
      "Optics operational data";
    container ots-och-ports {
      description
        "All Optics Port operational data";
      list ots-och-port {
        key "name";
        description
          "Optics operational data";
        container ots-och-info {
          description
            "Ots-Och operational data";
          uses OTS-EDM-INFO;
        }
        leaf name {
          type xr:Interface-name;
          description
            "Port name";
        }
      }
    }
  }
}
