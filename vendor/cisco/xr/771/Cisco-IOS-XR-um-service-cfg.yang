module Cisco-IOS-XR-um-service-cfg {
  namespace "http://cisco.com/ns/yang/Cisco-IOS-XR-um-service-cfg";
  prefix um-service-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR service package configuration.
     
     This YANG module augments the
     modules with configuration data.
     
     Copyright (c) 2022 by Cisco Systems, Inc.
     All rights reserved.";

  revision 2022-01-23 {
    description
      "Initial release";
    semver:module-version "1.0.0";
  }

  container service {
    description
      "Modify use of network based services";
    container unsupported-transceiver {
      presence "Indicates a unsupported-transceiver node is configured.";
      description
        "Allow unsupported-transceiver to be used on SPAs";
    }
  }
}
