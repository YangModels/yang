module Cisco-IOS-XR-um-line-exec-timeout-cfg {
  namespace "http://cisco.com/ns/yang/Cisco-IOS-XR-um-line-exec-timeout-cfg";
  prefix um-line-exec-timeout-cfg;

  import Cisco-IOS-XR-um-line-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR line-exec-timeout package configuration.
     
     This YANG module augments the
     modules with configuration data.
     
     Copyright (c) 2020 by Cisco Systems, Inc.
     All rights reserved.";

  revision 2020-09-18 {
    description
      "Initial release";
    semver:module-version "1.0.0";
  }

  augment "/a1:line/a1:console" {
    container exec-timeout {
      presence "Indicates a exec-timeout node is configured.";
      description
        "Set EXEC timeout";
      leaf timeout-in-minutes {
        type uint32 {
          range "0..35791" {
            description
              "Timeout in minutes";
          }
        }
        mandatory true;
        description
          "Set EXEC timeout";
      }
      leaf timeout-in-seconds {
        type uint32 {
          range "0..2147483" {
            description
              "Timeout in seconds";
          }
        }
        mandatory true;
        description
          "Timeout in seconds";
      }
    }
  }
  augment "/a1:line/a1:default" {
    container exec-timeout {
      presence "Indicates a exec-timeout node is configured.";
      description
        "Set EXEC timeout";
      leaf timeout-in-minutes {
        type uint32 {
          range "0..35791" {
            description
              "Timeout in minutes";
          }
        }
        mandatory true;
        description
          "Set EXEC timeout";
      }
      leaf timeout-in-seconds {
        type uint32 {
          range "0..2147483" {
            description
              "Timeout in seconds";
          }
        }
        mandatory true;
        description
          "Timeout in seconds";
      }
    }
  }
  augment "/a1:line/a1:templates/a1:template" {
    container exec-timeout {
      presence "Indicates a exec-timeout node is configured.";
      description
        "Set EXEC timeout";
      leaf timeout-in-minutes {
        type uint32 {
          range "0..35791" {
            description
              "Timeout in minutes";
          }
        }
        mandatory true;
        description
          "Set EXEC timeout";
      }
      leaf timeout-in-seconds {
        type uint32 {
          range "0..2147483" {
            description
              "Timeout in seconds";
          }
        }
        mandatory true;
        description
          "Timeout in seconds";
      }
    }
  }
}
