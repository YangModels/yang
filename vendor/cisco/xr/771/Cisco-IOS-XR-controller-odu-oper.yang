module Cisco-IOS-XR-controller-odu-oper {
  namespace "http://cisco.com/ns/yang/Cisco-IOS-XR-controller-odu-oper";
  prefix controller-odu-oper;

  import Cisco-IOS-XR-types {
    prefix xr;
  }
  import cisco-semver {
    prefix semver;
  }
  include Cisco-IOS-XR-controller-odu-oper-sub1 {
    revision-date 2022-03-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-odu package operational data.
     
     This module contains definitions
     for the following management objects:
       odu: ODU operational data
     
     Copyright (c) 2013-2022 by Cisco Systems, Inc.
     All rights reserved.";

  revision 2022-03-04 {
    description
      "Added flag indicating cross-connect status.
       2022-02-15
         Added 3 new enums to odu pt type.
       2021-12-01
         Added LED State
       2021-08-10
         Added PRBS error-inject feature support.";
    semver:module-version "1.5.0";
  }
  revision 2021-05-21 {
    description
      "Added support for ODU PLE information.";
    semver:module-version "1.4.0";
  }
  revision 2021-02-21 {
    description
      "Added IS_CEM_PACKETIZED to odu_resource_et enum for Private Line Emulation feature.
       2020-11-11
           Added PRBS bit errors and lock time support in bag odu_prbs_info.
       2020-09-25
           Added PRBS direction feature support.
       2020-09-22
           Changed existing bag to contain one more enum value for odu pt type
       2020-09-12
           Created New Bag for ODTU Remote Info and Far End Child Info.";
    semver:module-version "1.3.0";
  }
  revision 2019-08-05 {
    description
      "Separated ODTU info variables from ODU info bag and created new bag for ODTU data.";
    semver:module-version "1.2.0";
  }
  revision 2019-04-05 {
    description
      "Establish semantic version baseline.";
    semver:module-version "1.1.0";
  }
  revision 2015-11-09 {
    description
      "IOS XR 6.0 revision.";
  }

  container odu {
    config false;
    description
      "ODU operational data";
    container controllers {
      description
        "All ODU Port operational data";
      list controller {
        key "controller-name";
        description
          "ODU Port operational data";
        container prbs {
          description
            "ODU port operational data";
          uses ODU-PRBS-INFO;
        }
        container info {
          description
            "ODU port operational data";
          uses ODU-PER-PORT-INFO;
        }
        container ple-info {
          description
            "ODU PLE info";
          uses ODU-PLE-INFO-ST;
        }
        container cem-parameters {
          description
            "ODU CEM parameters";
          uses ODU-CEM-PARAM-ST;
        }
        container odtu-info {
          description
            "ODU port ODTU data";
          uses ODU-ODTU-OPER-DATA;
        }
        leaf controller-name {
          type xr:Interface-name;
          description
            "Port name";
        }
      }
    }
  }
}
