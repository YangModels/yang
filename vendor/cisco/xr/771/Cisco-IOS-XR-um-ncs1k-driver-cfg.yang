module Cisco-IOS-XR-um-ncs1k-driver-cfg {
  namespace "http://cisco.com/ns/yang/Cisco-IOS-XR-um-ncs1k-driver-cfg";
  prefix um-ncs1k-driver-cfg;

  import Cisco-IOS-XR-types {
    prefix xr;
  }
  import ietf-inet-types {
    prefix inet;
  }
  import Cisco-IOS-XR-um-interface-cfg {
    prefix a1;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1k-driver package configuration.
     
     This YANG module augments the
     modules with configuration data.
     
     Copyright (c) 2021-2022 by Cisco Systems, Inc.
     All rights reserved.";

  revision 2022-06-01 {
    description
      "Adjusted controller augmentation hierarchy";
    semver:module-version "1.0.0";
  }
  revision 2021-06-29 {
    description
      "Initial release";
  }

  grouping CONT-BODY {
    leaf holdoff-time-client-fault {
      type uint32 {
        range "10..20000" {
          description
            "Time in ms";
        }
      }
      description
        "Holdoff time configuration for client";
    }
  }

  grouping LOCATION-BODY {
    container location {
      description
        "Fully qualified location specification";
      container slice {
        description
          "Target slice";
        container all {
          description
            "Configure  all slice";
          container client {
            description
              "client side parameters";
            leaf bitrate {
              type enumeration {
                enum "10G" {
                  value 1;
                  description
                    "client bitrate 10G";
                }
                enum "40G" {
                  value 2;
                  description
                    "client bitrate 40G";
                }
                enum "100G" {
                  value 3;
                  description
                    "client bitrate 100G";
                }
                enum "10G-100G" {
                  value 4;
                  description
                    "client bitrate mixed mode 8x10G and 3x100G";
                }
              }
              description
                "bit rate ";
            }
            container trunk {
              description
                "trunk side parameters";
              leaf trunk-bitrate {
                type enumeration {
                  enum "100G" {
                    value 2;
                    description
                      "trunk bitrate 100G";
                  }
                  enum "200G" {
                    value 3;
                    description
                      "trunk bitrate 200G";
                  }
                  enum "250G" {
                    value 4;
                    description
                      "trunk bitrate 250G";
                  }
                }
                description
                  "bit rate ";
              }
              leaf fec {
                type enumeration {
                  enum "SoftDecision7" {
                    value 1;
                    description
                      "Forward Error Correction SoftDecision7";
                  }
                  enum "SoftDecision20" {
                    value 2;
                    description
                      "Forward Error Correction SoftDecision20";
                  }
                }
                description
                  "Forward Error Correction mode";
              }
              container encrypted {
                presence "Indicates a encrypted node is configured.";
                description
                  "Enable MACSec mode of operation";
              }
            }
          }
          container drop-lldp {
            presence "Indicates a drop-lldp node is configured.";
            description
              "Drop LLDP packets coming on client ports on this slice";
          }
          container client-port-ains-soak {
            description
              "Client ports AINS configuration";
            leaf hours {
              type uint32 {
                range "0..48" {
                  description
                    "Default AINS soak interval hours value";
                }
              }
              must "../minutes";
              description
                "Default AINS soak interval hours value";
            }
            leaf minutes {
              type uint32 {
                range "0..59" {
                  description
                    "Default AINS soak interval minutes value";
                }
              }
              must "../hours";
              description
                "Default AINS soak interval minutes value";
            }
          }
        }
      }
    }
  }

  augment "/a1:controllers/a1:controller" {
    uses CONT-BODY;
  }
  augment "/a1:controllers/a1:controller-preconfigure" {
    uses CONT-BODY;
  }
  augment "/location:locations/location:location" {
    uses LOCATION-BODY;
  }
  container patch-panel {
    presence "Indicates a patch-panel node is configured.";
    description
      "patch panel device";
    leaf ipv4 {
      type inet:ipv4-address-no-zone;
      description
        "IP Address";
    }
    leaf username {
      type xr:Cisco-ios-xr-string {
        length "1..800" {
          description
            "Enter user name";
        }
      }
      description
        "User Name";
    }
    container password {
      description
        "Password for the username";
      leaf seven {
        type xr:Proprietary-password;
        description
          "Specifies that an encrypted password will follow";
      }
    }
  }
  container terminal-device {
    description
      "Terminal Device";
    container logical-channel {
      description
        "Logical Channel";
      container logical-channel-numbers {
        description
          "Logical channel number (1-100000)";
        list logical-channel-number {
          key "logical-channel-number-id";
          description
            "Logical channel number (1-100000)";
          leaf logical-channel-number-id {
            type uint32 {
              range "1..100000" {
                description
                  "Logical channel number (1-100000)";
              }
            }
            description
              "Logical channel number (1-100000)";
          }
          container assignment-ids {
            description
              "Logical channel assignment id for logical channel";
            list assignment-id {
              key "assignment-id";
              description
                "Logical channel assignment id for logical channel";
              leaf assignment-id {
                type uint32 {
                  range "1..100000" {
                    description
                      "Assignment number (1 to 100000)";
                  }
                }
                description
                  "Logical channel assignment id for logical channel";
              }
              leaf assigned-logical-channel {
                type uint32 {
                  range "1..100000" {
                    description
                      "Logical channel number (1-100000)";
                  }
                }
                description
                  "Logical channel assigned to this assigment id";
              }
              leaf assigned-optical-channel {
                type xr:Cisco-ios-xr-string {
                  length "1..800" {
                    description
                      "Optical channel name";
                  }
                }
                description
                  "Optical channel assigned to this assigment id";
              }
              leaf assignment-type {
                type enumeration {
                  enum "logical" {
                    value 1;
                    description
                      "assignment type logical";
                  }
                  enum "optical" {
                    value 2;
                    description
                      "assignment type optical";
                  }
                }
                description
                  "Assignment type (logical or optical)";
              }
              leaf allocation {
                type uint32 {
                  range "0..4294967295" {
                    description
                      "Allocation (10, 40 or 100G)";
                  }
                }
                description
                  "Allocation";
              }
              leaf description {
                type string {
                  length "1..800" {
                    description
                      "Description";
                  }
                }
                description
                  "Description";
              }
            }
          }
          leaf description {
            type string {
              length "1..800" {
                description
                  "Description";
              }
            }
            description
              "Description";
          }
          leaf admin-state {
            type enumeration {
              enum "enable" {
                value 1;
                description
                  "enable";
              }
              enum "disable" {
                value 2;
                description
                  "shutdown";
              }
              enum "maintenance" {
                value 3;
                description
                  "Maintenance";
              }
            }
            description
              "Administrative state";
          }
          leaf loopback-mode {
            type enumeration {
              enum "none" {
                value 0;
                description
                  "none";
              }
              enum "facility" {
                value 1;
                description
                  "facility";
              }
              enum "terminal" {
                value 2;
                description
                  "terminal";
              }
            }
            description
              "Loopback mode";
          }
          leaf rate-class {
            type enumeration {
              enum "1G" {
                value 1;
                description
                  "1G tributary signal rate";
              }
              enum "1.5G" {
                value 2;
                description
                  "2.5G tributary signal rate";
              }
              enum "10G" {
                value 3;
                description
                  "10G tributary signal rate";
              }
              enum "40G" {
                value 4;
                description
                  "40G tributary signal rate";
              }
              enum "100G" {
                value 5;
                description
                  "100G tributary signal rate";
              }
            }
            description
              "Rate Class";
          }
          leaf trib-protocol {
            type enumeration {
              enum "1GE" {
                value 1;
                description
                  "1G Ethernet protocol";
              }
              enum "OC48" {
                value 2;
                description
                  "OC48 protocol";
              }
              enum "STM16" {
                value 3;
                description
                  "STM 16 protocol";
              }
              enum "10GE-LAN" {
                value 4;
                description
                  "10G Ethernet LAN protocol";
              }
              enum "10GE-WAN" {
                value 5;
                description
                  "10G Ethernet WAN protocol";
              }
              enum "OC192" {
                value 6;
                description
                  "OC 192 (9.6GB) port protocol";
              }
              enum "STM64" {
                value 7;
                description
                  "STM 64 protocol";
              }
              enum "OTU2" {
                value 8;
                description
                  "OTU 2 protocol";
              }
              enum "OTU2e" {
                value 9;
                description
                  "OTU 2e protocol";
              }
              enum "OTU1e" {
                value 10;
                description
                  "OTU 1e protocol";
              }
              enum "ODU2" {
                value 11;
                description
                  "ODU 2 protocol";
              }
              enum "ODU2e" {
                value 12;
                description
                  "ODU 2e protocol";
              }
              enum "40GE" {
                value 13;
                description
                  "40G Ethernet port protocol";
              }
              enum "OC768" {
                value 14;
                description
                  "OC 768 protocol";
              }
              enum "STM256" {
                value 15;
                description
                  "STM 256 protocol";
              }
              enum "OTU3" {
                value 16;
                description
                  "OTU 3 protocol";
              }
              enum "ODU3" {
                value 17;
                description
                  "ODU 3 protocol";
              }
              enum "100GE" {
                value 18;
                description
                  "100G Ethernet protocol";
              }
              enum "100G-MLG" {
                value 19;
                description
                  "100G MLG protocol";
              }
              enum "OTU4" {
                value 20;
                description
                  "OTU4 signal protocol (112G) for transporting 100GE signal";
              }
              enum "OTUCn" {
                value 21;
                description
                  "OTU Cn protocol";
              }
              enum "ODU4" {
                value 22;
                description
                  "ODU 4 protocol";
              }
            }
            description
              "Optical channel assigned to this assigment id";
          }
          leaf logical-channel-type {
            type enumeration {
              enum "Ethernet" {
                value 1;
                description
                  "Ethernet protocol framing";
              }
              enum "Otn" {
                value 2;
                description
                  "OTN protocol framing";
              }
            }
            description
              "Assignment type (logical or optical)";
          }
          leaf otn-tti-msg-transmit {
            type xr:Cisco-ios-xr-string {
              length "1..800" {
                description
                  "tti message transmit";
              }
            }
            description
              "tti message transmit";
          }
          leaf otn-tti-msg-expected {
            type xr:Cisco-ios-xr-string {
              length "1..800" {
                description
                  "tti message expected";
              }
            }
            description
              "tti message expected";
          }
          leaf otn-tti-msg-auto {
            type enumeration {
              enum "0" {
                value 0;
                description
                  "false";
              }
              enum "1" {
                value 1;
                description
                  "true";
              }
            }
            description
              "tti message auto";
          }
          leaf ethernet-client-als {
            type enumeration {
              enum "ethernet" {
                value 1;
                description
                  "ethernet";
              }
              enum "laser-shutdown" {
                value 2;
                description
                  "laser_shutdown";
              }
            }
            description
              "Configure the client-als";
          }
          leaf ethernet-als-delay {
            type uint32 {
              range "10..3000" {
                description
                  "als-delay in ms";
              }
            }
            description
              "Configure the als-delay";
          }
          leaf ingress-client-port {
            type xr:Interface-name {
              pattern "Optics.*";
            }
            description
              "Ingress client port of the logical channel";
          }
          leaf ingress-physical-channel {
            type uint32 {
              range "1..4" {
                description
                  "Physical channel id";
              }
            }
            description
              "Physical channel id for logical channel";
          }
        }
      }
    }
    container optical-channel {
      description
        "Optical Channel";
      container optical-channels {
        description
          "Optical Channel name";
        list optical-channel {
          key "optical-channel-name";
          description
            "Optical Channel name";
          leaf optical-channel-name {
            type xr:Cisco-ios-xr-string {
              length "1..800" {
                description
                  "Optical Channel name";
              }
            }
            description
              "Optical Channel name";
          }
          leaf line-port {
            type xr:Interface-name {
              pattern "Optics.*";
            }
            description
              "Line-Port";
          }
          leaf operational-mode {
            type uint32 {
              range "1..100000" {
                description
                  "Enter operational mode";
              }
            }
            description
              "Operational Mode";
          }
        }
      }
    }
    container transceiver {
      description
        "Transceiver";
      container transceivers {
        description
          "Transceiver name";
        list transceiver {
          key "transceiver-name";
          description
            "Transceiver name";
          leaf transceiver-name {
            type xr:Cisco-ios-xr-string {
              length "1..800" {
                description
                  "Transceiver name";
              }
            }
            description
              "Transceiver name";
          }
          leaf ethernet-fec-mode {
            type enumeration {
              enum "fec-enabled" {
                value 1;
                description
                  "fec_enabled";
              }
            }
            description
              "Configure the fec-mode";
          }
        }
      }
    }
  }
}
