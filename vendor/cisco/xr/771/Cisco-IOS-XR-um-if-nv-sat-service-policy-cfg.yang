module Cisco-IOS-XR-um-if-nv-sat-service-policy-cfg {
  namespace "http://cisco.com/ns/yang/Cisco-IOS-XR-um-if-nv-sat-service-policy-cfg";
  prefix um-if-nv-sat-service-policy-cfg;

  import Cisco-IOS-XR-um-interface-cfg {
    prefix a1;
  }
  import Cisco-IOS-XR-um-nv-satellite-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-nv-sat-service-policy package configuration.
     
     This YANG module augments the
     modules with configuration data.
     
     Copyright (c) 2020 by Cisco Systems, Inc.
     All rights reserved.";

  revision 2020-12-14 {
    description
      "Initial release";
    semver:module-version "1.0.0";
  }

  feature qos_ui_supp_qfab_cfg {
    description
      "qos ui supp qfab cfg";
  }

  feature qos_ui_supp_gre_qos {
    description
      "qos ui supp gre qos";
  }

  feature qos_ui_supp_l2_acct {
    description
      "qos ui supp l2 acct";
  }

  feature qos_ui_supp_spi {
    description
      "qos ui supp spi";
  }

  feature qos_ui_supp_subscriber_parent_policy {
    description
      "qos ui supp subscriber parent policy";
  }

  feature qos_ui_supp_subscriber_group {
    description
      "qos ui supp subscriber group";
  }

  feature qos_ui_supp_sfrag_parent_policy {
    description
      "qos ui supp sfrag parent policy";
  }

  feature qos_ui_supp_ipsec_policy {
    description
      "qos ui supp ipsec policy";
  }

  feature qos_ui_supp_l2transport_cac_acct {
    description
      "qos ui supp l2transport cac acct";
  }

  grouping IF-NV-BODY {
    container service-policy {
      description
        "Configure fabric QoS Service policy";
      container outputs {
        description
          "direction of service policy application";
        list output {
          key "service-policy-name";
          description
            "direction of service policy application";
          leaf service-policy-name {
            type string {
              length "1..800" {
                description
                  "Name of the service policy";
              }
              pattern "[a-zA-Z0-9][a-zA-Z0-9._@$%+#:=<>-]{0,62}";
            }
            description
              "direction of service policy application";
          }
        }
      }
    }
  }

  augment "/a1:interfaces/a1:interface/a2:nv/a2:satellite-fabric-link/a2:satellite" {
    uses IF-NV-BODY;
  }
  augment "/a1:interfaces/a1:interface-preconfigure/a2:nv/a2:satellite-fabric-link/a2:satellite" {
    uses IF-NV-BODY;
  }
}
