module Cisco-IOS-XR-um-router-convergence-cfg {
  namespace "http://cisco.com/ns/yang/Cisco-IOS-XR-um-router-convergence-cfg";
  prefix um-router-convergence-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR router-convergence package configuration.
     
     This YANG module augments the
     modules with configuration data.
     
     Copyright (c) 2020 by Cisco Systems, Inc.
     All rights reserved.";

  revision 2020-12-14 {
    description
      "Initial release";
    semver:module-version "1.0.0";
  }

  container router-convergence {
    presence "Indicates a router-convergence node is configured.";
    description
      "Configure Router Convergence Monitoring";
    container disable {
      presence "Indicates a disable node is configured.";
      description
        "Disable the monitoring of route convergence on the entire router";
    }
    leaf prefix-monitoring-limit {
      type uint32 {
        range "0..100" {
          description
            "Specify the number of events";
        }
      }
      description
        "Limits Individual Prefix Monitoring";
    }
    leaf monitoring-interval {
      type uint32 {
        range "5..120" {
          description
            "Specify the interval (in mins)";
        }
      }
      description
        "Interval in which to collect logs (in mins)";
    }
    leaf max-events-stored {
      type uint32 {
        range "10..500" {
          description
            "Specify the maximum number of events stored";
        }
      }
      description
        "Maximum number of events stored in the server";
    }
    leaf event-buffer-size {
      type uint32 {
        range "100..500" {
          description
            "Specify the number of events";
        }
      }
      description
        "Event buffer size for storing event traces (as number of events)";
    }
    container collect-diagnosticses {
      description
        "Collect diagnostics on specified node";
      list collect-diagnostics {
        key "collect-diagnostics-name";
        description
          "Collect diagnostics on specified node";
        leaf collect-diagnostics-name {
          type xr:Node-id;
          description
            "Collect diagnostics on specified node";
        }
      }
    }
    container protocols {
      description
        "Protocol for which to configure RCMD parameters";
      list protocol {
        key "protocol-id";
        description
          "Protocol for which to configure RCMD parameters";
        leaf protocol-id {
          type enumeration {
            enum "OSPF" {
              value 0;
              description
                "Configure parameters related to OSPF";
            }
            enum "ISIS" {
              value 1;
              description
                "Configure parameters related to ISIS";
            }
          }
          description
            "Protocol for which to configure RCMD parameters";
        }
        container priorities {
          description
            "Priority";
          list priority {
            key "priority-id";
            description
              "Priority";
            leaf priority-id {
              type enumeration {
                enum "Critical" {
                  value 0;
                  description
                    "Critical routes";
                }
                enum "High" {
                  value 1;
                  description
                    "High priority routes";
                }
                enum "Medium" {
                  value 2;
                  description
                    "Medium priority routes";
                }
                enum "Low" {
                  value 3;
                  description
                    "Low priority routes";
                }
              }
              description
                "Priority";
            }
            container disable {
              presence "Indicates a disable node is configured.";
              description
                "Disable the monitoring of route convergence for specified priority";
            }
            leaf threshold {
              type uint32 {
                range "0..4294967295" {
                  description
                    "Specify the threshold value (in msec)";
                }
              }
              description
                "Threshold value for convergence (in msec)";
            }
            leaf leaf-network {
              type uint32 {
                range "10..100" {
                  description
                    "Specify the maximum number of leaf networks monitored";
                }
              }
              description
                "Leaf Network monitoring";
            }
            leaf frr-threshold {
              type uint32 {
                range "1..100" {
                  description
                    "Specify the threshold value (in percentage)";
                }
              }
              description
                "Threshold value for Fast ReRoute Coverage (in percentage)";
            }
          }
        }
      }
    }
    container nodes {
      description
        "Configure parameters for the specified node (Partially qualified location allowed)";
      list node {
        key "node-id";
        description
          "Configure parameters for the specified node (Partially qualified location allowed)";
        leaf node-id {
          type xr:Pq-node-id;
          description
            "Configure parameters for the specified node (Partially qualified location allowed)";
        }
        container disable {
          presence "Indicates a disable node is configured.";
          description
            "Disable the monitoring of route convergence on specified location";
        }
      }
    }
    container storage-location {
      presence "Indicates a storage-location node is configured.";
      description
        "Absolute directory path for saving the archive files. Example /disk0:/rcmd/ or <tftp-location>/rcmd/";
      leaf reports {
        type xr:Cisco-ios-xr-string {
          length "1..800" {
            description
              "Specify the directory path. Example /disk0:/rcmd/ or <tftp-location>/rcmd/";
          }
        }
        description
          "Absolute directory path for storing reports. Example /disk0:/rcmd/ or <tftp-location>/rcmd/";
      }
      leaf reports-size {
        type uint32 {
          range "5..80" {
            description
              "Specify the maximum directory size(in %)";
          }
        }
        description
          "Maximum size of reports dir (5% - 80%) for local storage.";
      }
      leaf diagnostics {
        type xr:Cisco-ios-xr-string {
          length "1..800" {
            description
              "Specify the directory path. Example /disk0:/rcmd/ or <tftp-location>/rcmd/";
          }
        }
        description
          "Absolute directory path for storing diagnostic reports. Example /disk0:/rcmd/ or <tftp-location>/rcmd/";
      }
      leaf diagnostics-size {
        type uint32 {
          range "5..80" {
            description
              "Specify the maximum directory size(in %)";
          }
        }
        description
          "Maximum size of diagnostics dir (5% - 80%) for local storage.";
      }
    }
    container mpls-ldp {
      presence "Indicates a mpls-ldp node is configured.";
      description
        "RCMD related configuration for MPLS-LDP";
      container remote-lfa {
        presence "Indicates a remote-lfa node is configured.";
        description
          "Monitoring configuration for Remote LFA";
        leaf label-coverage-threshold {
          type uint32 {
            range "1..100" {
              description
                "Specify the threshold value (in percentage)";
            }
          }
          description
            "Threshold value for label coverage (in percentage)";
        }
      }
    }
  }
}
