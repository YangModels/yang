module Cisco-IOS-XR-mpls-io-oper {
  namespace "http://cisco.com/ns/yang/Cisco-IOS-XR-mpls-io-oper";
  prefix mpls-io-oper;

  import Cisco-IOS-XR-types {
    prefix xr;
  }
  import cisco-semver {
    prefix semver;
  }
  include Cisco-IOS-XR-mpls-io-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-io package operational data.
     
     This module contains definitions
     for the following management objects:
       mpls-ea: MPLS IO EA operational data
       mpls-ma: MPLS IO MA operational data
     
     Copyright (c) 2013-2019 by Cisco Systems, Inc.
     All rights reserved.";

  revision 2019-04-05 {
    description
      "Establish semantic version baseline.";
    semver:module-version "1.0.1";
  }
  revision 2019-03-21 {
    description
      "IOS XR 7.0.1 revision.";
  }
  revision 2015-11-09 {
    description
      "IOS XR 6.0 revision.";
  }

  container mpls-ea {
    config false;
    description
      "MPLS IO EA operational data";
    container nodes {
      description
        "NODE container class for MPLS IO EA operational
         data";
      list node {
        key "node-name";
        description
          "Per node MPLS IO EA operational data";
        container interfaces {
          description
            "MPLS IO EA Interfaces information ";
          list interface {
            key "interface-name";
            description
              "MPLS IO EA NODE Interface data ";
            leaf interface-name {
              type xr:Interface-name;
              description
                "Interface name";
            }
            uses MPLS-IO-SHOW-INTF-INFO;
          }
        }
        leaf node-name {
          type xr:Node-id;
          description
            "Node ID";
        }
      }
    }
  }
  container mpls-ma {
    config false;
    description
      "MPLS IO MA operational data";
    container nodes {
      description
        "NODE container class for MPLS IO MA operational
         data";
      list node {
        key "node-name";
        description
          "Per node MPLS IO MA operational data";
        container interfaces {
          description
            "MPLS IO MA Interfaces information ";
          list interface {
            key "interface-name";
            description
              "MPLS IO MA NODE Interface data ";
            leaf interface-name {
              type xr:Interface-name;
              description
                "Interface name";
            }
            uses MPLS-IO-SHOW-INTF-INFO;
          }
        }
        leaf node-name {
          type xr:Node-id;
          description
            "Node ID";
        }
      }
    }
  }
}
