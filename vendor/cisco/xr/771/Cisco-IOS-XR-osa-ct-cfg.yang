module Cisco-IOS-XR-osa-ct-cfg {
  namespace "http://cisco.com/ns/yang/Cisco-IOS-XR-osa-ct-cfg";
  prefix osa-ct-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa-ct package configuration.
     
     This module contains definitions
     for the following management objects:
       resrv-cli: Reserve Slot Cli Configuration
     
     Copyright (c) 2013-2022 by Cisco Systems, Inc.
     All rights reserved.";

  revision 2022-02-07 {
    description
      "Updating new PID Skinny BO LC for BH
       2022-01-17
         Adding new Skinny BO LC for BH
       2021-11-12
         Enhancement in CLI for NCS1010";
    semver:module-version "1.1.0";
  }
  revision 2020-05-28 {
    description
      "Initial Revision.";
    semver:module-version "1.0.0";
  }
  revision 2019-04-05 {
    description
      "Establish semantic version baseline.";
  }
  revision 2015-11-09 {
    description
      "IOS XR 6.0 revision.";
  }

  typedef Card {
    type enumeration {
      enum "ncs1k4-1.2t-k9" {
        value 1;
        description
          "C Band Card";
      }
      enum "ncs1k4-1.2t-l-k9" {
        value 2;
        description
          "Licensed Card";
      }
      enum "ncs1k4-1.2tl-k9" {
        value 3;
        description
          "L Band Card";
      }
      enum "ncs1k4-otn-xp" {
        value 4;
        description
          "BO Card";
      }
      enum "ncs1k4-otn-xpl" {
        value 5;
        description
          "BO Licensed Card";
      }
      enum "ncs1k4-2-qdd-c-k9" {
        value 6;
        description
          "BELLATRIX C Band Card";
      }
      enum "ncs1k4-lc-filler" {
        value 7;
        description
          "Filler Card";
      }
      enum "ncs1k-olt-c" {
        value 8;
        description
          "Line Terminal Card";
      }
      enum "ncs1k-olt-r-c" {
        value 9;
        description
          "Line Terminal + Raman Card";
      }
      enum "ncs1k-ila-c" {
        value 10;
        description
          "Line Amplifier Card";
      }
      enum "ncs1k-ila-r-c" {
        value 11;
        description
          "Line Amplifier + Raman Card";
      }
      enum "ncs1k-ila-2r-c" {
        value 12;
        description
          "Line Amplifier + 2Raman Card";
      }
      enum "ncs1k4-qxp-k9" {
        value 13;
        description
          "SKINNY BO Card";
      }
      enum "ncs1k4-qxp-l-k9" {
        value 14;
        description
          "SKINNY BO Licen";
      }
    }
    description
      "Card";
  }

  container resrv-cli {
    description
      "Reserve Slot Cli Configuration";
    list slot-info-cli {
      key "lc-slot";
      description
        "location of LC";
      leaf card-type-cli {
        type Card;
        description
          "CardType config type";
      }
      leaf lc-slot {
        type xr:Cisco-ios-xr-string;
        description
          "LC location";
      }
    }
  }
}
