module Cisco-IOS-XR-um-cont-sonet-pm-cfg {
  namespace "http://cisco.com/ns/yang/Cisco-IOS-XR-um-cont-sonet-pm-cfg";
  prefix um-cont-sonet-pm-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-sonet-pm package configuration.
     
     This YANG module augments the
     modules with configuration data.
     
     Copyright (c) 2020-2022 by Cisco Systems, Inc.
     All rights reserved.";

  revision 2022-06-01 {
    description
      "Adjusted controller augmentation hierarchy";
    semver:module-version "1.0.0";
  }
  revision 2020-06-10 {
    description
      "Initial release";
    semver:module-version "1.0.0";
  }

  grouping CONT-BODY {
    container pm {
      when "../a1:controller-name[starts-with(text(),'SONET')]" {
        tailf:dependency "../a1:controller-name";
      }
      description
        "Configure pm parameters";
      container interval-15-min {
        description
          "Configure pm parameters of 15 minute interval";
        container ocn {
          description
            "configure ocn performance monitoring";
          container threshold {
            description
              "Configure threshold on otn parameters";
            leaf cv-s {
              type uint32 {
                range "0..7967700" {
                  description
                    "CV-S threshold range";
                }
              }
              description
                "set cv-s threshold";
            }
            leaf es-s {
              type uint32 {
                range "0..900" {
                  description
                    "es-s threshold range";
                }
              }
              description
                "set es-s threshold";
            }
            leaf ses-s {
              type uint32 {
                range "0..900" {
                  description
                    "ses-s threshold range";
                }
              }
              description
                "set ses-s threshold";
            }
            leaf sefs-s {
              type uint32 {
                range "0..900" {
                  description
                    "sefs-s threshold range";
                }
              }
              description
                "set sefs-s threshold";
            }
            leaf cv-l-ne {
              type uint32 {
                range "0..8850600" {
                  description
                    "cv-l-ne threshold";
                }
              }
              description
                "set cv-l-ne threshold";
            }
            leaf es-l-ne {
              type uint32 {
                range "0..900" {
                  description
                    "es-l-ne threshold";
                }
              }
              description
                "set es-l-ne threshold";
            }
            leaf ses-l-ne {
              type uint32 {
                range "0..900" {
                  description
                    "ses-l-ne threshold range";
                }
              }
              description
                "set ses-l-ne threshold";
            }
            leaf uas-l-ne {
              type uint32 {
                range "0..900" {
                  description
                    "uas-l-ne threshold range";
                }
              }
              description
                "set uas-l-ne threshold";
            }
            leaf fc-l-ne {
              type uint32 {
                range "0..72" {
                  description
                    "fc-l-ne threshold range";
                }
              }
              description
                "set fc-l-ne threshold";
            }
            leaf cv-l-fe {
              type uint32 {
                range "0..8850600" {
                  description
                    "cv-l-fe threshold";
                }
              }
              description
                "set cv-l-fe threshold";
            }
            leaf es-l-fe {
              type uint32 {
                range "0..900" {
                  description
                    "es-l-fe threshold";
                }
              }
              description
                "set es-l-fe threshold";
            }
            leaf ses-l-fe {
              type uint32 {
                range "0..900" {
                  description
                    "ses-l-fe threshold range";
                }
              }
              description
                "set ses-l-fe threshold";
            }
            leaf uas-l-fe {
              type uint32 {
                range "0..900" {
                  description
                    "uas-l-fe threshold range";
                }
              }
              description
                "set uas-l-fe threshold";
            }
            leaf fc-l-fe {
              type uint32 {
                range "0..72" {
                  description
                    "fc-l-fe threshold range";
                }
              }
              description
                "set fc-l-fe threshold";
            }
          }
          container report {
            description
              "set ocn TCA reporting status";
            container sefs-s {
              description
                "set esr-sm TCA reporting status";
              container enable {
                presence "Indicates a enable node is configured.";
                description
                  "Enable TCA reporting";
              }
            }
            container cv-s {
              description
                "set es-pm TCA reporting status";
              container enable {
                presence "Indicates a enable node is configured.";
                description
                  "Enable TCA reporting";
              }
            }
            container es-s {
              description
                "set es-sm TCA reporting status";
              container enable {
                presence "Indicates a enable node is configured.";
                description
                  "Enable TCA reporting";
              }
            }
            container ses-s {
              description
                "set esr-pm TCA reporting status";
              container enable {
                presence "Indicates a enable node is configured.";
                description
                  "Enable TCA reporting";
              }
            }
            container cv-l-ne {
              description
                "set ses-pm TCA reporting status";
              container enable {
                presence "Indicates a enable node is configured.";
                description
                  "Enable TCA reporting";
              }
            }
            container es-l-ne {
              description
                "set ses-sm TCA reporting status";
              container enable {
                presence "Indicates a enable node is configured.";
                description
                  "Enable TCA reporting";
              }
            }
            container ses-l-ne {
              description
                "set sesr-pm TCA reporting status";
              container enable {
                presence "Indicates a enable node is configured.";
                description
                  "Enable TCA reporting";
              }
            }
            container uas-l-ne {
              description
                "set sesr-sm TCA reporting status";
              container enable {
                presence "Indicates a enable node is configured.";
                description
                  "Enable TCA reporting";
              }
            }
            container fc-l-ne {
              description
                "set uas-pm TCA reporting status";
              container enable {
                presence "Indicates a enable node is configured.";
                description
                  "Enable TCA reporting";
              }
            }
            container fc-l-fe {
              description
                "set uas-pm TCA reporting status";
              container enable {
                presence "Indicates a enable node is configured.";
                description
                  "Enable TCA reporting";
              }
            }
            container cv-l-fe {
              description
                "set ses-pm TCA reporting status";
              container enable {
                presence "Indicates a enable node is configured.";
                description
                  "Enable TCA reporting";
              }
            }
            container es-l-fe {
              description
                "set ses-sm TCA reporting status";
              container enable {
                presence "Indicates a enable node is configured.";
                description
                  "Enable TCA reporting";
              }
            }
            container ses-l-fe {
              description
                "set sesr-pm TCA reporting status";
              container enable {
                presence "Indicates a enable node is configured.";
                description
                  "Enable TCA reporting";
              }
            }
            container uas-l-fe {
              description
                "set sesr-sm TCA reporting status";
              container enable {
                presence "Indicates a enable node is configured.";
                description
                  "Enable TCA reporting";
              }
            }
          }
        }
        container sts {
          description
            "configure STS performance monitoring";
          container threshold {
            description
              "Configure threshold on sts parameters";
            container cv-p {
              description
                "set cv-p threshold";
              list sts {
                key "channel-number";
                leaf channel-number {
                  type uint32 {
                    range "1..48" {
                      description
                        " Channel Number";
                    }
                  }
                  description
                    "configure STS performance monitoring";
                }
                leaf threshold {
                  type uint32 {
                    range "0..7967700" {
                      description
                        "CV-P threshold range";
                    }
                  }
                  mandatory true;
                  description
                    "set cv-p threshold";
                }
              }
            }
            container es-p {
              description
                "set es-p threshold";
              list sts {
                key "channel-number";
                leaf channel-number {
                  type uint32 {
                    range "1..48" {
                      description
                        " Channel Number";
                    }
                  }
                  description
                    "configure STS performance monitoring";
                }
                leaf threshold {
                  type uint32 {
                    range "0..900" {
                      description
                        "es-p threshold range";
                    }
                  }
                  mandatory true;
                  description
                    "set es-p threshold";
                }
              }
            }
            container ses-p {
              description
                "set ses-p threshold";
              list sts {
                key "channel-number";
                leaf channel-number {
                  type uint32 {
                    range "1..48" {
                      description
                        " Channel Number";
                    }
                  }
                  description
                    "configure STS performance monitoring";
                }
                leaf threshold {
                  type uint32 {
                    range "0..900" {
                      description
                        "ses-p threshold range";
                    }
                  }
                  mandatory true;
                  description
                    "set ses-p threshold";
                }
              }
            }
            container uas-p {
              description
                "set uas-p threshold";
              list sts {
                key "channel-number";
                leaf channel-number {
                  type uint32 {
                    range "1..48" {
                      description
                        " Channel Number";
                    }
                  }
                  description
                    "configure STS performance monitoring";
                }
                leaf threshold {
                  type uint32 {
                    range "0..900" {
                      description
                        "uas-p threshold range";
                    }
                  }
                  mandatory true;
                  description
                    "set uas-p threshold";
                }
              }
            }
          }
          container reports {
            description
              "set sts TCA reporting status";
            list report {
              must "enable";
              key "channel-number reporting-status";
              description
                "set sts TCA reporting status";
              leaf channel-number {
                type uint32 {
                  range "1..48" {
                    description
                      " Channel Number";
                  }
                }
                description
                  "configure STS performance monitoring";
              }
              leaf reporting-status {
                type enumeration {
                  enum "cv-p" {
                    value 4194304;
                    description
                      "set cv TCA reporting status";
                  }
                  enum "es-p" {
                    value 4194305;
                    description
                      "set es TCA reporting status";
                  }
                  enum "ses-p" {
                    value 4194306;
                    description
                      "set ses TCA reporting status";
                  }
                  enum "uas-p" {
                    value 4194307;
                    description
                      "set uas TCA reporting status";
                  }
                }
                description
                  "set sts TCA reporting status";
              }
              container enable {
                presence "Indicates a enable node is configured.";
                description
                  "Enable the reporting status";
              }
            }
          }
        }
        container path {
          description
            "configure path performance monitoring";
          container threshold {
            description
              "Configure threshold on sonet path parameters";
            leaf cv-p {
              type uint32 {
                range "0..7967700" {
                  description
                    "CV-P threshold range";
                }
              }
              description
                "set cv-p threshold";
            }
            leaf es-p {
              type uint32 {
                range "0..900" {
                  description
                    "es-p threshold range";
                }
              }
              description
                "set es-p threshold";
            }
            leaf ses-p {
              type uint32 {
                range "0..900" {
                  description
                    "ses-p threshold range";
                }
              }
              description
                "set ses-p threshold";
            }
            leaf uas-p {
              type uint32 {
                range "0..900" {
                  description
                    "uas-p threshold range";
                }
              }
              description
                "set uas-p threshold";
            }
          }
          container report {
            description
              "set sonet path TCA reporting status";
            container cv-p {
              description
                "set cv TCA reporting status";
              container enable {
                presence "Indicates a enable node is configured.";
                description
                  "Enable TCA reporting";
              }
            }
            container es-p {
              description
                "set es TCA reporting status";
              container enable {
                presence "Indicates a enable node is configured.";
                description
                  "Enable TCA reporting";
              }
            }
            container ses-p {
              description
                "set ses TCA reporting status";
              container enable {
                presence "Indicates a enable node is configured.";
                description
                  "Enable TCA reporting";
              }
            }
            container uas-p {
              description
                "set uas TCA reporting status";
              container enable {
                presence "Indicates a enable node is configured.";
                description
                  "Enable TCA reporting";
              }
            }
          }
        }
      }
      container interval-24-hour {
        description
          "Configure pm parameters of 24 hour interval";
        container ocn {
          description
            "configure ocn performance monitoring";
          container threshold {
            description
              "Configure threshold on otn parameters";
            leaf cv-s {
              type uint32 {
                range "0..764899200" {
                  description
                    "CV-S threshold range";
                }
              }
              description
                "set cv-s threshold";
            }
            leaf es-s {
              type uint32 {
                range "0..86400" {
                  description
                    "es-s threshold range";
                }
              }
              description
                "set es-s threshold";
            }
            leaf ses-s {
              type uint32 {
                range "0..86400" {
                  description
                    "ses-s threshold range";
                }
              }
              description
                "set ses-s threshold";
            }
            leaf sefs-s {
              type uint32 {
                range "0..86400" {
                  description
                    "sefs-s threshold range";
                }
              }
              description
                "set sefs-s threshold";
            }
            leaf cv-l-ne {
              type uint32 {
                range "0..849657600" {
                  description
                    "cv-l-ne threshold";
                }
              }
              description
                "set cv-l-ne threshold";
            }
            leaf es-l-ne {
              type uint32 {
                range "0..86400" {
                  description
                    "es-l-ne threshold";
                }
              }
              description
                "set es-l-ne threshold";
            }
            leaf ses-l-ne {
              type uint32 {
                range "0..86400" {
                  description
                    "ses-l-ne threshold range";
                }
              }
              description
                "set ses-l-ne threshold";
            }
            leaf uas-l-ne {
              type uint32 {
                range "0..86400" {
                  description
                    "uas-l-ne threshold range";
                }
              }
              description
                "set uas-l-ne threshold";
            }
            leaf fc-l-ne {
              type uint32 {
                range "0..6912" {
                  description
                    "fc-l-ne threshold range";
                }
              }
              description
                "set fc-l-ne threshold";
            }
            leaf cv-l-fe {
              type uint32 {
                range "0..849657600" {
                  description
                    "cv-l-fe threshold";
                }
              }
              description
                "set cv-l-fe threshold";
            }
            leaf es-l-fe {
              type uint32 {
                range "0..86400" {
                  description
                    "es-l-fe threshold";
                }
              }
              description
                "set es-l-fe threshold";
            }
            leaf ses-l-fe {
              type uint32 {
                range "0..86400" {
                  description
                    "ses-l-fe threshold range";
                }
              }
              description
                "set ses-l-fe threshold";
            }
            leaf uas-l-fe {
              type uint32 {
                range "0..86400" {
                  description
                    "uas-l-fe threshold range";
                }
              }
              description
                "set uas-l-fe threshold";
            }
            leaf fc-l-fe {
              type uint32 {
                range "0..6912" {
                  description
                    "fc-l-fe threshold range";
                }
              }
              description
                "set fc-l-fe threshold";
            }
          }
          container report {
            description
              "set ocn TCA reporting status";
            container sefs-s {
              description
                "set esr-sm TCA reporting status";
              container enable {
                presence "Indicates a enable node is configured.";
                description
                  "Enable TCA reporting";
              }
            }
            container cv-s {
              description
                "set es-pm TCA reporting status";
              container enable {
                presence "Indicates a enable node is configured.";
                description
                  "Enable TCA reporting";
              }
            }
            container es-s {
              description
                "set es-sm TCA reporting status";
              container enable {
                presence "Indicates a enable node is configured.";
                description
                  "Enable TCA reporting";
              }
            }
            container ses-s {
              description
                "set esr-pm TCA reporting status";
              container enable {
                presence "Indicates a enable node is configured.";
                description
                  "Enable TCA reporting";
              }
            }
            container cv-l-ne {
              description
                "set ses-pm TCA reporting status";
              container enable {
                presence "Indicates a enable node is configured.";
                description
                  "Enable TCA reporting";
              }
            }
            container es-l-ne {
              description
                "set ses-sm TCA reporting status";
              container enable {
                presence "Indicates a enable node is configured.";
                description
                  "Enable TCA reporting";
              }
            }
            container ses-l-ne {
              description
                "set sesr-pm TCA reporting status";
              container enable {
                presence "Indicates a enable node is configured.";
                description
                  "Enable TCA reporting";
              }
            }
            container uas-l-ne {
              description
                "set sesr-sm TCA reporting status";
              container enable {
                presence "Indicates a enable node is configured.";
                description
                  "Enable TCA reporting";
              }
            }
            container fc-l-ne {
              description
                "set uas-pm TCA reporting status";
              container enable {
                presence "Indicates a enable node is configured.";
                description
                  "Enable TCA reporting";
              }
            }
            container fc-l-fe {
              description
                "set uas-pm TCA reporting status";
              container enable {
                presence "Indicates a enable node is configured.";
                description
                  "Enable TCA reporting";
              }
            }
            container cv-l-fe {
              description
                "set ses-pm TCA reporting status";
              container enable {
                presence "Indicates a enable node is configured.";
                description
                  "Enable TCA reporting";
              }
            }
            container es-l-fe {
              description
                "set ses-sm TCA reporting status";
              container enable {
                presence "Indicates a enable node is configured.";
                description
                  "Enable TCA reporting";
              }
            }
            container ses-l-fe {
              description
                "set sesr-pm TCA reporting status";
              container enable {
                presence "Indicates a enable node is configured.";
                description
                  "Enable TCA reporting";
              }
            }
            container uas-l-fe {
              description
                "set sesr-sm TCA reporting status";
              container enable {
                presence "Indicates a enable node is configured.";
                description
                  "Enable TCA reporting";
              }
            }
          }
        }
        container sts {
          description
            "configure STS performance monitoring";
          container threshold {
            description
              "Configure threshold on sts parameters";
            container cv-p {
              description
                "set cv-p threshold";
              list sts {
                key "channel-number";
                leaf channel-number {
                  type uint32 {
                    range "1..48" {
                      description
                        " Channel Number";
                    }
                  }
                  description
                    "configure STS performance monitoring";
                }
                leaf threshold {
                  type uint32 {
                    range "0..7967700" {
                      description
                        "CV-P threshold range";
                    }
                  }
                  mandatory true;
                  description
                    "set cv-p threshold";
                }
              }
            }
            container es-p {
              description
                "set es-p threshold";
              list sts {
                key "channel-number";
                leaf channel-number {
                  type uint32 {
                    range "1..48" {
                      description
                        " Channel Number";
                    }
                  }
                  description
                    "configure STS performance monitoring";
                }
                leaf threshold {
                  type uint32 {
                    range "0..900" {
                      description
                        "es-p threshold range";
                    }
                  }
                  mandatory true;
                  description
                    "set es-p threshold";
                }
              }
            }
            container ses-p {
              description
                "set ses-p threshold";
              list sts {
                key "channel-number";
                leaf channel-number {
                  type uint32 {
                    range "1..48" {
                      description
                        " Channel Number";
                    }
                  }
                  description
                    "configure STS performance monitoring";
                }
                leaf threshold {
                  type uint32 {
                    range "0..900" {
                      description
                        "ses-p threshold range";
                    }
                  }
                  mandatory true;
                  description
                    "set ses-p threshold";
                }
              }
            }
            container uas-p {
              description
                "set uas-p threshold";
              list sts {
                key "channel-number";
                leaf channel-number {
                  type uint32 {
                    range "1..48" {
                      description
                        " Channel Number";
                    }
                  }
                  description
                    "configure STS performance monitoring";
                }
                leaf threshold {
                  type uint32 {
                    range "0..900" {
                      description
                        "uas-p threshold range";
                    }
                  }
                  mandatory true;
                  description
                    "set uas-p threshold";
                }
              }
            }
          }
          container reports {
            description
              "set sts TCA reporting status";
            list report {
              must "enable";
              key "channel-number reporting-status";
              description
                "set sts TCA reporting status";
              leaf channel-number {
                type uint32 {
                  range "1..48" {
                    description
                      " Channel Number";
                  }
                }
                description
                  "configure STS performance monitoring";
              }
              leaf reporting-status {
                type enumeration {
                  enum "cv-p" {
                    value 4194304;
                    description
                      "set cv TCA reporting status";
                  }
                  enum "es-p" {
                    value 4194305;
                    description
                      "set es TCA reporting status";
                  }
                  enum "ses-p" {
                    value 4194306;
                    description
                      "set ses TCA reporting status";
                  }
                  enum "uas-p" {
                    value 4194307;
                    description
                      "set uas TCA reporting status";
                  }
                }
                description
                  "set sts TCA reporting status";
              }
              container enable {
                presence "Indicates a enable node is configured.";
                description
                  "Enable the reporting status";
              }
            }
          }
        }
        container path {
          description
            "configure path performance monitoring";
          container threshold {
            description
              "Configure threshold on sonet path parameters";
            leaf cv-p {
              type uint32 {
                range "0..764899200" {
                  description
                    "CV-P threshold range";
                }
              }
              description
                "set cv-p threshold";
            }
            leaf es-p {
              type uint32 {
                range "0..86400" {
                  description
                    "es-p threshold range";
                }
              }
              description
                "set es-p threshold";
            }
            leaf ses-p {
              type uint32 {
                range "0..86400" {
                  description
                    "ses-p threshold range";
                }
              }
              description
                "set ses-p threshold";
            }
            leaf uas-p {
              type uint32 {
                range "0..86400" {
                  description
                    "uas-p threshold range";
                }
              }
              description
                "set uas-p threshold";
            }
          }
          container report {
            description
              "set sonetpath TCA reporting status";
            container cv-p {
              description
                "set cv TCA reporting status";
              container enable {
                presence "Indicates a enable node is configured.";
                description
                  "Enable TCA reporting";
              }
            }
            container es-p {
              description
                "set es TCA reporting status";
              container enable {
                presence "Indicates a enable node is configured.";
                description
                  "Enable TCA reporting";
              }
            }
            container ses-p {
              description
                "set ses TCA reporting status";
              container enable {
                presence "Indicates a enable node is configured.";
                description
                  "Enable TCA reporting";
              }
            }
            container uas-p {
              description
                "set uas TCA reporting status";
              container enable {
                presence "Indicates a enable node is configured.";
                description
                  "Enable TCA reporting";
              }
            }
          }
        }
      }
    }
  }

  augment "/a1:controllers/a1:controller" {
    uses CONT-BODY;
  }
  augment "/a1:controllers/a1:controller-preconfigure" {
    uses CONT-BODY;
  }
}
