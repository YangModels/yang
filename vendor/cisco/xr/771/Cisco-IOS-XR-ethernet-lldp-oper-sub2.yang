submodule Cisco-IOS-XR-ethernet-lldp-oper-sub2 {
  belongs-to Cisco-IOS-XR-ethernet-lldp-oper {
    prefix Cisco-IOS-XR-ethernet-lldp-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ethernet-lldp package operational data.
     
     Copyright (c) 2013-2022 by Cisco Systems, Inc.
     All rights reserved.";

  revision 2022-04-01 {
    description
      "Added last clear time and transmit failure fields
       2022-03-01
         Added interface stats fields";
    semver:module-version "1.2.0";
  }
  revision 2020-09-01 {
    description
      "Fixing backward compatibility error in module.";
    semver:module-version "1.1.0";
  }
  revision 2019-04-05 {
    description
      "Establish semantic version baseline.";
    semver:module-version "1.0.1";
  }
  revision 2017-11-13 {
    description
      "Added a new notification.";
  }
  revision 2015-11-09 {
    description
      "IOS XR 6.0 revision.";
  }

  grouping LLDP-MGR-GLOBAL-INFO {
    description
      "LLDP global info";
    leaf chassis-id {
      type string;
      description
        "Chassis identifier";
      xr:event-telemetry "Subscribe Telemetry Event";
    }
    leaf chassis-id-sub-type {
      type uint8;
      description
        "Chassis ID sub type";
      xr:event-telemetry "Subscribe Telemetry Event";
    }
    leaf system-name {
      type string;
      description
        "System Name";
      xr:event-telemetry "Subscribe Telemetry Event";
    }
    leaf timer {
      type uint32;
      description
        "Rate at which LLDP packets re sent (in sec)";
      xr:event-telemetry "Subscribe Telemetry Event";
    }
    leaf hold-time {
      type uint32;
      description
        "Length  of time  (in sec)that receiver must keep
         thispacket";
      xr:event-telemetry "Subscribe Telemetry Event";
    }
    leaf re-init {
      type uint32;
      description
        "Delay (in sec) for LLDPinitialization on
         anyinterface";
      xr:event-telemetry "Subscribe Telemetry Event";
    }
  }
}
