submodule Cisco-IOS-XR-spirit-install-instmgr-oper-sub1 {

  belongs-to Cisco-IOS-XR-spirit-install-instmgr-oper {
    prefix Cisco-IOS-XR-spirit-install-instmgr-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR spirit-install-instmgr package operational data.

     Copyright (c) 2013-2016 by Cisco Systems, Inc.
     All rights reserved.";

  revision "2015-11-09" {
    description
      "IOS XR 6.0 revision.";
  }


  grouping INSTMGR-CALV-SHOW-INST-COMMIT-ROW {
    description "calvados show install committed";
    leaf error-message {
      type string;
      description "ErrorMessage";
    }
    leaf location {
      type string;
      description "Location";
    }
    leaf node-type {
      type string;
      description "NodeType";
    }
    leaf boot-partition-name {
      type string;
      description "BootPartitionName";
    }
    leaf number-of-committed-packages {
      type uint32;
      description "NumberOfCommittedPackages";
    }
    leaf committed-packages {
      type string;
      description "CommittedPackages";
    }
  }

  grouping INSTMGR-CALV-SHOW-INST-COMMIT {
    description "Calvados show install commit info";

    list committed-package-info {
      description "committed package info";
      uses INSTMGR-CALV-SHOW-INST-COMMIT-ROW;
    }
  }

  grouping INSTMGR-CALV-SHOW-INST-ACT-ROW {
    description "calvados show install active";
    leaf error-message {
      type string;
      description "ErrorMessage";
    }
    leaf location {
      type string;
      description "Location";
    }
    leaf node-type {
      type string;
      description "NodeType";
    }
    leaf boot-partition-name {
      type string;
      description "BootPartitionName";
    }
    leaf number-of-active-packages {
      type uint32;
      description "NumberOfActivePackages";
    }
    leaf active-packages {
      type string;
      description "ActivePackages";
    }
  }

  grouping INSTMGR-CALV-SHOW-INST-ACT {
    description "Calvados show install active info";

    list active-package-info {
      description "active package info";
      uses INSTMGR-CALV-SHOW-INST-ACT-ROW;
    }
  }

  grouping INST-STRING-PTR {
    description "inst string ptr";
    leaf package {
      type string;
      description "package";
    }
  }

  grouping INSTMGR-SHOW-INSTALL-PREPARE {
    description "show install prepare";
    leaf no-prepare-done {
      type string;
      description "NoPrepareDone";
    }
    leaf prepared-boot-image {
      type string;
      description "PreparedBootImage";
    }
    leaf prepared-boot-partition {
      type string;
      description "PreparedBootPartition";
    }
    leaf restart-type {
      type string;
      description "RestartType";
    }
    leaf activate-message {
      type string;
      description "ActivateMessage";
    }
    leaf prepare-clean-message {
      type string;
      description "PrepareCleanMessage";
    }

    list rpm {
      description "rpm";
      uses INST-STRING-PTR;
    }

    list package {
      description "package";
      uses INST-STRING-PTR;
    }
  }

  grouping INSTALL-LOG {
    description "Install Log";
    leaf log {
      type string;
      description "log";
    }
  }
}
