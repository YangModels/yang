submodule Cisco-IOS-XR-snmp-entitymib-oper-sub1 {

  belongs-to Cisco-IOS-XR-snmp-entitymib-oper {
    prefix Cisco-IOS-XR-snmp-entitymib-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-entitymib package operational data.

     Copyright (c) 2013-2016 by Cisco Systems, Inc.
     All rights reserved.";

  revision "2015-11-09" {
    description
      "IOS XR 6.0 revision.";
  }


  grouping ENTMIB-NODE2PATH-INFO {
    description "ENTITY-MIB Node To Path Map Record";
    leaf physical-index {
      type uint32;
      description "entPhysicalIndex";
    }
    leaf ent-physical-name {
      type string;
      description "entPhysicalName";
    }
    leaf location {
      type string;
      description "invmgr EDM path";
    }
    leaf ent-physical-descr {
      type string;
      description "EntPhysicalDescription";
    }
    leaf ent-physical-firmware-rev {
      type string;
      description "entphysicalFirmwareRev";
    }
    leaf ent-physical-hardware-rev {
      type string;
      description "entphysicalHardwareRev";
    }
    leaf ent-physical-modelname {
      type string;
      description "entphysicalModelName";
    }
    leaf ent-physical-serial-num {
      type string;
      description "entphysicalSerialNum";
    }
    leaf ent-physical-software-rev {
      type string;
      description "entphysicalSoftwareRev";
    }
    leaf ent-physical-mfg-name {
      type string;
      description "entphysicalMfgName";
    }
  }
}
