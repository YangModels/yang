submodule Cisco-IOS-XR-fretta-bcm-dpa-npu-stats-oper-sub1 {

  belongs-to Cisco-IOS-XR-fretta-bcm-dpa-npu-stats-oper {
    prefix Cisco-IOS-XR-fretta-bcm-dpa-npu-stats-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-bcm-dpa-npu-stats package operational data.

     Copyright (c) 2013-2016 by Cisco Systems, Inc.
     All rights reserved.";

  revision "2015-11-09" {
    description
      "IOS XR 6.0 revision.";
  }


  grouping DPA-VOQ-INGRESS-PACKET-STATISTICS {
    description "DPA VOQ INGRESS PACKET STATISTICS";
    leaf gport-received-bytes {
      type uint64;
      description "GportReceivedBytes";
    }
    leaf gport-received-pkts {
      type uint64;
      description "GportReceivedPkts";
    }
    leaf gport-dropped-bytes {
      type uint64;
      description "GportDroppedBytes";
    }
    leaf gport-dropped-pkts {
      type uint64;
      description "GportDroppedPkts";
    }
  }

  grouping DPA-VOQ-INTF-PORT {
    description "DPA VOQ INTF PORT";
    leaf is-inuse {
      type boolean;
      description "is inuse";
    }
    leaf rack-num {
      type uint8;
      description "rack num";
    }
    leaf slot-num {
      type uint8;
      description "slot num";
    }
    leaf npu-num {
      type uint8;
      description "npu num";
    }
    leaf npu-core {
      type uint8;
      description "npu core";
    }
    leaf port-num {
      type uint8;
      description "port num";
    }
    leaf ifhandle {
      type uint32;
      description "ifhandle";
    }
    leaf sysport {
      type uint32;
      description "sysport";
    }
    leaf pp-port {
      type uint32;
      description "pp port";
    }
    leaf port-speed {
      type uint32;
      description "port speed";
    }
    leaf voq-base {
      type uint32;
      description "voq base";
    }
    leaf connector-id {
      type uint32;
      description "connector id";
    }
    leaf is-local-port {
      type boolean;
      description "is local port";
    }

    list voq-stat {
      max-elements "8";
      description "voq stat";
      uses DPA-VOQ-INGRESS-PACKET-STATISTICS;
    }
  }

  grouping DPA-TRAP-STATS {
    description "DPA TRAP STATS";
    leaf trap-strength {
      type uint32;
      description "trap strength";
    }
    leaf priority {
      type uint32;
      description "priority";
    }
    leaf trap-id {
      type uint32;
      description "trap id";
    }
    leaf gport {
      type uint32;
      description "gport";
    }
    leaf fec-id {
      type uint32;
      description "fec id";
    }
    leaf policer-id {
      type uint32;
      description "policer id";
    }
    leaf stats-id {
      type uint32;
      description "stats id";
    }
    leaf encap-id {
      type uint32;
      description "encap id";
    }
    leaf mc-group {
      type uint32;
      description "mc group";
    }
    leaf trap-string {
      type string;
      description "trap string";
    }
    leaf id {
      type uint32;
      description "id";
    }
    leaf offset {
      type uint64;
      description "offset";
    }
    leaf npu-id {
      type uint64;
      description "npu id";
    }
    leaf packet-dropped {
      type uint64;
      description "packet dropped";
    }
    leaf packet-accepted {
      type uint64;
      description "packet accepted";
    }
  }

  grouping CLEAR-STATS {
    description "CLEAR STATS";
    leaf clear-status {
      type uint8;
      description "clear status";
    }
  }
}
