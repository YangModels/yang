submodule Cisco-IOS-XR-asr9k-sc-invmgr-oper-sub1 {

  belongs-to Cisco-IOS-XR-asr9k-sc-invmgr-oper {
    prefix Cisco-IOS-XR-asr9k-sc-invmgr-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-sc-invmgr package operational data.

     Copyright (c) 2013-2016 by Cisco Systems, Inc.
     All rights reserved.";

  revision "2017-01-04" {
    description
      "IOS-XR 6.2.1 revision.";
  }

  revision "2015-11-09" {
    description
      "IOS XR 6.0 revision.";
  }

  typedef Card-reset-reason {
    type enumeration {
      enum reset-unknown {
        value 1;
        description "reset unknown";
      }
      enum power-up {
        value 2;
        description "power up";
      }
      enum parity-error {
        value 3;
        description "parity error";
      }
      enum clear-config-reset {
        value 4;
        description "clear config reset";
      }
      enum manual-reset {
        value 5;
        description "manual reset";
      }
      enum watch-dog-timeout-reset {
        value 6;
        description "watch dog timeout reset";
      }
      enum resource-overflow-reset {
        value 7;
        description "resource overflow reset";
      }
      enum missing-task-reset {
        value 8;
        description "missing task reset";
      }
      enum low-voltage-reset {
        value 9;
        description "low voltage reset";
      }
      enum controller-reset {
        value 10;
        description "controller reset";
      }
      enum system-reset {
        value 11;
        description "system reset";
      }
      enum switchover-reset {
        value 12;
        description "switchover reset";
      }
      enum upgrade-reset {
        value 13;
        description "upgrade reset";
      }
      enum downgrade-reset {
        value 14;
        description "downgrade reset";
      }
      enum cache-error-reset {
        value 15;
        description "cache error reset";
      }
      enum device-driver-reset {
        value 16;
        description "device driver reset";
      }
      enum software-exception-reset {
        value 17;
        description "software exception reset";
      }
      enum restore-config-reset {
        value 18;
        description "restore config reset";
      }
      enum abort-rev-reset {
        value 19;
        description "abort rev reset";
      }
      enum burn-boot-reset {
        value 20;
        description "burn boot reset";
      }
      enum standby-cd-healthier-reset {
        value 21;
        description "standby cd healthier reset";
      }
      enum non-native-config-clear-reset {
        value 22;
        description "non native config clear reset";
      }
      enum memory-protection-error-reset {
        value 23;
        description "memory protection error reset";
      }
      enum card-reset-reason-max {
        value 24;
        description "card reset reason max";
      }
    }
    description "Card reset reason";
  }

  grouping INV-TIMESPEC {
    description "Inventory FRU Info Time Spec";
    leaf time-in-seconds {
      type int32;
      units "second";
      description "Time Value in Seconds";
    }
    leaf time-in-nano-seconds {
      type int32;
      units "nanosecond";
      description "Time Value in Nano-seconds";
    }
  }

  grouping INV-CARD-FRU-INFO {
    description "card (FRU) operation state bag";

    container last-operational-state-change {
      description "last card oper change state";
      uses INV-TIMESPEC;
    }

    container card-up-time {
      description "card up time";
      uses INV-TIMESPEC;
    }
    leaf card-administrative-state {
      type int32;
      description "card admin state: shutdown or not";
    }
    leaf power-administrative-state {
      type int32;
      description "power admin state: up or down";
    }
    leaf card-operational-state {
      type int32;
      description "card operation state";
    }
    leaf card-monitor-state {
      type int32;
      description
        "card is monitored by a manager or left
        unmonitored";
    }
    leaf card-reset-reason {
      type Card-reset-reason;
      description "card reset reason enum";
    }
    leaf power-current-measurement {
      type int32;
      description "power current: not implemented";
    }
    leaf power-operational-state {
      type int32;
      description "Power operation state";
    }
  }

  grouping INV-PHY-ENTITY-BASIC-INFO {
    description
      "Bag contains all the basic inventory information
      for each entity";
    leaf description {
      type string {
        length "0..255";
      }
      description
        "describes in user-readable terms       what the
        entity in question does";
    }
    leaf vendor-type {
      type string {
        length "0..255";
      }
      description "maps to the vendor OID string";
    }
    leaf name {
      type string {
        length "0..255";
      }
      description "name string for the entity";
    }
    leaf hardware-revision {
      type string {
        length "0..255";
      }
      description "hw revision string";
    }
    leaf firmware-revision {
      type string {
        length "0..255";
      }
      description "firmware revision string";
    }
    leaf software-revision {
      type string {
        length "0..255";
      }
      description "software revision string";
    }
    leaf chip-hardware-revision {
      type string {
        length "0..255";
      }
      description "chip module hw revision string";
    }
    leaf serial-number {
      type string {
        length "0..255";
      }
      description "serial number";
    }
    leaf manufacturer-name {
      type string {
        length "0..255";
      }
      description "manufacturer's name";
    }
    leaf model-name {
      type string {
        length "0..255";
      }
      description "model name";
    }
    leaf asset-id-str {
      type string {
        length "0..255";
      }
      description "asset Identification string";
    }
    leaf asset-identification {
      type int32;
      description "asset Identification";
    }
    leaf is-field-replaceable-unit {
      type boolean;
      description "1 if Field Replaceable Unit 0, if not";
    }
    leaf manufacturer-asset-tags {
      type int32;
      description "Manufacture Asset Tags";
    }
    leaf composite-class-code {
      type int32;
      description "Major&minor class of the entity";
    }
    leaf memory-size {
      type int32;
      description
        "Size of memory associated with       the entity
        where applicable";
    }
    leaf environmental-monitor-path {
      type string {
        length "0..255";
      }
      description "sysdb name of sensor in the envmon EDM";
    }
    leaf alias {
      type string {
        length "0..255";
      }
      description "useful for storing an entity alias ";
    }
    leaf group-flag {
      type boolean;
      description "indicates if this entity is group       or not";
    }
    leaf new-deviation-number {
      type int32;
      description "integer value for New Deviation Number 0x88";
    }
    leaf physical-layer-interface-module-type {
      type int32;
      description
        "integer value for plim type if     applicable to
        this entity";
    }
    leaf unrecognized-fru {
      type boolean;
      description "1 if UnrecognizedFRU and 0 for recognizedFRU";
    }
    leaf redundancystate {
      type int32;
      description
        "integer value for Redundancy State if    
        applicable to this entity";
    }
    leaf ceport {
      type boolean;
      description "1 if ce port found, 0 if not";
    }
    leaf xr-scoped {
      type boolean;
      description "1 if xr scoped, 0 if not";
    }
    leaf unique-id {
      type int32;
      description "Unique id for an entity";
    }
  }
}
