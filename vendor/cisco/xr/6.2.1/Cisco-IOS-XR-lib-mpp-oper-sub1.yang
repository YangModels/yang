submodule Cisco-IOS-XR-lib-mpp-oper-sub1 {

  belongs-to Cisco-IOS-XR-lib-mpp-oper {
    prefix Cisco-IOS-XR-lib-mpp-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lib-mpp package operational data.

     Copyright (c) 2013-2016 by Cisco Systems, Inc.
     All rights reserved.";

  revision "2015-01-07" {
    description
      "IOS XR 5.3.1 revision.";
  }

  typedef Mpp-in6-addr {
    type inet:ipv6-address;
    description "Mpp in6 addr";
  }
  typedef Mpp-in-addr {
    type inet:ipv4-address;
    description "Mpp in addr";
  }
  identity Mpp-af-id-base {
    description "Base identity for Mpp-af-id";
  }
  identity ipv4 {
    base Mpp-af-id-base;
    description "IPv4 address family";
  }
  identity ipv6 {
    base Mpp-af-id-base;
    description "IPv6 address family";
  }
  typedef Mpp-af-id {
    type identityref {
      base Mpp-af-id-base;
    }
    description "MPP address family types";
  }
  typedef Mpp-allow {
    type enumeration {
      enum ssh {
        description "SSH protocol";
      }
      enum telnet {
        description "TELNET protocol";
      }
      enum snmp {
        description "SNMP protocol";
      }
      enum tftp {
        description "TFTP protocol";
      }
      enum http {
        description "HTTP protocol";
      }
      enum xr-xml {
        description "XML";
      }
      enum netconf {
        description "NETCONF protocol";
      }
      enum all {
        description "All";
      }
    }
    description "MPP protocol types";
  }

  grouping IP-ADDR-T-UNION {
    description "IP ADDR T UNION";
    leaf af-name {
      type Mpp-af-id;
      description "AFName";
    }
    leaf ipv4-address {
      when "../af-name = 'ipv4'" {
        description "../AFName = 'IPv4'";
      }
      type Mpp-in-addr;
      description "IPv4 address";
    }
    leaf ipv6-address {
      when "../af-name = 'ipv6'" {
        description "../AFName = 'IPv6'";
      }
      type Mpp-in6-addr;
      description "IPv6 address";
    }
  }

  grouping MPP-INFO {
    description "MPP Information";
    leaf allow {
      type Mpp-allow;
      description "MPP allow";
    }
    leaf is-all-peers-allowed {
      type boolean;
      description "If TRUE, all peers are allowed";
    }

    list peer-address {
      description "List of peer addresses";
      uses IP-ADDR-T-UNION;
    }
  }

  grouping MPP-PROTO {
    description "MPP Interface protocols";

    list protocol {
      description "MPP Interface protocols";
      uses MPP-INFO;
    }
  }

  grouping VRF-INFO {
    description "Outband VRF name";
    leaf vrf-name {
      type string;
      description "Outband VRF name";
    }
  }
}
