submodule Cisco-IOS-XR-dnx-port-mapper-oper-sub1 {

  belongs-to Cisco-IOS-XR-dnx-port-mapper-oper {
    prefix Cisco-IOS-XR-dnx-port-mapper-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-port-mapper package operational data.

     Copyright (c) 2013-2016 by Cisco Systems, Inc.
     All rights reserved.";

  revision "2015-11-09" {
    description
      "IOS XR 6.0 revision.";
  }


  grouping OOR-SUMMARY {
    description "Lists interfaces in each of the three states";
    leaf red {
      type uint32;
      description "interfaces in red state";
    }
    leaf green {
      type uint32;
      description "interfaces in green state";
    }
    leaf yel-low {
      type uint32;
      description "interfaces in yellow state";
    }
  }

  grouping OOR-INTERFACE-SUMMARY {
    description "Overall Summary of states of all interfaces";
    leaf interface-name {
      type string;
      description "Name of the interface";
    }
    leaf interface-status {
      type string;
      description "The current state of the interface";
    }
    leaf hardware-resource {
      type string;
      description "Type of harware resoruce";
    }
  }

  grouping OOR-INTERFACE-DETAIL {
    description "OOR specific details for the interface";
    leaf interface-name {
      type string;
      description "Name of the interface";
    }
    leaf interface-status {
      type string;
      description "The current state of the interface";
    }
    leaf time-stamp {
      type string;
      description "Timestamp";
    }
    leaf npu-id {
      type string;
      description "Npuid of the interface";
    }
    leaf hardware-resource {
      type string;
      description "Type of harware resoruce";
    }
  }

  grouping OOR-BUNDLE-INTERFACE-DETAIL {
    description "OOR specific details for the bundle interface";
    leaf interface-state {
      type string;
      description "Current state of the interface";
    }
    leaf time-stamp {
      type string;
      description "Timestamp";
    }

    list member {
      max-elements "64";
      description "Member details";
      uses OOR-INTERFACE-DETAIL;
    }
  }

  grouping OOR-LT-HW-RESOURCE {
    description "OOR NPU resource for a logical (DPA) table";
    leaf name {
      type string;
      description "Logical (DPA) table name";
    }
    leaf in-use {
      type uint32;
      description
        "In-use entries of NPU resource DB for this
        logical table";
    }
    leaf in-use-percent {
      type uint32;
      description
        "In-use entries of NPU resource DB for this
        logical table";
    }
  }

  grouping OOR-MEMBER-NPU-RESOURCE {
    description "OOR NPU resource for a interface/bundle member";
    leaf interface-name {
      type string;
      description "Name of the member interface";
    }
    leaf location {
      type string;
      description "Rack/Slot/Instance of the interface";
    }
    leaf npu-id {
      type uint32;
      description "Npu Id of the interface";
    }
    leaf total-in-use {
      type uint32;
      description "Total In-use entries of NPU resource DB";
    }
    leaf total-in-use-percent {
      type uint32;
      units "percentage";
      description "Total In-use percentage of NPU resource DB";
    }
    leaf number-of-dpa-tables {
      type uint32;
      description
        "Number of logical tables using this NPU resource";
    }

    list dpa-table {
      description "Logical (DPA) tables information";
      uses OOR-LT-HW-RESOURCE;
    }
  }

  grouping OOR-INTERFACE-NPU-RESOURCE {
    description "OOR NPU resources for the interface/bundle";
    leaf name {
      type string;
      description "HW/NPU resource name";
    }
    leaf max-entries {
      type uint32;
      description "Max entries in NPU for this HW resource";
    }
    leaf red-threshold {
      type uint32;
      description "Red threshold";
    }
    leaf red-threshold-percent {
      type uint32;
      units "percentage";
      description "Red threshold percentage";
    }
    leaf yellow-threshold {
      type uint32;
      description "Yellow threshold";
    }
    leaf yellow-threshold-percent {
      type uint32;
      units "percentage";
      description "Yellow threshold percentage";
    }
    leaf interface-state {
      type string;
      description "Current OOR state of the interface/bundle";
    }
    leaf time-stamp {
      type string;
      description "Timestamp of last OOR change";
    }
    leaf number-of-members {
      type uint32;
      description
        "Number of bundle members. for non-bundles this
        will be 1";
    }

    list member {
      description "Interface/Bundle member HW/NPU resources";
      uses OOR-MEMBER-NPU-RESOURCE;
    }
  }
}
