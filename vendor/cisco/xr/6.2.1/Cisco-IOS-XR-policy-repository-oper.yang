module Cisco-IOS-XR-policy-repository-oper {

  /*** NAMESPACE / PREFIX DEFINITION ***/

  namespace "http://cisco.com/ns/yang"+
    "/Cisco-IOS-XR-policy-repository-oper";


  prefix "policy-repository-oper";

  /*** LINKAGE (IMPORTS / INCLUDES) ***/

  import Cisco-IOS-XR-types { prefix "xr"; }

  include Cisco-IOS-XR-policy-repository-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR policy-repository package operational data.

     This module contains definitions
     for the following management objects:
       routing-policy: Routing policy operational data

     Copyright (c) 2013-2016 by Cisco Systems, Inc.
     All rights reserved.";

  revision "2015-11-09" {
    description
      "IOS XR 6.0 revision.";
  }


  grouping UNUSED {
    description
      "Common node of policies, as-path, community,
      extended-community-cost, rd,
      extended-community-rt, extended-community-soo,
      extended-community-opaque,
      extended-community-seg-nh,
      extended-community-bandwidth, prefix, esi, etag,
      mac, tag, ospf-area";

    container unused {
      description
        "All objects of a given type that are not
        referenced at all";
      uses RPL-OBJECTS-INFO;
    }
  }

  grouping SET-TABLE {
    description
      "Common node of as-path, community,
      extended-community-cost, rd,
      extended-community-rt, extended-community-soo,
      extended-community-opaque,
      extended-community-seg-nh,
      extended-community-bandwidth, prefix, esi, etag,
      mac, tag, ospf-area";

    container sets {
      description "Information about individual sets";

      list set {
        key "set-name";
        description "Information about an individual set";
        leaf set-name {
          type xr:Cisco-ios-xr-string;
          description "Set name";
        }
        uses USED-BY;
        uses ATTACHED;
      }
    }
  }

  grouping INACTIVE {
    description
      "Common node of policies, as-path, community,
      extended-community-cost, rd,
      extended-community-rt, extended-community-soo,
      extended-community-opaque,
      extended-community-seg-nh,
      extended-community-bandwidth, prefix, esi, etag,
      mac, tag, ospf-area";

    container inactive {
      description
        "All objects of a given type that are not
        attached to a protocol";
      uses RPL-OBJECTS-INFO;
    }
  }

  grouping USED-BY {
    description "Common node of route-policy, set";

    container used-by {
      description
        "Policies that use this object, directly or
        indirectly";
      uses RPL-REFERENCES-INFO;
    }
  }

  grouping ACTIVE {
    description
      "Common node of policies, as-path, community,
      extended-community-cost, rd,
      extended-community-rt, extended-community-soo,
      extended-community-opaque,
      extended-community-seg-nh, prefix, esi, etag, mac
      , tag, ospf-area";

    container active {
      description
        "All objects of a given type that are attached to
        a protocol";
      uses RPL-OBJECTS-INFO;
    }
  }

  grouping ATTACHED {
    description "Common node of route-policy, set";

    container attached {
      description
        "Information about where this policy or set is
        attached";
      uses RPL-ATTACHMENT-INFO;
    }
  }

  container routing-policy {
    config false;
    description "Routing policy operational data";

    container limits {
      description
        "Information about configured limits and the
        current values";
      uses RPL-MAX-LIMITS-INFO;
    }

    container policies {
      description "Information about configured route policies";

      container route-policies {
        description "Information about individual policies";

        list route-policy {
          key "route-policy-name";
          description "Information about an individual policy";

          container policy-uses {
            description
              "Information about which policies and sets
              this policy uses";

            container directly-used-policies {
              description "Policies that this policy uses directly";
              uses RPL-OBJECTS-INFO;
            }

            container all-used-sets {
              description
                "Sets used by this policy, or by policies
                that it uses";
              uses RPL-SETS-INFO;
            }

            container directly-used-sets {
              description "Sets that this policy uses directly";
              uses RPL-SETS-INFO;
            }

            container all-used-policies {
              description
                "Policies used by this policy, or by policies
                that it uses";
              uses RPL-OBJECTS-INFO;
            }
          }
          leaf route-policy-name {
            type xr:Cisco-ios-xr-string;
            description "Route policy name";
          }
          uses USED-BY;
          uses ATTACHED;
        }
      }
      uses UNUSED;
      uses INACTIVE;
      uses ACTIVE;
    }

    container sets {
      description "Information about configured sets";

      container etag {
        description "Information about Etag sets";
        uses SET-TABLE;
        uses UNUSED;
        uses INACTIVE;
        uses ACTIVE;
      }

      container ospf-area {
        description "Information about OSPF Area sets";
        uses SET-TABLE;
        uses UNUSED;
        uses INACTIVE;
        uses ACTIVE;
      }

      container extended-community-opaque {
        description
          "Information about Extended Community Opaque
          sets";
        uses SET-TABLE;
        uses UNUSED;
        uses INACTIVE;
        uses ACTIVE;
      }

      container extended-community-seg-nh {
        description
          "Information about Extended Community SegNH sets";
        uses SET-TABLE;
        uses UNUSED;
        uses INACTIVE;
        uses ACTIVE;
      }

      container extended-community-soo {
        description "Information about Extended Community SOO sets";
        uses SET-TABLE;
        uses UNUSED;
        uses INACTIVE;
        uses ACTIVE;
      }

      container tag {
        description "Information about Tag sets";
        uses SET-TABLE;
        uses UNUSED;
        uses INACTIVE;
        uses ACTIVE;
      }

      container prefix {
        description "Information about AS Path sets";
        uses SET-TABLE;
        uses UNUSED;
        uses INACTIVE;
        uses ACTIVE;
      }

      container community {
        description "Information about Community sets";
        uses SET-TABLE;
        uses UNUSED;
        uses INACTIVE;
        uses ACTIVE;
      }

      container as-path {
        description "Information about AS Path sets";
        uses SET-TABLE;
        uses UNUSED;
        uses INACTIVE;
        uses ACTIVE;
      }

      container esi {
        description "Information about Esi sets";
        uses SET-TABLE;
        uses UNUSED;
        uses INACTIVE;
        uses ACTIVE;
      }

      container extended-community-bandwidth {
        description
          "Information about Extended Community Bandwidth
          sets";
        uses SET-TABLE;
        uses UNUSED;
        uses INACTIVE;
      }

      container extended-community-rt {
        description "Information about Extended Community RT sets";
        uses SET-TABLE;
        uses UNUSED;
        uses INACTIVE;
        uses ACTIVE;
      }

      container rd {
        description "Information about RD sets";
        uses SET-TABLE;
        uses UNUSED;
        uses INACTIVE;
        uses ACTIVE;
      }

      container mac {
        description "Information about Mac sets";
        uses SET-TABLE;
        uses UNUSED;
        uses INACTIVE;
        uses ACTIVE;
      }

      container extended-community-cost {
        description
          "Information about Extended Community Cost sets";
        uses SET-TABLE;
        uses UNUSED;
        uses INACTIVE;
        uses ACTIVE;
      }
    }
  }
}
