submodule Cisco-IOS-XR-ppp-ma-oper-sub3 {

  belongs-to Cisco-IOS-XR-ppp-ma-oper {
    prefix Cisco-IOS-XR-ppp-ma-oper;
  }

  /*** LINKAGE (IMPORTS / INCLUDES) ***/

  import Cisco-IOS-XR-types { prefix "xr"; }

  include Cisco-IOS-XR-ppp-ma-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ppp-ma package operational data.

     Copyright (c) 2013-2016 by Cisco Systems, Inc.
     All rights reserved.";

  revision "2015-11-09" {
    description
      "IOS XR 6.0 revision.";
  }


  grouping PPP-OPER-NCP-STATS-INTERFACE {
    description "PPP per-interface NCP statistics";
    leaf ncp-identifier {
      type Ncp-ident;
      description "NCP identifier";
    }
    leaf conf-req-sent {
      type uint16;
      description "Conf Req Packets Sent";
    }
    leaf conf-req-rcvd {
      type uint16;
      description "Conf Req Packets Received";
    }
    leaf conf-ack-sent {
      type uint16;
      description "Conf Ack Packets Sent";
    }
    leaf conf-ack-rcvd {
      type uint16;
      description "Conf Ack Packets Received";
    }
    leaf conf-nak-sent {
      type uint16;
      description "Conf Nak Packets Sent";
    }
    leaf conf-nak-rcvd {
      type uint16;
      description "Conf Nak Packets Received";
    }
    leaf conf-rej-sent {
      type uint16;
      description "Conf Rej Packets Sent";
    }
    leaf conf-rej-rcvd {
      type uint16;
      description "Conf Rej Packets Received";
    }
  }

  grouping PPP-OPER-AUTH-STATS-INTERFACE {
    description "PPP Authentication statistics";
    leaf pap-req-sent {
      type uint16;
      description "PAP Request packets sent";
    }
    leaf pap-req-rcvd {
      type uint16;
      description "PAP Request packets received";
    }
    leaf pap-ack-sent {
      type uint16;
      description "PAP Ack packets sent";
    }
    leaf pap-ack-rcvd {
      type uint16;
      description "PAP Ack packets received";
    }
    leaf pap-nak-sent {
      type uint16;
      description "PAP Nak packets sent";
    }
    leaf pap-nak-rcvd {
      type uint16;
      description "PAP Nak packets received";
    }
    leaf chap-chall-sent {
      type uint16;
      description "CHAP challenge packets sent";
    }
    leaf chap-chall-rcvd {
      type uint16;
      description "CHAP challenge packets received";
    }
    leaf chap-resp-sent {
      type uint16;
      description "CHAP response packets sent";
    }
    leaf chap-resp-rcvd {
      type uint16;
      description "CHAP response packets received";
    }
    leaf chap-rep-succ-sent {
      type uint16;
      description "CHAP reply success packets sent";
    }
    leaf chap-rep-succ-rcvd {
      type uint16;
      description "CHAP reply success packets received";
    }
    leaf chap-rep-fail-sent {
      type uint16;
      description "CHAP reply failure packets sent";
    }
    leaf chap-rep-fail-rcvd {
      type uint16;
      description "CHAP reply failure packets received";
    }
    leaf auth-timeout-count {
      type uint16;
      description "Authentication timeout count";
    }
  }

  grouping PPP-OPER-LCP-STATS-INTERFACE {
    description "PPP per-interface LCP statistics";
    leaf conf-req-sent {
      type uint16;
      description "Conf Req Packets Sent";
    }
    leaf conf-req-rcvd {
      type uint16;
      description "Conf Req Packets Received";
    }
    leaf conf-ack-sent {
      type uint16;
      description "Conf Ack Packets Sent";
    }
    leaf conf-ack-rcvd {
      type uint16;
      description "Conf Ack Packets Received";
    }
    leaf conf-nak-sent {
      type uint16;
      description "Conf Nak Packets Sent";
    }
    leaf conf-nak-rcvd {
      type uint16;
      description "Conf Nak Packets Received";
    }
    leaf conf-rej-sent {
      type uint16;
      description "Conf Rej Packets Sent";
    }
    leaf conf-rej-rcvd {
      type uint16;
      description "Conf Rej Packets Received";
    }
    leaf echo-req-sent {
      type uint16;
      description "Echo Req Packets Sent";
    }
    leaf echo-req-rcvd {
      type uint16;
      description "Echo Req Packets Received";
    }
    leaf echo-rep-sent {
      type uint16;
      description "Echo Rep Packets Sent";
    }
    leaf echo-rep-rcvd {
      type uint16;
      description "Echo Rep Packets Received";
    }
    leaf disc-req-sent {
      type uint16;
      description "Disc Req Packets Sent";
    }
    leaf disc-req-rcvd {
      type uint16;
      description "Disc Req Packets Received";
    }
    leaf link-up {
      type uint16;
      description "Line Protocol Up count";
    }
    leaf link-error {
      type uint16;
      description "Keepalive link failure count";
    }
  }

  grouping PPP-OPER-STATS-INTERFACE {
    description "PPP interface statistics information";

    container lcp-statistics {
      description "PPP LCP Statistics";
      uses PPP-OPER-LCP-STATS-INTERFACE;
    }

    container authentication-statistics {
      description "PPP Authentication statistics";
      uses PPP-OPER-AUTH-STATS-INTERFACE;
    }

    list ncp-statistics-array {
      description "Array of PPP NCP Statistics";
      uses PPP-OPER-NCP-STATS-INTERFACE;
    }
  }

  grouping PPP-OPER-NCP-STATS-GLOBAL {
    description "PPP Global NCP Statistics";
    leaf ncp-identifier {
      type Ncp-ident;
      description "NCP identifier";
    }
    leaf conf-req-sent {
      type uint64;
      description "Conf Req Packets Sent";
    }
    leaf conf-req-rcvd {
      type uint64;
      description "Conf Req Packets Received";
    }
    leaf conf-ack-sent {
      type uint64;
      description "Conf Ack Packets Sent";
    }
    leaf conf-ack-rcvd {
      type uint64;
      description "Conf Ack Packets Received";
    }
    leaf conf-nak-sent {
      type uint64;
      description "Conf Nak Packets Sent";
    }
    leaf conf-nak-rcvd {
      type uint64;
      description "Conf Nak Packets Received";
    }
    leaf conf-rej-sent {
      type uint64;
      description "Conf Rej Packets Sent";
    }
    leaf conf-rej-rcvd {
      type uint64;
      description "Conf Rej Packets Received";
    }
    leaf term-req-sent {
      type uint64;
      description "Term Req Packets Sent";
    }
    leaf term-req-rcvd {
      type uint64;
      description "Term Req Packets Received";
    }
    leaf term-ack-sent {
      type uint64;
      description "Term Ack Packets Sent";
    }
    leaf term-ack-rcvd {
      type uint64;
      description "Term Ack Packets Received";
    }
    leaf proto-rej-sent {
      type uint64;
      description "Proto Rej Packets Sent";
    }
    leaf proto-rej-rcvd {
      type uint64;
      description "Proto Rej Packets Received";
    }
  }

  grouping PPP-OPER-AUTH-STATS-GLOBAL {
    description "PPP Authentication statistics";
    leaf pap-req-sent {
      type uint64;
      description "PAP Request packets sent";
    }
    leaf pap-req-rcvd {
      type uint64;
      description "PAP Request packets received";
    }
    leaf pap-ack-sent {
      type uint64;
      description "PAP Ack packets sent";
    }
    leaf pap-ack-rcvd {
      type uint64;
      description "PAP Ack packets received";
    }
    leaf pap-nak-sent {
      type uint64;
      description "PAP Nak packets sent";
    }
    leaf pap-nak-rcvd {
      type uint64;
      description "PAP Nak packets received";
    }
    leaf chap-chall-sent {
      type uint64;
      description "CHAP challenge packets sent";
    }
    leaf chap-chall-rcvd {
      type uint64;
      description "CHAP challenge packets received";
    }
    leaf chap-resp-sent {
      type uint64;
      description "CHAP response packets sent";
    }
    leaf chap-resp-rcvd {
      type uint64;
      description "CHAP response packets received";
    }
    leaf chap-rep-succ-sent {
      type uint64;
      description "CHAP reply success packets sent";
    }
    leaf chap-rep-succ-rcvd {
      type uint64;
      description "CHAP reply success packets received";
    }
    leaf chap-rep-fail-sent {
      type uint64;
      description "CHAP reply failure packets sent";
    }
    leaf chap-rep-fail-rcvd {
      type uint64;
      description "CHAP reply failure packets received";
    }
    leaf auth-timeout-count {
      type uint64;
      description "Authentication timeout count";
    }
  }

  grouping PPP-OPER-LCP-STATS-GLOBAL {
    description "PPP Global LCP Statistics";
    leaf conf-req-sent {
      type uint64;
      description "Conf Req Packets Sent";
    }
    leaf conf-req-rcvd {
      type uint64;
      description "Conf Req Packets Received";
    }
    leaf conf-ack-sent {
      type uint64;
      description "Conf Ack Packets Sent";
    }
    leaf conf-ack-rcvd {
      type uint64;
      description "Conf Ack Packets Received";
    }
    leaf conf-nak-sent {
      type uint64;
      description "Conf Nak Packets Sent";
    }
    leaf conf-nak-rcvd {
      type uint64;
      description "Conf Nak Packets Received";
    }
    leaf conf-rej-sent {
      type uint64;
      description "Conf Rej Packets Sent";
    }
    leaf conf-rej-rcvd {
      type uint64;
      description "Conf Rej Packets Received";
    }
    leaf term-req-sent {
      type uint64;
      description "Term Req Packets Sent";
    }
    leaf term-req-rcvd {
      type uint64;
      description "Term Req Packets Received";
    }
    leaf term-ack-sent {
      type uint64;
      description "Term Ack Packets Sent";
    }
    leaf term-ack-rcvd {
      type uint64;
      description "Term Ack Packets Received";
    }
    leaf code-rej-sent {
      type uint64;
      description "Code Rej Packets Sent";
    }
    leaf code-rej-rcvd {
      type uint64;
      description "Code Rej Packets Received";
    }
    leaf proto-rej-sent {
      type uint64;
      description "Proto Rej Packets Sent";
    }
    leaf proto-rej-rcvd {
      type uint64;
      description "Proto Rej Packets Received";
    }
    leaf echo-req-sent {
      type uint64;
      description "Echo Req Packets Sent";
    }
    leaf echo-req-rcvd {
      type uint64;
      description "Echo Req Packets Received";
    }
    leaf echo-rep-sent {
      type uint64;
      description "Echo Rep Packets Sent";
    }
    leaf echo-rep-rcvd {
      type uint64;
      description "Echo Rep Packets Received";
    }
    leaf disc-req-sent {
      type uint64;
      description "Disc Req Packets Sent";
    }
    leaf disc-req-rcvd {
      type uint64;
      description "Disc Req Packets Received";
    }
    leaf link-up {
      type uint64;
      description "Line Protocol Up count";
    }
    leaf link-error {
      type uint64;
      description "Keepalive link failure count";
    }
  }

  grouping PPP-OPER-STATS-GLOBAL {
    description "PPP summary statistics information";

    container lcp-statistics {
      description "PPP LCP Statistics";
      uses PPP-OPER-LCP-STATS-GLOBAL;
    }

    container authentication-statistics {
      description "PPP Authentication statistics";
      uses PPP-OPER-AUTH-STATS-GLOBAL;
    }

    list ncp-statistics-array {
      description "Array of PPP NCP Statistics";
      uses PPP-OPER-NCP-STATS-GLOBAL;
    }
  }
}
