module Cisco-IOS-XR-qos-ma-sat-cfg {

  /*** NAMESPACE / PREFIX DEFINITION ***/

  namespace "http://cisco.com/ns/yang/Cisco-IOS-XR-qos-ma-sat-cfg";


  prefix "qos-ma-sat-cfg";

  /*** LINKAGE (IMPORTS / INCLUDES) ***/

  import Cisco-IOS-XR-types { prefix "xr"; }
 
  import Cisco-IOS-XR-ifmgr-cfg { prefix "a1"; }
 
  import Cisco-IOS-XR-icpe-infra-cfg { prefix "a2"; }
  
 
  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR qos satellite package configuration.

     This module contains definitions
     for the following management objects:
      qos satellite: QOS Satellite configuration.

     This YANG module augments the
       Cisco-IOS-XR-ifmgr-cfg,
       Cisco-IOS-XR-icpe-infra-cfg
     modules with configuration data.

     Copyright (c) 2013-2016 by Cisco Systems, Inc.
     All rights reserved.";

  revision "2016-12-15" {
    description
      "IOS XR 6.2.1 revision.";
  }

  grouping QOS {
    description
      "Common node of interface-configuration, 
      nv-satellite-access, nv-satellite-fabric-link, 
      satellites";

    container qos {
      description "Interface QOS configuration";

      container output {
        description "Egress service policy";
        uses SERVICE-POLICY;
      }

      container input {
        description "Ingress service policy";
        uses SERVICE-POLICY;
      }
    }
  }

  grouping SERVICE-POLICY {
    description "Common node of input, output";

    list service-policy {
      key "service-policy-name";
      description "Service policy details";
      leaf service-policy-name {
        type string {
          length "0..64";
        }
        description "Name of policy-map";
      }
    }
  }
  
  augment "/a1:interface-configurations/a1:interface-configuration"+
    "/a2:nv-satellite-access" {
    description
      "This augment extends the configuration data of
      'Cisco-IOS-XR-icpe-infra-cfg'";
    uses QOS;
  }

  augment "/a1:interface-configurations/a1:interface-configuration"+
    "/a2:nv-satellite-fabric-link" {
    description
      "This augment extends the configuration data of
      'Cisco-IOS-XR-icpe-infra-cfg'";
    uses QOS;
  }

  augment "/a1:interface-configurations/a1:interface-configuration"+
    "/a2:nv-satellite-fabric-network/a2:satellites" {
    description
      "This augment extends the configuration data of
      'Cisco-IOS-XR-icpe-infra-cfg'";
    uses QOS;
  }
}
