module cisco-xr-openconfig-routing-policy-deviations {

  /*** NAMESPACE / PREFIX DEFINITION ***/

  namespace "http://cisco.com/ns/yang/cisco-xr-openconfig-routing-policy-deviations";

  prefix "cisco-xr-oc-rpol-devs";

  /*** LINKAGE (IMPORTS / INCLUDES) ***/
  import openconfig-routing-policy { prefix rpol; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains the deviations of Open Config Routing Policy YANG 
    set for Cisco IOS-XR.

     Copyright (c) 2015-2016 by Cisco Systems, Inc.
     All rights reserved.";

  revision "2015-10-21" {
    description
      "Initial revision applicable to IOS-XR 5.3.2 and 6.0";
  }

  deviation /rpol:routing-policy/rpol:defined-sets/rpol:neighbor-sets {
    deviate not-supported;
  }

  deviation /rpol:routing-policy/rpol:policy-definitions/rpol:policy-definition/rpol:statements/rpol:statement/rpol:conditions/rpol:igp-conditions {
    deviate not-supported;
  }

  deviation /rpol:routing-policy/rpol:policy-definitions/rpol:policy-definition/rpol:statements/rpol:statement/rpol:conditions/rpol:match-neighbor-set {
    deviate not-supported;
  }

  deviation /rpol:routing-policy/rpol:policy-definitions/rpol:policy-definition/rpol:statements/rpol:statement/rpol:actions/rpol:igp-actions {
    deviate not-supported;
  }
}
