module Cisco-IOS-XR-terminal-device-oper {

  /*** NAMESPACE / PREFIX DEFINITION ***/

  namespace "http://cisco.com/ns/yang"+
    "/Cisco-IOS-XR-terminal-device-oper";


  prefix "terminal-device-oper";

  /*** LINKAGE (IMPORTS / INCLUDES) ***/

  import Cisco-IOS-XR-types { prefix "xr"; }

  include Cisco-IOS-XR-terminal-device-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR terminal-device package operational data.

     This module contains definitions
     for the following management objects:
       optical-interface: System-wide view of interface operational
         data

     Copyright (c) 2013-2016 by Cisco Systems, Inc.
     All rights reserved.";

  revision "2015-11-09" {
    description
      "IOS XR 6.0 revision.";
  }


  container optical-interface {
    config false;
    description "System-wide view of interface operational data";

    container config-status {
      description "Table containing status information";

      container partial-config {
        description "The bag containing partial config status";
        uses PARTIAL-CONFIG-STATUS;
      }

      container slice-tables {
        description
          "The container containing slice status
          information";

        list slice-table {
          key "index";
          description "The table contains list of slices present";

          container slice-status-attr {
            description "The bag containing slice config status";
            uses SLICE-CONFIG-STATUS-ATTRIBUTES;
          }
          leaf index {
            type int32;
            description "The index of slice";
          }
        }
      }
    }

    container optical-channel-interfaces {
      description
        "The operational attributes for a particular
        optical channel";

      list optical-channel-interface {
        key "location";
        description
          "The operational attributes for an optical
          channel";

        container optical-channel-interface-attr {
          description
            "The operational attributes for an optical
            channel";
          uses OPTICAL-CHANNEL-ATTRIBUTES;
        }
        leaf location {
          type xr:Cisco-ios-xr-string;
          description "The name of the optical-channel";
        }
      }
    }

    container graph {
      description
        "Table containing Graph Structure and related
        info";

      container adj-list-path {
        description
          "The path containg file which has adjacency list
          stored";
        uses ADJACENCY-LIST-PATH;
      }

      container graph-structure-path {
        description
          "The path containg file which has graph
          structure stored";
        uses GRAPH-STRUCTURE-PATH;
      }
    }

    container operational-modes {
      description "The Operational Mode Table";

      list operational-mode {
        key "mode-id";
        description "Mode supported on Device";

        container operational-mode-attributes {
          description
            "The operational attributes for mxp driver
            fec-mode";
          uses OPERATIONAL-MODE-ATTRIBUTES;
        }
        leaf mode-id {
          type int32;
          description "Mode-id for supported mode on Device";
        }
      }
    }

    container optical-logical-interfaces {
      description
        "The operational attributes for a logical channel";

      list optical-logical-interface {
        key "index";
        description
          "The operational attributes for a logical
          channel";

        container optical-logical-interface-attr {
          description
            "The operational attributes for a particular
            logical channel";
          uses LOGICAL-CHANNEL-ATTRIBUTES;
        }

        container "optical-logical-interface-logical-channel"+
          "-assignments" {
          description
            "The operational attributes for a particular
            interface";

          list "optical-logical-interface-logical-channel"+
            "-assignment" {
            key "index";
            description
              "The operational attributes for a logical
              channel assignment";

            container "optical-logical-interface-logical-channel"+
              "-assignment-attr" {
              description
                "The operational attributes for a logical
                channel assignment";
              uses LOGICAL-CHANNEL-ASSIGNMENT;
            }
            leaf index {
              type int32;
              description "The index of the logical-channel";
            }
          }
        }
        leaf index {
          type int32;
          description "The index of the logical-channel";
        }
      }
    }
  }
}
