module Cisco-IOS-XR-icpe-infra-oper {

  /*** NAMESPACE / PREFIX DEFINITION ***/

  namespace "http://cisco.com/ns/yang/Cisco-IOS-XR-icpe-infra-oper";


  prefix "icpe-infra-oper";

  /*** LINKAGE (IMPORTS / INCLUDES) ***/

  import Cisco-IOS-XR-types { prefix "xr"; }

  include Cisco-IOS-XR-icpe-infra-oper-sub12 {
    revision-date 2015-11-09;
  }

  include Cisco-IOS-XR-icpe-infra-oper-sub11 {
    revision-date 2015-11-09;
  }

  include Cisco-IOS-XR-icpe-infra-oper-sub10 {
    revision-date 2015-11-09;
  }

  include Cisco-IOS-XR-icpe-infra-oper-sub9 {
    revision-date 2015-11-09;
  }

  include Cisco-IOS-XR-icpe-infra-oper-sub8 {
    revision-date 2015-11-09;
  }

  include Cisco-IOS-XR-icpe-infra-oper-sub7 {
    revision-date 2015-11-09;
  }

  include Cisco-IOS-XR-icpe-infra-oper-sub6 {
    revision-date 2015-11-09;
  }

  include Cisco-IOS-XR-icpe-infra-oper-sub5 {
    revision-date 2015-11-09;
  }

  include Cisco-IOS-XR-icpe-infra-oper-sub4 {
    revision-date 2015-11-09;
  }

  include Cisco-IOS-XR-icpe-infra-oper-sub3 {
    revision-date 2015-11-09;
  }

  include Cisco-IOS-XR-icpe-infra-oper-sub2 {
    revision-date 2015-11-09;
  }

  include Cisco-IOS-XR-icpe-infra-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR icpe-infra package operational data.

     This module contains definitions
     for the following management objects:
       nv-satellite: Satellite operational information

     Copyright (c) 2013-2016 by Cisco Systems, Inc.
     All rights reserved.";

  revision "2015-11-09" {
    description
      "IOS XR 6.0 revision.";
  }


  container nv-satellite {
    config false;
    description "Satellite operational information";

    container reload-op-statuses {
      description "Detailed breakdown of reload status table";

      list reload-op-status {
        key "operation-id";
        description "Detailed breakdown of reload status";
        leaf operation-id {
          type uint32 {
            range "0..4294967295";
          }
          description "Operation ID";
        }
        uses ICPE-RELOAD-OP-STATUS-DETAIL;
      }
    }

    container install-statuses {
      description "Detailed breakdown of install status table";

      list install-status {
        key "satellite-range";
        description "Detailed breakdown of install status";
        leaf satellite-range {
          type xr:Cisco-ios-xr-string;
          description "Satellite range";
        }
        uses ICPE-INSTALL-STATUS-DETAIL;
      }
    }

    container sdacp-redundancies {
      description
        "nV Satellite Redundancy Protocol Information
        table";

      list sdacp-redundancy {
        key "iccp-group";
        description "nV Satellite Redundancy Protocol Information";
        leaf iccp-group {
          type uint32 {
            range "0..4294967295";
          }
          description "ICCP group";
        }
        uses ICPE-REDUNDANCY-SESSION;
      }
    }

    container install-shows {
      description "Detailed breakdown of install status table";

      list install-show {
        key "operation-id";
        description "Detailed breakdown of install status";
        leaf operation-id {
          type uint32 {
            range "0..4294967295";
          }
          description "Operation ID";
        }
        uses ICPE-INSTALL-SHOW-DETAIL-TYPE;
      }
    }

    container satellite-statuses {
      description "Satellite status information table";

      list satellite-status {
        key "satellite-id";
        description "Satellite status information";
        leaf satellite-id {
          type uint32 {
            range "0..4294967295";
          }
          description "Satellite ID";
        }
        uses ICPE-OPER-SAT-STATUS;
      }
    }

    container satellite-priorities {
      description "Satellite priority information table";

      list satellite-priority {
        key "satellite-id";
        description "Satellite priority information";
        leaf satellite-id {
          type uint32 {
            range "0..4294967295";
          }
          description "Satellite ID";
        }
        uses ICPE-GCO-PRIORITY-OPER-TYPE;
      }
    }

    container satellite-versions {
      description "Satellite remote version information table";

      list satellite-version {
        key "satellite-id";
        description "Satellite remote version information";
        leaf satellite-id {
          type uint32 {
            range "0..4294967295";
          }
          description "Satellite ID";
        }
        uses ICPE-OPER-SAT-REMOTE-VERSION-TYPE;
      }
    }

    container satellite-topologies {
      description "Satellite Topology Information table";

      list satellite-topology {
        key "interface-name";
        description "Satellite Topology Information";
        leaf interface-name {
          type xr:Cisco-ios-xr-string;
          description "Interface name";
        }
        uses ICPE-OPER-TOPO-CSFL-TYPE;
      }
    }

    container install-progresses {
      description "Current percentage of install table";

      list install-progress {
        key "progress-percentage";
        description "Current percentage of install";
        leaf progress-percentage {
          type uint32 {
            range "0..2147483647";
          }
          units "percentage";
          description "Progress percentage";
        }
        uses ICPE-INSTALL-PROGRESS;
      }
    }

    container reload-statuses {
      description "Detailed breakdown of reload status table";

      list reload-status {
        key "satellite-range";
        description "Detailed breakdown of reload status";
        leaf satellite-range {
          type xr:Cisco-ios-xr-string;
          description "Satellite range";
        }
        uses ICPE-RELOAD-STATUS-DETAIL;
      }
    }

    container install {
      description "Satellite Install Information";

      container satellite-software-versions {
        description "Satellite Software Package Information table";

        list satellite-software-version {
          key "satellite-id";
          description "Satellite Software Package Information";
          leaf satellite-id {
            type uint32 {
              range "0..4294967295";
            }
            description "Satellite ID";
          }
          uses ICPE-OPER-SAT-PACKAGE-INFORMATION-TYPE;
        }
      }
    }

    container install-op-statuses {
      description "Detailed breakdown of install status table";

      list install-op-status {
        key "operation-id";
        description "Detailed breakdown of install status";
        leaf operation-id {
          type uint32 {
            range "0..4294967295";
          }
          description "Operation ID";
        }
        uses ICPE-INSTALL-OP-STATUS-DETAIL;
      }
    }

    container satellite-properties {
      description "ICPE GCO operational information";

      container id-ranges {
        description "Satellite ID range table";

        list id-range {
          key "sat-id-range";
          description "Satellite ID range";
          leaf sat-id-range {
            type xr:Cisco-ios-xr-string;
            description "Sat ID range";
          }
          leaf min {
            type uint32 {
              range "0..2147483647";
            }
            description "Min";
          }
          leaf max {
            type uint32 {
              range "0..2147483647";
            }
            description "Max";
          }
        }
      }
    }
  }
}
