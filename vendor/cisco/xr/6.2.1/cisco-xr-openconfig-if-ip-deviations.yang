//*************  DO-NOT EDIT  **************
//*********** Auto-generated file ********** 

 module cisco-xr-openconfig-if-ip-deviations {

  prefix  "ocipdevs";

  namespace "http://cisco.com/ns/yang/cisco-xr-openconfig-if-ip-deviations";

  import openconfig-vlan { prefix vlan; }
  import openconfig-interfaces { prefix ocif; }
  import openconfig-if-ip { prefix ocip; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-if-ip.yang@2015-11-20 

     on Cisco IOS-XR devices.

     Copyright (c) 2016 by Cisco Systems, Inc.
     All rights reserved.";

  revision "2017-02-04" {
    description
      "Initial revision applicable to IOS-XR 6.2.1";
  }


  deviation /ocif:interfaces/ocif:interface/ocif:subinterfaces/ocif:subinterface/ocip:ipv4/ocip:config/ocip:enabled {
    deviate not-supported;
  }

  deviation /ocif:interfaces/ocif:interface/ocif:subinterfaces/ocif:subinterface/ocip:ipv4/ocip:state/ocip:enabled {
    deviate not-supported;
  }

  deviation /ocif:interfaces/ocif:interface/ocif:subinterfaces/ocif:subinterface/ocip:ipv6/ocip:autoconf/ocip:config/ocip:create-global-addresses {
    deviate not-supported;
  }

  deviation /ocif:interfaces/ocif:interface/ocif:subinterfaces/ocif:subinterface/ocip:ipv6/ocip:autoconf/ocip:config/ocip:create-temporary-addresses {
    deviate not-supported;
  }

  deviation /ocif:interfaces/ocif:interface/ocif:subinterfaces/ocif:subinterface/ocip:ipv6/ocip:autoconf/ocip:config/ocip:temporary-valid-lifetime {
    deviate not-supported;
  }

  deviation /ocif:interfaces/ocif:interface/ocif:subinterfaces/ocif:subinterface/ocip:ipv6/ocip:autoconf/ocip:config/ocip:temporary-preferred-lifetime {
    deviate not-supported;
  }

  deviation /ocif:interfaces/ocif:interface/ocif:subinterfaces/ocif:subinterface/ocip:ipv6/ocip:autoconf/ocip:state/ocip:create-global-addresses {
    deviate not-supported;
  }

  deviation /ocif:interfaces/ocif:interface/ocif:subinterfaces/ocif:subinterface/ocip:ipv6/ocip:autoconf/ocip:state/ocip:create-temporary-addresses {
    deviate not-supported;
  }

  deviation /ocif:interfaces/ocif:interface/ocif:subinterfaces/ocif:subinterface/ocip:ipv6/ocip:autoconf/ocip:state/ocip:temporary-valid-lifetime {
    deviate not-supported;
  }

  deviation /ocif:interfaces/ocif:interface/ocif:subinterfaces/ocif:subinterface/ocip:ipv6/ocip:autoconf/ocip:state/ocip:temporary-preferred-lifetime {
    deviate not-supported;
  }

  deviation /ocif:interfaces/ocif:interface/vlan:routed-vlan/ocip:ipv4/ocip:address {
    deviate not-supported;
  }

  deviation /ocif:interfaces/ocif:interface/vlan:routed-vlan/ocip:ipv4/ocip:neighbor {
    deviate not-supported;
  }

  deviation /ocif:interfaces/ocif:interface/vlan:routed-vlan/ocip:ipv4/ocip:config/ocip:enabled {
    deviate not-supported;
  }

  deviation /ocif:interfaces/ocif:interface/vlan:routed-vlan/ocip:ipv4/ocip:config/ocip:mtu {
    deviate not-supported;
  }

  deviation /ocif:interfaces/ocif:interface/vlan:routed-vlan/ocip:ipv4/ocip:state/ocip:enabled {
    deviate not-supported;
  }

  deviation /ocif:interfaces/ocif:interface/vlan:routed-vlan/ocip:ipv4/ocip:state/ocip:mtu {
    deviate not-supported;
  }

  deviation /ocif:interfaces/ocif:interface/vlan:routed-vlan/ocip:ipv6/ocip:address {
    deviate not-supported;
  }

  deviation /ocif:interfaces/ocif:interface/vlan:routed-vlan/ocip:ipv6/ocip:neighbor {
    deviate not-supported;
  }

  deviation /ocif:interfaces/ocif:interface/vlan:routed-vlan/ocip:ipv6/ocip:config/ocip:enabled {
    deviate not-supported;
  }

  deviation /ocif:interfaces/ocif:interface/vlan:routed-vlan/ocip:ipv6/ocip:config/ocip:mtu {
    deviate not-supported;
  }

  deviation /ocif:interfaces/ocif:interface/vlan:routed-vlan/ocip:ipv6/ocip:config/ocip:dup-addr-detect-transmits {
    deviate not-supported;
  }

  deviation /ocif:interfaces/ocif:interface/vlan:routed-vlan/ocip:ipv6/ocip:state/ocip:enabled {
    deviate not-supported;
  }

  deviation /ocif:interfaces/ocif:interface/vlan:routed-vlan/ocip:ipv6/ocip:state/ocip:mtu {
    deviate not-supported;
  }

  deviation /ocif:interfaces/ocif:interface/vlan:routed-vlan/ocip:ipv6/ocip:state/ocip:dup-addr-detect-transmits {
    deviate not-supported;
  }

  deviation /ocif:interfaces/ocif:interface/vlan:routed-vlan/ocip:ipv6/ocip:autoconf/ocip:config/ocip:create-global-addresses {
    deviate not-supported;
  }

  deviation /ocif:interfaces/ocif:interface/vlan:routed-vlan/ocip:ipv6/ocip:autoconf/ocip:config/ocip:create-temporary-addresses {
    deviate not-supported;
  }

  deviation /ocif:interfaces/ocif:interface/vlan:routed-vlan/ocip:ipv6/ocip:autoconf/ocip:config/ocip:temporary-valid-lifetime {
    deviate not-supported;
  }

  deviation /ocif:interfaces/ocif:interface/vlan:routed-vlan/ocip:ipv6/ocip:autoconf/ocip:config/ocip:temporary-preferred-lifetime {
    deviate not-supported;
  }

  deviation /ocif:interfaces/ocif:interface/vlan:routed-vlan/ocip:ipv6/ocip:autoconf/ocip:state/ocip:create-global-addresses {
    deviate not-supported;
  }

  deviation /ocif:interfaces/ocif:interface/vlan:routed-vlan/ocip:ipv6/ocip:autoconf/ocip:state/ocip:create-temporary-addresses {
    deviate not-supported;
  }

  deviation /ocif:interfaces/ocif:interface/vlan:routed-vlan/ocip:ipv6/ocip:autoconf/ocip:state/ocip:temporary-valid-lifetime {
    deviate not-supported;
  }

  deviation /ocif:interfaces/ocif:interface/vlan:routed-vlan/ocip:ipv6/ocip:autoconf/ocip:state/ocip:temporary-preferred-lifetime {
    deviate not-supported;
  }


}
//total deviations:32
