module Cisco-IOS-XR-telemetry-model-driven-oper {

  /*** NAMESPACE / PREFIX DEFINITION ***/

  namespace "http://cisco.com/ns/yang"+
    "/Cisco-IOS-XR-telemetry-model-driven-oper";


  prefix "telemetry-model-driven-oper";

  /*** LINKAGE (IMPORTS / INCLUDES) ***/

  import Cisco-IOS-XR-types { prefix "xr"; }

  include Cisco-IOS-XR-telemetry-model-driven-oper-sub1 {
    revision-date 2016-07-14;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR telemetry-model-driven package operational data.

     This module contains definitions
     for the following management objects:
       telemetry-model-driven: Telemetry operational data

     Copyright (c) 2013-2016 by Cisco Systems, Inc.
     All rights reserved.";

  revision "2016-07-14" {
    description
      "Initial 6.2.1 revision";
  }

  revision "2015-11-09" {
    description
      "IOS XR 6.0 revision.";
  }


  container telemetry-model-driven {
    config false;
    description "Telemetry operational data";

    container destinations {
      description "Telemetry Destinations";

      list destination {
        key "destination-id";
        description "Telemetry Destination";
        leaf destination-id {
          type xr:Cisco-ios-xr-string;
          description "Id of the destination";
        }
        uses MDT-DESTINATION-GROUP-DETAIL;
      }
    }

    container subscriptions {
      description "Telemetry Subscriptions";

      list subscription {
        key "subscription-id";
        description "Telemetry Subscription";
        leaf subscription-id {
          type xr:Cisco-ios-xr-string;
          description "Id of the subscription";
        }
        uses MDT-SUBSCRIPTION-DETAILS;
      }
    }

    container sensor-groups {
      description "Telemetry Sensor Groups";

      list sensor-group {
        key "sensor-group-id";
        description "Telemetry Sensor Groups";
        leaf sensor-group-id {
          type xr:Cisco-ios-xr-string;
          description "Id of the sensor group";
        }
        uses MDT-SENSOR-GROUP;
      }
    }
  }
}
