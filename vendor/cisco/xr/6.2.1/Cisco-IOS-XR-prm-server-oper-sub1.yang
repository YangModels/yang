submodule Cisco-IOS-XR-prm-server-oper-sub1 {

  belongs-to Cisco-IOS-XR-prm-server-oper {
    prefix Cisco-IOS-XR-prm-server-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR prm-server package operational data.

     Copyright (c) 2013-2016 by Cisco Systems, Inc.
     All rights reserved.";

  revision "2016-02-22" {
    description
      "Initial revision.";
  }

  revision "2015-11-09" {
    description
      "IOS XR 6.0 revision.";
  }


  grouping RESOURCE-EDM-DATA {
    description "Resource Summary Data";
    leaf resource-name {
      type string {
        length "0..1024";
      }
      description "Resource Name";
    }
    leaf resource-type {
      type uint32;
      description "Resource Type";
    }
    leaf total-num {
      type uint32;
      description "Total Resource Count";
    }
    leaf free-num {
      type uint32;
      description "Free Resource Count";
    }
    leaf first-available-index {
      type uint32;
      description "Next Free Index";
    }
    leaf start-index {
      type uint32;
      description "Start Index";
    }
    leaf availability-status {
      type boolean;
      description "Availability Status";
    }
    leaf flags {
      type uint8;
      description "Resource Flags";
    }
    leaf inconsistent {
      type boolean;
      description "Inconsistice Flags";
    }
  }

  grouping PLAT-DROP-STATS-INFO {
    description "Plat drop stats data";
    leaf drop-reason {
      type string {
        length "0..1024";
      }
      description "Drop Reason";
    }
    leaf counters {
      type uint32;
      description "Counter";
    }
  }

  grouping PLAT-DROP-CAPTURED-PAK {
    description "Plat drop captured packets";
    leaf total-captured {
      type uint32;
      description "Total packets Captured";
    }
    leaf captured-pak {
      type string {
        length "0..1024";
      }
      description "Captured Packet";
    }
    leaf pkt-index {
      type uint8;
      description "Packet Index";
    }
    leaf ifhandle {
      type uint32;
      description "If Handle";
    }
    leaf buffer-len {
      type uint32;
      description "Buffer Length";
    }
    leaf reason-hi {
      type uint32;
      description "Reason Hi";
    }
    leaf reason {
      type uint32;
      description "Reason";
    }
    leaf years {
      type uint64;
      description "Year";
    }
    leaf hours {
      type uint64;
      units "hour";
      description "Hours";
    }
    leaf days {
      type uint64;
      units "day";
      description "Days";
    }
    leaf mins {
      type uint64;
      units "minute";
      description "Minutes";
    }
    leaf secs {
      type uint64;
      units "second";
      description "Seconds";
    }
  }

  grouping BCM-EDM-COSQ-INFO {
    description "BCM CosQ EDM data";
    leaf cos-q-name {
      type string {
        length "0..1024";
      }
      description "CosQ Name";
    }
    leaf cos-q {
      type uint8;
      description "CosQ No";
    }
    leaf rx-channel {
      type uint32;
      description "Rx DMA Channel";
    }
    leaf flow-rate {
      type uint32;
      description "Flow Rate";
    }
    leaf burst {
      type uint32;
      description "Burst";
    }
    leaf accepted {
      type uint64;
      description "Accepted";
    }
    leaf dropped {
      type uint64;
      description "Dropped";
    }
  }
}
