submodule Cisco-IOS-XR-Ethernet-SPAN-oper-sub1 {

  belongs-to Cisco-IOS-XR-Ethernet-SPAN-oper {
    prefix Cisco-IOS-XR-Ethernet-SPAN-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR Ethernet-SPAN package operational data.

     Copyright (c) 2013-2016 by Cisco Systems, Inc.
     All rights reserved.";

  revision "2015-11-09" {
    description
      "IOS XR 6.0 revision.";
  }

  typedef Mirror-interval {
    type enumeration {
      enum mirror-interval-all {
        value 0;
        description "Mirror all packets";
      }
      enum mirror-interval512 {
        value 1;
        description "Mirror Interval 512";
      }
      enum mirror-interval1k {
        value 2;
        description "Mirror Interval 1K";
      }
      enum mirror-interval2k {
        value 3;
        description "Mirror Interval 2K";
      }
      enum mirror-interval4k {
        value 4;
        description "Mirror Interval 4K";
      }
      enum mirror-interval8k {
        value 5;
        description "Mirror Interval 8K";
      }
      enum mirror-interval16k {
        value 6;
        description "Mirror Interval 16K";
      }
    }
    description "Monitor-session mirror intervals";
  }
  typedef Traffic-direction {
    type enumeration {
      enum invalid {
        value 0;
        description "Invalid";
      }
      enum rx-only {
        value 1;
        description "Received";
      }
      enum tx-only {
        value 2;
        description "Transmitted";
      }
      enum both {
        value 3;
        description "Both";
      }
    }
    description "Monitor-session traffic directions";
  }
  typedef Optional-value {
    type uint32;
    description "Optional Value";
  }
  typedef Destination-class {
    type enumeration {
      enum interface-class {
        value 0;
        description "Destination is an interface";
      }
      enum pseudowire-class {
        value 1;
        description "Destination is a pseudowire";
      }
      enum next-hop-ipv4-class {
        value 2;
        description "Destination is a next-hop IPv4 address";
      }
      enum next-hop-ipv6-class {
        value 3;
        description "Destination is a next-hop IPv6 address";
      }
      enum invalid-class {
        value 255;
        description "Destination is not specified";
      }
    }
    description "Destination class";
  }
  typedef Session-class {
    type enumeration {
      enum ethernet-class {
        value 0;
        description "Ethernet mirroring session";
      }
      enum ipv4-class {
        value 1;
        description "IPv4 mirroring session";
      }
      enum ipv6-class {
        value 2;
        description "IPv6 mirroring session";
      }
      enum invalid-class {
        value 65535;
        description "Invalid session class";
      }
    }
    description "Session class";
  }

  grouping SPAN-EA-ATTACHMENT-BAG {
    description "SPAN EA Attachment Information";

    container destination-id {
      description "Destination ID";
      uses DESTINATION-ID;
    }

    container traffic-mirroring-parameters {
      description "Traffic mirroring parameters";
      uses TRAFFIC-MIRRORING-PARAMETERS;
    }
    leaf class {
      type Session-class;
      description "Attachment class";
    }
  }

  grouping SPAN-EA-INTF-BAG {
    description "SPAN EA Source Interface Information";

    container destination-id {
      description "Destination ID (deprecated by Attachment)";
      uses DESTINATION-ID;
    }

    container traffic-mirroring-parameters {
      description
        "Traffic mirroring parameters (deprecated by
        Attachment)";
      uses TRAFFIC-MIRRORING-PARAMETERS;
    }
    leaf source-interface {
      type xr:Interface-name;
      description "Source interface";
    }
    leaf platform-error {
      type uint32;
      description
        "Last error observed for this interface while
        programming the hardware";
    }
    leaf destination-interface {
      type xr:Interface-name;
      description
        "Destination interface (deprecated by Attachment)";
    }
    leaf traffic-direction {
      type Traffic-direction;
      description
        "Traffic mirroring direction (deprecated by
        Attachment)";
    }

    list attachment {
      description "Attachment information";
      uses SPAN-EA-ATTACHMENT-BAG;
    }
  }

  grouping SPAN-EA-SESS-BAG {
    description "SPAN EA Session Information";

    container destination-id {
      description "Destination ID";
      uses DESTINATION-ID;
    }
    leaf id {
      type uint32;
      description "Assigned numerical ID for this session";
    }
    leaf name {
      type string;
      description "Configured Session Name";
    }
    leaf session-class-xr {
      type Session-class;
      description "Session class";
    }
    leaf destination-interface {
      type xr:Interface-name;
      description
        "Destination interface (deprecated by
        DestinationID, invalid for pseudowires)";
    }
    leaf platform-error {
      type uint32;
      description
        "Last error observed for this session while
        programming the hardware";
    }
  }

  grouping TRAFFIC-MIRRORING-PARAMETERS {
    description "Monitor-session traffic mirroring parameters";
    leaf traffic-direction {
      type Traffic-direction;
      description "Direction";
    }
    leaf port-level {
      type boolean;
      description "Port level mirroring";
    }
    leaf is-acl-enabled {
      type boolean;
      description "ACL enabled";
    }
    leaf mirror-bytes {
      type Optional-value;
      units "byte";
      description "Number of bytes to mirror";
    }
    leaf mirror-interval {
      type Mirror-interval;
      description "Interval between mirrored packets";
    }
  }

  grouping IPV6-NEXT-HOP-DESTINATION-ID {
    description "IPv6 next-hop destination ID";
    leaf ipv6-address {
      type inet:ipv6-address;
      description "IPv6 address";
    }
    leaf vrf-name {
      type string;
      description "VRF";
    }
  }

  grouping IPV4-NEXT-HOP-DESTINATION-ID {
    description "IPv4 next-hop destination ID";
    leaf ipv4-address {
      type inet:ipv4-address;
      description "IPv4 address";
    }
    leaf vrf-name {
      type string;
      description "VRF";
    }
  }

  grouping DESTINATION-ID {
    description "Destination ID";

    container ipv4-address-and-vrf {
      when "../destination-class = 'next-hop-ipv4-class'" {
        description "../DestinationClass = 'NextHopIPv4Class'";
      }
      description "IPv4 address";
      uses IPV4-NEXT-HOP-DESTINATION-ID;
    }

    container ipv6-address-and-vrf {
      when "../destination-class = 'next-hop-ipv6-class'" {
        description "../DestinationClass = 'NextHopIPv6Class'";
      }
      description "IPv6 address";
      uses IPV6-NEXT-HOP-DESTINATION-ID;
    }
    leaf destination-class {
      type Destination-class;
      description "DestinationClass";
    }
    leaf interface {
      when "../destination-class = 'interface-class'" {
        description "../DestinationClass = 'InterfaceClass'";
      }
      type xr:Interface-name;
      description "Interface Handle";
    }
    leaf pseudowire-id {
      when "../destination-class = 'pseudowire-class'" {
        description "../DestinationClass = 'PseudowireClass'";
      }
      type Optional-value;
      description "Pseudowire XCID";
    }
    leaf invalid-value {
      when "../destination-class != 'interface-class' and"+
        " ../destination-class != 'pseudowire-class' and"+
        " ../destination-class != 'next-hop-ipv4-class' and"+
        " ../destination-class != 'next-hop-ipv6-class'" {
          description
            "../DestinationClass != 'InterfaceClass' and .
            ./DestinationClass != 'PseudowireClass' and .
            ./DestinationClass != 'NextHopIPv4Class' and .
            ./DestinationClass != 'NextHopIPv6Class'";
      }
      type Optional-value;
      description "Invalid Parameter";
    }
  }
}
