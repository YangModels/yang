submodule Cisco-IOS-XR-ipv6-traceroute-act {
  belongs-to Cisco-IOS-XR-traceroute-act {
    prefix traceroute-act;
  }

  import cisco-semver {
    prefix semver;
  }
  include Cisco-IOS-XR-ipv4-traceroute-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR IPv6 traceroute action package configuration.
     
     Copyright (c) 2016-2019, 2021-2022 by Cisco Systems, Inc.
     All rights reserved.";

  revision 2022-12-06 {
    description
      "Additional leaves for google_b4_traceroute";
    semver:module-version "2.0.0";
  }
  revision 2021-03-05 {
    description
      "Removed support for use-srv6-op-sid";
    semver:module-version "2.0.0";
  }
  revision 2019-10-01 {
    description
      "Made changes to be RFC6087 compliant";
    semver:module-version "1.1.0";
  }
  revision 2019-04-05 {
    description
      "Establish semantic version baseline.";
    semver:module-version "1.0.0";
  }
  revision 2016-09-17 {
    description
      "IOS XR 6.2.1 revision.";
  }

  grouping IPV6-SPECIFIC-OPTIONS {
    description
      "IPv6 specific options";
    leaf priority {
      type uint16 {
        range "0..15";
      }
      description
        "Priority of hte packet";
    }
    leaf outgoing-interface {
      type string;
      description
        "Outgoing interface, needed in case of traceroute to link local address";
    }
    leaf flowlabel {
      type uint32 {
        range "0..1048575";
      }
      description
        "Flowlabel of hte packet";
    }
  }

  grouping IPV6-TRACEROUTE-INPUT {
    description
      "IPv6 traceroute input";
    uses TRACEROUTE-OPTIONS;
    uses IPV6-SPECIFIC-OPTIONS;
  }
}
