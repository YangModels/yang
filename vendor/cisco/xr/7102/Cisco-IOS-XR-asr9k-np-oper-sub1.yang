submodule Cisco-IOS-XR-asr9k-np-oper-sub1 {
  belongs-to Cisco-IOS-XR-asr9k-np-oper {
    prefix Cisco-IOS-XR-asr9k-np-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-np package operational data.
     
     Copyright (c) 2013-2023 by Cisco Systems, Inc.
     All rights reserved.";

  revision 2023-03-14 {
    description
      "add support for NP soft-errors
       2023-03-10
         add support for NP Punt-path-counters
       2023-03-03
         add support for NP fabric-counters
       2023-02-13
         add support for NP interlaken interface status
       2023-01-23
         add support for NP interrupts
       2023-01-09
         add support for NP summary
       2021-12-18
         add support for NP resources";
    semver:module-version "1.2.0";
  }
  revision 2021-05-26 {
    description
      "add support for NP ucode counter query by index";
    semver:module-version "1.1.0";
  }
  revision 2021-04-23 {
    description
      "add/update sh controllers np portmap for xml support";
    semver:module-version "1.0.0";
  }
  revision 2020-12-21 {
    description
      "add/update sh controllers np valid-port-groups";
  }
  revision 2019-10-29 {
    description
      "Add more specific descriptions to address Good description issue";
  }
  revision 2019-04-05 {
    description
      "Establish semantic version baseline.";
  }
  revision 2015-11-09 {
    description
      "IOS XR 6.0 revision.";
  }

  typedef Lc {
    type enumeration {
      enum "tomahawk" {
        value 1;
        description
          "tomahawk";
      }
      enum "light-speed" {
        value 2;
        description
          "light speed";
      }
    }
    description
      "List of different LC Types";
  }

  grouping PRM-NP-PUNT-CNT {
    description
      "NP Punt Path Counters";
    leaf npu-id {
      type int32;
      description
        "NPU ID";
    }
    leaf host-interface {
      type string;
      description
        "HOST Interface ID";
    }
    leaf if-cnt-rx-byte {
      type string;
      description
        "IF CNT RX BYTE";
    }
    leaf if-cnt-rx-frm {
      type string;
      description
        "IF CNT RX FRM";
    }
    leaf if-cnt-rx-frm-unicast {
      type string;
      description
        "IF CNT RX FRM UNICAST";
    }
    leaf if-cnt-rx-frm-multicast {
      type string;
      description
        "IF CNT RX FRM MULTICAST";
    }
    leaf if-cnt-rx-frm-broadcast {
      type string;
      description
        "IF CNT RX FRM BROADCAST";
    }
    leaf if-cnt-rx-frm-control {
      type string;
      description
        "IF CNT RX FRM CONTROL";
    }
    leaf if-cnt-rx-frm-pause {
      type string;
      description
        "IF CNT RX FRM PAUSE";
    }
    leaf if-cnt-rx-frm-priority-control {
      type string;
      description
        "IF CNT RX FRM PRIORITY CONTROL";
    }
    leaf if-cnt-rx-frm-efa-control {
      type string;
      description
        "IF CNT RX FRM EFA CONTROL";
    }
    leaf if-cnt-rx-frm-fcs-err {
      type string;
      description
        "IF CNT RX FRM FCS ERR";
    }
    leaf if-cnt-rx-frm-length-err {
      type string;
      description
        "IF CNT RX FRM LENGTH ERR";
    }
    leaf if-cnt-rx-frm-code-err {
      type string;
      description
        "IF CNT RX FRM CODE ERR";
    }
    leaf if-cnt-rx-frm-under-size-go-od {
      type string;
      description
        "IF CNT RX FRM UNDERSIZE GOOD";
    }
    leaf if-cnt-rx-frm-under-size-bad {
      type string;
      description
        "IF CNT RX FRM UNDERSIZE BAD";
    }
    leaf if-cnt-rx-frm-64 {
      type string;
      description
        "IF CNT RX FRM 64";
    }
    leaf if-cnt-rx-frm-65-127 {
      type string;
      description
        "IF CNT RX FRM 65 127";
    }
    leaf if-cnt-rx-frm-128-255 {
      type string;
      description
        "IF CNT RX FRM 128 255";
    }
    leaf if-cnt-rx-frm-256-511 {
      type string;
      description
        "IF CNT RX FRM 256 511";
    }
    leaf if-cnt-rx-frm-512-1023 {
      type string;
      description
        "IF CNT RX FRM 512 1023";
    }
    leaf if-cnt-rx-frm-1024-1518 {
      type string;
      description
        "IF CNT RX FRM 1024 1518";
    }
    leaf if-cnt-rx-frm-1519-1522 {
      type string;
      description
        "IF CNT RX FRM 1519 1522";
    }
    leaf if-cnt-rx-frm-1523-2047 {
      type string;
      description
        "IF CNT RX FRM 1523 2047";
    }
    leaf if-cnt-rx-frm-2048-4095 {
      type string;
      description
        "IF CNT RX FRM 2048 4095";
    }
    leaf if-cnt-rx-frm-4096-8191 {
      type string;
      description
        "IF CNT RX FRM 4096 8191";
    }
    leaf if-cnt-rx-frm-8192-max {
      type string;
      description
        "IF CNT RX FRM 8192 MAX";
    }
    leaf if-cnt-rx-frm-exceed-max-go-od {
      type string;
      description
        "IF CNT RX FRM EXCEED MAX GOOD";
    }
    leaf if-cnt-rx-frm-exceed-max-bad {
      type string;
      description
        "IF CNT RX FRM EXCEED MAX BAD";
    }
    leaf if-cnt-rx-frm-over-size-go-od {
      type string;
      description
        "IF CNT RX FRM OVERSIZE GOOD";
    }
    leaf if-cnt-rx-frm-over-size-bad {
      type string;
      description
        "IF CNT RX FRM OVERSIZE BAD";
    }
    leaf if-cnt-tx-byte {
      type string;
      description
        "IF CNT TX BYTE";
    }
    leaf if-cnt-tx-frm {
      type string;
      description
        "IF CNT TX FRM";
    }
    leaf if-cnt-tx-frm-unicast {
      type string;
      description
        "IF CNT TX FRM UNICAST";
    }
    leaf if-cnt-tx-frm-multicast {
      type string;
      description
        "IF CNT TX FRM MULTICAST";
    }
    leaf if-cnt-tx-frm-broadcast {
      type string;
      description
        "IF CNT TX FRM BROADCAST";
    }
    leaf if-cnt-tx-frm-control {
      type string;
      description
        "IF CNT TX FRM CONTROL";
    }
    leaf if-cnt-tx-frm-pause {
      type string;
      description
        "IF CNT TX FRM PAUSE";
    }
    leaf if-cnt-tx-frm-priority-control {
      type string;
      description
        "IF CNT TX FRM PRIORITY CONTROL";
    }
    leaf if-cnt-tx-frm-efa-control {
      type string;
      description
        "IF CNT TX FRM EFA CONTROL";
    }
    leaf if-cnt-tx-frm-fcs-err {
      type string;
      description
        "IF CNT TX FRM FCS ERR";
    }
    leaf if-cnt-tx-frm-length-err {
      type string;
      description
        "IF CNT TX FRM LENGTH ERR";
    }
    leaf if-cnt-tx-frm-code-err {
      type string;
      description
        "IF CNT TX FRM CODE ERR";
    }
    leaf if-cnt-tx-frm-under-size-go-od {
      type string;
      description
        "IF CNT TX FRM UNDERSIZE GOOD";
    }
    leaf if-cnt-tx-frm-under-size-bad {
      type string;
      description
        "IF CNT TX FRM UNDERSIZE BAD";
    }
    leaf if-cnt-tx-frm-64 {
      type string;
      description
        "IF CNT TX FRM 64";
    }
    leaf if-cnt-tx-frm-65-127 {
      type string;
      description
        "IF CNT TX FRM 65 127";
    }
    leaf if-cnt-tx-frm-128-255 {
      type string;
      description
        "IF CNT TX FRM 128 255";
    }
    leaf if-cnt-tx-frm-256-511 {
      type string;
      description
        "IF CNT TX FRM 256 511";
    }
    leaf if-cnt-tx-frm-512-1023 {
      type string;
      description
        "IF CNT TX FRM 512 1023";
    }
    leaf if-cnt-tx-frm-1024-1518 {
      type string;
      description
        "IF CNT TX FRM 1024 1518";
    }
    leaf if-cnt-tx-frm-1519-1522 {
      type string;
      description
        "IF CNT TX FRM 1519 1522";
    }
    leaf if-cnt-tx-frm-1523-2047 {
      type string;
      description
        "IF CNT TX FRM 1523 2047";
    }
    leaf if-cnt-tx-frm-2048-4095 {
      type string;
      description
        "IF CNT TX FRM 2048 4095";
    }
    leaf if-cnt-tx-frm-4096-8191 {
      type string;
      description
        "IF CNT TX FRM 4096 8191";
    }
    leaf if-cnt-tx-frm-8192-max {
      type string;
      description
        "IF CNT TX FRM 8192 MAX";
    }
    leaf if-cnt-tx-frm-exceed-max-go-od {
      type string;
      description
        "IF CNT TX FRM EXCEED MAX GOOD";
    }
    leaf if-cnt-tx-frm-exceed-max-bad {
      type string;
      description
        "IF CNT TX FRM EXCEED MAX BAD";
    }
    leaf if-cnt-tx-frm-over-size-go-od {
      type string;
      description
        "IF CNT TX FRM OVERSIZE GOOD";
    }
    leaf if-cnt-tx-frm-over-size-bad {
      type string;
      description
        "IF CNT TX FRM OVERSIZE BAD";
    }
  }

  grouping PRM-EFD {
    description
      "EFD cos to priority mapping";
    leaf hp-list-is-supported {
      type uint32;
      description
        "high-priority-list CLI is supported";
    }
    leaf burst-absorption {
      type uint32;
      description
        "EFD burst-absorption enabled";
    }
    leaf burst-absorb-applied {
      type uint32;
      description
        "EFD burst-absorption applied";
    }
    leaf burst-absorb-supported {
      type uint32;
      description
        "EFD burst-absorption supported";
    }
    list vlan-cos-mapping {
      max-elements "8";
      description
        "Array of VLAN COS Mapping";
      leaf entry {
        type uint32;
        description
          "Array of VLAN COS Mapping";
      }
    }
    list mplscos-mapping {
      max-elements "8";
      description
        "Array of MPLS COS Mapping";
      leaf entry {
        type uint32;
        description
          "Array of MPLS COS Mapping";
      }
    }
    list ipcos-mapping {
      max-elements "8";
      description
        "Array of IP COS Mapping";
      leaf entry {
        type uint32;
        description
          "Array of IP COS Mapping";
      }
    }
  }

  grouping PRM-NP-FAST-DROP-A {
    description
      "NP fast drop";
    leaf interface-name {
      type string;
      description
        "Name of the NP interface which generates fast
         drop";
    }
    leaf counter-value {
      type uint64;
      description
        "The Value of the counter";
    }
  }

  grouping PRM-NP-FAST-DROP {
    description
      "Array of NP Fast Drop Counters";
    list np-fast-drop {
      description
        "Array of NP Fast Drop Counters";
      uses PRM-NP-FAST-DROP-A;
    }
  }

  grouping PRM-RESOURCES-TCAM-FEATURE {
    description
      "Resources TCAM feature";
    leaf feature-id {
      type string;
      description
        "Feature ID";
    }
    leaf total-vmrids {
      type uint32;
      description
        "Total VMR IDs for feature";
    }
    leaf total-used-entries {
      type uint32;
      description
        "Total entries used by feature";
    }
    leaf total-allocated-entries {
      type uint32;
      description
        "Total entries allocated by feature";
    }
    leaf utilization-percent {
      type uint32;
      units "percentage";
      description
        "Total utilization percentage for feature";
    }
  }

  grouping PRM-NP-INDEX-COUNTER-A {
    description
      "NP Indexed Counter";
    leaf counter-index {
      type uint32;
      description
        "Index of NP counter";
    }
    leaf counter-value {
      type uint64;
      description
        "The accurate value of the counter";
    }
    leaf rate {
      type uint32;
      units "packet/s";
      description
        "Rate in Packets Per Second";
    }
    leaf counter-type {
      type string;
      description
        "Counter TypeDROP: Drop counterPUNT: Punt
         counterFWD:  Forward or generic counterUNKNOWN:
         Counter type unknown";
    }
    leaf counter-name {
      type string;
      description
        "Name of NP counter";
    }
  }

  grouping PRM-NP-INDEXED-COUNTER {
    description
      "NP Counter by counter index";
    container np-indexed-counter {
      description
        "NP Indexed Counter";
      uses PRM-NP-INDEX-COUNTER-A;
    }
  }

  grouping PRM-NP-COUNTERS-A {
    description
      "NP Counters";
    leaf counter-index {
      type uint32;
      description
        "Index of NP counter";
    }
    leaf counter-value {
      type uint64;
      description
        "The accurate value of the counter";
    }
    leaf rate {
      type uint32;
      units "packet/s";
      description
        "Rate in Packets Per Second";
    }
    leaf counter-type {
      type string;
      description
        "Counter Type: DROP: Drop counter PUNT: Punt
         counter FWD:  Forward or generic counter UNKNOWN
         : Counter type unknown";
    }
    leaf counter-name {
      type string;
      description
        "Name of NP counter";
    }
  }

  grouping PRM-NP-COUNTERS {
    description
      "Array of NP Counters";
    list np-counter {
      description
        "Array of NP Counters";
      uses PRM-NP-COUNTERS-A;
    }
  }

  grouping PRM-NP-PROFILE {
    description
      "np profile info";
    leaf scale {
      type string;
      description
        "Scale";
    }
  }

  grouping PRM-NP-L2RM-HW-RSC-TCAM-PAR {
    description
      "NP L2RM TCAM Par info";
    leaf tcam-par {
      type uint32;
      description
        "Index of TCAM partition";
    }
    leaf total {
      type uint32;
      description
        "Number of total TCAM entries";
    }
    leaf free {
      type uint32;
      description
        "Number of free TCAM entries";
    }
  }

  grouping PRM-NP-L2RM-HW-RSC-HASH-BLK {
    description
      "NP L2RM Hash Block info";
    leaf hash-blk {
      type uint32;
      description
        "Index of the L2RM hash block";
    }
    leaf total {
      type uint32;
      description
        "Number of total L2RM hash entries";
    }
    leaf free {
      type uint32;
      description
        "Number of free L2RM hash entries";
    }
  }

  grouping PRM-NP-L2RM-HW-RSC-A {
    description
      "NP L2RM hw_rsc detail";
    list hash-block {
      description
        "Hash Block hw blk";
      uses PRM-NP-L2RM-HW-RSC-HASH-BLK;
    }
    list tcam-partition {
      description
        "TCAM partition per hw blk";
      uses PRM-NP-L2RM-HW-RSC-TCAM-PAR;
    }
  }

  grouping PRM-NP-L2RM-HW-RSC {
    description
      "NP L2RM  hw_rsc";
    container hw-resource {
      description
        "resources per hw blk";
      uses PRM-NP-L2RM-HW-RSC-A;
    }
    leaf ppt-alloc {
      type uint64;
      description
        "Number of the allocated tcam partitions";
    }
    leaf ppt-write {
      type uint64;
      description
        "Number of written partitions";
    }
    leaf ppt-free {
      type uint64;
      description
        "Number of free partitions";
    }
  }

  grouping PRM-NP-ILKN-STS-A {
    description
      "NP Interlaken Interface Entry";
    leaf npu {
      type int32;
      description
        "NPU ID";
    }
    leaf interface-name {
      type string;
      description
        "NP Interface Name";
    }
    leaf interface-status {
      type string;
      description
        "NP Interface Status";
    }
    leaf pll-lock {
      type string;
      description
        "PLL Lock";
    }
    leaf rcv-status {
      type string;
      description
        "Rcv Status";
    }
    leaf pcs-sync {
      type string;
      description
        "PCS Sync";
    }
    leaf pcs-sync-blk {
      type string;
      description
        "PCS Sync Block";
    }
  }

  grouping PRM-NP-ILKN-STS {
    description
      "NP Interlaken Interfaces";
    list intf-entry {
      description
        "Array of NP Interlaken Interfaces";
      uses PRM-NP-ILKN-STS-A;
    }
  }

  grouping TCAM-VMR-ENTRY {
    description
      "Application VMR entry";
    leaf num-vmr-ids {
      type uint32;
      description
        "Vmr IDs";
    }
    leaf num-active-entries {
      type uint32;
      description
        "The number of active vmr entries";
    }
    leaf num-allocated-entries {
      type uint32;
      description
        "The number of active vmr entries";
    }
  }

  grouping ACL-COMM-REGION {
    description
      "acl common region";
    leaf free-entries {
      type uint32;
      description
        "Free entries in the table";
    }
    leaf allocated-entries {
      type uint32;
      description
        "The number of active vmr entries";
    }
  }

  grouping TCAM-ODS-TABLE {
    description
      "tcam ods table";
    container acl-common {
      description
        "ACL common region";
      uses ACL-COMM-REGION;
    }
    container app-id-ifib {
      description
        "App IFIB entry";
      uses TCAM-VMR-ENTRY;
    }
    container app-id-qos {
      description
        "App qos entry";
      uses TCAM-VMR-ENTRY;
    }
    container app-id-acl {
      description
        "App acl entry";
      uses TCAM-VMR-ENTRY;
    }
    container app-id-afmon {
      description
        "App afmon entry";
      uses TCAM-VMR-ENTRY;
    }
    container app-id-li {
      description
        "App LI entry";
      uses TCAM-VMR-ENTRY;
    }
    container app-id-pbr {
      description
        "App PBR entry";
      uses TCAM-VMR-ENTRY;
    }
    container app-id-edpl {
      description
        "App EDPL entry";
      uses TCAM-VMR-ENTRY;
    }
    leaf free-entries {
      type uint32;
      description
        "Free entries in the table";
    }
    leaf reserved-entries {
      type uint32;
      description
        "The number of active vmr entries";
    }
  }

  grouping TCAM-L2-TABLE-A {
    description
      "tcam l2 table";
    leaf partition-id {
      type uint32;
      description
        "PartitionID";
    }
    leaf priority {
      type uint32;
      description
        "The priority of the table";
    }
    leaf valid-entries {
      type uint32;
      description
        "Number of valid TCAM L2 entries";
    }
    leaf free-entries {
      type uint32;
      description
        "Number of free TCAM L2 entries";
    }
  }

  grouping TCAM-SHOW-SUM {
    description
      "tcam summary";
    container tcam-lt-ods2 {
      description
        "TCAM ODS2 partition summary";
      uses TCAM-ODS-TABLE;
    }
    container tcam-lt-ods8 {
      description
        "TCAM ODS8 partition summary";
      uses TCAM-ODS-TABLE;
    }
    list tcam-lt-l2 {
      description
        "Array of TCAM L2 partition summaries";
      uses TCAM-L2-TABLE-A;
    }
  }

  grouping TCAM-VMR-ENTRY-INT {
    description
      "Application VMR entry internal";
    leaf num-vmr-ids {
      type uint32;
      description
        "Vmr IDs";
    }
    leaf total-used-entries {
      type uint32;
      description
        "number of used vmr entries";
    }
    leaf total-allocated-entries {
      type uint32;
      description
        "The number of active vmr entries";
    }
  }

  grouping TCAM-ODS-TABLE-INT {
    description
      "tcam ods table internal";
    container app-id-ifib {
      description
        "App IFIB entry";
      uses TCAM-VMR-ENTRY-INT;
    }
    container app-id-qos {
      description
        "App qos entry";
      uses TCAM-VMR-ENTRY-INT;
    }
    container app-id-acl {
      description
        "App acl entry";
      uses TCAM-VMR-ENTRY-INT;
    }
    container app-id-afmon {
      description
        "App afmon entry";
      uses TCAM-VMR-ENTRY-INT;
    }
    container app-id-li {
      description
        "App LI entry";
      uses TCAM-VMR-ENTRY-INT;
    }
    container app-id-pbr {
      description
        "App PBR entry";
      uses TCAM-VMR-ENTRY-INT;
    }
    container application-edpl-entry {
      description
        "App EDPL entry";
      uses TCAM-VMR-ENTRY-INT;
    }
    leaf max-entries {
      type uint32;
      description
        "Max number of entries for internal tcam ods
         table";
    }
    leaf free-entries {
      type uint32;
      description
        "Number of the entries which are free to use in
         the table";
    }
  }

  grouping TCAM-L2-TABLE-INT-A {
    description
      "tcam l2 table internal";
    leaf partition-id {
      type uint32;
      description
        "PartitionID";
    }
    leaf valid-entries {
      type uint32;
      description
        "Number of valid TCAM entries";
    }
    leaf free-entries {
      type uint32;
      description
        "Number of free TCAM entries";
    }
  }

  grouping TCAM-SHOW-SUM-INT {
    description
      "tcam summary internal";
    container tcam-lt-ods2 {
      description
        "TCAM LT ODS 2 summary";
      uses TCAM-ODS-TABLE-INT;
    }
    container tcam-lt-ods8 {
      description
        "TCAM LT_ODS 8 summary";
      uses TCAM-ODS-TABLE-INT;
    }
    list tcam-lt-l2 {
      description
        "Array of TCAM LT L2 partition summaries";
      uses TCAM-L2-TABLE-INT-A;
    }
  }

  grouping TCAM-INFO-SHOW-SUM {
    description
      "tcam summary info";
    container internal-tcam-info {
      description
        "Internal tcam summary info";
      uses TCAM-SHOW-SUM-INT;
    }
    container tcam-info {
      description
        "External tcam summary info";
      uses TCAM-SHOW-SUM;
    }
  }

  grouping PRM-NP-LOAD {
    description
      "np load info";
    leaf utilization {
      type uint32;
      units "percentage";
      description
        "Percent load on the NP engines";
    }
    leaf packet-per-second-rate {
      type uint32;
      description
        "Packet rate load on NP engines";
    }
  }

  grouping NPU-NP-INTR {
    description
      "NPU NP INTR";
    leaf total-np-interrupts {
      type int32;
      description
        "Total NP Interrupts";
    }
  }

  grouping PRM-SERV-INTR {
    description
      "PRM SERV INTR";
    leaf burst {
      type int32;
      description
        "Burst";
    }
    leaf cs {
      type string;
      description
        "Cause Set";
    }
    leaf msk {
      type string;
      description
        "Mask Set";
    }
    leaf callback {
      type string;
      description
        "Callback Function";
    }
  }

  grouping NP-INTR-LC-TYPE {
    description
      "NP INTR LC TYPE";
    container prm-np-interrupts {
      when "../lc-type = 'tomahawk'" {
        description
          "../Lc_Type = 'TOMAHAWK'";
      }
      description
        "Tomahawk LC NP Interrupts";
      uses PRM-SERV-INTR;
    }
    container npu-server-interrupts {
      when "../lc-type = 'light-speed'" {
        description
          "../Lc_Type = 'LIGHTSPEED'";
      }
      description
        "Lightspeed LC NP Interrupts";
      uses NPU-NP-INTR;
    }
    leaf lc-type {
      type Lc;
      description
        "Lc Type";
    }
  }

  grouping PRM-NP-INTERRUPTS-A {
    description
      "NP Interrupt Entry";
    container lc-type-inf {
      description
        "LC type";
      uses NP-INTR-LC-TYPE;
    }
    leaf npu {
      type int32;
      description
        "NPU ID";
    }
    leaf interrupt-name {
      type string;
      description
        "NP Interrupt Name";
    }
    leaf id {
      type int32;
      description
        "Interrupt Id";
    }
    leaf count {
      type int32;
      description
        "Interrupt Count";
    }
  }

  grouping PRM-NP-INTERRUPTS {
    description
      "NP Interrupts";
    list intrs-entry {
      description
        "Array of NP Interrupts";
      uses PRM-NP-INTERRUPTS-A;
    }
  }

  grouping PRM-NP-FAB-CNT-A {
    description
      "NP Interlaken Interface Entry";
    leaf npu-id {
      type int32;
      description
        "NPU ID";
    }
    leaf fabric-to-bridge-interface-id {
      type int32;
      description
        "Fabric to Bridge Interface ID";
    }
    leaf interlaken-cnt-tx-bytes {
      type string;
      units "byte";
      description
        "INTERLAKEN CNT TX BYTES";
    }
    leaf interlaken-cnt-tx-frm-go-od {
      type string;
      description
        "INTERLAKEN CNT TX FRM GOOD";
    }
    leaf interlaken-cnt-tx-frm-bad {
      type string;
      description
        "INTERLAKEN CNT TX FRM BAD";
    }
    leaf interlaken-cnt-rx-bytes {
      type string;
      units "byte";
      description
        "INTERLAKEN CNT RX BYTES";
    }
    leaf interlaken-cnt-rx-frm-go-od {
      type string;
      description
        "INTERLAKEN CNT RX FRM GOOD";
    }
    leaf interlaken-cnt-rx-frm-bad {
      type string;
      description
        "INTERLAKEN CNT RX FRM BAD";
    }
    leaf interlaken-cnt-rx-burst-crc32-error {
      type string;
      description
        "INTERLAKEN CNT RX BURST CRC32 ERROR";
    }
    leaf interlaken-cnt-rx-burst-crc24-error {
      type string;
      description
        "INTERLAKEN CNT RX BURST CRC24 ERROR";
    }
    leaf interlaken-cnt-rx-burst-size-error {
      type string;
      description
        "INTERLAKEN CNT RX BURST SIZE ERROR";
    }
  }

  grouping PRM-NP-FAB-CNT {
    description
      "NP Fabric Counters";
    list fabric-intferface-counter {
      description
        "Array of NP Interlaken Interfaces";
      uses PRM-NP-FAB-CNT-A;
    }
  }

  grouping NPU-SERV-SUM {
    description
      "NPU SERV SUM";
    leaf hw-rev {
      type int32;
      description
        "HW Revision";
    }
    leaf rdl-version {
      type uint32;
      description
        "RDL Version";
    }
    leaf vendor-id {
      type uint32;
      description
        "Vendor ID";
    }
    leaf device-id {
      type uint32;
      description
        "Device ID";
    }
    leaf np-clock-frequency {
      type string;
      description
        "NP Clock freqency";
    }
    leaf hbm-frequency {
      type string;
      description
        "HBM freqency";
    }
    leaf np-reset-threshold {
      type string;
      description
        "NP Reset Threshold";
    }
    leaf np-reset-action {
      type string;
      description
        "NP Reset Action";
    }
    leaf np-reset-logging {
      type string;
      description
        "NP Reset Logging";
    }
    leaf location {
      type string;
      description
        "NP Location String";
    }
    leaf pon-reset {
      type int32;
      description
        "PON Reset";
    }
    leaf hard-reset {
      type int32;
      description
        "Hard Reset";
    }
    leaf details {
      type string;
      description
        "NP Details";
    }
  }

  grouping PRM-NP-SUM {
    description
      "PRM NP SUM";
    leaf hardware-revision {
      type string;
      description
        "Hardware Revision";
    }
    leaf np-core-frequency {
      type string;
      description
        "NP core frequency";
    }
    leaf ddr-frequency {
      type string;
      description
        "DDR frequency";
    }
    leaf driver-version {
      type string;
      description
        "Driver Version";
    }
  }

  grouping NP-SUM-LC-TYPE {
    description
      "NP SUM LC TYPE";
    container prm-np-summary {
      when "../lc-type = 'tomahawk'" {
        description
          "../Lc_Type = 'TOMAHAWK'";
      }
      description
        "Tomahawk LC NP Summary";
      uses PRM-NP-SUM;
    }
    container npu-server-summary {
      when "../lc-type = 'light-speed'" {
        description
          "../Lc_Type = 'LIGHTSPEED'";
      }
      description
        "Lightspeed LC NP Summary";
      uses NPU-SERV-SUM;
    }
    leaf lc-type {
      type Lc;
      description
        "Lc Type";
    }
  }

  grouping PRM-NP-SUMMARY {
    description
      "NP Summary Entry";
    container lc-type-inf {
      description
        "LC type";
      uses NP-SUM-LC-TYPE;
    }
    leaf total-n-ps {
      type int32;
      description
        "Total NPs";
    }
    leaf np-instance {
      type int32;
      description
        "NP Instance";
    }
    leaf np-state {
      type string;
      description
        "NP State";
    }
    leaf ucode-version {
      type string;
      description
        "Ucode Build Version";
    }
  }

  grouping PRM-NP-CHN-LOAD-A {
    description
      "NP Channel load counters";
    leaf flow-ctr-counter {
      type uint32;
      description
        "Counters of NP flow control";
    }
    leaf avg-rfd-usage {
      type uint32;
      description
        "Average RFD Usage";
    }
    leaf peak-rfd-usage {
      type uint32;
      description
        "Peak RFD Usage";
    }
    leaf avg-guar-rfd-usage {
      type uint32;
      description
        "Average of guaranteed RFD usage";
    }
    leaf peak-guar-rfd-usage {
      type uint32;
      description
        "Peak of guaranteed RFD usage";
    }
    leaf interface-name {
      type string;
      description
        "Name of the interface to show the np load
         counter";
    }
  }

  grouping PRM-NP-CHN-LOAD {
    description
      "Array of NP Channel load counters";
    list np-chn-load {
      description
        "Array of NP Channel load counters";
      uses PRM-NP-CHN-LOAD-A;
    }
  }

  grouping TCAM-VMR-ENTRY-ID {
    description
      "Feature VMR entry";
    leaf vmr-id {
      type uint32;
      description
        "Vmr ID";
    }
    leaf used-entries {
      type uint32;
      description
        "The number of used vmr entries";
    }
    leaf allocated-entries {
      type uint32;
      description
        "The number of active vmr entries";
    }
  }

  grouping TCAM-FEATURE-ENTRY {
    description
      "tcam feature info";
    leaf feature-id {
      type string;
      description
        "Feature ID";
    }
    leaf num-vmr-ids {
      type uint32;
      description
        "Number of VRM IDs";
    }
    leaf total-used-entries {
      type uint32;
      description
        "Number of used VMR entries";
    }
    leaf total-allocated-entries {
      type uint32;
      description
        "Total number of allocated VMR entries";
    }
    list vmr-entry {
      description
        "VMR entries";
      uses TCAM-VMR-ENTRY-ID;
    }
  }

  grouping TCAM-REGION-TABLE-INT {
    description
      "tcam table internal region";
    leaf region-name {
      type string;
      description
        "Name of TCAM region";
    }
    leaf allocated-blocks {
      type uint32;
      description
        "Number of allocated TCAM blocks";
    }
    leaf max-entries {
      type uint32;
      description
        "Max number of TCAM entries";
    }
    leaf free-entries {
      type uint32;
      description
        "Number of free TCAM entries";
    }
    list feature {
      description
        "Features of the TCAM region";
      uses TCAM-FEATURE-ENTRY;
    }
  }

  grouping TCAM-SHOW-SUM-INT-REGION {
    description
      "tcam summary internal region";
    leaf total-blocks {
      type uint32;
      description
        "Total TCAM blocks";
    }
    leaf free-blocks {
      type uint32;
      description
        "Free TCAM blocks";
    }
    list tcam-region {
      description
        "TCAM Regions";
      uses TCAM-REGION-TABLE-INT;
    }
  }

  grouping TCAM-INFO-SHOW-SUM-REGION {
    description
      "tcam info summary region";
    container internal-tcam-info {
      description
        "Internal tcam summary info";
      uses TCAM-SHOW-SUM-INT-REGION;
    }
  }

  grouping PRM-NP-PORTS-A {
    description
      "NP Ports Entry";
    leaf np-inst {
      type uint32;
      description
        "NP instance";
    }
    leaf fia {
      type uint32;
      description
        "Fia";
    }
    leaf ports {
      type string;
      description
        "Name of the ports";
    }
  }

  grouping PRM-NP-PORTS {
    description
      "NP Ports";
    list ports-entry {
      description
        "Array of NP Port Maps";
      uses PRM-NP-PORTS-A;
    }
  }

  grouping PRM-NP-PORTMAP-A {
    description
      "NP Port Map Entry";
    leaf np-inst {
      type uint32;
      description
        "NP instance";
    }
    leaf physical-port-num {
      type uint32;
      description
        "physical port number";
    }
    leaf interface-name {
      type string;
      description
        "Name of the interface";
    }
    leaf mapped-src-port {
      type uint32;
      description
        "mapped source port";
    }
  }

  grouping PRM-NP-PORTMAP {
    description
      "NP Port Map";
    list portmap-entry {
      description
        "Array of NP Port Map Entry";
      uses PRM-NP-PORTMAP-A;
    }
  }

  grouping PRM-NP-UIDB-A {
    description
      "NP uidb";
    leaf interface-name {
      type string;
      description
        "Name of the interface which UIDB serves";
    }
    leaf interface-handle {
      type uint32;
      description
        "Handle of the interface which UIDB serves";
    }
    leaf index {
      type uint16;
      description
        "UIDB Index";
    }
    leaf interface-type {
      type string;
      description
        "Type of the interface which UIDB serves";
    }
  }

  grouping PRM-NP-UIDB {
    description
      "Array of NP UIDB Index";
    list uidb-index {
      description
        "Array of NP UIDB Index";
      uses PRM-NP-UIDB-A;
    }
  }

  grouping PRM-NP-SOFT-ERR-A {
    description
      "NP Soft Errors";
    leaf npu {
      type int32;
      description
        "NPU ID";
    }
    leaf block-number {
      type int32;
      description
        "Block Number";
    }
    leaf block-name {
      type string;
      description
        "Block Name";
    }
    leaf ignored {
      type int32;
      description
        "Ignored";
    }
    leaf fixed {
      type int32;
      description
        "Fixed";
    }
    leaf sticky {
      type int32;
      description
        "Sticky";
    }
    leaf reset {
      type int32;
      description
        "Reset";
    }
    leaf fast-reset {
      type int32;
      description
        "Fast Reset";
    }
  }

  grouping PRM-NP-SOFT-ERR {
    description
      "NP Blocks";
    list np-block {
      description
        "Array of NP Blocks";
      uses PRM-NP-SOFT-ERR-A;
    }
  }

  grouping PRM-MAC-CFGMODE-A {
    description
      "MAC Cfgmode Entry";
    leaf flags {
      type uint32;
      description
        "flag for show header";
    }
    leaf str-len {
      type int32;
      description
        "actual show_str length";
    }
    leaf show-str {
      type string {
        length "0..2000";
      }
      description
        "one cfgmode display string";
    }
  }

  grouping PRM-MAC-CFGMODE {
    description
      "MAC Config Modes";
    list cfg-entry {
      description
        "Array of MAC CFG Entry";
      uses PRM-MAC-CFGMODE-A;
    }
  }
}
