submodule Cisco-IOS-XR-tunnel-nve-oper-sub1 {
  belongs-to Cisco-IOS-XR-tunnel-nve-oper {
    prefix Cisco-IOS-XR-tunnel-nve-oper;
  }

  import ietf-inet-types {
    prefix inet;
  }
  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tunnel-nve package operational data.
     
     Copyright (c) 2013-2023 by Cisco Systems, Inc.
     All rights reserved.";

  revision 2023-08-01 {
    description
      "Added a new capabilities in nve platform capability
       2022-10-08
         Added support for viewing platform capability details.
       2022-09-08
         global: Added vxlan-interfaceless-l3vni-bringup indication.
       2022-09-08
         global: Added system mac information.
       2022-02-25
         Added member-vni table with extended keys to complement vni
       2022-02-08
         Added support for show nve vrf
       2022-01-28
         Added nve-interface IPv6 support";
    semver:module-version "1.1.0";
  }
  revision 2019-04-05 {
    description
      "Establish semantic version baseline.";
    semver:module-version "1.0.1";
  }
  revision 2015-11-09 {
    description
      "IOS XR 6.0 revision.";
  }

  grouping NVE-SHOW-NVE-INTF-BD {
    description
      "NVE Interface Information";
    container v4-add-ltep {
      description
        "v4 publish time";
      uses NVE-TIMESPEC;
    }
    container v4-del-ltep {
      description
        "v4 unpublish time";
      uses NVE-TIMESPEC;
    }
    container v6-add-ltep {
      description
        "v6 publish time";
      uses NVE-TIMESPEC;
    }
    container v6-del-ltep {
      description
        "v6 unpublish time";
      uses NVE-TIMESPEC;
    }
    leaf interface-name-xr {
      type string;
      description
        "Interface name";
    }
    leaf state {
      type int8;
      description
        "State";
    }
    leaf admin-state {
      type int8;
      description
        "Admin State";
    }
    leaf flags {
      type uint32;
      description
        "Flags";
    }
    leaf encap {
      type int8;
      description
        "Encap";
    }
    leaf source-interface-name {
      type string;
      description
        "Source Interface name";
    }
    leaf source-ipv4-address {
      type inet:ipv4-address;
      description
        "Source IPv4 Address";
    }
    leaf source-ipv6-address {
      type inet:ipv6-address;
      description
        "Source IPv6 Address";
    }
    leaf if-handle {
      type uint64;
      description
        "NVE IfHandle";
    }
    leaf source-state {
      type int8;
      description
        "Source Intf State";
    }
    leaf udp-port {
      type uint32;
      description
        "UDP Port";
    }
    leaf any-cast-source-interface-name {
      type string;
      description
        "Anycast Source Interface name";
    }
    leaf any-cast-source-ipv4-address {
      type inet:ipv4-address;
      description
        "Anycast Source IPv4 Address";
    }
    leaf any-cast-source-state {
      type int8;
      description
        "Anycast Source Interface State";
    }
    leaf sync-mcast-ipv4-address {
      type inet:ipv4-address;
      description
        "MCAST sync group IPv4 Address";
    }
    leaf sync-mcast-flags {
      type uint32;
      description
        "Sync McastFlags";
    }
    leaf peer-ip-lkup-disable {
      type boolean;
      description
        "Peer IP Lookup Disable";
    }
  }

  grouping NVE-GLOBAL {
    description
      "NVE global data";
    leaf vni-scope-local {
      type boolean;
      description
        "VNI Local Scope";
    }
    leaf vxlan-src-port-msb {
      type uint32;
      description
        "VxLAN udp src port msb";
    }
    leaf vxlan-dst-port {
      type uint32;
      description
        "VxLAN dst udp port";
    }
    leaf interface-mpls-o-udp-encap-count {
      type uint32;
      description
        "NVE interfaces with MPLSoUDP encap";
    }
    leaf vxlan-interfaceless-l3vni-bringup {
      type boolean;
      description
        "VxLAN interfaceless l3vni bringup";
    }
    leaf system-mac {
      type yang:mac-address;
      description
        "Global System MAC";
    }
  }

  grouping NVE-PDCAP {
    description
      "NVE System Capabilities";
    leaf max-system-mpls-o-udp {
      type uint32;
      description
        "Max NVE interfaces with MPLSoUDP encap";
    }
    leaf v6-supported {
      type boolean;
      description
        "Is v6 supported";
    }
    leaf global-nve-decap-list {
      type boolean;
      description
        "Is global nve decap list supported";
    }
    leaf global-nve-ud-pport-src-msb {
      type boolean;
      description
        "Is global nve udp port src supported";
    }
    leaf global-nve-ud-pport-dest {
      type boolean;
      description
        "Is global nve udp port dest supported";
    }
    leaf global-nve-per-vrf-policer-rate-support {
      type boolean;
      description
        "Is global nve per VRF policer rate supported";
    }
    leaf peer-ip-lkup-disable {
      type boolean;
      description
        "Peer IP Lookup Disable Support";
    }
    leaf vni-mcast-support {
      type boolean;
      description
        "Is vni mcast config supported";
    }
    leaf vni-hr-bgp {
      type boolean;
      description
        "Is host-reachability proto bgp supported";
    }
    leaf nve-ir-support {
      type boolean;
      description
        "Is nve ingress-replication config supported";
    }
  }

  grouping NVE-PARENT-VNI-BR {
    description
      "Parent vni brief information";
    leaf vni {
      type uint32;
      description
        "VNI Number";
    }
    leaf nve-num {
      type uint32;
      description
        "NVE Interface number";
    }
  }

  grouping NVE-AF-INFO {
    description
      "Vrf afi specific information";
    leaf table-id {
      type uint32;
      description
        "Vrf Table ID";
    }
  }

  grouping NVE-SHOW-VRF {
    description
      "VRF Information";
    leaf vrf-name {
      type string;
      description
        "L3 VRF Name";
    }
    leaf vrf-id {
      type uint64;
      description
        "vrf id";
    }
    leaf policer-rate {
      type uint32;
      description
        "Policer rate";
    }
    leaf policer-rate-unit {
      type uint8;
      description
        "Policer rate unit";
    }
    list af-info {
      description
        "AF info";
      uses NVE-AF-INFO;
    }
    list vni-info {
      description
        "Brief Vni Info";
      uses NVE-PARENT-VNI-BR;
    }
  }

  grouping NVE-TIMESPEC {
    description
      "NVE TIMESPEC";
    leaf seconds {
      type uint64;
      description
        "Seconds";
    }
    leaf nanoseconds {
      type uint64;
      description
        "Nanoseconds";
    }
  }

  grouping NVE-SHOW-VNI-BD {
    description
      "VNI Information";
    container v4-add-ltep {
      description
        "v4 publish time";
      uses NVE-TIMESPEC;
    }
    container v4-del-ltep {
      description
        "v4 unpublish time";
      uses NVE-TIMESPEC;
    }
    container v6-add-ltep {
      description
        "v6 publish time";
      uses NVE-TIMESPEC;
    }
    container v6-del-ltep {
      description
        "v6 unpublish time";
      uses NVE-TIMESPEC;
    }
    leaf interface-name {
      type string;
      description
        "NVE Interface name";
    }
    leaf vni-xr {
      type uint32;
      description
        "VNI Number";
    }
    leaf state {
      type int8;
      description
        "State";
    }
    leaf mcast-ipv4-address {
      type inet:ipv4-address;
      description
        "MCAST IPv4 Address";
    }
    leaf flags {
      type uint32;
      description
        "Flags";
    }
    leaf vni-min {
      type uint32;
      description
        "VNI Min in Range";
    }
    leaf vni-max {
      type uint32;
      description
        "VNI Max in Range";
    }
    leaf mcast-flags {
      type uint32;
      description
        "McastFlags";
    }
    leaf udp-port {
      type uint32;
      description
        "UDP Port";
    }
    leaf bvi-ifh {
      type uint32;
      description
        "BVI Interface Handle";
    }
    leaf bvi-state {
      type uint8;
      description
        "BVI Interface Oper State";
    }
    leaf bvi-mac {
      type yang:hex-string;
      description
        "BVI MAC address";
    }
    leaf vrf-name {
      type string;
      description
        "L3 VRF Name";
    }
    leaf vrf-id {
      type uint32;
      description
        "L3 VRF ID";
    }
    leaf ipv4-tbl-id {
      type uint32;
      description
        "IPv4 Table ID";
    }
    leaf ipv6-tbl-id {
      type uint32;
      description
        "IPv6 Table ID";
    }
    leaf vrf-vni {
      type uint32;
      description
        "VRF VNI";
    }
    leaf topo-valid {
      type boolean;
      description
        "TOPO ID valid flag";
    }
    leaf topo-id {
      type uint32;
      description
        "L2RIB Topology ID";
    }
    leaf topo-name {
      type string {
        length "0..50";
      }
      description
        "L2RIB Topology Name";
    }
  }
}
