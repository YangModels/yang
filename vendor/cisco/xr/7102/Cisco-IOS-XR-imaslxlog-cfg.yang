module Cisco-IOS-XR-imaslxlog-cfg {
  namespace "http://cisco.com/ns/yang/Cisco-IOS-XR-imaslxlog-cfg";
  prefix imaslxlog-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR imaslxlog package configuration.
     
     This module contains definitions
     for the following management objects:
       imaslxlog-global: IMA SLX Logger configuration
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container imaslxlog-global {
    description
      "IMA SLX Logger configuration";
    leaf reduce-severity {
      type empty;
      description
        "Reduce SELinux syslog severity level.";
    }
  }
}
