module Cisco-IOS-XR-ncs1001-esd-cfg {
  namespace "http://cisco.com/ns/yang/Cisco-IOS-XR-ncs1001-esd-cfg";
  prefix ncs1001-esd-cfg;

  import Cisco-IOS-XR-config-mda-cfg {
    prefix node;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-esd package configuration.
     
     This YANG module augments the
       Cisco-IOS-XR-config-mda-cfg
     module with configuration data.
     
     Copyright (c) 2013-2023 by Cisco Systems, Inc.
     All rights reserved.";

  revision 2023-04-20 {
    description
      "added Cisco-IOS-XR-config-mda-cfg IosSetYangSchemaRev Cisco-IOS-XR-ncs1001-esd-cfg";
    semver:module-version "1.0.0";
  }
  revision 2019-04-05 {
    description
      "Establish semantic version baseline.";
  }
  revision 2015-11-09 {
    description
      "IOS XR 6.0 revision.";
  }

  typedef Eth-switch-port {
    type enumeration {
      enum "sfp-udc3" {
        value 0;
        description
          "SFP  slot 3 port    ( 0)";
      }
      enum "sfp-udc2" {
        value 4;
        description
          "SFP  slot 2 port    ( 4)";
      }
      enum "sfp-udc1" {
        value 8;
        description
          "SFP  slot 1 port    ( 8)";
      }
      enum "rj45-udc1" {
        value 12;
        description
          "UDC1 port           (12)";
      }
      enum "rj45-udc2" {
        value 16;
        description
          "UDC2 port           (16)";
      }
      enum "rj45-udc3" {
        value 20;
        description
          "UDC3 port           (20)";
      }
      enum "cpu-mgmt" {
        value 24;
        description
          "CPU side Mgmt ports (24)";
      }
      enum "rj45-mgmt" {
        value 26;
        description
          "RJ45 Mgmt port      (26)";
      }
      enum "sfp-mgmt" {
        value 27;
        description
          "SFP  Mgmt port      (27)";
      }
    }
    description
      "Eth switch port";
  }

  grouping NODE-CFG {
    description
      "active/preconfigured nodes configuration";
    container eth-switch {
      description
        "Ethernet switch Config";
      list port {
        key "port";
        description
          "Port Id";
        leaf enable-loopback {
          type empty;
          description
            "enable internal loopback";
        }
        leaf enable-clear-on-read {
          type empty;
          description
            "clear on read enabled";
        }
        leaf disable {
          type empty;
          description
            "disable port";
        }
        leaf port {
          type Eth-switch-port;
          description
            "Set port";
        }
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
