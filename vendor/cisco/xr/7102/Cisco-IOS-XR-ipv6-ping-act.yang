submodule Cisco-IOS-XR-ipv6-ping-act {
  belongs-to Cisco-IOS-XR-ping-act {
    prefix ping-act;
  }

  import cisco-semver {
    prefix semver;
  }
  include Cisco-IOS-XR-ipv4-ping-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR IPv6 ping action package configuration.
     
     Copyright (c) 2016-2019, 2021-2023 by Cisco Systems, Inc.
     All rights reserved.";

  revision 2023-09-13 {
    description
      "Corrected grouping for ping response.
       2022-08-11
         Addition of new leaves.";
    semver:module-version "3.0.0";
  }
  revision 2021-03-05 {
    description
      "Removed support for use-srv6-op-sid";
    semver:module-version "2.0.0";
  }
  revision 2019-10-01 {
    description
      "Made changes to be RFC6087 compliant";
    semver:module-version "1.1.0";
  }
  revision 2019-04-05 {
    description
      "Establish semantic version baseline.";
    semver:module-version "1.0.0";
  }
  revision 2018-11-28 {
    description
      "IOS XR 7.0.1 revision.";
  }
  revision 2016-09-13 {
    description
      "IOS XR 6.2.1 revision.";
  }

  grouping IPV6-SPECIFIC-OPTIONS {
    description
      "IPv6 specific options";
    leaf priority {
      type uint8 {
        range "0..15";
      }
      description
        "Priority of the packet";
    }
    leaf outgoing-interface {
      type string;
      description
        "Outgoing interface, needed in case of ping to link local address";
    }
    container flowlabel {
      description
        "Flowlabel value or flowlabel random,
         if both are given then flowabel value is chosen.";
      leaf value {
        type uint32 {
          range "0..1048575";
        }
        description
          "Flowlabel of the packet";
      }
      leaf random {
        type empty;
        description
          "Random flowlabel value of the packet,
           repeats after every 5 packets";
      }
    }
  }

  grouping IPV6-PING-INPUT {
    description
      "IPv6 ping input";
    uses PING-OPTIONS;
    uses IPV6-SPECIFIC-OPTIONS;
    leaf vrf-name {
      type string;
      description
        "VRF name";
    }
  }

  grouping IPV6-PING-OUTPUT {
    description
      "IPv6 ping output";
    uses PING-OPTIONS;
    leaf sweep-min {
      type uint32;
      description
        "Minimum value of sweep size";
    }
    leaf sweep-max {
      type uint64;
      description
        "Maximum value of sweep size";
    }
    leaf rotate-pattern {
      type boolean;
      description
        "Rotate Pattern is enabled";
    }
    container replies {
      description
        "IPv6 ping replies";
      list reply {
        key "reply-index";
        description
          "IPv6 ping reply";
        leaf reply-index {
          type uint64 {
            range "1..2147483647";
          }
          description
            "Index of the reply list";
        }
        leaf result {
          type string;
          description
            "Response for each packet";
        }
        leaf reply-source {
          type string;
          description
            "Source of each response packet";
        }
        leaf time {
          type uint64 {
            range "1..2147483647";
          }
          description
            "Time taken to receive each response packet in nanoseconds";
        }
        leaf ttl {
          type uint64 {
            range "1..2147483647";
          }
          description
            "TTL value for each packet";
        }
        leaf bytes {
          type uint64 {
            range "1..2147483647";
          }
          description
            "Number of bytes for each packet";
        }
      }
    }
    leaf hits {
      type uint64;
      description
        "Number of packets reach to destination and get reply back";
    }
    leaf total {
      type uint64;
      description
        "Total number of packets sent out";
    }
    leaf success-rate {
      type uint64;
      description
        "Successful rate of ping";
    }
    leaf rtt-min {
      type uint64;
      description
        "Minimum value of Round Trip Time";
    }
    leaf rtt-avg {
      type uint64;
      description
        "Average value of Round Trip Time";
    }
    leaf rtt-max {
      type uint64;
      description
        "Maximum value of Round Trip Time";
    }
    leaf std-dev {
      type uint64;
      description
        "standard deviation of Ping responses in nanoseconds";
    }
  }
}
