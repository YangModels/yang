module Cisco-IOS-XR-um-spanning-tree-cfg {
  namespace "http://cisco.com/ns/yang/Cisco-IOS-XR-um-spanning-tree-cfg";
  prefix um-spanning-tree-cfg;

  import Cisco-IOS-XR-types {
    prefix xr;
  }
  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR spanning-tree package configuration.
     
     This YANG module augments the
     modules with configuration data.
     
     Copyright (c) 2022 by Cisco Systems, Inc.
     All rights reserved.";

  revision 2022-10-31 {
    description
      "Add in MSTAG startup-bpdus config item";
    semver:module-version "1.0.0";
  }
  revision 2022-09-08 {
    description
      "Initial release";
  }

  container spanning-tree {
    description
      "Configure Spanning Tree Protocol.";
    container mst {
      description
        "Configure Multiple Spanning Tree Protocol.";
      container protocol-instances {
        description
          "Protocol Instance name.";
        list protocol-instance {
          key "protocol-instance-name";
          description
            "Protocol Instance name.";
          leaf protocol-instance-name {
            type xr:Cisco-ios-xr-string {
              length "1..800" {
                description
                  "Protocol Instance name.";
              }
            }
            description
              "Protocol Instance name.";
          }
          container interfaces {
            description
              "Enable and Configure MSTP on an interface.";
            list interface {
              key "interface-name";
              description
                "Enable and Configure MSTP on an interface.";
              leaf interface-name {
                type xr:Interface-name;
                description
                  "Enable and Configure MSTP on an interface.";
              }
              leaf external-cost {
                type uint32 {
                  range "1..200000000" {
                    description
                      "Interface External Cost.";
                  }
                }
                description
                  "Interface External Cost.";
              }
              leaf hello-time {
                type uint32 {
                  range "1..2" {
                    description
                      "Interface Hello Time in seconds.  Only 2 is supported on bundles.";
                  }
                }
                description
                  "Interface Hello Time.";
              }
              container link-type {
                description
                  "Configure the Link Type of an Interface.";
                container point-to-point {
                  must "not(../multipoint)";
                  presence "Indicates a point-to-point node is configured.";
                  description
                    "Point to Point link.";
                }
                container multipoint {
                  must "not(../point-to-point)";
                  presence "Indicates a multipoint node is configured.";
                  description
                    "Multipoint link.";
                }
              }
              container portfast {
                presence "Indicates a portfast node is configured.";
                description
                  "Set PortFast on Interface.";
                container bpduguard {
                  presence "Indicates a bpduguard node is configured.";
                  description
                    "Enable BPDU Guard on Interface.";
                }
              }
              container guard {
                description
                  "Configure bridge guard features";
                container root {
                  presence "Indicates a root node is configured.";
                  description
                    "Set Guard Root on Interface.";
                }
                container topology-change {
                  presence "Indicates a topology-change node is configured.";
                  description
                    "Set Guard topology-change on Interface.";
                }
              }
              container instances {
                description
                  "MSTI Specific configuration for this interface.";
                list instance {
                  key "instance-id";
                  description
                    "MSTI Specific configuration for this interface.";
                  leaf instance-id {
                    type uint32 {
                      range "0..4094" {
                        description
                          "MSTI ID";
                      }
                    }
                    description
                      "MSTI Specific configuration for this interface.";
                  }
                  leaf port-priority {
                    type uint32 {
                      range "0..240" {
                        description
                          "Port Priority. Must be a multiple of 16.";
                      }
                    }
                    description
                      "Priority of this port on this MSTI.";
                  }
                  leaf cost {
                    type uint32 {
                      range "1..200000000" {
                        description
                          "Port Cost";
                      }
                    }
                    description
                      "Cost of this port on this MSTI.";
                  }
                }
              }
            }
          }
          container instances {
            description
              "Configure an MSTP instance.";
            list instance {
              key "instance-id";
              description
                "Configure an MSTP instance.";
              leaf instance-id {
                type uint32 {
                  range "0..4094" {
                    description
                      "MSTI ID";
                  }
                }
                description
                  "Configure an MSTP instance.";
              }
              leaf vlan-ids {
                type xr:Cisco-ios-xr-string {
                  length "1..800" {
                    description
                      "List of VLAN Ranges in the form a-b,c,d,e-f,g";
                  }
                }
                description
                  "Assign ranges of VLANs to the specified MSTI.";
              }
              leaf priority {
                type uint32 {
                  range "0..61440" {
                    description
                      "MSTI Priority. Must be a multiple of 4096.";
                  }
                }
                description
                  "MSTI Priority.";
              }
            }
          }
          leaf name {
            type xr:Cisco-ios-xr-string {
              length "1..800" {
                description
                  "Configuration name";
              }
            }
            description
              "Configuration name";
          }
          leaf revision {
            type uint32 {
              range "0..65535" {
                description
                  "Revision number.";
              }
            }
            description
              "Bridge revision number.";
          }
          leaf forward-delay {
            type uint32 {
              range "4..30" {
                description
                  "Forward delay time in seconds.";
              }
            }
            description
              "Bridge forward delay time.";
          }
          container maximum {
            description
              "Bridge maximums, such as max-age";
            leaf hops {
              type uint32 {
                range "6..40" {
                  description
                    "Bridge Maximum number of hops.";
                }
              }
              description
                "Bridge maximum number of hops.";
            }
            leaf age {
              type uint32 {
                range "6..40" {
                  description
                    "Bridge Maximum Age time in seconds.";
                }
              }
              description
                "Bridge maximum age time.";
            }
          }
          container transmit {
            description
              "Bridge transmit options";
            leaf hold-count {
              type uint32 {
                range "1..10" {
                  description
                    "Bridge Transmit Hold Count.";
                }
              }
              description
                "Bridge Transmit Hold Count.";
            }
          }
          container provider-bridge {
            presence "Indicates a provider-bridge node is configured.";
            description
              "Provider Bridge mode.";
          }
          container flush {
            description
              "Flush options";
            container containment {
              description
                "Flush containment options";
              container disable {
                presence "Indicates a disable node is configured.";
                description
                  "Disable flush containment";
              }
            }
          }
          container allow-legacy-bpdu {
            presence "Indicates a allow-legacy-bpdu node is configured.";
            description
              "Permit legacy STP BDPU TCNs to cause flushes";
          }
          container bringup {
            description
              "Bringup options.";
            container delay {
              description
                "Bringup delay for newly created interfaces.";
              leaf for {
                type uint32 {
                  range "0..3600" {
                    description
                      "Length of time to delay for (hours, minutes, or seconds)";
                  }
                }
                description
                  "Specify length of time to delay bringup for";
              }
              container seconds {
                must "not(../minutes or ../hours)";
                presence "Indicates a seconds node is configured.";
                description
                  "Time is in seconds";
              }
              container minutes {
                must "not(../seconds or ../hours)";
                presence "Indicates a minutes node is configured.";
                description
                  "Time is in minutes";
              }
              container hours {
                must "not(../seconds or ../minutes)";
                presence "Indicates a hours node is configured.";
                description
                  "Time is in hours";
              }
            }
          }
        }
      }
    }
    container pvrst {
      description
        "Configure Per-VLAN Rapid Spaning Tree Protocol.";
      container protocol-instances {
        description
          "Protocol Instance name.";
        list protocol-instance {
          key "protocol-instance-name";
          description
            "Protocol Instance name.";
          leaf protocol-instance-name {
            type xr:Cisco-ios-xr-string {
              length "1..800" {
                description
                  "Protocol Instance name.";
              }
            }
            description
              "Protocol Instance name.";
          }
          leaf forward-delay {
            type uint32 {
              range "4..30" {
                description
                  "Forward delay time in seconds.";
              }
            }
            description
              "Bridge forward delay time.";
          }
          container maximum {
            description
              "Bridge maximums";
            leaf age {
              type uint32 {
                range "6..40" {
                  description
                    "Bridge Maximum Age time in seconds.";
                }
              }
              description
                "Bridge maximum age time.";
            }
          }
          container transmit {
            description
              "Bridge transmit options";
            leaf hold-count {
              type uint32 {
                range "1..10" {
                  description
                    "Bridge Transmit Hold Count.";
                }
              }
              description
                "Bridge Transmit Hold Count.";
            }
          }
          container interfaces {
            description
              "Enable and Configure PVRST on an interface.";
            list interface {
              key "interface-name";
              description
                "Enable and Configure PVRST on an interface.";
              leaf interface-name {
                type xr:Interface-name;
                description
                  "Enable and Configure PVRST on an interface.";
              }
              leaf hello-time {
                type uint32 {
                  range "1..2" {
                    description
                      "Interface Hello Time in seconds.  Only 2 is supported on bundles.";
                  }
                }
                description
                  "Interface Hello Time.";
              }
              container link-type {
                description
                  "Configure the Link Type of an Interface.";
                container point-to-point {
                  must "not(../multipoint)";
                  presence "Indicates a point-to-point node is configured.";
                  description
                    "Point to Point link.";
                }
                container multipoint {
                  must "not(../point-to-point)";
                  presence "Indicates a multipoint node is configured.";
                  description
                    "Multipoint link.";
                }
              }
              container portfast {
                presence "Indicates a portfast node is configured.";
                description
                  "Set PortFast on Interface.";
                container bpduguard {
                  presence "Indicates a bpduguard node is configured.";
                  description
                    "Enable BPDU Guard on Interface.";
                }
              }
              container guard {
                description
                  "Configure bridge guard features";
                container root {
                  presence "Indicates a root node is configured.";
                  description
                    "Set Guard Root on Interface.";
                }
              }
              container vlans {
                description
                  "VLAN Specific configuration for this interface.";
                list vlan {
                  key "vlan-id";
                  description
                    "VLAN Specific configuration for this interface.";
                  leaf vlan-id {
                    type uint32 {
                      range "1..4094" {
                        description
                          "VLAN ID";
                      }
                    }
                    description
                      "VLAN Specific configuration for this interface.";
                  }
                  leaf port-priority {
                    type uint32 {
                      range "0..240" {
                        description
                          "Port Priority. Must be a multiple of 16.";
                      }
                    }
                    description
                      "Priority of this port on this VLAN.";
                  }
                  leaf cost {
                    type uint32 {
                      range "1..200000000" {
                        description
                          "Port Cost";
                      }
                    }
                    description
                      "Cost of this port on this VLAN.";
                  }
                }
              }
            }
          }
          container vlans {
            description
              "Configure PVRST on a VLAN.";
            list vlan {
              key "vlan-id";
              description
                "Configure PVRST on a VLAN.";
              leaf vlan-id {
                type uint32 {
                  range "1..4094" {
                    description
                      "VLAN ID";
                  }
                }
                description
                  "Configure PVRST on a VLAN.";
              }
              leaf priority {
                type uint32 {
                  range "0..61440" {
                    description
                      "Bridge Priority. Must be a multiple of 4096.";
                  }
                }
                description
                  "Bridge Priority.";
              }
            }
          }
        }
      }
    }
    container mstag {
      description
        "Configure MST Access Gateway";
      container protocol-instances {
        description
          "Protocol Instance name.";
        list protocol-instance {
          key "protocol-instance-name";
          description
            "Protocol Instance name.";
          leaf protocol-instance-name {
            type xr:Cisco-ios-xr-string {
              length "1..800" {
                description
                  "Protocol Instance name.";
              }
            }
            description
              "Protocol Instance name.";
          }
          container preempt {
            description
              "Configure pre-empt behavior";
            container delay {
              description
                "Specify delay period during which startup BPDUs should be sent, before pre-empting";
              container until {
                presence "Indicates a startup BPDUs delay-until node is configured.";
                description
                  "Specify time to delay preempting until, as 24-hour hh:mm:ss.";
                leaf hours {
                  type uint32 {
                    range "0..23" {
                      description
                        "Hours (hh:mm:ss)";
                    }
                  }
                  mandatory true;
                  description
                    "Specify time to delay preempting until, as 24-hour hh:mm:ss";
                }
                leaf minutes {
                  type uint32 {
                    range "0..59" {
                      description
                        "Minutes (hh:mm:ss)";
                    }
                  }
                  mandatory true;
                  description
                    "Minutes (hh:mm:ss)";
                }
                leaf seconds {
                  type uint32 {
                    range "0..59" {
                      description
                        "Seconds (hh:mm:ss)";
                    }
                  }
                  mandatory true;
                  description
                    "Seconds (hh:mm:ss)";
                }
              }
              container for {
                presence "Indicates a startup BPDUs duration node is configured.";
                description
                  "Startup BPDU duration.";
                leaf for {
                  type uint32 {
                    range "0..86400" {
                      description
                        "Length of time to delay for (hours, minutes, or seconds)";
                    }
                  }
                  must "../seconds or ../minutes or ../hours";
                  mandatory true;
                  description
                    "Specify length of time to delay preempting for";
                }
                container seconds {
                  must "not(../minutes or ../hours)";
                  presence "Indicates a seconds node is configured.";
                  description
                    "Time is in seconds";
                }
                container minutes {
                  must "not(../seconds or ../hours)";
                  presence "Indicates a minutes node is configured.";
                  description
                    "Time is in minutes";
                }
                container hours {
                  must "not(../seconds or ../minutes)";
                  presence "Indicates a hours node is configured.";
                  description
                    "Time is in hours";
                }
              }
            }
          }
          container issu {
            description
              "Configure behavior during ISSU operations";
            container send {
              description
                "Specify the type of BPDUs to send during ISSU operations";
              container startup-bpdus {
                presence "Indicates a startup-bpdus node is configured.";
                description
                  "Send startup BPDUs during ISSU operations";
              }
            }
          }
          container interfaces {
            description
              "Enable and Configure MSTAG on an interface.";
            list interface {
              key "interface-name";
              description
                "Enable and Configure MSTAG on an interface.";
              leaf interface-name {
                type xr:Interface-name;
                description
                  "Enable and Configure MSTAG on an interface.";
              }
              container name {
                description
                  "Configuration name";
                leaf configuration-name {
                  type xr:Cisco-ios-xr-string {
                    length "1..800" {
                      description
                        "Configuration name";
                    }
                  }
                  description
                    "Configuration name";
                }
                container none {
                  presence "Indicates a none node is configured.";
                  description
                    "Use a NULL MST name";
                }
              }
              leaf revision {
                type uint32 {
                  range "0..65535" {
                    description
                      "Revision number.";
                  }
                }
                description
                  "Bridge revision number.";
              }
              container max {
                description
                  "Bridge maximums, such as max-age";
                leaf age {
                  type uint32 {
                    range "6..40" {
                      description
                        "Bridge Maximum Age time in seconds.";
                    }
                  }
                  description
                    "Bridge maximum age time.";
                }
              }
              container provider-bridge {
                presence "Indicates a provider-bridge node is configured.";
                description
                  "Provider Bridge mode.";
              }
              leaf hello-time {
                type uint32 {
                  range "1..2" {
                    description
                      "Interface Hello Time in seconds.  Only 2 is supported on bundles.";
                  }
                }
                description
                  "Interface Hello Time.";
              }
              container bridge-id {
                presence "Indicates a bridge ID node is configured.";
                description
                  "Bridge ID.";
                leaf bridge-id {
                  type yang:mac-address;
                  mandatory true;
                  description
                    "Set the Bridge ID this port should use";
                }
                leaf startup-value {
                  type yang:mac-address;
                  description
                    "Set the Bridge ID to be used during pre-empt delay";
                }
              }
              container port-id {
                presence "Indicates an interface port ID node is configured.";
                description
                  "Interface Port ID.";
                leaf port-id {
                  type uint32 {
                    range "1..4095" {
                      description
                        "Interface Port ID.";
                    }
                  }
                  mandatory true;
                  description
                    "Interface Port ID.";
                }
                leaf startup-value {
                  type uint32 {
                    range "1..4095" {
                      description
                        "Interface Port ID.";
                    }
                  }
                  description
                    "Set the Port ID to be used during pre-empt delay";
                }
              }
              container external-cost {
                presence "Indicates an interface external cost node is configured.";
                description
                  "Interface External Cost.";
                leaf external-cost {
                  type uint32 {
                    range "1..200000000" {
                      description
                        "Interface External Cost.";
                    }
                  }
                  mandatory true;
                  description
                    "Interface External Cost.";
                }
                leaf startup-value {
                  type uint32 {
                    range "1..200000000" {
                      description
                        "Interface External Cost.";
                    }
                  }
                  description
                    "Set the External Cost to be used during pre-empt delay";
                }
              }
              container instances {
                description
                  "Enable and Configure an instance on this interface.";
                list instance {
                  key "instance-id";
                  description
                    "Enable and Configure an instance on this interface.";
                  leaf instance-id {
                    type uint32 {
                      range "0..4094" {
                        description
                          "MSTI ID";
                      }
                    }
                    description
                      "Enable and Configure an instance on this interface.";
                  }
                  leaf vlan-ids {
                    type xr:Cisco-ios-xr-string {
                      length "1..800" {
                        description
                          "List of VLAN Ranges in the form a-b,c,d,e-f,g";
                      }
                    }
                    description
                      "Assign ranges of VLANs to the specified MSTI.";
                  }
                  container priority {
                    presence "Indicates an MSTI priority node is configured.";
                    description
                      "MSTI priority.";
                    leaf priority {
                      type uint32 {
                        range "0..61440" {
                          description
                            "MSTI Priority. Must be a multiple of 4096.";
                        }
                      }
                      mandatory true;
                      description
                        "MSTI Priority.";
                    }
                    leaf startup-value {
                      type uint32 {
                        range "0..61440" {
                          description
                            "MSTI Priority. Must be a multiple of 4096.";
                        }
                      }
                      description
                        "Set the MSTI Priority to be used during pre-empt delay";
                    }
                  }
                  container port-priority {
                    presence "Indicates a port priority node is configured.";
                    description
                      "Port priority.";
                    leaf port-priority {
                      type uint32 {
                        range "0..240" {
                          description
                            "Port Priority. Must be a multiple of 16.";
                        }
                      }
                      mandatory true;
                      description
                        "Priority of this port on this MSTI.";
                    }
                    leaf startup-value {
                      type uint32 {
                        range "0..240" {
                          description
                            "Port Priority. Must be a multiple of 16.";
                        }
                      }
                      description
                        "Set the priority of this port on this MSTI to be used during pre-empt delay";
                    }
                  }
                  container cost {
                    presence "Indicates a port cost node is configured.";
                    description
                      "Port cost.";
                    leaf cost {
                      type uint32 {
                        range "1..200000000" {
                          description
                            "Port Cost";
                        }
                      }
                      mandatory true;
                      description
                        "Cost of this port on this MSTI.";
                    }
                    leaf startup-value {
                      type uint32 {
                        range "1..200000000" {
                          description
                            "Port Cost";
                        }
                      }
                      description
                        "Set the cost of this port on this MSTI to be used during pre-empt delay";
                    }
                  }
                  container root-priority {
                    presence "Indicates a MSTI root-priority node is configured.";
                    description
                      "MSTI root-priority.";
                    leaf root-priority {
                      type uint32 {
                        range "0..61440" {
                          description
                            "MSTI Priority. Must be a multiple of 4096.";
                        }
                      }
                      mandatory true;
                      description
                        "Priority of the root for this instance.";
                    }
                    leaf startup-value {
                      type uint32 {
                        range "0..61440" {
                          description
                            "MSTI Priority. Must be a multiple of 4096.";
                        }
                      }
                      description
                        "Set the priority of the root for this instance to be used during pre-empt delay";
                    }
                  }
                  container root-id {
                    presence "Indicates a root bridge ID node is configured.";
                    description
                      "Root bridge ID.";
                    leaf root-id {
                      type yang:mac-address;
                      mandatory true;
                      description
                        "Set the Bridge ID of the root for this instance";
                    }
                    leaf startup-value {
                      type yang:mac-address;
                      description
                        "Set the Bridge ID to be used during pre-empt delay";
                    }
                  }
                  container edge-mode {
                    presence "Indicates a edge-mode node is configured.";
                    description
                      "Enable Access Gateway Edge Mode for this MSTI.";
                  }
                }
              }
            }
          }
          container track {
            description
              "Configure core connectivity tracking";
            container interfaces {
              description
                "Configure an interface as core facing for MSTAG";
              list interface {
                key "interface-name";
                description
                  "Configure an interface as core facing for MSTAG";
                leaf interface-name {
                  type xr:Interface-name;
                  description
                    "Configure an interface as core facing for MSTAG";
                }
              }
            }
          }
        }
      }
    }
    container repag {
      description
        "Configure REP Access Gateway";
      container protocol-instances {
        description
          "Protocol Instance name";
        list protocol-instance {
          key "protocol-instance-name";
          description
            "Protocol Instance name";
          leaf protocol-instance-name {
            type xr:Cisco-ios-xr-string {
              length "1..800" {
                description
                  "Protocol Instance name";
              }
            }
            description
              "Protocol Instance name";
          }
          container interfaces {
            description
              "Enable and Configure REPAG on an interface.";
            list interface {
              key "interface-name";
              description
                "Enable and Configure REPAG on an interface.";
              leaf interface-name {
                type xr:Interface-name;
                description
                  "Enable and Configure REPAG on an interface.";
              }
              container auto-configure-edge {
                presence "Indicates a auto-configure-edge node is configured.";
                description
                  "Auto-configure RENN on the edge node of a REP segment.";
              }
              container instances {
                description
                  "Enable and Configure an instance on this interface.";
                list instance {
                  key "instance-id";
                  description
                    "Enable and Configure an instance on this interface.";
                  leaf instance-id {
                    type uint32 {
                      range "0..4094" {
                        description
                          "MSTI ID";
                      }
                    }
                    description
                      "Enable and Configure an instance on this interface.";
                  }
                  leaf vlan-ids {
                    type xr:Cisco-ios-xr-string {
                      length "1..800" {
                        description
                          "List of VLAN Ranges in the form a-b,c,d,e-f,g";
                      }
                    }
                    description
                      "Assign ranges of VLANs to the specified MSTI.";
                  }
                  container priority {
                    presence "Indicates a MSTI priority node is configured.";
                    description
                      "MSTI priority.";
                    leaf priority {
                      type uint32 {
                        range "0..61440" {
                          description
                            "MSTI Priority. Must be a multiple of 4096.";
                        }
                      }
                      mandatory true;
                      description
                        "MSTI Priority.";
                    }
                    leaf startup-value {
                      type uint32 {
                        range "0..61440" {
                          description
                            "MSTI Priority. Must be a multiple of 4096.";
                        }
                      }
                      description
                        "Set the MSTI Priority to be used during pre-empt delay";
                    }
                  }
                  container port-priority {
                    presence "Indicates a port priority node is configured.";
                    description
                      "Port priority.";
                    leaf port-priority {
                      type uint32 {
                        range "0..240" {
                          description
                            "Port Priority. Must be a multiple of 16.";
                        }
                      }
                      mandatory true;
                      description
                        "Priority of this port on this MSTI.";
                    }
                    leaf startup-value {
                      type uint32 {
                        range "0..240" {
                          description
                            "Port Priority. Must be a multiple of 16.";
                        }
                      }
                      description
                        "Set the priority of this port on this MSTI to be used during pre-empt delay";
                    }
                  }
                  container cost {
                    presence "Indicates a port cost node is configured.";
                    description
                      "Port cost.";
                    leaf cost {
                      type uint32 {
                        range "1..200000000" {
                          description
                            "Port Cost";
                        }
                      }
                      mandatory true;
                      description
                        "Cost of this port on this MSTI.";
                    }
                    leaf startup-value {
                      type uint32 {
                        range "1..200000000" {
                          description
                            "Port Cost";
                        }
                      }
                      description
                        "Set the cost of this port on this MSTI to be used during pre-empt delay";
                    }
                  }
                  container root-priority {
                    presence "Indicates a root priority node is configured.";
                    description
                      "Root priority.";
                    leaf root-priority {
                      type uint32 {
                        range "0..61440" {
                          description
                            "MSTI Priority. Must be a multiple of 4096.";
                        }
                      }
                      mandatory true;
                      description
                        "Priority of the root for this instance.";
                    }
                    leaf startup-value {
                      type uint32 {
                        range "0..61440" {
                          description
                            "MSTI Priority. Must be a multiple of 4096.";
                        }
                      }
                      description
                        "Set the priority of the root for this instance to be used during pre-empt delay";
                    }
                  }
                  container root-id {
                    presence "Indicates a root bridge ID node is configured.";
                    description
                      "Root bridge ID.";
                    leaf root-id {
                      type yang:mac-address;
                      mandatory true;
                      description
                        "Set the Bridge ID of the root for this instance";
                    }
                    leaf startup-value {
                      type yang:mac-address;
                      description
                        "Set the Bridge ID to be used during pre-empt delay";
                    }
                  }
                  container edge-mode {
                    presence "Indicates an edge-mode node is configured.";
                    description
                      "Enable Access Gateway Edge Mode for this MSTI.";
                  }
                }
              }
            }
          }
        }
      }
    }
    container pvstag {
      description
        "Configure PVST+ Access Gateway";
      container protocol-instances {
        description
          "Protocol Instance name";
        list protocol-instance {
          key "protocol-instance-name";
          description
            "Protocol Instance name";
          leaf protocol-instance-name {
            type xr:Cisco-ios-xr-string {
              length "1..800" {
                description
                  "Protocol Instance name";
              }
            }
            description
              "Protocol Instance name";
          }
          container preempt {
            description
              "Configure pre-empt behavior";
            container delay {
              description
                "Specify delay period during which startup BPDUs should be sent, before pre-empting";
              container until {
                presence "Indicates a startup BPDUs delay-until node is configured.";
                description
                  "Specify time to delay preempting until, as 24-hour hh:mm:ss.";
                leaf hours {
                  type uint32 {
                    range "0..23" {
                      description
                        "Hours (hh:mm:ss)";
                    }
                  }
                  mandatory true;
                  description
                    "Specify time to delay preempting until, as 24-hour hh:mm:ss";
                }
                leaf minutes {
                  type uint32 {
                    range "0..59" {
                      description
                        "Minutes (hh:mm:ss)";
                    }
                  }
                  mandatory true;
                  description
                    "Minutes (hh:mm:ss)";
                }
                leaf seconds {
                  type uint32 {
                    range "0..59" {
                      description
                        "Seconds (hh:mm:ss)";
                    }
                  }
                  mandatory true;
                  description
                    "Seconds (hh:mm:ss)";
                }
              }
              container for {
                presence "Length of time to delay for (hours, minutes, or seconds) up to one day.";
                description
                  "Specify time to delay preempting until, as 24-hour hh:mm:ss.";
                leaf for {
                  type uint32 {
                    range "1..86400" {
                      description
                        "Length of time to delay for (hours, minutes, or seconds) up to one day";
                    }
                  }
                  must "../hours or ../minutes or ../seconds";
                  mandatory true;
                  description
                    "Specify length of time to delay preempting for";
                }
                container seconds {
                  must "not(../minutes or ../hours)";
                  presence "Indicates a seconds node is configured.";
                  description
                    "Time is in seconds";
                }
                container minutes {
                  must "not(../seconds or ../hours)";
                  presence "Indicates a minutes node is configured.";
                  description
                    "Time is in minutes";
                }
                container hours {
                  must "not(../seconds or ../minutes)";
                  presence "Indicates a hours node is configured.";
                  description
                    "Time is in hours";
                }
              }
            }
          }
          container issu {
            description
              "Configure behavior during ISSU operations";
            container send {
              description
                "Specify the type of BPDUs to send during ISSU operations";
              container startup-bpdus {
                presence "Indicates a startup-bpdus node is configured.";
                description
                  "Send startup BPDUs during ISSU operations";
              }
            }
          }
          container interfaces {
            description
              "Enable and Configure PVST+AG on an interface";
            list interface {
              key "interface-name";
              description
                "Enable and Configure PVST+AG on an interface";
              leaf interface-name {
                type xr:Interface-name;
                description
                  "Enable and Configure PVST+AG on an interface";
              }
              container vlans {
                description
                  "Enable and Configure a VLAN on this interface";
                list vlan {
                  key "vlan-id";
                  description
                    "Enable and Configure a VLAN on this interface";
                  leaf vlan-id {
                    type uint32 {
                      range "1..4094" {
                        description
                          "VLAN ID";
                      }
                    }
                    description
                      "Enable and Configure a VLAN on this interface";
                  }
                  container root-priority {
                    presence "Indicates a root priority node is configured.";
                    description
                      "Root priority.";
                    leaf root-priority {
                      type uint32 {
                        range "0..65535" {
                          description
                            "Root Priority. For PVRSTAG, must be a multiple of 4096.";
                        }
                      }
                      mandatory true;
                      description
                        "Priority of the root to send in BPDUs";
                    }
                    leaf startup-value {
                      type uint32 {
                        range "0..65535" {
                          description
                            "Root Priority. For PVRSTAG, must be a multiple of 4096.";
                        }
                      }
                      description
                        "Set the priority of the root to be used during pre-empt delay";
                    }
                  }
                  container root-id {
                    presence "Indicates a root bridge ID node is configured.";
                    description
                      "Root bridge ID.";
                    leaf root-id {
                      type yang:mac-address;
                      mandatory true;
                      description
                        "Bridge ID of the root to send in BPDUs";
                    }
                    leaf startup-value {
                      type yang:mac-address;
                      description
                        "Set the root bridge ID to be used during pre-empt delay";
                    }
                  }
                  container root-cost {
                    presence "Indicates a root cost node is configured.";
                    description
                      "Root cost.";
                    leaf root-cost {
                      type uint32 {
                        range "0..4294967295" {
                          description
                            "Root Cost";
                        }
                      }
                      mandatory true;
                      description
                        "Root cost to send in BPDUs";
                    }
                    leaf startup-value {
                      type uint32 {
                        range "0..4294967295" {
                          description
                            "Root Cost";
                        }
                      }
                      description
                        "Set the cost of the root to send in BPDUs to be used during pre-empt delay";
                    }
                  }
                  container priority {
                    presence "Indicates a bridge priority node is configured.";
                    description
                      "Bridge priority.";
                    leaf priority {
                      type uint32 {
                        range "0..65535" {
                          description
                            "Bridge Priority. For PVRSTAG, must be a multiple of 4096.";
                        }
                      }
                      mandatory true;
                      description
                        "Priority of the Bridge to send in BPDUs";
                    }
                    leaf startup-value {
                      type uint32 {
                        range "0..65535" {
                          description
                            "Bridge Priority. For PVRSTAG, must be a multiple of 4096.";
                        }
                      }
                      description
                        "Set the priority of this bridge to be used during pre-empt delay";
                    }
                  }
                  container bridge-id {
                    presence "Indicates a bridge ID node is configured.";
                    description
                      "Bridge ID.";
                    leaf bridge-id {
                      type yang:mac-address;
                      mandatory true;
                      description
                        "Bridge ID to use in BPDUs";
                    }
                    leaf startup-value {
                      type yang:mac-address;
                      description
                        "Set the Bridge ID to be used during pre-empt delay";
                    }
                  }
                  container port-priority {
                    presence "Indicates a port priority node is configured.";
                    description
                      "Port priority.";
                    leaf port-priority {
                      type uint32 {
                        range "0..255" {
                          description
                            "Port Priority. For PVRSTAG, must be a multiple of 16.";
                        }
                      }
                      mandatory true;
                      description
                        "Port priority to send in BPDUs";
                    }
                    leaf startup-value {
                      type uint32 {
                        range "0..255" {
                          description
                            "Port Priority. For PVRSTAG, must be a multiple of 16.";
                        }
                      }
                      description
                        "Set the priority of this port to be used during pre-empt delay";
                    }
                  }
                  container port-id {
                    presence "Indicates a port ID is configured.";
                    description
                      "Port ID.";
                    leaf port-id {
                      type uint32 {
                        range "0..255" {
                          description
                            "Port ID.";
                        }
                      }
                      mandatory true;
                      description
                        "Interface Port ID to send in BPDUs";
                    }
                    leaf startup-value {
                      type uint32 {
                        range "0..255" {
                          description
                            "Port ID.";
                        }
                      }
                      description
                        "Set the Port ID to be used during pre-empt delay";
                    }
                  }
                  leaf hello-time {
                    type uint32 {
                      range "1..2" {
                        description
                          "How often to send BPDUs";
                      }
                    }
                    description
                      "How often to send BPDUs";
                  }
                  container max {
                    description
                      "Maximum age to send in BPDUs";
                    leaf age {
                      type uint32 {
                        range "0..240" {
                          description
                            "Port Priority. Must be a multiple of 16.";
                        }
                      }
                      description
                        "Priority of this port on this MSTI.";
                    }
                  }
                }
              }
            }
          }
        }
      }
    }
    container pvrstag {
      description
        "Configure PVRST Access Gateway";
      container protocol-instances {
        description
          "Protocol Instance name";
        list protocol-instance {
          key "protocol-instance-name";
          description
            "Protocol Instance name";
          leaf protocol-instance-name {
            type xr:Cisco-ios-xr-string {
              length "1..800" {
                description
                  "Protocol Instance name";
              }
            }
            description
              "Protocol Instance name";
          }
          container preempt {
            description
              "Configure pre-empt behavior";
            container delay {
              description
                "Specify delay period during which startup BPDUs should be sent, before pre-empting";
              container until {
                presence "Indicates a startup BPDUs delay-until node is configured.";
                description
                  "Specify time to delay preempting until, as 24-hour hh:mm:ss.";
                leaf hours {
                  type uint32 {
                    range "0..23" {
                      description
                        "Hours (hh:mm:ss)";
                    }
                  }
                  mandatory true;
                  description
                    "Specify time to delay preempting until, as 24-hour hh:mm:ss";
                }
                leaf minutes {
                  type uint32 {
                    range "0..59" {
                      description
                        "Minutes (hh:mm:ss)";
                    }
                  }
                  mandatory true;
                  description
                    "Minutes (hh:mm:ss)";
                }
                leaf seconds {
                  type uint32 {
                    range "0..59" {
                      description
                        "Seconds (hh:mm:ss)";
                    }
                  }
                  mandatory true;
                  description
                    "Seconds (hh:mm:ss)";
                }
              }
              container for {
                presence "Length of time to delay for (hours, minutes, or seconds) up to one day.";
                description
                  "Specify time to delay preempting until, as 24-hour hh:mm:ss.";
                leaf for {
                  type uint32 {
                    range "1..86400" {
                      description
                        "Length of time to delay for (hours, minutes, or seconds) up to one day";
                    }
                  }
                  must "../hours or ../minutes or ../seconds";
                  mandatory true;
                  description
                    "Specify length of time to delay preempting for";
                }
                container seconds {
                  must "not(../minutes or ../hours)";
                  presence "Indicates a seconds node is configured.";
                  description
                    "Time is in seconds";
                }
                container minutes {
                  must "not(../seconds or ../hours)";
                  presence "Indicates a minutes node is configured.";
                  description
                    "Time is in minutes";
                }
                container hours {
                  must "not(../seconds or ../minutes)";
                  presence "Indicates a hours node is configured.";
                  description
                    "Time is in hours";
                }
              }
            }
          }
          container issu {
            description
              "Configure behavior during ISSU operations";
            container send {
              description
                "Specify the type of BPDUs to send during ISSU operations";
              container startup-bpdus {
                presence "Indicates a startup-bpdus node is configured.";
                description
                  "Send startup BPDUs during ISSU operations";
              }
            }
          }
          container interfaces {
            description
              "Enable and Configure PVRSTAG on an interface";
            list interface {
              key "interface-name";
              description
                "Enable and Configure PVRSTAG on an interface";
              leaf interface-name {
                type xr:Interface-name;
                description
                  "Enable and Configure PVRSTAG on an interface";
              }
              container vlans {
                description
                  "Enable and Configure a VLAN on this interface";
                list vlan {
                  key "vlan-id";
                  description
                    "Enable and Configure a VLAN on this interface";
                  leaf vlan-id {
                    type uint32 {
                      range "1..4094" {
                        description
                          "VLAN ID";
                      }
                    }
                    description
                      "Enable and Configure a VLAN on this interface";
                  }
                  container root-priority {
                    presence "Indicates a root priority node is configured.";
                    description
                      "Root priority.";
                    leaf root-priority {
                      type uint32 {
                        range "0..61440" {
                          description
                            "Root Priority. For PVRSTAG, must be a multiple of 4096.";
                        }
                      }
                      mandatory true;
                      description
                        "Priority of the root to send in BPDUs";
                    }
                    leaf startup-value {
                      type uint32 {
                        range "0..61440" {
                          description
                            "Root Priority. For PVRSTAG, must be a multiple of 4096.";
                        }
                      }
                      description
                        "Set the priority of the root to be used during pre-empt delay";
                    }
                  }
                  container root-id {
                    presence "Indicates a root bridge ID node is configured.";
                    description
                      "Root bridge ID.";
                    leaf root-id {
                      type yang:mac-address;
                      mandatory true;
                      description
                        "Bridge ID of the root to send in BPDUs";
                    }
                    leaf startup-value {
                      type yang:mac-address;
                      description
                        "Set the root bridge ID to be used during pre-empt delay";
                    }
                  }
                  container root-cost {
                    presence "Indicates a root cost node is configured.";
                    description
                      "Root cost.";
                    leaf root-cost {
                      type uint32 {
                        range "0..4294967295" {
                          description
                            "Root Cost";
                        }
                      }
                      mandatory true;
                      description
                        "Root cost to send in BPDUs";
                    }
                    leaf startup-value {
                      type uint32 {
                        range "0..4294967295" {
                          description
                            "Root Cost";
                        }
                      }
                      description
                        "Set the cost of the root to send in BPDUs to be used during pre-empt delay";
                    }
                  }
                  container priority {
                    presence "Indicates a bridge priority node is configured.";
                    description
                      "Bridge priority.";
                    leaf priority {
                      type uint32 {
                        range "0..61440" {
                          description
                            "Bridge Priority. For PVRSTAG, must be a multiple of 4096.";
                        }
                      }
                      mandatory true;
                      description
                        "Priority of the Bridge to send in BPDUs";
                    }
                    leaf startup-value {
                      type uint32 {
                        range "0..61440" {
                          description
                            "Bridge Priority. For PVRSTAG, must be a multiple of 4096.";
                        }
                      }
                      description
                        "Set the priority of this bridge to be used during pre-empt delay";
                    }
                  }
                  container bridge-id {
                    presence "Indicates a bridge ID node is configured.";
                    description
                      "Bridge ID.";
                    leaf bridge-id {
                      type yang:mac-address;
                      mandatory true;
                      description
                        "Bridge ID to use in BPDUs";
                    }
                    leaf startup-value {
                      type yang:mac-address;
                      description
                        "Set the Bridge ID to be used during pre-empt delay";
                    }
                  }
                  container port-priority {
                    presence "Indicates a port priority node is configured.";
                    description
                      "Port priority.";
                    leaf port-priority {
                      type uint32 {
                        range "0..240" {
                          description
                            "Port Priority. For PVRSTAG, must be a multiple of 16.";
                        }
                      }
                      mandatory true;
                      description
                        "Port priority to send in BPDUs";
                    }
                    leaf startup-value {
                      type uint32 {
                        range "0..240" {
                          description
                            "Port Priority. For PVRSTAG, must be a multiple of 16.";
                        }
                      }
                      description
                        "Set the priority of this port to be used during pre-empt delay";
                    }
                  }
                  container port-id {
                    presence "Indicates a port ID node is configured.";
                    description
                      "Port ID.";
                    leaf port-id {
                      type uint32 {
                        range "0..4095" {
                          description
                            "Port ID.";
                        }
                      }
                      mandatory true;
                      description
                        "Interface Port ID to send in BPDUs";
                    }
                    leaf startup-value {
                      type uint32 {
                        range "0..4095" {
                          description
                            "Port ID.";
                        }
                      }
                      description
                        "Set the Port ID to be used during pre-empt delay";
                    }
                  }
                }
              }
            }
          }
        }
      }
    }
  }
}
