module Cisco-IOS-XR-feature-agent-oper {
  namespace "http://cisco.com/ns/yang/Cisco-IOS-XR-feature-agent-oper";
  prefix feature-agent-oper;

  import Cisco-IOS-XR-types {
    prefix xr;
  }
  import cisco-semver {
    prefix semver;
  }
  include Cisco-IOS-XR-feature-agent-oper-sub1 {
    revision-date 2021-06-16;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR feature-agent package operational data.
     
     This module contains definitions
     for the following management objects:
       feature-capabilities: XR Features
     
     Copyright (c) 2013-2021 by Cisco Systems, Inc.
     All rights reserved.";

  revision 2021-06-16 {
    description
      "Fixed user permission";
    semver:module-version "1.0.0";
  }
  revision 2021-03-25 {
    description
      "IOS XR 7.05.01 version";
  }
  revision 2019-04-05 {
    description
      "Establish semantic version baseline.";
  }
  revision 2015-11-09 {
    description
      "IOS XR 6.0 revision.";
  }

  container feature-capabilities {
    config false;
    description
      "XR Features";
    container features {
      description
        "XR Features";
      list feature {
        key "feature-id";
        description
          "Data for Feature";
        leaf feature-id {
          type xr:Cisco-ios-xr-string;
          description
            "Feature ID";
        }
        uses FEATURE;
      }
    }
  }
}
