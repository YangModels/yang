module Cisco-IOS-XR-um-vpdn-cfg {
  namespace "http://cisco.com/ns/yang/Cisco-IOS-XR-um-vpdn-cfg";
  prefix um-vpdn-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR vpdn package configuration.
     
     This YANG module augments the
     modules with configuration data.
     
     Copyright (c) 2020-2025 by Cisco Systems, Inc., and/or its affiliates.
     All rights reserved.";

  revision 2020-12-10 {
    description
      "Initial release";
    semver:module-version "1.0.0";
  }

  container vpdn {
    presence "Indicates a vpdn node is configured.";
    description
      "VPDN configuration";
    container history {
      description
        "VPDN history logging";
      container failure {
        presence "Indicates a failure node is configured.";
        description
          "User failure";
      }
    }
    container local {
      description
        "VPDN Local radius process configuration";
      leaf secret {
        type xr:Cisco-ios-xr-string {
          length "1..32" {
            description
              "secret password";
          }
        }
        must "../profile-dir";
        description
          "Radius secret key";
      }
      leaf profile-dir {
        type xr:Cisco-ios-xr-string {
          length "1..64" {
            description
              "local path of the saved profile";
          }
        }
        must "../secret";
        description
          "Enter the location of stored profile";
      }
      container cache-disabled {
        presence "Indicates a cache-disabled node is configured.";
        description
          "disable config file cache, impact performance significantly";
      }
      leaf port {
        type uint32 {
          range "1..65535" {
            description
              "port value";
          }
        }
        description
          "port to listen. Default is 1645.";
      }
    }
    container logging {
      description
        "Configure logging for VPDN";
      container cause {
        description
          "Cause of termination";
        container normal {
          presence "Indicates a normal node is configured.";
          description
            "Normal termination";
        }
      }
      container events {
        description
          "configure this node";
        list event {
          key "event-name";
          description
            "configure this node";
          leaf event-name {
            type enumeration {
              enum "local" {
                value 1;
                description
                  "Log VPDN events locally";
              }
              enum "user" {
                value 2;
                description
                  "Log VPDN user events";
              }
              enum "dead-cache" {
                value 8;
                description
                  "Log VPDN dead cache";
              }
              enum "tunnel-drop" {
                value 16;
                description
                  "Log VPDN tunnel drops";
              }
            }
            description
              "configure this node";
          }
        }
      }
    }
    leaf session-limit {
      type uint32 {
        range "1..131072" {
          description
            "Number of sessions";
        }
      }
      description
        "Maximum simultaneous VPDN sessions";
    }
    container softshut {
      presence "Indicates a softshut node is configured.";
      description
        "New session no longer allowed";
    }
    container caller-id {
      description
        "Options to apply on calling station ID";
      container mask-method {
        description
          "Mask characters by method";
        container remove {
          description
            "Remove CLID";
          leaf match {
            type xr:Cisco-ios-xr-string {
              length "1..63" {
                description
                  "Match substring";
              }
            }
            description
              "Set match string";
          }
        }
      }
    }
    container l2tp {
      description
        "L2TPv2 protocol commands";
      container session-id {
        description
          "Session ID commands";
        container space {
          description
            "Session ID space commands";
          container hierarchical {
            presence "Indicates a hierarchical node is configured.";
            description
              "Session ID space hierarchical command";
          }
        }
      }
      leaf tcp-mss-adjust {
        type uint32 {
          range "1280..1460" {
            description
              "TCP MSS adjust value. The acceptable values might be further limited depending on platform.";
          }
        }
        description
          "TCP MSS adjust value";
      }
    }
    container redundancy {
      presence "Indicates a redundancy node is configured.";
      description
        "Enable VPDN redundancy";
      container process-failures {
        description
          "Process crash configuration";
        container switchover {
          presence "Indicates a switchover node is configured.";
          description
            "Force a switchover if the process crashes";
        }
      }
    }
    container template {
      description
        "VPDN template configuration";
      container vpdn-templates {
        description
          "VPDN template name";
        list vpdn-template {
          key "vpdn-template-name";
          description
            "VPDN template name";
          leaf vpdn-template-name {
            type xr:Cisco-ios-xr-string {
              length "1..63" {
                description
                  "VPDN template name";
              }
              pattern "[a-zA-Z][-_.a-z0-9A-Z]*";
            }
            description
              "VPDN template name";
          }
          leaf description {
            type string {
              length "1..100" {
                description
                  "Up to 100 characters describing this VPDN template";
              }
            }
            description
              "Description for this VPDN template";
          }
          leaf l2tp-class {
            type xr:Cisco-ios-xr-string {
              length "1..79" {
                description
                  "L2TP class name";
              }
            }
            description
              "L2TP class  command";
          }
          container tunnel {
            description
              "L2TP tunnel commands";
            container busy {
              description
                "Busy list commands";
              leaf timeout {
                type uint32 {
                  range "60..65535" {
                    description
                      "Busy time out value in seconds";
                  }
                }
                description
                  "Busy timeout value";
              }
            }
          }
          container ipv4 {
            description
              "IPv4 settings for tunnel";
            leaf df-bit {
              type enumeration {
                enum "clear" {
                  value 0;
                  description
                    "Clear df bit";
                }
                enum "reflect" {
                  value 1;
                  description
                    "Reflect df bit from inner ip header";
                }
                enum "set" {
                  value 2;
                  description
                    "Set df bit";
                }
              }
              description
                "IPv4 don't fragment bit set/clear/reflect";
            }
            leaf source-addr {
              type inet:ipv4-address-no-zone;
              description
                "Set IP source";
            }
          }
          container ip {
            description
              "Set IP TOS value";
            leaf tos {
              type union {
                type enumeration {
                  enum "reflect" {
                    value -1;
                    description
                      "Reflect IP payload ToS on tunnel";
                  }
                }
                type uint32 {
                  range "0..255" {
                    description
                      "Type of service value";
                  }
                }
              }
              description
                "IP TOS value";
            }
          }
          container vpn {
            description
              "VPN ID/VRF name";
            leaf vrf {
              type xr:Cisco-ios-xr-string {
                length "1..32" {
                  description
                    "VRF name";
                }
              }
              description
                "VRF name";
            }
            container id {
              presence "Indicates id node is configured.";
              description
                "VPN ID";
              leaf oui {
                type xr:Hex-integer;
                mandatory true;
                description
                  "VPN ID, (OUI:VPN-Index) format(hex), 3 bytes OUI Part";
              }
              leaf index {
                type xr:Hex-integer;
                mandatory true;
                description
                  "VPN ID, (OUI:VPN-Index) format(hex), 4 bytes VPN_Index Part";
              }
            }
          }
          container dsl-line-info-forwarding {
            presence "Indicates a dsl-line-info-forwarding node is configured.";
            description
              "Forward DSL Line Info attributes";
          }
          container rate-convert-speed-avps {
            presence "Indicates a rate-convert-speed-avps node is configured.";
            description
              "DSL Line bps Info attributes";
          }
          container cisco-avp100-format-e-enable {
            presence "Indicates a cisco-avp100-format-e-enable node is configured.";
            description
              "To support NAS-Port format e in Cisco AVP 100";
          }
          container caller-id {
            description
              "Options to apply on calling station id";
            container mask-method {
              description
                "Mask characters by method";
              container remove {
                description
                  "Remove CLID";
                leaf match {
                  type xr:Cisco-ios-xr-string {
                    length "1..63" {
                      description
                        "Match substring";
                    }
                  }
                  description
                    "set match string";
                }
              }
            }
          }
        }
      }
    }
  }
}
