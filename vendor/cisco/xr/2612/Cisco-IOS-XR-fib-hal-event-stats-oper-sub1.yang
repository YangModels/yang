submodule Cisco-IOS-XR-fib-hal-event-stats-oper-sub1 {
  belongs-to Cisco-IOS-XR-fib-hal-event-stats-oper {
    prefix Cisco-IOS-XR-fib-hal-event-stats-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-hal-event-stats package operational data.
     
     Copyright (c) 2013-2026 by Cisco Systems, Inc.
     All rights reserved.";

  revision 2026-02-10 {
    description
      "Added new section for GTRIE leaf statistics";
    semver:module-version "1.0.0";
  }
  revision 2025-02-17 {
    description
      "Added new leaves for backwalk counters and engine failures";
  }
  revision 2024-03-27 {
    description
      "Event stats for LDI type change";
  }
  revision 2019-04-05 {
    description
      "Establish semantic version baseline.";
  }
  revision 2015-11-09 {
    description
      "IOS XR 6.0 revision.";
  }

  grouping FIB-HAL-BAG-LDI-TYPE-CHANGE-EVT-STATS {
    description
      "LDI Type Change Event Stats";
    leaf-list evt-cnt {
      type uint32;
      max-elements "4";
      description
        "evt cnt";
    }
  }

  grouping FIB-HAL-BAG-GTRIE-EVENT-STATS {
    description
      "Gtrie Event Stats";
    leaf-list event-time {
      type uint64;
      max-elements "5";
      description
        "event time";
    }
    leaf-list eng-event-time {
      type uint64;
      max-elements "5";
      description
        "eng event time";
    }
    list event-cnt {
      max-elements "5";
      description
        "event cnt";
      uses FIB-HAL-BAG-EVENT-COUNT;
    }
  }

  grouping FIB-HAL-BAG-PER-HALOBJ-EVENT-STATS {
    description
      "HAL Obj Event Stats";
    leaf-list hal-event-time {
      type uint64;
      max-elements "28";
      description
        "hal event time";
    }
    leaf-list eng-event-time {
      type uint64;
      max-elements "28";
      description
        "eng event time";
    }
    leaf-list hal-bkwlk-event-time {
      type uint64;
      max-elements "28";
      description
        "hal bkwlk event time";
    }
    leaf-list eng-bkwlk-event-time {
      type uint64;
      max-elements "28";
      description
        "eng bkwlk event time";
    }
    list event-cnt {
      max-elements "28";
      description
        "event cnt";
      uses FIB-HAL-BAG-EVENT-COUNT;
    }
    list bkwlk-event-cnt {
      max-elements "28";
      description
        "bkwlk event cnt";
      uses FIB-HAL-BAG-EVENT-COUNT;
    }
  }

  grouping FIB-HAL-BAG-EVENT-COUNT {
    description
      "HAL Event Count";
    leaf success {
      type uint32;
      description
        "success";
    }
    leaf failure {
      type uint32;
      description
        "failure";
    }
    leaf engine-failure-cnt {
      type uint32;
      description
        "engine failure cnt";
    }
    leaf timing-anomaly {
      type uint32;
      description
        "timing anomaly";
    }
    leaf timed-events {
      type uint32;
      description
        "timed events";
    }
  }

  grouping FIB-HAL-BAG-PER-FIBOBJ-EVENT-STATS {
    description
      "FIB Obj Event Stats";
    leaf-list event-time {
      type uint64;
      max-elements "28";
      description
        "event time";
    }
    list event-cnt {
      max-elements "28";
      description
        "event cnt";
      uses FIB-HAL-BAG-EVENT-COUNT;
    }
  }

  grouping FIB-HAL-BAG-EVENT-STATS {
    description
      "FIB HAL Gtrie Events Stats";
    leaf cycles-per-sec {
      type uint64;
      description
        "cycles per sec";
    }
    leaf first-event-time {
      type uint64;
      description
        "first event time";
    }
    leaf last-event-time {
      type uint64;
      description
        "last event time";
    }
    leaf total-anomaly-time {
      type uint64;
      description
        "total anomaly time";
    }
    leaf ler {
      type uint32;
      description
        "ler";
    }
    leaf cfg-ler {
      type uint32;
      description
        "cfg ler";
    }
    leaf timing-freq {
      type uint32;
      description
        "timing freq";
    }
    leaf gl-ler {
      type boolean;
      description
        "gl ler";
    }
    list fibobj {
      max-elements "116";
      description
        "fibobj";
      uses FIB-HAL-BAG-PER-FIBOBJ-EVENT-STATS;
    }
    list halobj {
      max-elements "176";
      description
        "halobj";
      uses FIB-HAL-BAG-PER-HALOBJ-EVENT-STATS;
    }
    list gtrie {
      max-elements "16";
      description
        "gtrie";
      uses FIB-HAL-BAG-GTRIE-EVENT-STATS;
    }
    list type-change {
      max-elements "6";
      description
        "type change";
      uses FIB-HAL-BAG-LDI-TYPE-CHANGE-EVT-STATS;
    }
  }
}
