module Cisco-IOS-XR-sysadmin-ethsw-esdma-mgmt-agent {
  namespace "http://www.cisco.com/ns/yang/Cisco-IOS-XR-sysadmin-ethsw-esdma-mgmt-agent";
  prefix esdma_mgmt_agent;

  import ietf-inet-types {
    prefix inet;
  }
  import Cisco-IOS-XR-sysadmin-ethsw-esdma-types {
    prefix esdma_types;
  }
  import Cisco-IOS-XR-sysadmin-ethsw-esdma-trace {
    prefix esdma_trace;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch mgmt-agent' commands.
     
     Copyright (c) 2011-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping esdma-debug {
    container connections {
      container esdma-info {
        leaf active-esdma-address {
          type inet:ip-address;
        }
      }
      list sdr-nm-client-id {
        leaf sdr-nm-ip-address {
          type inet:ip-address;
        }
        leaf sdr-nm-port-num {
          type inet:port-number;
        }
      }
      leaf sdr-nm-num-clients {
        type uint32;
      }
      list esd-client-id {
        leaf esd-client-ip-address {
          type inet:ip-address;
        }
        leaf esd-client-port-num {
          type inet:port-number;
        }
        leaf esd-client-location {
          type string;
        }
        leaf esd-client-switch-info-cached {
          type esdma_types:esdma-switch-yes-no-enum;
        }
        leaf esd-client-sdr-info-cached {
          type esdma_types:esdma-switch-yes-no-enum;
        }
      }
      leaf esd-client-num-clients {
        type uint32;
      }
      list mlap-client-id {
        leaf mlap-client-ip-address {
          type inet:ip-address;
        }
        leaf mlap-client-port-num {
          type inet:port-number;
        }
        leaf mlap-client-location {
          type string;
        }
        leaf mlap-client-switch-info-cached {
          type esdma_types:esdma-switch-yes-no-enum;
        }
      }
      leaf mlap-client-num-clients {
        type uint32;
      }
    }
  }

  grouping esdma-mgmt-group {
    container mgmt-agent {
      uses esdma_trace:esdma-ctrace;
      uses esdma-debug;
    }
  }
}
