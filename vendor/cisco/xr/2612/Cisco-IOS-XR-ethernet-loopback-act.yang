module Cisco-IOS-XR-ethernet-loopback-act {
  namespace "http://cisco.com/ns/yang/Cisco-IOS-XR-ethernet-loopback-act";
  prefix ethernet-loopback-act;

  import ietf-yang-types {
    prefix yang;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet loopback actions.
     
     Copyright (c) 2020-2021, 2023 by Cisco Systems, Inc.
     All rights reserved.";

  revision 2021-09-15 {
    description
      "Add ethernet-services task name to the RPCs.";
  }
  revision 2020-03-06 {
    description
      "IOS XR 7.4.1 revision.";
  }

  typedef loopback-direction {
    type enumeration {
      enum "external" {
        description
          "External loopback (wire loopback)";
      }
      enum "internal" {
        description
          "Internal loopback (bridge loopback)";
      }
    }
    description
      "Direction of loopback";
  }

  typedef loopback-status {
    type enumeration {
      enum "inactive" {
        description
          "Loopback is not active";
      }
      enum "active" {
        description
          "Loopback is active";
      }
    }
    description
      "Status of loopback session";
  }

  typedef vlan-type {
    type enumeration {
      enum "dot1q" {
        description
          "Dot1q outer VLAN type";
      }
      enum "dot1ad" {
        description
          "Dot1ad outer VLAN type";
      }
    }
    description
      "Type of the outer VLAN ID";
  }

  grouping EDPL-REMOTE-VLAN-TYPE {
    description
      "Encapsulation specification for remote loopback commands";
    leaf outer-type {
      type vlan-type;
      description
        "Type of outer VLAN ID";
    }
    leaf outer-vlan-ids {
      type string;
      description
        "Outer VLAN ID";
    }
    leaf inner-vlan-ids {
      type string;
      description
        "Inner VLAN ID";
    }
    leaf all-vlans {
      type boolean;
      description
        "Include the all-vlans flag in the remote request";
    }
  }

  grouping EDPL-CFM-INFO-TYPE {
    description
      "CFM domain and service specification";
    leaf domain {
      type string;
      mandatory true;
      description
        "CFM domain name";
    }
    leaf service {
      type string;
      mandatory true;
      description
        "CFM service name";
    }
  }

  grouping EDPL-REMOTE-TARGET-TYPE {
    description
      "Information on remote session target";
    leaf mac {
      type yang:mac-address;
      description
        "Target remote mac address";
    }
    leaf mep {
      type uint16;
      description
        "ID of target remote MEP";
    }
  }

  grouping EDPL-REMOTE-SESSION-LIST-TYPE {
    description
      "List of remote sessions";
    list session {
      description
        "List of remote sessions";
      leaf mac {
        type yang:mac-address;
        description
          "Remote mac address";
      }
      leaf direction {
        type loopback-direction;
        description
          "Loopback session direction";
      }
      leaf timer {
        type uint32;
        description
          "Remaining session time, in seconds";
      }
      leaf status {
        type loopback-status;
        description
          "Loopback session status";
      }
    }
  }

  rpc ethernet-loopback-start-local {
    description
      "Start a local ethernet loopback session";
    input {
      leaf interface {
        type xr:Interface-name;
        mandatory true;
        description
          "Interface on which to start the loopback";
      }
      leaf direction {
        type loopback-direction;
        mandatory true;
        description
          "Loopback direction";
      }
      leaf source-mac {
        type yang:mac-address;
        description
          "Source mac to filter on";
      }
      leaf dest-mac {
        type yang:mac-address;
        description
          "Destination mac to filter on";
      }
      leaf outer-type {
        type vlan-type;
        description
          "Type of outer VLAN ID to filter on";
      }
      leaf outer-vlan-ids {
        type string;
        description
          "Outer VLAN ID or IDs to filter on";
      }
      leaf inner-vlan-ids {
        type string;
        description
          "Inner VLAN ID or IDs to filter on";
      }
      leaf ether-type {
        type uint16;
        description
          "Ether-type to filter";
      }
      leaf cos {
        type uint8 {
          range "0..7";
        }
        description
          "Class of service to filter on";
      }
      leaf llc-oui {
        type uint32 {
          range "0..16777215";
        }
        description
          "LLC-OUI to filter on";
      }
      leaf timeout {
        type uint32 {
          range "0..604800";
        }
        description
          "Loopback duration in seconds";
      }
    }
    output {
      leaf id {
        type uint32;
        description
          "Session ID";
      }
    }
    xr:xr-task "ethernet-services";
  }
  rpc ethernet-loopback-stop-local {
    description
      "Stop a local ethernet loopback session";
    input {
      leaf interface {
        type xr:Interface-name;
        mandatory true;
        description
          "Interface on which the loopback session is running";
      }
      leaf id {
        type uint32;
        mandatory true;
        description
          "ID of session to stop";
      }
    }
    xr:xr-task "ethernet-services";
  }
  rpc ethernet-loopback-extend-local {
    description
      "Extend a local ethernet loopback session";
    input {
      leaf interface {
        type xr:Interface-name;
        mandatory true;
        description
          "Interface on which the loopback session is running";
      }
      leaf id {
        type uint32;
        mandatory true;
        description
          "ID of session to extend";
      }
      leaf timeout {
        type uint32 {
          range "0..604800";
        }
        description
          "Loopback duration in seconds";
      }
    }
    xr:xr-task "ethernet-services";
  }
  rpc ethernet-loopback-start-remote {
    description
      "Start a remote ethernet loopback session";
    input {
      leaf interface {
        type xr:Interface-name;
        mandatory true;
        description
          "Interface on which to send the request";
      }
      uses EDPL-REMOTE-TARGET-TYPE;
      uses EDPL-CFM-INFO-TYPE;
      uses EDPL-REMOTE-VLAN-TYPE;
      leaf timeout {
        type uint32 {
          range "1..604800";
        }
        mandatory true;
        description
          "Loopback duration in seconds";
      }
    }
    xr:xr-task "ethernet-services";
  }
  rpc ethernet-loopback-stop-remote {
    description
      "Stop a remote ethernet loopback session";
    input {
      leaf interface {
        type xr:Interface-name;
        mandatory true;
        description
          "Interface on which to send the request";
      }
      uses EDPL-REMOTE-TARGET-TYPE;
      uses EDPL-CFM-INFO-TYPE;
      uses EDPL-REMOTE-VLAN-TYPE;
    }
    xr:xr-task "ethernet-services";
  }
  rpc ethernet-loopback-extend-remote {
    description
      "Extend a remote ethernet loopback session";
    input {
      leaf interface {
        type xr:Interface-name;
        mandatory true;
        description
          "Interface on which to send the request";
      }
      uses EDPL-REMOTE-TARGET-TYPE;
      uses EDPL-CFM-INFO-TYPE;
      uses EDPL-REMOTE-VLAN-TYPE;
      leaf timeout {
        type uint32 {
          range "1..604800";
        }
        mandatory true;
        description
          "Loopback duration in seconds";
      }
    }
    xr:xr-task "ethernet-services";
  }
  rpc ethernet-loopback-get-state-remote {
    description
      "Retrieve the state of a remote ethernet loopback session";
    input {
      leaf interface {
        type xr:Interface-name;
        mandatory true;
        description
          "Interface on which to send the request";
      }
      uses EDPL-REMOTE-TARGET-TYPE;
      uses EDPL-CFM-INFO-TYPE;
      uses EDPL-REMOTE-VLAN-TYPE;
    }
    output {
      uses EDPL-REMOTE-SESSION-LIST-TYPE;
    }
    xr:xr-task "ethernet-services";
  }
  rpc ethernet-loopback-discover-remote {
    description
      "Send a discovery request to retrieve information on remote loopback sessions";
    input {
      leaf interface {
        type xr:Interface-name;
        mandatory true;
        description
          "Interface on which to send the request";
      }
      uses EDPL-CFM-INFO-TYPE;
      uses EDPL-REMOTE-VLAN-TYPE;
    }
    output {
      uses EDPL-REMOTE-SESSION-LIST-TYPE;
    }
    xr:xr-task "ethernet-services";
  }
}
