module Cisco-IOS-XR-infra-fti-oper {
  namespace "http://cisco.com/ns/yang/Cisco-IOS-XR-infra-fti-oper";
  prefix infra-fti-oper;

  import Cisco-IOS-XR-types {
    prefix xr;
  }
  import cisco-semver {
    prefix semver;
  }
  include Cisco-IOS-XR-infra-fti-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-fti package operational data.
     
     This module contains definitions
     for the following management objects:
       dci-fabric-interconnect: Display FTI operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container dci-fabric-interconnect {
    config false;
    description
      "Display FTI operational data";
    container opflex-session-infos {
      description
        "FTI Opflex Session Info for all fabrics";
      list opflex-session-info {
        key "id1";
        description
          "FTI Opflex Session Info for a particular fabric";
        leaf id1 {
          type uint32 {
            range "1000..9999";
          }
          description
            "fabric identifier";
        }
        uses FTI-FABRIC-SESSION-INFO;
      }
    }
    container fabric-vrf-dbs {
      description
        "FTI Fabric-VRF DB for all fabrics";
      list fabric-vrf-db {
        key "id1";
        description
          "FTI Fabric-VRF DB for a particular fabric";
        leaf id1 {
          type uint32 {
            range "1000..9999";
          }
          description
            "fabric identifier";
        }
        uses FTI-FABRIC-VRF-INFO;
      }
    }
    container dci-vrfs {
      description
        "FTI DCI-VRF DB for all VRFs";
      list dci-vrf {
        key "vrf1";
        description
          "FTI DCI-VRF Info for a particular VRF";
        leaf vrf1 {
          type xr:Cisco-ios-xr-string;
          description
            "vrf name";
        }
        uses FTI-DCI-VRF-INFO;
      }
    }
    container acp {
      description
        "Auto Config Pool Info";
      uses FTI-ACP;
    }
  }
}
