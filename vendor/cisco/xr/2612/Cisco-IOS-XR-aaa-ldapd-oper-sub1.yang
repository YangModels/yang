submodule Cisco-IOS-XR-aaa-ldapd-oper-sub1 {
  belongs-to Cisco-IOS-XR-aaa-ldapd-oper {
    prefix Cisco-IOS-XR-aaa-ldapd-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR aaa-ldapd package operational data.
     
     Copyright (c) 2013-2022 by Cisco Systems, Inc.
     All rights reserved.";

  revision 2022-05-20 {
    description
      "Dynamic NACM feature commit.";
    semver:module-version "1.0.0";
  }
  revision 2019-04-05 {
    description
      "Establish semantic version baseline.";
  }
  revision 2015-11-09 {
    description
      "IOS XR 6.0 revision.";
  }

  grouping AAA-LDAPD-SERVERBAG {
    description
      "AAA LDAPD SERVERBAG";
    leaf addr {
      type inet:ipv4-address;
      description
        "internet address of ldap server";
    }
    leaf port {
      type uint32;
      description
        "per server port to use";
    }
    leaf bytes-in {
      type uint64;
      units "byte";
      description
        "# of bytes read";
    }
    leaf bytes-out {
      type uint64;
      units "byte";
      description
        "# of bytes out";
    }
    leaf closes {
      type uint32;
      description
        "socket closes";
    }
    leaf opens {
      type uint32;
      description
        "socket opens";
    }
    leaf errors {
      type uint32;
      description
        "error count";
    }
    leaf aborts {
      type uint32;
      description
        "abort count";
    }
    leaf paks-in {
      type uint32;
      description
        "# of incoming packets read";
    }
    leaf paks-out {
      type uint32;
      description
        "# of outgoing packets sent";
    }
    leaf replies-expected {
      type uint32;
      description
        "# of replies expected to arrive";
    }
    leaf up {
      type boolean;
      description
        "is the server UP or down ?";
    }
    leaf conn-up {
      type boolean;
      description
        "is the server connected ?";
    }
    leaf is-private {
      type boolean;
      description
        "is this a private server ?";
    }
    leaf connect-timeout {
      type uint32;
      description
        "Connect timeout: configured range 0-1000sec";
    }
    leaf bind-timeout {
      type uint32;
      description
        "Bind timeout: configured range 0-1000sec";
    }
    leaf search-timeout {
      type uint32;
      description
        "Search timeout: configured range 0-1000sec";
    }
    leaf connection-attempted {
      type int64;
      description
        "last attempted contact time";
    }
    leaf vrf-name {
      type string {
        length "0..33";
      }
      description
        "VRF in which server is reachable";
    }
    leaf addr-buf {
      type string {
        length "0..46";
      }
      description
        "IP address buffer";
    }
    leaf family {
      type string {
        length "0..5";
      }
      description
        "IP address Family";
    }
  }

  grouping AAA-LDAPD-SERVERS {
    description
      "AAA LDAPD SERVERS";
    list server {
      key "addr port";
      description
        "server";
      uses AAA-LDAPD-SERVERBAG;
    }
  }
}
