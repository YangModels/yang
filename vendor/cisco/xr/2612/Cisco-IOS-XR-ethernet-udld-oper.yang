module Cisco-IOS-XR-ethernet-udld-oper {
  namespace "http://cisco.com/ns/yang/Cisco-IOS-XR-ethernet-udld-oper";
  prefix ethernet-udld-oper;

  import Cisco-IOS-XR-types {
    prefix xr;
  }
  import cisco-semver {
    prefix semver;
  }
  include Cisco-IOS-XR-ethernet-udld-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-udld package operational data.
     
     This module contains definitions
     for the following management objects:
       udld: UDLD operational information
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container udld {
    config false;
    description
      "UDLD operational information";
    container statistics-nodes {
      description
        "Per node operational statistics";
      list statistics-node {
        key "node";
        description
          "UDLD statistics for the node";
        leaf node {
          type xr:Node-id;
          description
            "Node";
        }
        uses UDLD-BAG-STATS-NODE-DATA;
      }
    }
    container data-interfaces {
      description
        "Per interface UDLD operational data";
      list data-interface {
        key "udld-interface";
        description
          "UDLD data for the interface";
        leaf udld-interface {
          type xr:Interface-name;
          description
            "UDLD interface";
        }
        uses UDLD-BAG-PORT-DATA;
      }
    }
    container statistics-interfaces {
      description
        "Per UDLD interface operational statistics";
      list statistics-interface {
        key "udld-interface";
        description
          "UDLD statistics for the interface";
        leaf udld-interface {
          type xr:Interface-name;
          description
            "UDLD interface";
        }
        uses UDLD-BAG-STATS-PORT-DATA;
      }
    }
  }
}
