submodule Cisco-IOS-XR-8000-platforms-npu-latency-histogram-oper-sub1 {
  belongs-to Cisco-IOS-XR-8000-platforms-npu-latency-histogram-oper {
    prefix Cisco-IOS-XR-8000-platforms-npu-latency-histogram-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR 8000-platforms-npu-latency-histogram package operational data.
     
     Copyright (c) 2013-2025 by Cisco Systems, Inc.
     All rights reserved.";

  revision 2025-03-12 {
    description
      "Create the initial npu-latency-histogram oper yang model.";
    semver:module-version "1.0.0";
  }
  revision 2019-04-05 {
    description
      "Establish semantic version baseline.";
  }
  revision 2015-11-09 {
    description
      "IOS XR 6.0 revision.";
  }

  grouping OFA-TCLATENCYHISTOGRAM-BINS {
    description
      "Per time record structure for a tclatency
       histogram bins info";
    leaf timestamp {
      type uint64;
      description
        "timestamp of record";
    }
    leaf tc {
      type uint8;
      description
        "traffic class";
    }
    leaf slice {
      type uint8;
      description
        "slice";
    }
    leaf ifg {
      type uint8;
      description
        "interface grouping";
    }
    leaf-list bins {
      type uint64;
      max-elements "9";
      description
        "latency interval bins";
    }
  }

  grouping OFA-TCLATENCYHISTOGRAM-BINS-ARRAY-ST {
    description
      "Resource level information";
    leaf npu-id {
      type uint8;
      description
        "NPU ID";
    }
    leaf cfg-value-bin-max-delay {
      type string {
        length "0..32";
      }
      description
        "max delay header label";
    }
    leaf entry-count {
      type uint32;
      description
        "entry count";
    }
    leaf-list cfg-value-bin {
      type uint64;
      max-elements "8";
      description
        "configured value bins";
    }
    list record {
      key "timestamp";
      description
        "per TC entry";
      uses OFA-TCLATENCYHISTOGRAM-BINS;
    }
  }
}
