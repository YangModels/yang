module Cisco-IOS-XR-ipv4-telnet-cfg {
  namespace "http://cisco.com/ns/yang/Cisco-IOS-XR-ipv4-telnet-cfg";
  prefix ipv4-telnet-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-telnet package configuration.
     
     This module contains definitions
     for the following management objects:
       ipv6-telnet: IPv6 telnet configuration. (Telnet is deprecated
         since 25.4.1. SSH is recommended instead.)
       ipv4-telnet: IPv4 telnet configuration. (Telnet is deprecated
         since 25.4.1. SSH is recommended instead.)
     
     Copyright (c) 2013-2025 by Cisco Systems, Inc.
     All rights reserved.";

  revision 2025-08-22 {
    description
      "Deprecated Telnet Configurations";
    semver:module-version "1.1.0";
  }
  revision 2019-04-05 {
    description
      "Establish semantic version baseline.";
    semver:module-version "1.0.1";
  }
  revision 2015-11-09 {
    description
      "IOS XR 6.0 revision.";
  }

  grouping CLIENT {
    description
      "Common node of ipv4-telnet, ipv6-telnet";
    container client {
      status deprecated;
      description
        "Telnet client configuration. (Telnet is
         deprecated since 25.4.1. SSH is recommended
         instead.)";
      leaf source-interface {
        type xr:Interface-name;
        description
          "Source interface for telnet sessions";
      }
    }
  }

  container ipv6-telnet {
    status deprecated;
    description
      "IPv6 telnet configuration. (Telnet is deprecated
       since 25.4.1. SSH is recommended instead.)";
    uses CLIENT;
  }
  container ipv4-telnet {
    status deprecated;
    description
      "IPv4 telnet configuration. (Telnet is deprecated
       since 25.4.1. SSH is recommended instead.)";
    uses CLIENT;
  }
}
