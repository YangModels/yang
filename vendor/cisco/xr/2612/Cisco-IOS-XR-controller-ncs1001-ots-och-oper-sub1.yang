submodule Cisco-IOS-XR-controller-ncs1001-ots-och-oper-sub1 {
  belongs-to Cisco-IOS-XR-controller-ncs1001-ots-och-oper {
    prefix Cisco-IOS-XR-controller-ncs1001-ots-och-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-ncs1001-ots-och package operational data.
     
     Copyright (c) 2013-2024 by Cisco Systems, Inc.
     All rights reserved.";

  revision 2024-10-15 {
    description
      "Added last link flap field";
    semver:module-version "1.0.0";
  }
  revision 2022-11-24 {
    description
      "leaves receive-power, transmit-power are removed and receive-power-dbm, transmit-power-dbm are modified to receive-power, transmit-power in OTS-EDM-LANE-DATA group";
  }
  revision 2019-04-05 {
    description
      "Establish semantic version baseline.";
  }
  revision 2015-11-09 {
    description
      "IOS XR 6.0 revision.";
  }

  typedef Ta-state {
    type enumeration {
      enum "ta-state-ui-oos" {
        value 0;
        description
          "Out Of Service";
      }
      enum "ta-state-ui-main" {
        value 1;
        description
          "Maintenance";
      }
      enum "ta-state-ui-is" {
        value 2;
        description
          "In Service";
      }
      enum "ta-state-ui-ains" {
        value 3;
        description
          "Automatic In Service";
      }
    }
    description
      "Ta state";
  }

  typedef Controller-state {
    type enumeration {
      enum "state-up" {
        value 0;
        description
          "Up";
      }
      enum "state-down" {
        value 1;
        description
          "Down";
      }
      enum "state-admin-down" {
        value 2;
        description
          "Administratively Down";
      }
    }
    description
      "Controller state";
  }

  typedef Ots-port-status {
    type enumeration {
      enum "active" {
        value 0;
        description
          "Active";
      }
      enum "standby" {
        value 1;
        description
          "Standby";
      }
    }
    description
      "Ots port status";
  }

  typedef Ots-laser-state {
    type enumeration {
      enum "on" {
        value 0;
        description
          "On";
      }
      enum "off" {
        value 1;
        description
          "Off";
      }
      enum "unknown" {
        value 2;
        description
          "Unknown";
      }
      enum "apr" {
        value 3;
        description
          "Apr";
      }
      enum "na" {
        value 4;
        description
          "N/A";
      }
    }
    description
      "Ots laser state";
  }

  typedef Ots-port {
    type enumeration {
      enum "com" {
        value 0;
        description
          "Com";
      }
      enum "line" {
        value 1;
        description
          "Line";
      }
      enum "osc" {
        value 2;
        description
          "Osc";
      }
      enum "com-check" {
        value 3;
        description
          "Com Check";
      }
      enum "work" {
        value 4;
        description
          "Working";
      }
      enum "prot" {
        value 5;
        description
          "Protected";
      }
    }
    description
      "Ots port";
  }

  grouping ALARM-DETAIL {
    description
      "Alarm Detail";
    leaf is-detected {
      type boolean;
      description
        "Flag indicating if defect is detected";
    }
    leaf counter {
      type uint32;
      description
        "Alarm counter";
    }
  }

  grouping OTS-OCH-EDM-ALARM-INFO {
    description
      "Ots-Och Alarm Information";
    container low-tx-power {
      description
        "Low Tx Power in units of 0.1 dBm";
      uses ALARM-DETAIL;
    }
    container low-rx-power {
      description
        "Low Rx Power in units of 0.1 dBm";
      uses ALARM-DETAIL;
    }
  }

  grouping OTS-EDM-LANE-DATA {
    description
      "Grey lane data";
    leaf laser-bias-current-milli-amps {
      type uint32;
      description
        "Laser Bias Current in units of 0.01mA";
    }
    leaf laser-bias-current-percent {
      type uint32;
      units "percentage";
      description
        "Laser Bias Current in units of 0.01 percentage";
    }
    leaf receive-power {
      type int32;
      description
        "Transponder receive power in the units of 0
         .01dBm";
    }
    leaf transmit-power {
      type int32;
      description
        "Transmit power in the units of 0.01dBm";
    }
  }

  grouping OTS-OCH-EDM-INFO {
    description
      "Ots-Och transponder information";
    container lane-data {
      description
        "Lane information";
      uses OTS-EDM-LANE-DATA;
    }
    container ots-och-alarm-info {
      description
        "Ots-Och Alarm information";
      uses OTS-OCH-EDM-ALARM-INFO;
    }
    leaf port-type {
      type Ots-port;
      description
        "Port type information";
    }
    leaf laser-state {
      type Ots-laser-state;
      description
        "Laser State information";
    }
    leaf port-status {
      type Ots-port-status;
      description
        "Port status information";
    }
    leaf channel-width {
      type uint32;
      description
        "Channel Width (in units of GHz)";
    }
    leaf channel-central-freq {
      type uint64;
      description
        "Channel Central Frequency";
    }
    leaf rx-psd {
      type string;
      description
        "Received Power spectral density in microwatts
         per megahertz, uW/MHz";
    }
    leaf tx-psd {
      type string;
      description
        "Transmit Power spectral density in microwatts
         per megahertz, uW/MHz";
    }
    leaf controller-state {
      type Controller-state;
      description
        "Ots-Och controller state";
      xr:event-telemetry "Subscribe Telemetry Event";
    }
    leaf transport-admin-state {
      type Ta-state;
      description
        "Transport Admin State";
      xr:event-telemetry "Subscribe Telemetry Event";
    }
    leaf rx-low-threshold {
      type int32;
      description
        "Rx Low threshold value in units of 0.1dBm";
    }
    leaf tx-low-threshold {
      type int32;
      description
        "Tx Low threshold value in units of 0.1dBm";
    }
    leaf rx-power-th-configurable {
      type boolean;
      description
        "Is Rx Low Threshold Configurable";
    }
    leaf tx-power-th-configurable {
      type boolean;
      description
        "Is Tx Low Threshold Configurable";
    }
  }
}
