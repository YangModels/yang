module Cisco-IOS-XR-ip-icmp-probe-act {
  namespace "http://cisco.com/ns/yang/Cisco-IOS-XR-ip-icmp-probe-act";
  prefix ip-icmp-probe-act;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ICMP Probe (RFC-8335) action data.
     
     Copyright (c) 2025 by Cisco Systems, Inc., and/or its affiliates.
     All rights reserved.";

  revision 2025-02-26 {
    description
      "Initial release of RFC-8335 Probe RPC";
    semver:module-version "1.0.0";
  }

  typedef probe-reply-state {
    type enumeration {
      enum "reserved" {
        value 0;
        description
          "Reserved";
      }
      enum "incomplete" {
        value 1;
        description
          "Incomplete";
      }
      enum "reachable" {
        value 2;
        description
          "Reachable";
      }
      enum "stale" {
        value 3;
        description
          "Stale";
      }
      enum "delay" {
        value 4;
        description
          "Delay";
      }
      enum "probe" {
        value 5;
        description
          "Probe";
      }
      enum "failed" {
        value 6;
        description
          "Failed";
      }
    }
    description
      "Probe reply state type";
  }

  typedef probe-reply-code {
    type enumeration {
      enum "no-error" {
        value 0;
        description
          "No Error";
      }
      enum "malformed-query" {
        value 1;
        description
          "Malformed Query";
      }
      enum "no-such-interface" {
        value 2;
        description
          "No Such Interface";
      }
      enum "no-such-table-entry" {
        value 3;
        description
          "No Such Table Entry";
      }
      enum "multiple-interfaces-satisfy-query" {
        value 4;
        description
          "Multiple Interfaces Satisfy Query";
      }
    }
    description
      "Probe reply code type";
  }

  rpc icmp-probe {
    description
      "Initiate Probe Request";
    input {
      leaf destination {
        type string;
        mandatory true;
        description
          "Destination address or hostname";
      }
      leaf source-interface {
        type xr:Interface-name;
        description
          "Source interface";
      }
      leaf source-address {
        type inet:ip-address-no-zone;
        description
          "Source address";
      }
      leaf vrf-name {
        type string;
        description
          "VRF name";
      }
      leaf repeat-count {
        type uint32;
        description
          "Number of probes to send";
      }
      leaf timeout {
        type uint32;
        description
          "Timeout in seconds";
      }
      leaf ttl {
        type uint32;
        description
          "Time to live";
      }
      leaf local-probed-interface {
        type xr:Interface-name;
        description
          "Local probed interface";
      }
      leaf remote-probed-address {
        type inet:ip-address-no-zone;
        description
          "Remote probed address";
      }
    }
    output {

      grouping probe-reply {
        description
          "Probe reply including timeout response";
        leaf sequence-num {
          type uint32;
          description
            "Sequence number from Probe Reply, or the sequence number of the Probe Request that timed out";
        }
        leaf timed-out {
          type boolean;
          description
            "No response was received before the next packet was sent";
        }
        leaf ttl {
          type uint8;
          description
            "IPv4 TTL or IPv6 Hop Limit in Probe Reply";
        }
        leaf rtt {
          type uint32;
          units "microseconds";
          description
            "Round trip time, in microseconds";
        }
        leaf bytes {
          type uint32;
          units "bytes";
          description
            "Size of ICMP reply, in bytes";
        }
        leaf reply-source {
          type inet:ip-address-no-zone;
          description
            "Source address from the Probe Reply packet";
        }
        leaf active {
          type boolean;
          description
            "The A-bit from the Probe Reply packet";
        }
        leaf ipv4 {
          type boolean;
          description
            "The 4-bit from the Probe Reply packet";
        }
        leaf ipv6 {
          type boolean;
          description
            "The 6-bit from the Probe Reply packet";
        }
        leaf state {
          type probe-reply-state;
          description
            "The State field from the Probe Reply packet";
        }
        leaf code {
          type probe-reply-code;
          description
            "The Code field from the Probe Reply packet";
        }
      }
      container probe-replies {
        description
          "list of responses";
        list probe-reply {
          description
            "probe-reply";
          uses probe-reply;
        }
      }
    }
  }
}
