module Cisco-IOS-XR-wd-death-notif-configured-proc-oper {
  namespace "http://cisco.com/ns/yang/Cisco-IOS-XR-wd-death-notif-configured-proc-oper";
  prefix wd-death-notif-configured-proc-oper;

  import Cisco-IOS-XR-types {
    prefix xr;
  }
  import cisco-semver {
    prefix semver;
  }
  include Cisco-IOS-XR-wd-death-notif-configured-proc-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR wd-death-notif-configured-proc package operational data.
     
     This module contains definitions
     for the following management objects:
       process-death-notification: Process death notification
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container process-death-notification {
    config false;
    description
      "Process death notification";
    container processes-configured {
      description
        "Processes configured to receive death
         notification";
      container nodes {
        description
          "Table for per-node configured process data";
        list node {
          key "node";
          description
            "Per node configured process data";
          leaf node {
            type xr:Node-id;
            description
              "Node location";
          }
          uses CONFIGURED-PROC-INFO-BAG;
        }
      }
    }
  }
}
