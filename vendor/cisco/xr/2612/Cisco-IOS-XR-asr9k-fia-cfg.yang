module Cisco-IOS-XR-asr9k-fia-cfg {
  namespace "http://cisco.com/ns/yang/Cisco-IOS-XR-asr9k-fia-cfg";
  prefix asr9k-fia-cfg;

  import Cisco-IOS-XR-config-mda-cfg {
    prefix node;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-fia package configuration.
     
     This module contains definitions
     for the following management objects:
       fabric-fia-config: Configure Global Fabric Fia Settings
     
     This YANG module augments the
       Cisco-IOS-XR-config-mda-cfg
     module with configuration data.
     
     Copyright (c) 2013-2019 by Cisco Systems, Inc.
     All rights reserved.";

  revision 2019-04-05 {
    description
      "Establish semantic version baseline.";
    semver:module-version "1.0.0";
  }
  revision 2017-08-17 {
    description
      "IOS XR 6.4.1 revision.";
  }
  revision 2015-11-09 {
    description
      "IOS XR 6.0 revision.";
  }

  grouping NODE-CFG {
    description
      "active/preconfigured nodes configuration";
    container fia-buffer-profile-cfg {
      description
        "Fia Buffer Profile configuration";
      leaf xl {
        type boolean;
        description
          "Enable to use Extra large Buffer profile";
      }
    }
    container fia-vqi-shaper-cfg {
      description
        "Fia VQI Shaper configuration";
      leaf enhance {
        type boolean;
        description
          "Enable to use Enhanced VQI shaper limit";
      }
    }
    container port-queue-remaps {
      description
        "Remap front panel port to fabric queue for
         A9K-48X10GE-1G-xx and A9K-24X10GE-1G-xx ";
      list port-queue-remap {
        key "port";
        description
          "Front panel port number";
        leaf fabric-queue {
          type uint32 {
            range "0..19";
          }
          description
            "queue number <0-19>";
        }
        leaf port {
          type uint32 {
            range "0..47";
          }
          description
            "port number <10,11,22,23 34,35,46,47>";
        }
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
  container fabric-fia-config {
    description
      "Configure Global Fabric Fia Settings";
    container fia-intf-policer {
      description
        "FIA interface rate-limiter on 7-Fabric LC";
      leaf disable {
        type boolean;
        description
          "disable FIA interface policer ";
      }
    }
  }
}
