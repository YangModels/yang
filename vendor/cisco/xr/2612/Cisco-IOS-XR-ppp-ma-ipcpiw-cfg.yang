module Cisco-IOS-XR-ppp-ma-ipcpiw-cfg {
  namespace "http://cisco.com/ns/yang/Cisco-IOS-XR-ppp-ma-ipcpiw-cfg";
  prefix ppp-ma-ipcpiw-cfg;

  import ietf-inet-types {
    prefix inet;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ppp-ma-ipcpiw package configuration.
     
     This YANG module augments the
       Cisco-IOS-XR-ifmgr-cfg
     module with configuration data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/a1:interface-configurations/a1:interface-configuration" {
    description
      "This augment extends the configuration data of
       'Cisco-IOS-XR-ifmgr-cfg'";
    container ppp {
      description
        "Interface PPP configuration data";
      container ipcpiw {
        description
          "PPP IPCPIW configuration data";
        leaf proxy-address {
          type inet:ipv4-address-no-zone;
          description
            "Specify an IP address to publish to peers
             through IPCPIW";
        }
      }
    }
  }
}
