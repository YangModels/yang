module Cisco-IOS-XR-controller-sonet-oper {
  namespace "http://cisco.com/ns/yang/Cisco-IOS-XR-controller-sonet-oper";
  prefix controller-sonet-oper;

  import Cisco-IOS-XR-types {
    prefix xr;
  }
  import cisco-semver {
    prefix semver;
  }
  include Cisco-IOS-XR-controller-sonet-oper-sub2 {
    revision-date 2022-03-01;
  }
  include Cisco-IOS-XR-controller-sonet-oper-sub1 {
    revision-date 2022-03-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-sonet package operational data.
     
     This module contains definitions
     for the following management objects:
       stm: STM operational data
       vc: VC operational data
       sts: STS operational data
       oc: OC operational data
     
     Copyright (c) 2013-2022 by Cisco Systems, Inc.
     All rights reserved.";

  revision 2022-03-01 {
    description
      "Added LED state field to port common info";
    semver:module-version "1.0.0";
  }
  revision 2022-02-15 {
    description
      "64 byte trace mode added to j0_info";
  }
  revision 2019-04-05 {
    description
      "Establish semantic version baseline.";
  }
  revision 2015-11-09 {
    description
      "IOS XR 6.0 revision.";
  }

  container stm {
    config false;
    description
      "STM operational data";
    container stm-controllers {
      description
        "All STM controller operational data";
      list stm-controller {
        key "controller-name";
        description
          "STM controller operational data";
        container stm-info {
          description
            "STM controller operational data";
          uses SDH-PORT-INFO;
        }
        leaf controller-name {
          type xr:Interface-name;
          description
            "Interface name";
        }
      }
    }
  }
  container vc {
    config false;
    description
      "VC operational data";
    container vc-controllers {
      description
        "All VC controller operational data";
      list vc-controller {
        key "controller-name";
        description
          "VC controller operational data";
        container vc-info {
          description
            "VC controller operational data";
          uses SONET-PATH-INFO;
        }
        leaf controller-name {
          type xr:Interface-name;
          description
            "Interface name";
        }
      }
    }
  }
  container sts {
    config false;
    description
      "STS operational data";
    container sts-controllers {
      description
        "All STS controller operational data";
      list sts-controller {
        key "controller-name";
        description
          "STS controller operational data";
        container sts-info {
          description
            "STS controller operational data";
          uses SONET-PATH-INFO;
        }
        leaf controller-name {
          type xr:Interface-name;
          description
            "Interface name";
        }
      }
    }
  }
  container oc {
    config false;
    description
      "OC operational data";
    container oc-controllers {
      description
        "All OC controller operational data";
      list oc-controller {
        key "controller-name";
        description
          "OC controller operational data";
        container oc-info {
          description
            "OC controller operational data";
          uses SONET-MA-PORT-INFO;
        }
        leaf controller-name {
          type xr:Interface-name;
          description
            "Interface name";
        }
      }
    }
  }
}
