//*************  DO-NOT EDIT  **************
//*********** Auto-generated file ********** 

 module cisco-xr-openconfig-keychain-deviations {

  prefix  "oc-keychaindevs";

  namespace "http://cisco.com/ns/yang/cisco-xr-openconfig-keychain-deviations";

  import openconfig-keychain { prefix oc-keychain; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-keychain.yang@2022-11-05 

     on Cisco IOS-XR devices.

     Copyright (c) 2017, 2023 by Cisco Systems, Inc.
     All rights reserved.";

  revision "2023-06-22" {
    description
      "Initial revision applicable to IOS-XR 6.4.1";
  }


  deviation /oc-keychain:keychains/oc-keychain:keychain/oc-keychain:keys/oc-keychain:key/oc-keychain:send-lifetime/oc-keychain:config/oc-keychain:send-and-receive {
    deviate not-supported;
  }

  deviation /oc-keychain:keychains/oc-keychain:keychain/oc-keychain:keys/oc-keychain:key/oc-keychain:send-lifetime/oc-keychain:state/oc-keychain:send-and-receive {
    deviate not-supported;
  }


}
//total deviations:2
