module Cisco-IOS-XR-infra-iccp-oper {
  namespace "http://cisco.com/ns/yang/Cisco-IOS-XR-infra-iccp-oper";
  prefix infra-iccp-oper;

  import Cisco-IOS-XR-types {
    prefix xr;
  }
  import cisco-semver {
    prefix semver;
  }
  include Cisco-IOS-XR-infra-iccp-oper-sub1 {
    revision-date 2024-04-18;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-iccp package operational data.
     
     This module contains definitions
     for the following management objects:
       iccp: ICCP operational data
     
     Copyright (c) 2013-2024 by Cisco Systems, Inc.
     All rights reserved.";

  revision 2024-04-18 {
    description
      "Created.";
    semver:module-version "1.0.0";
  }
  revision 2019-04-05 {
    description
      "Establish semantic version baseline.";
  }
  revision 2015-11-09 {
    description
      "IOS XR 6.0 revision.";
  }

  grouping ICCP-GROUP-TABLE {
    description
      "Common node of active, node";
    container iccp-groups {
      description
        "The ICCP Redundancy Group Table";
      list iccp-group {
        key "group-number";
        description
          "Redundancy Group information";
        leaf group-number {
          type uint32 {
            range "1..4294967295";
          }
          description
            "The redundancy group number";
        }
        uses ICCP-MGMT-RG-INFO;
      }
    }
  }

  container iccp {
    config false;
    description
      "ICCP operational data";
    container global {
      description
        "Global ICCP operational data";
      container active {
        description
          "Active ICCP operational data";
        uses ICCP-GROUP-TABLE;
      }
    }
    container nodes {
      description
        "Location ICCP operational data";
      list node {
        key "node-name";
        description
          "The ICCP operational data for a particular node";
        leaf node-name {
          type xr:Node-id;
          description
            "The identifier for the node";
        }
        uses ICCP-GROUP-TABLE;
      }
    }
  }
}
