module Cisco-IOS-XR-um-8000-fpd-cfg {
  namespace "http://cisco.com/ns/yang/Cisco-IOS-XR-um-8000-fpd-cfg";
  prefix um-8000-fpd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco fpd package configuration.
     Copyright (c) 2024 by Cisco Systems, Inc.
     All rights reserved.";

  revision 2024-05-14 {
    description
      "Containers enable and disable are replaced with single leaf
       auto-upgrade-configuration under container auto-upgrade with
       enum values enable and disable.
       Containers include and exclude are added as cases for choice
       EXCLUDE-CONFIGURATION under container exclude-configuration.
       2022-02-17
         Added container exclude";
    semver:module-version "2.0.0";
  }
  revision 2020-12-22 {
    description
      "Initial release";
    semver:module-version "1.0.0";
  }

  container fpd {
    description
      "FPD firmware configuration";
    container auto-upgrade {
      description
        "FPD auto-upgrade configuration";
      leaf auto-upgrade-configuration {
        type enumeration {
          enum "enable" {
            value 1;
            description
              "Enable fpd auto upgrade";
          }
          enum "disable" {
            value 0;
            description
              "Disable fpd auto upgrade";
          }
        }
        description
          "FPD auto-upgrade configuration";
      }
      container exclude-configuration {
        description
          "FPD auto-upgrade exclude configuration";
        choice EXCLUDE-CONFIGURATION {
          description
            "FPD auto-upgrade exclude configuration";
          case EXCLUDE {
            container exclude {
              description
                "Power module entity to be excluded";
              leaf pm {
                type empty;
                description
                  "Power module entity to be excluded";
              }
            }
          }
          case INCLUDE {
            container include {
              description
                "Power module entity to be included";
              leaf pm {
                type empty;
                description
                  "Power module entity to be excluded";
              }
            }
          }
        }
      }
    }
  }
}
