module Cisco-IOS-XR-um-subscriber-redundancy-cfg {
  namespace "http://cisco.com/ns/yang/Cisco-IOS-XR-um-subscriber-redundancy-cfg";
  prefix um-subscriber-redundancy-cfg;

  import Cisco-IOS-XR-types {
    prefix xr;
  }
  import ietf-inet-types {
    prefix inet;
  }
  import ietf-yang-types {
    prefix yang;
  }
  import Cisco-IOS-XR-um-subscriber-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-redundancy package configuration.
     
     This YANG module augments the
     modules with configuration data.
     
     Copyright (c) 2021-2022 by Cisco Systems, Inc.
     All rights reserved.";

  revision 2022-07-11 {
    description
      "Added missing description statement to nodes";
    semver:module-version "1.0.0";
  }
  revision 2021-06-29 {
    description
      "Initial release";
    semver:module-version "1.0.0";
  }

  augment "/a1:subscriber" {
    description
      "This augment extends subscriber nodes configuration";
    container redundancy {
      presence "Indicates a redundancy node is configured.";
      description
        "Subscriber Redundancy configuration";
      container disable {
        presence "Indicates a disable node is configured.";
        description
          "Disable Subscriber Redundancy for all Groups";
      }
      container cpe-tracking {
        presence "Indicates a cpe-tracking node is configured.";
        description
          "Enable CPE tracking for SRG";
      }
      container preferred-role {
        description
          "Preferred Role for all Groups";
        container primary {
          must "not(../subordinate)";
          presence "Indicates a primary node is configured.";
          description
            "Primary Role";
        }
        container subordinate {
          must "not(../primary)";
          presence "Indicates a subordinate node is configured.";
          description
            "Subordinate Role";
        }
      }
      leaf source-interface {
        type xr:Interface-name;
        description
          "Source Interface for Redundancy Peer Communication";
      }
      container subordinate-mode {
        description
          "Subordinate Mode for all Groups";
        container warm {
          must "not(../hot)";
          presence "Indicates a warm node is configured.";
          description
            "Warm Standby";
        }
        container hot {
          must "not(../warm)";
          presence "Indicates a hot node is configured.";
          description
            "Hot Standby (Default)";
        }
      }
      leaf hold-timer {
        type uint32 {
          range "1..65535" {
            description
              "Value of hold time in minutes";
          }
        }
        description
          "Hold Timer for all Groups";
      }
      container holdtimer-default-disable {
        presence "Indicates a holdtimer-default-disable node is configured.";
        description
          "Disable Default Hold timer for this Group";
      }
      leaf virtual-mac-prefix {
        type yang:mac-address;
        description
          "Virtual MAC Prefix for Subscriber Redundancy";
      }
      leaf revertive-timer {
        type uint32 {
          range "1..65535" {
            description
              "Value of revertive time in minutes";
          }
        }
        must "../maximum";
        description
          "Revertive Timer for all groups";
      }
      leaf maximum {
        type uint32 {
          range "1..65535" {
            description
              "Value of MAX Revertive Timer";
          }
        }
        must "../revertive-timer";
        description
          "Max Revertive Timer for all group";
      }
      leaf sync-timer {
        type uint32 {
          range "1..255" {
            description
              "Value of sync time in minutes";
          }
        }
        description
          "Sync Timer for all Groups";
      }
      container peers {
        description
          "Redundancy Peer configuration";
        list peer {
          must "ipv4-address or ipv6-address";
          key "peer-name";
          description
            "Redundancy Peer configuration";
          leaf peer-name {
            type xr:Cisco-ios-xr-string {
              length "1..1024" {
                description
                  "Peer Name";
              }
            }
            description
              "Peer Name";
          }
          leaf ipv4-address {
            type inet:ipv4-address-no-zone;
            must "not(../ipv6-address)";
            description
              "IPv4 peer address";
          }
          leaf ipv6-address {
            type inet:ipv6-address-no-zone;
            must "not(../ipv4-address)";
            description
              "IPv6 peer address";
          }
          leaf tcp-port {
            type uint32 {
              range "2001..4000" {
                description
                  "TCP port";
              }
            }
            mandatory true;
            description
              "TCP port";
          }
        }
      }
      leaf keepalive {
        type uint32 {
          range "3..300" {
            description
              "Keepalive interval in seconds";
          }
        }
        must "../keepalive-retry-count";
        description
          "Keepalive configuration for all peers";
      }
      leaf keepalive-retry-count {
        type uint32 {
          range "1..100" {
            description
              "Keepalive retry count";
          }
        }
        must "../keepalive";
        description
          "Keepalive retry count";
      }
      leaf dscp {
        type enumeration {
          enum "0" {
            value 0;
            description
              "SRG DSCP Value DSCP_CS0";
          }
          enum "32" {
            value 32;
            description
              "SRG DSCP Value DSCP_CS1";
          }
          enum "64" {
            value 64;
            description
              "SRG DSCP Value DSCP_CS2";
          }
          enum "96" {
            value 96;
            description
              "SRG DSCP Value DSCP_CS3";
          }
          enum "128" {
            value 128;
            description
              "SRG DSCP Value DSCP_CS4";
          }
          enum "160" {
            value 160;
            description
              "SRG DSCP Value DSCP_CS5";
          }
          enum "192" {
            value 192;
            description
              "SRG DSCP Value DSCP_CS6";
          }
        }
        description
          "dscp value";
      }
      container groups {
        description
          "Redundancy Group configuration";
        list group {
          key "group-id";
          description
            "Redundancy Group configuration";
          leaf group-id {
            type uint32 {
              range "1..4000" {
                description
                  "Group ID";
              }
            }
            description
              "Redundancy Group configuration";
          }
          container interface-list {
            presence "Indicates a interface-list node is configured.";
            description
              "List of Interfaces for this Group";
            list interface-id {
              key "interface-name";
              description
                "Interface for this Group";
              leaf interface-name {
                type xr:Interface-name;
                description
                  "Interface for this Group";
              }
              leaf id {
                type uint32 {
                  range "1..65535" {
                    description
                      "ID for the interface to be mapped on to subordinate";
                  }
                }
                description
                  "Map Identifier";
              }
            }
            list interface-sub-if-range {
              must "sub-if-ranges/sub-if-range";
              key "interface-name";
              description
                "Interface for this Group";
              leaf interface-name {
                type xr:Interface-name;
                description
                  "Interface for this Group";
              }
              container sub-if-ranges {
                description
                  "Sub Interface Range";
                list sub-if-range {
                  key "sub-if-start sub-if-end";
                  description
                    "Sub Interface Range";
                  leaf sub-if-start {
                    type uint32 {
                      range "0..2147483647" {
                        description
                          "Sub Interface Start Range";
                      }
                    }
                    description
                      "Sub Interface Range";
                  }
                  leaf sub-if-end {
                    type uint32 {
                      range "0..2147483647" {
                        description
                          "Sub Interface End Range";
                      }
                    }
                    description
                      "Sub Interface End Range";
                  }
                  leaf map-id-start {
                    type uint32 {
                      range "1..65535" {
                        description
                          "Starting Map Identifier for the Sub Interface Range";
                      }
                    }
                    mandatory true;
                    description
                      "Identifier";
                  }
                  leaf map-id-end {
                    type uint32 {
                      range "1..65535" {
                        description
                          "Ending Map Identifier for the Sub Interface Range";
                      }
                    }
                    mandatory true;
                    description
                      "Ending Map Identifier for the Sub Interface Range";
                  }
                }
              }
            }
          }
          container disable {
            presence "Indicates a disable node is configured.";
            description
              "Disable this Group";
          }
          container preferred-role {
            description
              "Preferred Role for this Group";
            container primary {
              must "not(../subordinate)";
              presence "Indicates a primary node is configured.";
              description
                "Primary Role";
            }
            container subordinate {
              must "not(../primary)";
              presence "Indicates a subordinate node is configured.";
              description
                "Subordinate Role";
            }
          }
          leaf virtual-mac {
            type yang:mac-address;
            description
              "Virtual MAC Address for this Group";
          }
          container virtual-mac-disable {
            presence "Indicates a virtual-mac-disable node is configured.";
            description
              "Disable Virtual MAC Address for this Group";
          }
          container peer {
            description
              "Peer config for this Group";
            leaf ipv4-address {
              type inet:ipv4-address-no-zone;
              must "not(../ipv6-address)";
              description
                "IPv4 peer address";
            }
            leaf ipv6-address {
              type inet:ipv6-address-no-zone;
              must "not(../ipv4-address)";
              description
                "IPv6 peer address";
            }
            container route-disable {
              presence "Indicates a route-disable node is configured.";
              description
                "Disable route addition on SRG Subordinate";
            }
            leaf peer-name {
              type xr:Cisco-ios-xr-string {
                length "1..800" {
                  description
                    "Peer to use for this group";
                }
              }
              description
                "Peer to use for this group";
            }
          }
          container enable-fast-switchover {
            presence "Indicates a enable-fast-switchover node is configured.";
            description
              "Enable fast switchover for this Group";
          }
          container state-control-route {
            description
              "state control route config for this Group";
            container ipv4 {
              description
                "IPv4 route";
              container ipv4-routes {
                description
                  "IPv4 route with named vrf";
                list ipv4-route {
                  key "address length vrf";
                  description
                    "IPv4 route";
                  leaf address {
                    type inet:ipv4-address-no-zone;
                    description
                      "IPv4 route";
                  }
                  leaf length {
                    type uint32 {
                      range "0..128";
                    }
                    description
                      "IPv4 route";
                  }
                  leaf vrf {
                    type union {
                      type string {
                        pattern "default" {
                          description
                            "Default VRF";
                        }
                      }
                      type xr:Cisco-ios-xr-string {
                        length "1..800" {
                          description
                            "VRF name";
                        }
                      }
                    }
                    description
                      "Set vrf for the route";
                  }
                  leaf interface {
                    type xr:Interface-name {
                      pattern "Null0";
                    }
                    description
                      "Outgoing Interface";
                  }
                  leaf tag {
                    type uint32 {
                      range "1..4294967295" {
                        description
                          "Tag value";
                      }
                    }
                    description
                      "Set a tag value for the route";
                  }
                }
              }
            }
            container ipv6 {
              description
                "IPv6 route";
              container iana {
                description
                  "IANA route";
                container iana-routes {
                  description
                    "IANA route with default vrf";
                  list iana-route {
                    key "address length vrf";
                    description
                      "IANA route";
                    leaf address {
                      type inet:ipv6-address-no-zone;
                      description
                        "IANA route";
                    }
                    leaf length {
                      type uint32 {
                        range "0..128";
                      }
                      description
                        "IANA route";
                    }
                    leaf vrf {
                      type union {
                        type string {
                          pattern "default" {
                            description
                              "Default VRF";
                          }
                        }
                        type xr:Cisco-ios-xr-string {
                          length "1..800" {
                            description
                              "VRF name";
                          }
                        }
                      }
                      description
                        "Set vrf for the route";
                    }
                    leaf interface {
                      type xr:Interface-name {
                        pattern "Null0";
                      }
                      description
                        "Outgoing Interface";
                    }
                    leaf tag {
                      type uint32 {
                        range "1..4294967295" {
                          description
                            "Tag value";
                        }
                      }
                      description
                        "Set a tag value for the route";
                    }
                  }
                }
              }
              container iapd {
                description
                  "IAPD route";
                container iapd-routes {
                  description
                    "IAPD route";
                  list iapd-route {
                    key "address length vrf";
                    description
                      "IAPD route";
                    leaf address {
                      type inet:ipv6-address-no-zone;
                      description
                        "IAPD route";
                    }
                    leaf length {
                      type uint32 {
                        range "0..128";
                      }
                      description
                        "IAPD route";
                    }
                    leaf vrf {
                      type union {
                        type string {
                          pattern "default" {
                            description
                              "Default VRF";
                          }
                        }
                        type xr:Cisco-ios-xr-string {
                          length "1..800" {
                            description
                              "VRF name";
                          }
                        }
                      }
                      description
                        "Set vrf for the route";
                    }
                    leaf interface {
                      type xr:Interface-name {
                        pattern "Null0";
                      }
                      description
                        "Outgoing Interface";
                    }
                    leaf tag {
                      type uint32 {
                        range "1..4294967295" {
                          description
                            "Tag value";
                        }
                      }
                      description
                        "Set a tag value for the route";
                    }
                  }
                }
              }
            }
          }
          leaf l2tp-source-ip {
            type inet:ipv4-address-no-zone;
            description
              "L2TP Tunnel Source IP Address for this Group";
          }
          container subordinate-mode {
            description
              "Subordinate Mode for this Group";
            container warm {
              must "not(../hot)";
              presence "Indicates a warm node is configured.";
              description
                "Warm Standby";
            }
            container hot {
              must "not(../warm)";
              presence "Indicates a hot node is configured.";
              description
                "Hot Standby (Default)";
            }
          }
          leaf hold-timer {
            type uint32 {
              range "1..65535" {
                description
                  "Value of hold time in minutes";
              }
            }
            description
              "Hold Timer for this Group";
          }
          container holdtimer-default-disable {
            presence "Indicates a holdtimer-default-disable node is configured.";
            description
              "Disable Default Hold timer for this Group";
          }
          leaf description {
            type string {
              length "1..800" {
                description
                  "Description for this Group";
              }
            }
            description
              "Description for this Group";
          }
          leaf core-tracking {
            type xr:Cisco-ios-xr-string {
              length "1..800" {
                description
                  "Tracking Object Name";
              }
            }
            description
              "Core Tracking Object for this Group";
          }
          leaf access-tracking {
            type xr:Cisco-ios-xr-string {
              length "1..800" {
                description
                  "Tracking Object Name";
              }
            }
            description
              "Access Tracking Object for this Group";
          }
          container tracking-disable {
            presence "Indicates a tracking-disable node is configured.";
            description
              "Disable Tracking Object for this Group";
          }
          leaf revertive-timer {
            type uint32 {
              range "1..65535" {
                description
                  "Value of revertive time in minutes";
              }
            }
            must "../maximum";
            description
              "Revertive Timer for this group";
          }
          leaf maximum {
            type uint32 {
              range "1..65535" {
                description
                  "Value of MAX Revertive Timer";
              }
            }
            must "../revertive-timer";
            description
              "Max Revertive Timer for this group";
          }
        }
      }
    }
  }
}
