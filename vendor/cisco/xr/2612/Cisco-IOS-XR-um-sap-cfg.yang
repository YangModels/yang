module Cisco-IOS-XR-um-sap-cfg {
  namespace "http://cisco.com/ns/yang/Cisco-IOS-XR-um-sap-cfg";
  prefix um-sap-cfg;

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sap package configuration.
     
     This YANG module augments the
     modules with configuration data.
     
     Copyright (c) 2021-2025 by Cisco Systems, Inc., and/or its affiliates.
     All rights reserved.";

  revision 2021-05-10 {
    description
      "Initial release";
    semver:module-version "1.0.0";
  }

  container sap {
    description
      "SAP Commands";
    container listens {
      description
        "Listen to the session announcements via SAP";
      list listen {
        key "group-address";
        description
          "Listen to the session announcements via SAP";
        leaf group-address {
          type inet:ipv4-address-no-zone;
          description
            "Group to listen to for announcements";
        }
      }
    }
    leaf cache-timeout {
      type uint32 {
        range "1..1440" {
          description
            "Time (in minutes)";
        }
      }
      description
        "Define time period for which SAP entry will remain active";
    }
  }
}
