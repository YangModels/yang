module Cisco-IOS-XR-optics-server-configurability-cfg {
  namespace "http://cisco.com/ns/yang/Cisco-IOS-XR-optics-server-configurability-cfg";
  prefix optics-server-configurability-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-server-configurability package configuration.
     
     This module contains definitions
     for the following management objects:
       configurability: Configurability cfg
     
     Copyright (c) 2013-2024 by Cisco Systems, Inc.
     All rights reserved.";

  revision 2024-11-20 {
    description
      "Schema added.";
    semver:module-version "1.0.0";
  }
  revision 2019-04-05 {
    description
      "Establish semantic version baseline.";
  }
  revision 2015-11-09 {
    description
      "IOS XR 6.0 revision.";
  }

  container configurability {
    description
      "Configurability cfg";
    container tcvr-vendor-names {
      description
        "Configurability Tcvr Vendor";
      list tcvr-vendor-name {
        key "name";
        description
          "Configurability Tcvr Vendor Name";
        leaf name {
          type xr:Cisco-ios-xr-string {
            length "1..16";
          }
          description
            "Name of the Vendor Profile of maximum length
             16";
        }
        list tcvr-part-number {
          key "name";
          description
            "Part Number";
          leaf tcvr-profile-name {
            type xr:Cisco-ios-xr-string {
              length "1..16";
            }
            description
              "Name of the Vendor Profile of maximum length
               16";
          }
          leaf name {
            type xr:Cisco-ios-xr-string {
              length "1..16";
            }
            description
              "Part Number of the Vendor Profile of maximum
               length 16";
          }
        }
      }
    }
    container system-profile-names {
      description
        "Configurability System Profile";
      list system-profile-name {
        key "name";
        description
          "Configurability System Profile Name";
        container cmis {
          description
            "Configurability CMIS Items";
          container datapath-tx-turn-on-time {
            presence "Indicates a datapath-tx-turn-on-time node is configured.";
            description
              "Datapath Tx TurnOn Time min and max value in
               the range(0,10000000)ms";
            leaf datapath-tx-turn-on-time-min {
              type uint32 {
                range "0..10000000";
              }
              mandatory true;
              description
                "Min module datapath tx turn on time time in
                 ms";
            }
            leaf datapath-tx-turn-on-time-max {
              type uint32 {
                range "0..10000000";
              }
              mandatory true;
              description
                "Max module datapath tx turn on time time in
                 ms";
            }
          }
          container datapath-init-time {
            presence "Indicates a datapath-init-time node is configured.";
            description
              "Datapath Init Time min and max value in the
               range(0,10000000)ms";
            leaf datapath-init-time-min {
              type uint32 {
                range "0..10000000";
              }
              mandatory true;
              description
                "Min module data init time in ms";
            }
            leaf datapath-init-time-max {
              type uint32 {
                range "0..10000000";
              }
              mandatory true;
              description
                "Max module data init time in ms";
            }
          }
          container module-power-up-time {
            description
              "Module PowerUp Time min and max value in the
               range(0,10000000)ms";
            leaf module-power-up-time-min {
              type uint32 {
                range "0..10000000";
              }
              description
                "Min module power up time in ms";
            }
            leaf module-power-up-time-max {
              type uint32 {
                range "0..10000000";
              }
              description
                "Max module power up time in ms";
            }
          }
          container datapath-tx-turn-off-time {
            presence "Indicates a datapath-tx-turn-off-time node is configured.";
            description
              "Datapath Tx TurnOff Time min and max value in
               the range(0,10000000)ms";
            leaf datapath-tx-turn-off-time-min {
              type uint32 {
                range "0..10000000";
              }
              mandatory true;
              description
                "Min module datapath tx turn off time time in
                 ms";
            }
            leaf datapath-tx-turn-off-time-max {
              type uint32 {
                range "0..10000000";
              }
              mandatory true;
              description
                "Max module datapath tx turn off time time in
                 ms";
            }
          }
          container module-power-down-time {
            presence "Indicates a module-power-down-time node is configured.";
            description
              "Module PowerDown Time min and max value in
               the range(0,10000000)ms";
            leaf module-power-down-time-min {
              type uint32 {
                range "0..10000000";
              }
              mandatory true;
              description
                "Min module power down time in ms";
            }
            leaf module-power-down-time-max {
              type uint32 {
                range "0..10000000";
              }
              mandatory true;
              description
                "Max module power down time in ms";
            }
          }
          container datapath-deinit-time {
            presence "Indicates a datapath-deinit-time node is configured.";
            description
              "Datapath Deinit Time min and max value in the
               range(0,10000000)ms";
            leaf datapath-deinit-time-min {
              type uint32 {
                range "0..10000000";
              }
              mandatory true;
              description
                "Min module data deinit time in ms";
            }
            leaf datapath-deinit-time-max {
              type uint32 {
                range "0..10000000";
              }
              mandatory true;
              description
                "Max module data deinit time in ms";
            }
          }
          leaf state-machine-retry-count {
            type uint32 {
              range "0..10";
            }
            description
              "State Maching Retry Count value in the
               range(0,10)";
          }
        }
        container sff {
          description
            "Configurability SFF Items";
          leaf flag-assert-time {
            type uint32 {
              range "0..600";
            }
            description
              "Flag Assert Time value in the range(0,600)ms";
          }
          leaf squelch-disable-deassert-time {
            type uint32 {
              range "0..2000";
            }
            description
              "Squelch Disable Deassert Time value in the
               range(0,2000)ms";
          }
          leaf rx-squelch-assert-time {
            type uint32 {
              range "0..4000";
            }
            description
              "Rx Squelch Assert Time value in the range(0
               ,4000)ms";
          }
          leaf rx-output-disable-assert-time {
            type uint32 {
              range "0..2000";
            }
            description
              "Rx Output Disable Assert Time value in the
               range(0,2000)ms";
          }
          leaf lpmode-deassert-time {
            type uint32 {
              range "0..6000";
            }
            description
              "Lpmode Deassert Time value in the range(0
               ,6000)ms";
          }
          leaf squelch-disable-assert-time {
            type uint32 {
              range "0..2000";
            }
            description
              "Squelch Disable Assert Time value in the
               range(0,2000)ms";
          }
          leaf rx-output-disable-deassert-time {
            type uint32 {
              range "0..2000";
            }
            description
              "Rx Output Disable Deassert Time value in the
               range(0,2000)ms";
          }
          leaf lpmode-assert-time {
            type uint32 {
              range "0..2000";
            }
            description
              "Lpmode Assert Time value in the range(0
               ,2000)ms";
          }
          leaf rx-squelch-deassert-time {
            type uint32 {
              range "0..3000";
            }
            description
              "Rx Squelch Deassert Time value in the range(0
               ,3000)ms";
          }
        }
        container common {
          description
            "Configurability Common Items";
          leaf interrupt-deassert-time {
            type uint32 {
              range "0..50";
            }
            description
              "Interrupt Deassert Time value in the range(0
               ,50)ms";
          }
          leaf tx-disable-deassert-time {
            type uint32 {
              range "0..2000";
            }
            description
              "Tx Disable Deassert Time value in the range(0
               ,2000)ms";
          }
          leaf tx-disable-assert-time {
            type uint32 {
              range "0..600";
            }
            description
              "Tx Disable Assert Time value in the range(0
               ,600)ms";
          }
          leaf initialization-time {
            type uint32 {
              range "0..10000";
            }
            description
              "Initialization Time value in the range(0
               ,10000)ms";
          }
          leaf interrupt-assert-time {
            type uint32 {
              range "0..5000";
            }
            description
              "Interrupt Assert Time value in the range(0
               ,5000)ms";
          }
        }
        leaf name {
          type xr:Cisco-ios-xr-string {
            length "1..16";
          }
          description
            "Name of the System Profile of maximum length
             16";
        }
      }
    }
  }
}
