submodule Cisco-IOS-XR-tty-server-oper-sub5 {
  belongs-to Cisco-IOS-XR-tty-server-oper {
    prefix Cisco-IOS-XR-tty-server-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tty-server package operational data.
     
     Copyright (c) 2013-2019 by Cisco Systems, Inc.
     All rights reserved.";

  revision 2019-04-05 {
    description
      "Establish semantic version baseline.";
    semver:module-version "1.0.0";
  }
  revision 2019-02-25 {
    description
      "Fixed unconstrained data type issues";
  }
  revision 2017-09-07 {
    description
      "Fixed type translation error.";
  }
  revision 2015-07-30 {
    description
      "Descriptions updated.";
  }
  revision 2015-01-07 {
    description
      "IOS XR 5.3.1 revision.";
  }

  grouping TTY-RS232-STATS {
    description
      "RS232 TTY statistics";
    leaf data-bits {
      type uint32;
      units "bit";
      description
        "Number of databits";
    }
    leaf exec-disabled {
      type boolean;
      description
        "Exec disabled on TTY";
    }
    leaf hardware-flow-control-status {
      type uint32;
      description
        "Setting of hardware flow control";
    }
    leaf parity-status {
      type uint32;
      description
        "Setting the parity type";
    }
    leaf baud-rate {
      type uint32;
      units "bit/s";
      description
        "Inbound/Outbound baud rate in bps";
    }
    leaf stop-bits {
      type uint32;
      units "bit";
      description
        "Number of stopbits";
    }
    leaf overrun-error-count {
      type uint32;
      description
        "Count of overrun error";
    }
    leaf framing-error-count {
      type uint32;
      description
        "Count of framing error";
    }
    leaf parity-error-count {
      type uint32;
      description
        "Count of parity error";
    }
  }
}
