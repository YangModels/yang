module cisco-xr-ietf-yang-push-deviations {
  namespace "http://cisco.com/ns/yang/cisco-xr-ietf-yang-push-deviations";
  prefix xr-yp-d;

  import ietf-subscribed-notifications {
    prefix sn;
  }

  import ietf-yang-push {
    prefix yp;
  }

  organization "Cisco Systems, Inc.";

  contact
    "Cisco Systems, Inc.
     Customer Service

     Postal: 170 West Tasman Drive
     San Jose, CA 95134

     Tel: +1 800 553-NETS

     E-mail: cs-yang@cisco.com";

  description
    "This module contains a set of 'not-supported' deviations of:

        ietf-yang-push@2019-09-09

     on Cisco IOS-XR devices.

     Copyright (c) 2025 by Cisco Systems, Inc., and/or its affiliates.
     All rights reserved.";


  revision 2025-01-20 {
    description
      "Initial version.";
  }

  /*
   * If in the future this deviations file only contains RPC or notification
   * nodes, it will stop appearing in Yang Library or capabilities/hello
   * output.
   * See CSCwn84289 for more details. This comment can be removed once the
   * issue is resolved.
   */

  // DATA MODEL DEVIATIONS

  deviation /sn:subscriptions/sn:subscription/sn:target/yp:datastore/yp:selection-filter/yp:by-reference {
    deviate not-supported;
  }

  deviation /sn:subscriptions/sn:subscription/sn:target/yp:datastore/yp:selection-filter/yp:within-subscription/yp:filter-spec/yp:datastore-subtree-filter {
    deviate not-supported;
  }

  deviation /sn:subscriptions/sn:subscription/yp:update-trigger/yp:on-change/yp:on-change/yp:dampening-period {
    deviate not-supported;
  }

  deviation /sn:subscriptions/sn:subscription/yp:update-trigger/yp:on-change/yp:on-change/yp:excluded-change {
    deviate not-supported;
  }

  deviation /yp:resync-subscription {
    deviate not-supported;
  }


  // NOTIFICATION DEVIATIONS

  deviation /sn:subscription-started/sn:target/yp:datastore/yp:selection-filter/yp:within-subscription/yp:filter-spec/yp:datastore-subtree-filter {
    deviate not-supported;
  }

  deviation /sn:subscription-started/sn:target/yp:datastore/yp:selection-filter/yp:by-reference {
    deviate not-supported;
  }

  deviation /sn:subscription-started/yp:update-trigger/yp:on-change/yp:on-change/yp:dampening-period {
    deviate not-supported;
  }

  deviation /sn:subscription-started/yp:update-trigger/yp:on-change/yp:on-change/yp:excluded-change {
    deviate not-supported;
  }

  deviation /yp:push-update/yp:incomplete-update {
    deviate not-supported;
  }

  deviation /yp:push-change-update/yp:datastore-changes/yp:yang-patch/yp:edit/yp:point {
    deviate not-supported;
  }

  deviation /yp:push-change-update/yp:datastore-changes/yp:yang-patch/yp:edit/yp:where {
    deviate not-supported;
  }

  deviation /yp:push-change-update/yp:datastore-changes/yp:yang-patch/yp:comment {
    deviate not-supported;
  }

  deviation /yp:push-change-update/yp:incomplete-update {
    deviate not-supported;
  }

}
