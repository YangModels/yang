module Cisco-IOS-XR-sysadmin-ds {
  namespace "http://www.cisco.com/ns/yang/Cisco-IOS-XR-sysadmin-ds";
  prefix xr-ds;

  import ietf-inet-types {
    prefix inet;
  }
  import Cisco-IOS-XR-sysadmin-show-trace {
    prefix show_trace;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     The Directory Services (DS).
     
     Copyright (c) 2010-2020, 2024 by Cisco Systems, Inc.
     All rights reserved.";

  revision 2024-10-22 {
    description
      "Update yang descriptions to pass yang validation checks";
    semver:module-version "1.2.0";
  }
  revision 2019-10-31 {
    description
      "Changed prefix due to conflict with ietf-datastores";
    semver:module-version "1.1.0";
  }
  revision 2019-04-15 {
    description
      "Establish semantic version baseline.";
    semver:module-version "1.0.0";
  }
  revision 2018-05-21 {
    description
      "Added string description for some show options";
  }
  revision 2017-04-12 {
    description
      "Changed the namespace and module name";
  }
  revision 2016-10-12 {
    description
      "Unhide commands and configs. Moved to advanced-grp";
  }
  revision 2016-05-11 {
    description
      "Initial version.";
  }

  typedef service-scope {
    type enumeration {
      enum "None" {
        description
          "Invalid DS service scope";
      }
      enum "Rack" {
        description
          "Rack service scope";
      }
      enum "System" {
        description
          "System service scope";
      }
      enum "Node" {
        description
          "Node service scope";
      }
    }
    description
      "DS Service Scope";
  }

  typedef process-role {
    type enumeration {
      enum "NoRole" {
        description
          "Process No Redundancy Role";
      }
      enum "Active" {
        description
          "Process Active Redundancy Role";
      }
      enum "Standby" {
        description
          "Process Standby Redundancy Role";
      }
      enum "None" {
        description
          "Process Redundancy Role None";
      }
      enum "Unknown" {
        value 254;
        description
          "Process Unknown Redundancy Role";
      }
    }
    description
      "Process Redundancy Role";
  }

  typedef process-issu-role {
    type enumeration {
      enum "Primary" {
        value 1;
        description
          "ISSU Primary Role";
      }
      enum "Secondary" {
        value 2;
        description
          "ISSU Secondary Role";
      }
      enum "Tertiary" {
        value 3;
        description
          "ISSU Tertiary Role";
      }
      enum "Unknown" {
        value 254;
        description
          "ISSU Role Unknown";
      }
    }
    description
      "Process ISSU Role";
  }

  grouping servicesGroup {
    description
      "DS Services grouping";
    list services {
      key "name";
      description
        "list of services";
      leaf name {
        type string;
        description
          "Name of the service";
      }
      list endpoint {
        description
          "endpoint info for a service in DS";
        leaf scope {
          type service-scope;
          description
            "Service scope info of endpoint";
        }
        leaf ip {
          type inet:ipv4-address;
          description
            "End point IP address";
        }
        leaf port {
          type inet:port-number;
          description
            "End point port number";
        }
        leaf role {
          type process-role;
          description
            "Process redundancy role";
        }
        leaf issu_role {
          type process-issu-role;
          description
            "Process issu role";
        }
        leaf node {
          type string;
          description
            "Ethernet address of the node hosting the endpoint";
        }
      }
      list registrations {
        description
          "clients registered for a service in DS";
        leaf client {
          type string;
          description
            "client registered for service";
        }
        leaf pid {
          type uint32;
          description
            "process ID of client registered";
        }
      }
    }
  }

  container services {
    config false;
    description
      "Directory Services Entries";
    list all-locations {
      key "location";
      description
        "list of all locations";
      leaf location {
        type string;
        description
          "Node Location";
      }
      uses servicesGroup;
    }
  }
  container services-stats {
    config false;
    description
      "Directory Services Stats";
    container ds {
      config false;
      description
        "services stats for ds";
      uses show_trace:traceable;
    }
    list all-locations {
      key "location";
      description
        "all locations list";
      leaf location {
        type string;
        description
          "Card location";
      }
      list stats {
        key "name";
        description
          "Directory service statistcs";
        leaf name {
          type string;
          description
            "Name of the service";
        }
        leaf published {
          type uint32;
          description
            "number of endpoints published for this service";
        }
        leaf deleted {
          type uint32;
          description
            "number of endpoints deleted for this service";
        }
        leaf modified {
          type uint32;
          description
            "number of endpoints modified for this service";
        }
        leaf registered {
          type uint32;
          description
            "number of clients registered for this service";
        }
        leaf unregistered {
          type uint32;
          description
            "number of clients un-registered for this service";
        }
        leaf notifications {
          type uint32;
          description
            "number of clients notified for this service";
        }
        leaf remote_sent {
          type uint32;
          description
            "number of remote service updates sent to remote nodes";
        }
        leaf remote_recv {
          type uint32;
          description
            "number of remote service received from remote nodes";
        }
      }
    }
  }
}
