module Cisco-IOS-XR-ofa-fib-encap-oper {
  namespace "http://cisco.com/ns/yang/Cisco-IOS-XR-ofa-fib-encap-oper";
  prefix ofa-fib-encap-oper;

  import Cisco-IOS-XR-types {
    prefix xr;
  }
  import cisco-semver {
    prefix semver;
  }
  include Cisco-IOS-XR-ofa-fib-encap-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ofa-fib-encap package operational data.
     
     This module contains definitions
     for the following management objects:
       ofafib-encap-stats: OFA-FIB Encap-id Schema
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container ofafib-encap-stats {
    config false;
    description
      "OFA-FIB Encap-id Schema";
    container nodes {
      description
        "Table of Nodes";
      list node {
        key "node-name";
        description
          "Information about a particular node";
        container ofafib-encap {
          description
            "OFA-FIB encap-id information";
          container stats {
            description
              "OFA-FIB encap-id statistics information";
            uses OFA-FIB-BAG-ENCAP-STATS;
          }
        }
        leaf node-name {
          type xr:Node-id;
          description
            "Node name";
        }
      }
    }
  }
}
