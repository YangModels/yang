module Cisco-IOS-XR-openconfig-transport-line-common-ext {
  namespace "http://cisco.com/ns/yang/Cisco-IOS-XR-openconfig-transport-line-common-ext";
  prefix oc-line-com-ext;

  import openconfig-platform {
    prefix oc-platform;
  }
  import openconfig-transport-line-common {
    prefix oc-line-com;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of optical transport line common model
     and contains the definition of extended parameters for transport line
     common to configure the rx and tx thresholds of optics
     
     This module contains definitions for the following management objects:
     General Parameters
     Submarine Parameters
     
     Copyright (c) 2025 by Cisco Systems, Inc.
     All rights reserved.";

  revision 2025-06-25 {
    description
      "Added support for channel control and management.";
    reference "25.4.1";
  }
  revision 2025-03-25 {
    description
      "IOS XR 6.0 revision";
    reference "7.3.1";
  }

  grouping thresholds-config {
    description
      "Configuration data for a thresholds";
    leaf input-signal-power-lower {
      type decimal64 {
        fraction-digits 2;
      }
      units "0.01dBm";
      description
        "Lower power threshold for laser input power
         in unit of 0.01dBm";
    }
    leaf input-signal-power-upper {
      type decimal64 {
        fraction-digits 2;
      }
      units "0.01dBm";
      description
        "Upper power threshold for laser input power
         in unit of 0.01dBm";
    }
    leaf output-signal-power-lower {
      type decimal64 {
        fraction-digits 2;
      }
      units "0.01dBm";
      description
        "Lower power threshold for laser output power
         in unit of 0.01dBm";
    }
    leaf output-signal-power-upper {
      type decimal64 {
        fraction-digits 2;
      }
      units "0.01dBm";
      description
        "Upper power threshold for laser output power
         in unit of 0.01dBm";
    }
    leaf input-channel-power-delta-lower {
      type decimal64 {
        fraction-digits 2;
      }
      units "dB";
      description
        "Channel recieve power low threshold
         in unit of dB";
    }
    leaf input-channel-power-delta-upper {
      type decimal64 {
        fraction-digits 2;
      }
      units "dB";
      description
        "Channel recieve power high threshold
         in unit of dB";
    }
  }

  grouping thresholds-state {
    description
      "State data for a thresholds";
  }

  grouping channel-control-config {
    description
      "Configuration data for Channel Startup Management";
    leaf channel-minimum-input-psd {
      type decimal64 {
        fraction-digits 2;
      }
      units "dBm";
      description
        "Channel minimum input PSD in
         in unit of dBm per 12.5 GHz";
    }
    leaf input-power-total-expected {
      type decimal64 {
        fraction-digits 2;
      }
      units "dBm";
      description
        "Channel expected total input power in
         unit of dBm";
    }
  }

  grouping channel-control-state {
    description
      "State data for Channel Startup Management";
  }

  grouping oc-line-extended-threshold {
    description
      "Extended transport line common parameters";
    container cisco {
      description
        "Extended transport line common parameters";
      container thresholds {
        description
          "Enclosing container for alarm thresholds.";
        container config {
          description
            "Extended Thresholds Configuration parameters";
          uses thresholds-config;
        }
        container state {
          config false;
          description
            "Extended Thresholds Operational parameters";
          uses thresholds-config;
          uses thresholds-state;
        }
      }
      container channel-control {
        description
          "Enclosing container for Channel Startup Management parameters.";
        container config {
          description
            "Extended Channel Startup Management Configuration parameters";
          uses channel-control-config;
        }
        container state {
          config false;
          description
            "Extended Channel Startup Management Operational parameters";
          uses channel-control-config;
          uses channel-control-state;
        }
      }
    }
  }

  augment "/oc-platform:components/oc-platform:component/oc-platform:port/oc-line-com:optical-port" {
    description
      "This augment extends the configuration data of oc-line-com";
    uses oc-line-extended-threshold;
  }
}
