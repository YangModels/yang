module Cisco-IOS-XR-linux-security-diskenc-act {
  namespace "http://cisco.com/ns/yang/Cisco-IOS-XR-linux-security-diskenc-act";
  prefix diskenc-act;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2021-2025 by Cisco Systems, Inc., and/or its affiliates.
     All rights reserved.";

  revision 2025-07-30 {
    description
      "Canonical Ordering in IOS XR 25.4.1 revision.";
  }
  revision 2021-12-06 {
    description
      "IOS XR 7.6.1 revision.";
  }

  rpc diskenc-activate {
    description
      "Action to start encryption activation";
    input {
      leaf location {
        type string;
        mandatory true;
        description
          "Location string to start encryption activation";
      }
    }
    xr:xr-task "cisco-support";
    xr:cli-command "disk-encryption activate location <location>";
  }
  rpc diskenc-deactivate {
    description
      "Action to start encryption deactivation";
    input {
      leaf location {
        type string;
        mandatory true;
        description
          "Location string to start encryption deactivation";
      }
    }
    xr:xr-task "cisco-support";
    xr:cli-command "disk-encryption deactivate location <location>";
  }
}
