submodule Cisco-IOS-XR-fretta-bcm-dpa-qos-egq-resources-oper-sub1 {
  belongs-to Cisco-IOS-XR-fretta-bcm-dpa-qos-egq-resources-oper {
    prefix Cisco-IOS-XR-fretta-bcm-dpa-qos-egq-resources-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fretta-bcm-dpa-qos-egq-resources package operational data.
     
     Copyright (c) 2013-2023 by Cisco Systems, Inc.
     All rights reserved.";

  revision 2023-06-06 {
    description
      "Added schema for qos egq resource utilization cli";
    semver:module-version "1.0.0";
  }
  revision 2019-04-05 {
    description
      "Establish semantic version baseline.";
  }
  revision 2015-11-09 {
    description
      "IOS XR 6.0 revision.";
  }

  grouping BCMDPA-QOS-EGQ-RESOURCES-INFO-PER-CORE {
    description
      "BCMDPA QOS EGQ RESOURCES INFO PER CORE";
    leaf egq-total-count {
      type uint32;
      description
        "egq total count";
    }
    leaf egq-used-count {
      type uint32;
      description
        "egq used count";
    }
    leaf egq-free-count {
      type uint32;
      description
        "egq free count";
    }
  }

  grouping BCMDPA-QOS-EGQ-RESOURCES-INFO {
    description
      "BCMDPA QOS EGQ RESOURCES INFO";
    leaf num-cores {
      type uint16;
      description
        "num cores";
    }
    list core {
      max-elements "2";
      description
        "core";
      uses BCMDPA-QOS-EGQ-RESOURCES-INFO-PER-CORE;
    }
  }
}
