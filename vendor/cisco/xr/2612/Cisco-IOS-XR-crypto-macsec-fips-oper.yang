module Cisco-IOS-XR-crypto-macsec-fips-oper {
  namespace "http://cisco.com/ns/yang/Cisco-IOS-XR-crypto-macsec-fips-oper";
  prefix crypto-macsec-fips-oper;

  import Cisco-IOS-XR-types {
    prefix xr;
  }
  import cisco-semver {
    prefix semver;
  }
  include Cisco-IOS-XR-crypto-macsec-fips-oper-sub1 {
    revision-date 2024-09-06;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-macsec-fips package operational data.
     
     This module contains definitions
     for the following management objects:
       macsec: Macsec operational data
     
     Copyright (c) 2013-2024 by Cisco Systems, Inc.
     All rights reserved.";

  revision 2024-09-06 {
    description
      "Added MACsec FIPS operational info";
    semver:module-version "1.0.0";
  }
  revision 2019-04-05 {
    description
      "Establish semantic version baseline.";
  }
  revision 2015-11-09 {
    description
      "IOS XR 6.0 revision.";
  }

  container macsec {
    config false;
    description
      "Macsec operational data";
    container standby {
      description
        "MACsec Operational Data from Standby";
    }
    container fips {
      description
        "MACsec FIPS Operational Data";
      container nodes {
        description
          "Per node Macsec FIPS operational data";
        list node {
          key "node-name";
          description
            "The MACsec FIPS operational data for a
             particular node";
          container status {
            description
              "MACsec FIPS Mode Status";
            uses MACSEC-FIPS-STATUS;
          }
          leaf node-name {
            type xr:Node-id;
            description
              "The identifier for the node";
          }
        }
      }
    }
  }
}
