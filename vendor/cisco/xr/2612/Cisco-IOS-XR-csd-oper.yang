module Cisco-IOS-XR-csd-oper {
  namespace "http://cisco.com/ns/yang/Cisco-IOS-XR-csd-oper";
  prefix csd-oper;

  import Cisco-IOS-XR-types {
    prefix xr;
  }
  import cisco-semver {
    prefix semver;
  }
  include Cisco-IOS-XR-csd-oper-sub1 {
    revision-date 2021-07-23;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR csd package operational data.
     
     This module contains definitions
     for the following management objects:
       security: All Stamped Passport related data
     
     Copyright (c) 2013-2021 by Cisco Systems, Inc.
     All rights reserved.";

  revision 2021-07-23 {
    description
      "Removed the trusted_peers endpoint.";
    semver:module-version "1.0.0";
  }
  revision 2021-04-19 {
    description
      "Oper yang for CSD.";
  }
  revision 2019-04-05 {
    description
      "Establish semantic version baseline.";
  }
  revision 2015-11-09 {
    description
      "IOS XR 6.0 revision.";
  }

  container security {
    config false;
    description
      "All Stamped Passport related data";
    container passport {
      description
        "Stamped passport Peers and Attestation results
         data";
      container nodes {
        description
          "Node specific Stamped Passport data";
        list node {
          key "node-name";
          description
            "Per node peers and results data";
          container peers {
            description
              "All Peers Data";
            uses CANARYSTAMP-PEERS;
          }
          container result {
            description
              "Attestation results data";
            uses ATT-RESULTS-DATA;
          }
          container encoded-result {
            description
              "Encoded Attestation results data";
            uses ENCODED-ATT-RESULTS-DATA;
          }
          leaf node-name {
            type xr:Node-id;
            description
              "The node";
          }
        }
      }
    }
  }
}
