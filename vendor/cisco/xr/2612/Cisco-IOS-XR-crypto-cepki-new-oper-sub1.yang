submodule Cisco-IOS-XR-crypto-cepki-new-oper-sub1 {
  belongs-to Cisco-IOS-XR-crypto-cepki-new-oper {
    prefix Cisco-IOS-XR-crypto-cepki-new-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-cepki-new package operational data.
     
     Copyright (c) 2013-2022 by Cisco Systems, Inc.
     All rights reserved.";

  revision 2022-12-15 {
    description
      "Added field to display SSH Authentication keys in OpenSSH format.";
    semver:module-version "1.0.0";
  }
  revision 2022-12-05 {
    description
      "Added fields describing Passwordless SSH Authentication keys.";
  }
  revision 2022-06-08 {
    description
      "oper support added for mypub key ECDSA.";
  }
  revision 2022-05-04 {
    description
      "oper support added for mypub key DSA and RSA.";
  }
  revision 2019-04-05 {
    description
      "Establish semantic version baseline.";
  }
  revision 2015-11-09 {
    description
      "IOS XR 6.0 revision.";
  }

  typedef Yang2bag-string {
    type string;
    description
      "Yang2bag string";
  }

  grouping CEPKI-MYPUBKEY-DSA {
    description
      "Crypto key mypubkey DSA info";
    leaf key-label {
      type string {
        length "0..128";
      }
      description
        "Crypto key mypubkey DSA key label";
    }
    leaf key-type {
      type string {
        length "0..100";
      }
      description
        "Crypto key mypubkey DSA key type";
    }
    leaf key-size {
      type uint32;
      description
        "Crypto key mypubkey DSA key size mod bits";
    }
    leaf key-creation-time {
      type uint32;
      units "second";
      description
        "Key creation timestamp in Epoch seconds";
    }
    leaf tam-status {
      type Yang2bag-string;
      description
        "DSA TAM status";
    }
    leaf key-data {
      type string {
        length "0..5000";
      }
      description
        "DSA key data";
    }
  }

  grouping CEPKI-MYPUBKEY-ECDSA {
    description
      "Crypto key mypubkey ECDSA info";
    leaf key-label {
      type string {
        length "0..128";
      }
      description
        "Crypto key mypubkey ECDSA key label";
    }
    leaf key-type {
      type string {
        length "0..100";
      }
      description
        "Crypto key mypubkey ECDSA key type";
    }
    leaf degree {
      type uint32;
      description
        "Crypto key mypubkey ECDSA key size mod bits";
    }
    leaf key-creation-time {
      type uint32;
      units "second";
      description
        "Key creation timestamp in Epoch seconds";
    }
    leaf tam-status {
      type Yang2bag-string;
      description
        "DSA TAM status";
    }
    leaf key-data {
      type string {
        length "0..5000";
      }
      description
        "ECDSA key data";
    }
  }

  grouping CEPKI-MYPUBKEY-RSA {
    description
      "Crypto key mypubkey RSA info";
    leaf key-label {
      type string {
        length "0..128";
      }
      description
        "Crypto key mypubkey RSA key label";
    }
    leaf key-type {
      type string {
        length "0..100";
      }
      description
        "Crypto key mypubkey RSA key type";
    }
    leaf key-size {
      type uint32;
      description
        "Crypto key mypubkey RSA key size mod bits";
    }
    leaf key-creation-time {
      type uint32;
      units "second";
      description
        "Key creation timestamp in Epoch seconds";
    }
    leaf tam-status {
      type Yang2bag-string;
      description
        "DSA TAM status";
    }
    leaf key-data {
      type string {
        length "0..5000";
      }
      description
        "RSA key data";
    }
  }

  grouping CEPKI-MYPUBKEY-AUTH-SSH {
    description
      "Crypto SSH Authentication Public Key Information";
    leaf key-label {
      type string {
        length "0..128";
      }
      description
        "Crypto SSH Authentication key label";
    }
    leaf key-type {
      type string {
        length "0..100";
      }
      description
        "Crypto SSH Authentication key type";
    }
    leaf key-size {
      type uint32;
      description
        "Crypto SSH Authentication key size mod bits";
    }
    leaf key-creation-time {
      type uint32;
      units "second";
      description
        "Key creation timestamp in epoch seconds";
    }
    leaf key-data {
      type string {
        length "0..5000";
      }
      description
        "Crypto SSH Authentication key data";
    }
    leaf openssh-key-data {
      type string {
        length "0..5000";
      }
      description
        "Crypto SSH Authentication OpenSSH key data";
    }
  }
}
