module Cisco-IOS-XR-sysadmin-wdmon {
  namespace "http://www.cisco.com/ns/yang/Cisco-IOS-XR-sysadmin-wdmon";
  prefix wdmonh;

  import tailf-xsd-types {
    prefix xs;
  }
  import Cisco-IOS-XR-sysadmin-show-trace {
    prefix show_trace;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }

  container wdmon {
    config false;
    uses show_trace:traceable;
  }
  container wdmon-info {
    config false;
    list all-locations {
      key "location";
      leaf location {
        type string;
      }
      leaf start-timestamp {
        type string;
        description
          "Last start date and time for wdmon";
      }
      leaf hushd-timeout {
        type xs:double;
        description
          "wdmon/Calv/Hushd liveness timeout";
      }
      leaf calv-restart-timeout {
        type uint32;
        description
          "Calvados restart timeout";
      }
      leaf hushd-wd-action-disable {
        type boolean;
        description
          "Hushd WD expire action disable or not";
      }
      leaf hushd-wd-action-timestamp {
        type string;
        description
          "Last Hushd WD expire action date and time";
      }
      leaf hushd-capi-up {
        type boolean;
        description
          "Hushd CAPI up or not";
      }
      leaf hushd-pending-resp {
        type boolean;
        description
          "Any pending response from Hushd";
      }
      leaf hushd-stop-punching {
        type boolean;
        description
          "Hushd HB punching stopped";
      }
      leaf hushd-capi-up-timestamp {
        type string;
        description
          "Last Hushd CAPI up date and time";
      }
      leaf hushd-last-hb-resp {
        type xs:double;
        description
          "How long ago was last HB response from Hushd";
      }
      leaf hushd-num-capi-connects {
        type uint32;
        description
          "Num of Hushd CAPI connects";
      }
      leaf wds-action-disable {
        type boolean;
        description
          "wdmon client timeout action disabled or not";
      }
      leaf wds-action-timestamp {
        type string;
        description
          "Last wdmon client timeout action date and time";
      }
      leaf wds-restart-timeout {
        type uint32;
        description
          "wdmon client restart timeout";
      }
      leaf wds-liveness-timeout {
        type uint32;
        description
          "wdmon client liveness timeout";
      }
      leaf wds-client-up {
        type boolean;
        description
          "wdmon client is up or not";
      }
      leaf wds-client-pid {
        type uint32;
        description
          "Process ID of the wdmon client";
      }
      leaf wds-client-up-timestamp {
        type string;
        description
          "Last wdmon client connect date and time";
      }
      leaf wds-client-last-hb {
        type xs:double;
        description
          "How long ago was last HB from wdmon client";
      }
      leaf wds-client-num-connects {
        type uint32;
        description
          "Total number of client connects";
      }
      leaf wds-num-liveness-timeout {
        type uint32;
        description
          "Total number of client liveness timeouts";
      }
      leaf wds-num-restart-timeout {
        type uint32;
        description
          "Total number of client restart timeouts";
      }
      leaf wds-client-reported-status {
        type string;
        description
          "Status reported by wdmon client";
      }
    }
  }
}
