module Cisco-IOS-XR-l2-snoop-cfg {
  namespace "http://cisco.com/ns/yang/Cisco-IOS-XR-l2-snoop-cfg";
  prefix l2-snoop-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR l2-snoop package configuration.
     
     This module contains definitions
     for the following management objects:
       igmp-snooping: IGMP snooping configuration
       mld-snooping: MLD snooping configuration
     
     Copyright (c) 2013-2024 by Cisco Systems, Inc.
     All rights reserved.";

  revision 2024-10-10 {
    description
      "Adding new parameter for evpn sync
       2024-07-23
         Increasing acl name length to 128 chars";
    semver:module-version "1.1.0";
  }
  revision 2021-06-21 {
    description
      "Added the Snooping cfg yang model";
    semver:module-version "1.0.0";
  }
  revision 2019-04-05 {
    description
      "Establish semantic version baseline.";
  }
  revision 2015-11-09 {
    description
      "IOS XR 6.0 revision.";
  }

  container igmp-snooping {
    description
      "IGMP snooping configuration";
    container profiles {
      description
        "IGMP snooping profile table";
      list profile {
        key "profile-name";
        description
          "IGMP snoooping profile";
        container static-groups {
          description
            "Configure a static group ip address";
          list static-group {
            key "group-address";
            description
              "Enter a valid multicast address";
            container sources {
              description
                "<S,G> static group";
              list source {
                key "source-address";
                description
                  "Unicast IP source address";
                leaf source-address {
                  type inet:ipv4-address-no-zone;
                  description
                    "Unicast IP source adsress";
                }
              }
            }
            leaf star-g {
              type empty;
              description
                "<*,G> static group";
            }
            leaf group-address {
              type inet:ipv4-address-no-zone;
              description
                "Group multicast address";
            }
          }
        }
        container group-limit {
          presence "Indicates a group-limit node is configured.";
          description
            "IGMP group limit";
          leaf count {
            type uint32 {
              range "0..65535";
            }
            mandatory true;
            description
              "Enter group limit";
          }
          leaf threshold {
            type uint32 {
              range "0..65535";
            }
            description
              "Enter group threshold limit";
          }
        }
        leaf startup-query-max-response-time {
          type uint32 {
            range "1..25";
          }
          units "second";
          default "10";
          description
            "IGMP startup query max-response-time";
        }
        leaf immediate-leave {
          type empty;
          description
            "IGMP immediate-leave";
        }
        leaf internal-querier-max-response-time {
          type uint32 {
            range "1..25";
          }
          units "second";
          default "10";
          description
            "IGMP internal-querier max response time";
        }
        leaf internal-querier-tcn-query-interval {
          type uint32 {
            range "1..18000";
          }
          units "second";
          default "60";
          description
            "IGMP internal-querier tcn query interval";
        }
        leaf startup-query-count {
          type uint32 {
            range "0..7";
          }
          default "2";
          description
            "Enter starup query count";
        }
        leaf router-alert-check-disable {
          type empty;
          description
            "IGMP router alert check disable";
        }
        leaf querier-query-interval {
          type uint32 {
            range "1..18000";
          }
          units "second";
          default "60";
          description
            "Enter query interval in seconds";
        }
        leaf tcn-flood-query-count {
          type uint32 {
            range "1..10";
          }
          default "2";
          description
            "Enter IGMP tcn flood query count";
        }
        leaf minimum-version {
          type uint32 {
            range "2..3";
          }
          default "2";
          description
            "Enter minimum version";
        }
        leaf system-ip-address {
          type inet:ipv4-address-no-zone;
          description
            "System ip address for internal-querier or tcn
             query solicit";
        }
        leaf tcn-query-solicit {
          type empty;
          description
            "IGMP tcn query solicit";
        }
        leaf internal-querier-tcn-query-max-response-time {
          type uint32 {
            range "1..25";
          }
          units "second";
          default "10";
          description
            "IGMP internal-querier tcn query
             max-response-time";
        }
        leaf default-profile {
          type empty;
          description
            "Configure this profile as default-profile";
        }
        leaf ttl-check-disable {
          type empty;
          description
            "IGMP ttl check disable";
        }
        leaf access-group {
          type xr:Cisco-ios-xr-string {
            length "1..128";
          }
          description
            "Enter access-list name";
        }
        leaf startup-query-port-up-disable {
          type empty;
          description
            "Disable IGMP startup query on port-up";
        }
        leaf unsolicited-report-interval {
          type uint32 {
            range "100..5000";
          }
          units "millisecond";
          default "1000";
          description
            "Enter unsolicated-report-interval in
             milliseconds";
        }
        leaf report-suppression-disable {
          type empty;
          description
            "IGMP report suppression disable";
        }
        leaf startup-query-tcn {
          type empty;
          description
            "IGMP startup query on topology-change";
        }
        leaf mrouter {
          type empty;
          description
            "IGMP static mrouter";
        }
        leaf iccp-group-report-standby-state-disable {
          type empty;
          description
            "Disable current-state reports of standby port
             state";
        }
        leaf mrouter-forwarding-disable {
          type empty;
          description
            "IGMP mrouter forwarding disable";
        }
        leaf internal-querier-version {
          type uint32 {
            range "2..3";
          }
          default "3";
          description
            "Enter internal querier version";
        }
        leaf tcn-flood-disable {
          type empty;
          description
            "IGMP tcn flood disable";
        }
        leaf last-member-query-interval {
          type uint32 {
            range "100..5000";
          }
          units "millisecond";
          default "1000";
          description
            "Enter last member query interval in
             milliseconds";
        }
        leaf startup-query-tcn-sync {
          type empty;
          description
            "IGMP startup query TCN sync";
        }
        leaf startup-query-tcn-always {
          type empty;
          description
            "IGMP startup query TCN always";
        }
        leaf internal-querier {
          type empty;
          description
            "IGMP internal-querier";
        }
        leaf startup-query-iccp-group-port-active {
          type empty;
          description
            "IGMP startup query on interchassis-group
             port-active";
        }
        leaf router-guard {
          type empty;
          description
            "IGMP router-guard";
        }
        leaf internal-querier-robustness-variable {
          type uint32 {
            range "1..7";
          }
          default "2";
          description
            "Enter robustness-variable";
        }
        leaf startup-query-process-start {
          type empty;
          description
            "IGMP startup query on process start";
        }
        leaf startup-query-interval {
          type uint32 {
            range "1..18000";
          }
          units "second";
          default "60";
          description
            "Enter query interval in seconds";
        }
        leaf startup-query-process-start-sync {
          type empty;
          description
            "IGMP startup query process start sync";
        }
        leaf internal-querier-timer-expiry {
          type uint32 {
            range "60..300";
          }
          units "second";
          default "255";
          description
            "IGMP internal-querier timer expiry";
        }
        leaf internal-querier-query-interval {
          type uint32 {
            range "1..18000";
          }
          units "second";
          default "60";
          description
            "IGMP internal-querier query interval";
        }
        leaf group-policy {
          type xr:Cisco-ios-xr-string {
            length "1..256";
          }
          description
            "Enter route policy name";
        }
        leaf internal-querier-tcn-query-count {
          type uint32 {
            range "0..7";
          }
          default "2";
          description
            "IGMP internal-querier tcn query count";
        }
        leaf querier-robustness-variable {
          type uint32 {
            range "1..7";
          }
          default "2";
          description
            "Enter robustness-variable";
        }
        leaf last-member-query-count {
          type uint32 {
            range "1..7";
          }
          default "2";
          description
            "Enter last member query count";
        }
        leaf profile-name {
          type xr:Cisco-ios-xr-string {
            length "1..32";
          }
          description
            "Profile Name";
        }
      }
    }
  }
  container mld-snooping {
    description
      "MLD snooping configuration";
    container profiles {
      description
        "MLD snooping profile table";
      list profile {
        key "profile-name";
        description
          "MLD snoooping profile";
        container static-groups {
          description
            "Configure a static group ip address";
          list static-group {
            key "group-address";
            description
              "Enter a valid multicast address";
            container sgs {
              description
                "<S,G> static group";
              list sg {
                key "source-address";
                description
                  "Unicast IP source address";
                leaf source-address {
                  type inet:ipv6-address-no-zone;
                  description
                    "Unicast IP source address";
                }
              }
            }
            leaf star-g {
              type empty;
              description
                "<*,G> static group";
            }
            leaf group-address {
              type inet:ipv6-address-no-zone;
              description
                "Group multicast address";
            }
          }
        }
        container group-limit {
          presence "Indicates a group-limit node is configured.";
          description
            "MLD group limit";
          leaf count {
            type uint32 {
              range "0..65535";
            }
            mandatory true;
            description
              "Enter group limit";
          }
          leaf threshold {
            type uint32 {
              range "0..65535";
            }
            description
              "Enter group threshold limit";
          }
        }
        leaf system-ip-address {
          type inet:ipv6-address-no-zone;
          description
            "System ip address for internal-querier or tcn
             query solicit";
        }
        leaf access-group {
          type xr:Cisco-ios-xr-string {
            length "1..128";
          }
          description
            "Enter access-list name";
        }
        leaf last-member-query-interval {
          type uint32 {
            range "100..5000";
          }
          units "millisecond";
          default "1000";
          description
            "Enter last member query interval in
             milliseconds";
        }
        leaf tcn-flood-disable {
          type empty;
          description
            "MLD tcn flood disable";
        }
        leaf mrouter {
          type empty;
          description
            "MLD static mrouter";
        }
        leaf mrouter-forwarding-disable {
          type empty;
          description
            "MLD mrouter forwarding disable";
        }
        leaf startup-query-process-start-sync {
          type empty;
          description
            "MLD startup query process start sync";
        }
        leaf tcn-query-solicit {
          type empty;
          description
            "MLD tcn query solicit";
        }
        leaf internal-querier-tcn-query-interval {
          type uint32 {
            range "1..18000";
          }
          units "second";
          default "125";
          description
            "MLD internal-querier tcn query interval";
        }
        leaf startup-query-count {
          type uint32 {
            range "0..7";
          }
          default "2";
          description
            "Enter starup query count";
        }
        leaf iccp-group-report-standby-state-disable {
          type empty;
          description
            "Disable current-state reports of standby port
             state";
        }
        leaf last-member-query-count {
          type uint32 {
            range "1..7";
          }
          default "2";
          description
            "Enter last member query count";
        }
        leaf startup-query-process-start {
          type empty;
          description
            "MLD startup query on process start";
        }
        leaf internal-querier-query-interval {
          type uint32 {
            range "1..18000";
          }
          units "second";
          default "125";
          description
            "MLD internal-querier query interval";
        }
        leaf report-suppression-disable {
          type empty;
          description
            "MLD report suppression disable";
        }
        leaf router-alert-check-disable {
          type empty;
          description
            "MLD router alert check disable";
        }
        leaf startup-query-port-up-disable {
          type empty;
          description
            "Disable MLD startup query on port-up";
        }
        leaf internal-querier-version {
          type uint32 {
            range "1..2";
          }
          default "2";
          description
            "Enter internal querier version";
        }
        leaf startup-query-tcn-always {
          type empty;
          description
            "MLD startup query TCN always";
        }
        leaf immediate-leave {
          type empty;
          description
            "MLD immediate-leave";
        }
        leaf tcn-flood-query-count {
          type uint32 {
            range "1..10";
          }
          default "2";
          description
            "Enter MLD tcn flood query count";
        }
        leaf startup-query-iccp-group-port-active {
          type empty;
          description
            "MLD startup query on interchassis-group
             port-active";
        }
        leaf router-guard {
          type empty;
          description
            "MLD router-guard";
        }
        leaf internal-querier-robustness-variable {
          type uint32 {
            range "1..7";
          }
          default "2";
          description
            "Enter robustness-variable";
        }
        leaf internal-querier-timer-expiry {
          type uint32 {
            range "60..300";
          }
          units "second";
          default "255";
          description
            "MLD internal-querier timer expiry";
        }
        leaf ttl-check-disable {
          type empty;
          description
            "MLD ttl check disable";
        }
        leaf startup-query-tcn {
          type empty;
          description
            "MLD startup query on topology-change";
        }
        leaf startup-query-max-response-time {
          type uint32 {
            range "1..25";
          }
          units "second";
          default "10";
          description
            "MLD startup query max-response-time";
        }
        leaf internal-querier-tcn-query-max-response-time {
          type uint32 {
            range "1..25";
          }
          units "second";
          default "10";
          description
            "MLD internal-querier tcn query
             max-response-time";
        }
        leaf internal-querier {
          type empty;
          description
            "MLD internal-querier";
        }
        leaf internal-querier-max-response-time {
          type uint32 {
            range "1..25";
          }
          units "second";
          default "10";
          description
            "MLD internal-querier max response time";
        }
        leaf unsolicited-report-interval {
          type uint32 {
            range "100..5000";
          }
          units "millisecond";
          default "1000";
          description
            "Enter unsolicated-report-interval in
             milliseconds";
        }
        leaf startup-query-tcn-sync {
          type empty;
          description
            "MLD startup query TCN sync";
        }
        leaf group-policy {
          type xr:Cisco-ios-xr-string {
            length "1..256";
          }
          description
            "Enter route policy name";
        }
        leaf internal-querier-tcn-query-count {
          type uint32 {
            range "0..7";
          }
          default "2";
          description
            "MLD internal-querier tcn query count";
        }
        leaf querier-query-interval {
          type uint32 {
            range "1..18000";
          }
          units "second";
          default "125";
          description
            "Enter query interval in seconds";
        }
        leaf minimum-version {
          type uint32 {
            range "1..2";
          }
          default "1";
          description
            "Enter minimum version";
        }
        leaf startup-query-interval {
          type uint32 {
            range "1..18000";
          }
          units "second";
          default "125";
          description
            "Enter query interval in seconds";
        }
        leaf querier-robustness-variable {
          type uint32 {
            range "1..7";
          }
          default "2";
          description
            "Enter robustness-variable";
        }
        leaf profile-name {
          type xr:Cisco-ios-xr-string {
            length "1..32";
          }
          description
            "Profile Name";
        }
      }
    }
  }
}
