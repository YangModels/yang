submodule Cisco-IOS-XR-ofa-fib-encap-oper-sub1 {
  belongs-to Cisco-IOS-XR-ofa-fib-encap-oper {
    prefix Cisco-IOS-XR-ofa-fib-encap-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-fib-encap package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping OFA-FIB-BAG-ENCAP-INFO {
    description
      "OFA FIB Encap Info";
    leaf timestamp {
      type uint64;
      description
        "timestamp";
    }
    leaf status {
      type boolean;
      description
        "status";
    }
  }

  grouping OFA-FIB-BAG-ENCAP-STATS-ENTRY {
    description
      "OFA FIB Encaps Stats";
    container first {
      description
        "first";
      uses OFA-FIB-BAG-ENCAP-INFO;
    }
    container last {
      description
        "last";
      uses OFA-FIB-BAG-ENCAP-INFO;
    }
    leaf counter {
      type uint32;
      description
        "counter";
    }
  }

  grouping OFA-FIB-BAG-ENCAP-STATS {
    description
      "OFA FIB Encap Stats";
    list stats {
      max-elements "18";
      description
        "stats";
      uses OFA-FIB-BAG-ENCAP-STATS-ENTRY;
    }
  }
}
