module Cisco-IOS-XR-otnsec-cfg {
  namespace "http://cisco.com/ns/yang/Cisco-IOS-XR-otnsec-cfg";
  prefix otnsec-cfg;

  import ietf-inet-types {
    prefix inet;
  }
  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR otnsec package configuration.
     
     This module contains definitions
     for the following management objects:
       otnsec-fips-mode: FipsMode config
       otnsec-policies: Global scoped configuration for otnsec
     
     This YANG module augments the
       Cisco-IOS-XR-ifmgr-cfg
     module with configuration data.
     
     Copyright (c) 2013-2025 by Cisco Systems, Inc.
     All rights reserved.";

  revision 2025-08-07 {
    description
      "Selective Fipsmode support provided";
    semver:module-version "1.1.0";
  }
  revision 2019-04-05 {
    description
      "Establish semantic version baseline.";
    semver:module-version "1.0.1";
  }
  revision 2019-01-07 {
    description
      "Should secure support removal from security policy";
  }
  revision 2018-12-13 {
    description
      "Restricting sak-rekey-interval to 1209600";
  }
  revision 2018-09-02 {
    description
      "Initial Config schema support";
  }
  revision 2015-11-09 {
    description
      "IOS XR 6.0 revision.";
  }

  typedef Cipher-suite {
    type enumeration {
      enum "aes-gcm-256" {
        value 0;
        description
          "AES GCM 256";
      }
    }
    description
      "Cipher suite";
  }

  typedef Secure-policy {
    type enumeration {
      enum "must-secure" {
        value 1;
        description
          "Mandatory security";
      }
    }
    description
      "Secure policy";
  }

  augment "/a1:interface-configurations/a1:interface-configuration" {
    description
      "This augment extends the configuration data of
       'Cisco-IOS-XR-ifmgr-cfg'";
    container odu-otnsec {
      description
        "ODU controller otnsec configuration";
      container ipv4 {
        description
          "Ipv4 address";
        leaf session-id {
          type uint32 {
            range "1..65535";
          }
          description
            "IKEv2 session ID";
        }
        leaf destination-address {
          type inet:ipv4-address-no-zone;
          description
            "Destination IP address";
        }
        leaf source-address {
          type inet:ipv4-address-no-zone;
          description
            "Source IP address";
        }
      }
      leaf ik-ev2-profile {
        type string;
        description
          "IKEv2 profile";
      }
      leaf policy {
        type string {
          length "1..32";
        }
        description
          "Otnsec policy string";
      }
    }
  }
  container otnsec-fips-mode {
    description
      "FipsMode config";
    leaf fips-mode {
      type empty;
      description
        "Enable FIPS mode for OTNSec";
    }
  }
  container otnsec-policies {
    description
      "Global scoped configuration for otnsec";
    list otnsec-policy {
      key "policy-string";
      description
        "Otnsec policy global configuration";
      leaf cipher-suite {
        type Cipher-suite;
        description
          "Encryption/decryption datapath algorithm.";
      }
      leaf sak-rekey-interval {
        type uint32 {
          range "30..1209600";
        }
        units "second";
        description
          "Rekey timeout in seconds";
      }
      leaf security-policy {
        type Secure-policy;
        description
          "Securing policy";
      }
      leaf exist {
        type empty;
        description
          "Otnsec policy global configuration";
      }
      leaf policy-string {
        type xr:Cisco-ios-xr-string {
          length "1..32";
        }
        description
          "Policy string";
      }
    }
  }
}
