module Cisco-IOS-XR-um-power-mgmt-cfg {
  namespace "http://cisco.com/ns/yang/Cisco-IOS-XR-um-power-mgmt-cfg";
  prefix um-power-mgmt-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco power-mgmt package configuration.
     Copyright (c) 2025 by Cisco Systems, Inc., and/or its affiliates.
     All rights reserved.";

  revision 2025-01-16 {
    description
      "Initial UM2 release
       2024-03-28
         Fix schema path and add new containers for power capacity
       2022-02-17
         Added new container action under container power-mgmt";
    semver:module-version "2.0.0";
  }
  revision 2020-12-04 {
    description
      "Initial release";
    semver:module-version "1.0.0";
  }

  container power-mgmt {
    description
      "global power management commands";
    container action {
      description
        "action for controlling power budget to not exceed power capacity";
      leaf disable {
        type empty;
        description
          "disable power budgeting";
      }
    }
    container single-feed-mode {
      description
        "action for suppressing alarms for missing feed (only for dual feed) supplies";
      leaf enable {
        type empty;
        description
          "enable single feed";
      }
    }
    container configured-power-capacity {
      description
        "limit the chassis power consumption to power devices and features";
      leaf max-power-consumption {
        type uint32 {
          range "0..65535" {
            description
              "Max power consumption limit for the chassis";
          }
        }
        description
          "Max power consumption limit for the chassis";
      }
    }
    container feed-redundancy {
      description
        "feed failure protection across all power modules";
      choice FEED-REDUNDANCY {
        description
          "feed failure protection across all power modules";
        case SINGLE-FAULT-PROTECTION {
          container single-fault-protection {
            presence "system protection against power supply feed failure or PSU redundancy failure";
            description
              "system protection against power supply feed failure or PSU redundancy failure";
            leaf capacity {
              type uint32 {
                range "0..65535" {
                  description
                    "PSU single feed capacity for feed redundancy budget calculation in (watts)";
                }
              }
              mandatory true;
              description
                "feed capacity in watts";
            }
          }
        }
        case DUAL-FAULT-PROTECTION {
          container dual-fault-protection {
            presence "system protection against power supply feed failure and PSU redundancy failure (Recommended)";
            description
              "system protection against power supply feed failure and PSU redundancy failure (Recommended)";
            leaf capacity {
              type uint32 {
                range "0..65535" {
                  description
                    "PSU single feed capacity for feed redundancy budget calculation in (watts)";
                }
              }
              mandatory true;
              description
                "feed capacity in watts";
            }
          }
        }
      }
    }
    leaf redundancy-num-pms {
      type uint32 {
        range "0..23" {
          description
            "Number of redundant PEMS";
        }
      }
      description
        "disable power tray level redundancy and convert to power module redundancy";
    }
    container used-threshold-upper {
      description
        "Power used-threshold-upper percentage";
      container locations {
        description
          "Component whose power usage is monitored";
        list location {
          key "component";
          description
            "Component whose power usage is monitored";
          leaf component {
            type string {
              length "1..1024" {
                description
                  "Fully qualified location specification";
              }
            }
            description
              "Fully qualified location specification";
          }
          leaf used-threshold-upper-number {
            type uint32 {
              range "0..99" {
                description
                  "Percentage used power above which used-threshold flag will be set";
              }
            }
            mandatory true;
            description
              "Percentage used power above which used-threshold flag will be set";
          }
        }
      }
    }
    container used-threshold-upper-clear {
      description
        "Power used-threshold-upper-clear percentage";
      container locations {
        description
          "Component whose power usage is monitored";
        list location {
          key "component";
          description
            "Component whose power usage is monitored";
          leaf component {
            type string {
              length "1..1024" {
                description
                  "Fully qualified location specification";
              }
            }
            description
              "Fully qualified location specification";
          }
          leaf used-threshold-upper-clear-number {
            type uint32 {
              range "1..100" {
                description
                  "Percentage used power below which used-threshold flag will be cleared";
              }
            }
            description
              "Percentage used power below which used-threshold flag will be cleared";
          }
        }
      }
    }
    container extended-temp {
      description
        "action for setting power budget for extended temp mode";
      leaf enable {
        type empty;
        description
          "enable extended temp mode";
      }
    }
  }
}
