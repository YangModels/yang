module Cisco-IOS-XR-um-object-group-cfg {
  namespace "http://cisco.com/ns/yang/Cisco-IOS-XR-um-object-group-cfg";
  prefix um-object-group-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco object-group package configuration.
     Copyright (c) 2024 by Cisco Systems, Inc.
     All rights reserved.";

  revision 2024-04-21 {
    description
      "Added feature for udf
       2024-03-25
         Updating model for um2 changes
       2022-07-11
         Added missing description statement to nodes";
    semver:module-version "3.0.0";
  }
  revision 2020-10-07 {
    description
      "Changed type of starting-port and ending-port to allow port number range";
    semver:module-version "2.0.0";
  }
  revision 2019-06-10 {
    description
      "Establish semantic version baseline.";
    semver:module-version "1.0.0";
  }
  revision 2019-04-02 {
    description
      "Initial version";
  }

  feature udf-supported {
    description
      "UDF configuration supported within this model";
  }

  container udfs {
    if-feature "udf-supported";
    description
      "UDF configuration";
    list udf {
      key "udf-string";
      description
        "UDF configuration";
      leaf udf-string {
        type xr:Cisco-ios-xr-string {
          length "1..16" {
            description
              "UDF name - maximum 16 characters";
          }
        }
        description
          "UDF name - maximum 16 characters";
      }
      container header {
        presence "Header for UDF";
        description
          "Header for UDF";
        leaf header-value {
          type enumeration {
            enum "inner" {
              value 0;
              description
                "Inner header for UDF";
            }
            enum "outer" {
              value 1;
              description
                "Outer header for UDF";
            }
          }
          mandatory true;
          description
            "Header for UDF";
        }
        leaf udf-layer {
          type enumeration {
            enum "l2" {
              value 0;
              description
                "L2 layer for UDF";
            }
            enum "l3" {
              value 1;
              description
                "L3 layer for UDF";
            }
            enum "l4" {
              value 2;
              description
                "L4 layer for UDF";
            }
          }
          mandatory true;
          description
            "udf-layer";
        }
        leaf offset {
          type uint32 {
            range "0..65535" {
              description
                "Configure the offset value (bytes)";
            }
          }
          mandatory true;
          description
            "Configure the offset (bytes) in the header";
        }
        leaf header-length {
          type uint32 {
            range "0..65535" {
              description
                "Configure the length (bytes)";
            }
          }
          description
            "Configure the length (bytes) in the header";
        }
      }
    }
  }
  container object-group {
    description
      "Object-group configuration";
    container ports {
      description
        "Port object group";
      list port {
        key "port-object-group-name";
        description
          "Port object group";
        leaf port-object-group-name {
          type xr:Cisco-ios-xr-string {
            length "1..64" {
              description
                "Port object group name - maximum 64 characters";
            }
            pattern "[a-z0-9A-Z][-_.:a-z0-9A-Z]*";
          }
          description
            "Port object group name - maximum 64 characters";
        }
        leaf object-group-description {
          type string {
            length "1..100" {
              description
                "Up to 100 characters describing this object";
            }
          }
          description
            "description for the object group";
        }
        container object-groups {
          description
            "nested object group";
          list object-group {
            key "object-group-string";
            description
              "nested object group";
            leaf object-group-string {
              type xr:Cisco-ios-xr-string {
                length "1..64" {
                  description
                    "Name of a nested object group";
                }
              }
              description
                "Name of a nested object group";
            }
          }
        }
        container port-ranges {
          description
            "Match only packets on a given port range";
          list port-range {
            key "lower-port-range upper-port-range";
            description
              "Match only packets on a given port range";
            leaf lower-port-range {
              type union {
                type uint32 {
                  range "0..65535" {
                    description
                      "Port number";
                  }
                }
                type enumeration {
                  enum "echo" {
                    value 7;
                    description
                      "Echo (7)";
                  }
                  enum "discard" {
                    value 9;
                    description
                      "Discard (9)";
                  }
                  enum "daytime" {
                    value 13;
                    description
                      "Daytime (13)";
                  }
                  enum "chargen" {
                    value 19;
                    description
                      "Character generator (19)";
                  }
                  enum "ftp-data" {
                    value 20;
                    description
                      "FTP data connections (used infrequently, 20)";
                  }
                  enum "ftp" {
                    value 21;
                    description
                      "File Transfer Protocol (21)";
                  }
                  enum "ssh" {
                    value 22;
                    description
                      "Secure Shell (22)";
                  }
                  enum "telnet" {
                    value 23;
                    description
                      "Telnet (23)";
                  }
                  enum "smtp" {
                    value 25;
                    description
                      "Simple Mail Transport Protocol (25)";
                  }
                  enum "time" {
                    value 37;
                    description
                      "Time (37)";
                  }
                  enum "whois" {
                    value 43;
                    description
                      "Nicname (43)";
                  }
                  enum "tacacs" {
                    value 49;
                    description
                      "TAC Access Control System (49)";
                  }
                  enum "domain" {
                    value 53;
                    description
                      "Domain Name Service (53)";
                  }
                  enum "gopher" {
                    value 70;
                    description
                      "Gopher (70)";
                  }
                  enum "finger" {
                    value 79;
                    description
                      "Finger (79)";
                  }
                  enum "www" {
                    value 80;
                    description
                      "World Wide Web (HTTP, 80)";
                  }
                  enum "hostname" {
                    value 101;
                    description
                      "NIC hostname server (101)";
                  }
                  enum "pop2" {
                    value 109;
                    description
                      "Post Office Protocol v2 (109)";
                  }
                  enum "pop3" {
                    value 110;
                    description
                      "Post Office Protocol v3 (110)";
                  }
                  enum "sunrpc" {
                    value 111;
                    description
                      "Sun Remote Procedure Call (111)";
                  }
                  enum "ident" {
                    value 113;
                    description
                      "Ident Protocol (113)";
                  }
                  enum "nntp" {
                    value 119;
                    description
                      "Network News Transport Protocol (119)";
                  }
                  enum "bgp" {
                    value 179;
                    description
                      "Border Gateway Protocol (179)";
                  }
                  enum "irc" {
                    value 194;
                    description
                      "Internet Relay Chat (194)";
                  }
                  enum "pim-auto-rp" {
                    value 496;
                    description
                      "PIM Auto-RP (496)";
                  }
                  enum "exec" {
                    value 512;
                    description
                      "Exec (rsh, 512)";
                  }
                  enum "login" {
                    value 513;
                    description
                      "Login (rlogin, 513)";
                  }
                  enum "cmd" {
                    value 514;
                    description
                      "Remote commands (rcmd, 514)";
                  }
                  enum "lpd" {
                    value 515;
                    description
                      "Printer service (515)";
                  }
                  enum "uucp" {
                    value 540;
                    description
                      "Unix-to-Unix Copy Program (540)";
                  }
                  enum "klogin" {
                    value 543;
                    description
                      "Kerberos login (543)";
                  }
                  enum "kshell" {
                    value 544;
                    description
                      "Kerberos shell (544)";
                  }
                  enum "talk" {
                    value 517;
                    description
                      "Talk (517)";
                  }
                  enum "ldp" {
                    value 646;
                    description
                      "LDP session connection attempts (MPLS, 646)";
                  }
                }
              }
              description
                "Match only packets on a given port range";
            }
            leaf upper-port-range {
              type union {
                type uint32 {
                  range "0..65535" {
                    description
                      "Port number";
                  }
                }
                type enumeration {
                  enum "echo" {
                    value 7;
                    description
                      "Echo (7)";
                  }
                  enum "discard" {
                    value 9;
                    description
                      "Discard (9)";
                  }
                  enum "daytime" {
                    value 13;
                    description
                      "Daytime (13)";
                  }
                  enum "chargen" {
                    value 19;
                    description
                      "Character generator (19)";
                  }
                  enum "ftp-data" {
                    value 20;
                    description
                      "FTP data connections (used infrequently, 20)";
                  }
                  enum "ftp" {
                    value 21;
                    description
                      "File Transfer Protocol (21)";
                  }
                  enum "ssh" {
                    value 22;
                    description
                      "Secure Shell (22)";
                  }
                  enum "telnet" {
                    value 23;
                    description
                      "Telnet (23)";
                  }
                  enum "smtp" {
                    value 25;
                    description
                      "Simple Mail Transport Protocol (25)";
                  }
                  enum "time" {
                    value 37;
                    description
                      "Time (37)";
                  }
                  enum "whois" {
                    value 43;
                    description
                      "Nicname (43)";
                  }
                  enum "tacacs" {
                    value 49;
                    description
                      "TAC Access Control System (49)";
                  }
                  enum "domain" {
                    value 53;
                    description
                      "Domain Name Service (53)";
                  }
                  enum "gopher" {
                    value 70;
                    description
                      "Gopher (70)";
                  }
                  enum "finger" {
                    value 79;
                    description
                      "Finger (79)";
                  }
                  enum "www" {
                    value 80;
                    description
                      "World Wide Web (HTTP, 80)";
                  }
                  enum "hostname" {
                    value 101;
                    description
                      "NIC hostname server (101)";
                  }
                  enum "pop2" {
                    value 109;
                    description
                      "Post Office Protocol v2 (109)";
                  }
                  enum "pop3" {
                    value 110;
                    description
                      "Post Office Protocol v3 (110)";
                  }
                  enum "sunrpc" {
                    value 111;
                    description
                      "Sun Remote Procedure Call (111)";
                  }
                  enum "ident" {
                    value 113;
                    description
                      "Ident Protocol (113)";
                  }
                  enum "nntp" {
                    value 119;
                    description
                      "Network News Transport Protocol (119)";
                  }
                  enum "bgp" {
                    value 179;
                    description
                      "Border Gateway Protocol (179)";
                  }
                  enum "irc" {
                    value 194;
                    description
                      "Internet Relay Chat (194)";
                  }
                  enum "pim-auto-rp" {
                    value 496;
                    description
                      "PIM Auto-RP (496)";
                  }
                  enum "exec" {
                    value 512;
                    description
                      "Exec (rsh, 512)";
                  }
                  enum "login" {
                    value 513;
                    description
                      "Login (rlogin, 513)";
                  }
                  enum "cmd" {
                    value 514;
                    description
                      "Remote commands (rcmd, 514)";
                  }
                  enum "lpd" {
                    value 515;
                    description
                      "Printer service (515)";
                  }
                  enum "uucp" {
                    value 540;
                    description
                      "Unix-to-Unix Copy Program (540)";
                  }
                  enum "klogin" {
                    value 543;
                    description
                      "Kerberos login (543)";
                  }
                  enum "kshell" {
                    value 544;
                    description
                      "Kerberos shell (544)";
                  }
                  enum "talk" {
                    value 517;
                    description
                      "Talk (517)";
                  }
                  enum "ldp" {
                    value 646;
                    description
                      "LDP session connection attempts (MPLS, 646)";
                  }
                }
              }
              description
                "upper-port-range";
            }
          }
        }
        container match-packets {
          description
            "match-packtes";
          list match-packet {
            key "op-string port";
            description
              "match-packtes";
            leaf op-string {
              type enumeration {
                enum "eq" {
                  value 0;
                  description
                    "Match packets on ports equal to entered port number";
                }
                enum "neq" {
                  value 1;
                  description
                    "Match packets on ports not equal to entered port number";
                }
                enum "gt" {
                  value 2;
                  description
                    "Match packets on ports greater than entered port number";
                }
                enum "lt" {
                  value 3;
                  description
                    "Match packets on ports less than entered port number";
                }
              }
              description
                "op-string";
            }
            leaf port {
              type union {
                type uint32 {
                  range "0..65535" {
                    description
                      "Port number";
                  }
                }
                type enumeration {
                  enum "echo" {
                    value 7;
                    description
                      "Echo (7)";
                  }
                  enum "discard" {
                    value 9;
                    description
                      "Discard (9)";
                  }
                  enum "daytime" {
                    value 13;
                    description
                      "Daytime (13)";
                  }
                  enum "chargen" {
                    value 19;
                    description
                      "Character generator (19)";
                  }
                  enum "ftp-data" {
                    value 20;
                    description
                      "FTP data connections (used infrequently, 20)";
                  }
                  enum "ftp" {
                    value 21;
                    description
                      "File Transfer Protocol (21)";
                  }
                  enum "ssh" {
                    value 22;
                    description
                      "Secure Shell (22)";
                  }
                  enum "telnet" {
                    value 23;
                    description
                      "Telnet (23)";
                  }
                  enum "smtp" {
                    value 25;
                    description
                      "Simple Mail Transport Protocol (25)";
                  }
                  enum "time" {
                    value 37;
                    description
                      "Time (37)";
                  }
                  enum "whois" {
                    value 43;
                    description
                      "Nicname (43)";
                  }
                  enum "tacacs" {
                    value 49;
                    description
                      "TAC Access Control System (49)";
                  }
                  enum "domain" {
                    value 53;
                    description
                      "Domain Name Service (53)";
                  }
                  enum "gopher" {
                    value 70;
                    description
                      "Gopher (70)";
                  }
                  enum "finger" {
                    value 79;
                    description
                      "Finger (79)";
                  }
                  enum "www" {
                    value 80;
                    description
                      "World Wide Web (HTTP, 80)";
                  }
                  enum "hostname" {
                    value 101;
                    description
                      "NIC hostname server (101)";
                  }
                  enum "pop2" {
                    value 109;
                    description
                      "Post Office Protocol v2 (109)";
                  }
                  enum "pop3" {
                    value 110;
                    description
                      "Post Office Protocol v3 (110)";
                  }
                  enum "sunrpc" {
                    value 111;
                    description
                      "Sun Remote Procedure Call (111)";
                  }
                  enum "ident" {
                    value 113;
                    description
                      "Ident Protocol (113)";
                  }
                  enum "nntp" {
                    value 119;
                    description
                      "Network News Transport Protocol (119)";
                  }
                  enum "bgp" {
                    value 179;
                    description
                      "Border Gateway Protocol (179)";
                  }
                  enum "irc" {
                    value 194;
                    description
                      "Internet Relay Chat (194)";
                  }
                  enum "pim-auto-rp" {
                    value 496;
                    description
                      "PIM Auto-RP (496)";
                  }
                  enum "exec" {
                    value 512;
                    description
                      "Exec (rsh, 512)";
                  }
                  enum "login" {
                    value 513;
                    description
                      "Login (rlogin, 513)";
                  }
                  enum "cmd" {
                    value 514;
                    description
                      "Remote commands (rcmd, 514)";
                  }
                  enum "lpd" {
                    value 515;
                    description
                      "Printer service (515)";
                  }
                  enum "uucp" {
                    value 540;
                    description
                      "Unix-to-Unix Copy Program (540)";
                  }
                  enum "klogin" {
                    value 543;
                    description
                      "Kerberos login (543)";
                  }
                  enum "kshell" {
                    value 544;
                    description
                      "Kerberos shell (544)";
                  }
                  enum "talk" {
                    value 517;
                    description
                      "Talk (517)";
                  }
                  enum "ldp" {
                    value 646;
                    description
                      "LDP session connection attempts (MPLS, 646)";
                  }
                }
              }
              description
                "port";
            }
          }
        }
      }
    }
    container network {
      description
        "Network object group";
      container ipv6s {
        description
          "IPv6 object group";
        list ipv6 {
          key "ipv6-object-group-name";
          description
            "IPv6 object group";
          leaf ipv6-object-group-name {
            type xr:Cisco-ios-xr-string {
              length "1..64" {
                description
                  "IPv6 object group name - maximum 64 characters";
              }
            }
            description
              "IPv6 object group name - maximum 64 characters";
          }
          leaf object-group-description {
            type string {
              length "1..100" {
                description
                  "Up to 100 characters describing this object";
              }
            }
            description
              "Description for the object group";
          }
          container hosts {
            description
              "A single host address";
            list host {
              key "host-address";
              description
                "A single host address";
              leaf host-address {
                type inet:ipv6-address-no-zone;
                description
                  "host ipv6 address";
              }
            }
          }
          container object-groups {
            description
              "nested object group";
            list object-group {
              key "object-group-string";
              description
                "nested object group";
              leaf object-group-string {
                type xr:Cisco-ios-xr-string {
                  length "1..64" {
                    description
                      "Enter the name of a nested object group";
                  }
                }
                description
                  "Enter the name of a nested object group";
              }
            }
          }
          container host-address-ranges {
            description
              "Range of host addresses";
            list host-address-range {
              key "starting-ipv6-address ending-ipv6-address";
              description
                "Range of host addresses";
              leaf starting-ipv6-address {
                type inet:ipv6-address-no-zone;
                description
                  "IPv6 address";
              }
              leaf ending-ipv6-address {
                type inet:ipv6-address-no-zone;
                description
                  "IPv6 address";
              }
            }
          }
          container ipv6-addresses {
            description
              "Range of ipv6 addresses";
            list ipv6-address {
              key "address address-prefix";
              description
                "Range of ipv6 addresses";
              leaf address {
                type inet:ipv6-address-no-zone;
                description
                  "IPv6 prefix x:x::x/y";
              }
              leaf address-prefix {
                type uint32 {
                  range "0..128";
                }
                description
                  "IPv6 address prefix";
              }
            }
          }
        }
      }
      container ipv4s {
        description
          "IPv4 object group";
        list ipv4 {
          key "ipv4-object-group-name";
          description
            "IPv4 object group";
          leaf ipv4-object-group-name {
            type xr:Cisco-ios-xr-string {
              length "1..64" {
                description
                  "IPv4 object group name - maximum 64 characters";
              }
            }
            description
              "IPv4 object group name - maximum 64 characters";
          }
          leaf object-group-description {
            type string {
              length "1..100" {
                description
                  "Up to 100 characters describing this object";
              }
            }
            description
              "Description for the object group";
          }
          container hosts {
            description
              "A single host address";
            list host {
              key "host-address";
              description
                "A single host address";
              leaf host-address {
                type inet:ipv4-address-no-zone;
                description
                  "Host ipv4 address";
              }
            }
          }
          container object-groups {
            description
              "Nested object group";
            list object-group {
              key "object-group-string";
              description
                "Nested object group";
              leaf object-group-string {
                type xr:Cisco-ios-xr-string {
                  length "1..64" {
                    description
                      "Nested object group";
                  }
                }
                description
                  "Nested object group";
              }
            }
          }
          container host-address-ranges {
            description
              "Range of host addresses";
            list host-address-range {
              key "starting-ipv4-address ending-ipv4-address";
              description
                "Range of host addresses";
              leaf starting-ipv4-address {
                type inet:ipv4-address-no-zone;
                description
                  "IPv4 address";
              }
              leaf ending-ipv4-address {
                type inet:ipv4-address-no-zone;
                description
                  "IPv4 address";
              }
            }
          }
          container ipv4-addresses {
            description
              "Range of ipv4 addresses";
            list ipv4-address {
              key "address prefix-length";
              description
                "Range of ipv4 addresses";
              leaf address {
                type inet:ipv4-address-no-zone;
                description
                  "IPv4 address/prefix";
              }
              leaf prefix-length {
                type xr:Ipv4-prefix-length;
                description
                  "IPv4 address prefix";
              }
            }
          }
        }
      }
    }
  }
}
