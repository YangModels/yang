module Cisco-IOS-XR-ptp-datatypes {
  namespace "http://cisco.com/ns/yang/Cisco-IOS-XR-ptp-datatypes";
  prefix ptp-datatypes;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Ptp-time {
    type enumeration {
      enum "interval" {
        value 0;
        description
          "Time interval in seconds";
      }
      enum "frequency" {
        value 1;
        description
          "Frequency per second";
      }
    }
    description
      "Ptp time";
  }

  typedef Ptp-clock-advertisement-mode {
    type enumeration {
      enum "1588v2" {
        value 0;
        description
          "Use 1588v2 clock selection";
      }
      enum "telecom-profile" {
        value 1;
        description
          "Use Telecom Profile clock selection";
      }
    }
    description
      "Ptp clock advertisement mode";
  }

  typedef Ptp-encap {
    type enumeration {
      enum "ethernet" {
        value 1;
        description
          "Ethernet Encapsulation";
      }
      enum "ipv4" {
        value 2;
        description
          "IPv4 Encapsulation";
      }
      enum "ipv6" {
        value 3;
        description
          "IPv6 Encapsulation";
      }
    }
    description
      "Ptp encap";
  }

  typedef Ptp-time-period {
    type enumeration {
      enum "1" {
        value 0;
        description
          "One";
      }
      enum "2" {
        value 1;
        description
          "Two";
      }
      enum "4" {
        value 2;
        description
          "Four";
      }
      enum "8" {
        value 3;
        description
          "Eight";
      }
      enum "16" {
        value 4;
        description
          "Sixteen";
      }
      enum "32" {
        value 5;
        description
          "Thirty Two";
      }
      enum "64" {
        value 6;
        description
          "Sixty Four";
      }
      enum "128" {
        value 7;
        description
          "One Hundred and Twenty-Eight";
      }
    }
    description
      "Ptp time period";
  }

  typedef Ptp-clock-operation {
    type enumeration {
      enum "two-step" {
        value 0;
        description
          "Two-step clock operation";
      }
      enum "one-step" {
        value 1;
        description
          "One-step clock operation";
      }
    }
    description
      "Ptp clock operation";
  }

  typedef Ptp-clock-selection-mode {
    type enumeration {
      enum "1588v2" {
        value 0;
        description
          "Use 1588v2 clock selection";
      }
      enum "telecom-profile" {
        value 1;
        description
          "Use Telecom Profile clock selection";
      }
    }
    description
      "Ptp clock selection mode";
  }

  typedef Ptp-timescale {
    type enumeration {
      enum "ptp" {
        value 0;
        description
          "PTP timescale";
      }
      enum "arb" {
        value 1;
        description
          "ARB timescale";
      }
    }
    description
      "Ptp timescale";
  }

  typedef Transparent-clock-domain {
    type string {
      pattern "(all)";
    }
    description
      "all: Set for all domains";
  }

  typedef Ptp-delay-asymmetry-units {
    type enumeration {
      enum "nanoseconds" {
        value 0;
        description
          "Nanoseconds";
      }
      enum "microseconds" {
        value 1;
        description
          "Microseconds";
      }
      enum "milliseconds" {
        value 2;
        description
          "Milliseconds";
      }
    }
    description
      "Ptp delay asymmetry units";
  }

  typedef Ptp-time-source {
    type enumeration {
      enum "unknown" {
        value 0;
        description
          "Unknown";
      }
      enum "atomic-clock" {
        value 16;
        description
          "Atomic Clock";
      }
      enum "gps" {
        value 32;
        description
          "GPS";
      }
      enum "terrestrial-radio" {
        value 48;
        description
          "Terrestrial Radio";
      }
      enum "ptp" {
        value 64;
        description
          "PTP";
      }
      enum "ntp" {
        value 80;
        description
          "NTP";
      }
      enum "hand-set" {
        value 96;
        description
          "Hand set";
      }
      enum "other" {
        value 144;
        description
          "Other";
      }
      enum "internal-oscillator" {
        value 160;
        description
          "Internal Oscillator";
      }
    }
    description
      "Ptp time source";
  }

  typedef Ptp-port-state {
    type enumeration {
      enum "any" {
        value 0;
        description
          "Any port state allowed";
      }
      enum "slave-only" {
        value 1;
        description
          "Restrict to slave";
      }
      enum "master-only" {
        value 2;
        description
          "Restrict to master";
      }
    }
    description
      "Ptp port state";
  }

  typedef Ptp-clock-profile {
    type enumeration {
      enum "default" {
        value 0;
        description
          "Default clock profile";
      }
      enum "g82651" {
        value 1;
        description
          "G.8265.1 profile";
      }
      enum "g82751" {
        value 2;
        description
          "G.8275.1 profile";
      }
      enum "g82752" {
        value 3;
        description
          "G.8275.2 profile";
      }
    }
    description
      "Ptp clock profile";
  }

  typedef Ptp-transport {
    type enumeration {
      enum "unicast" {
        value 0;
        description
          "Unicast communication";
      }
      enum "mixed-mode" {
        value 1;
        description
          "Mixed-mode communication";
      }
      enum "multicast" {
        value 2;
        description
          "Multicast communication";
      }
    }
    description
      "Ptp transport";
  }

  typedef Ptp-clock-id {
    type enumeration {
      enum "router-mac" {
        value 0;
        description
          "Use the router's MAC";
      }
      enum "user-mac" {
        value 1;
        description
          "Use a user-specified MAC";
      }
      enum "eui" {
        value 2;
        description
          "Use a user-specified EUI-64 number";
      }
    }
    description
      "Ptp clock id";
  }

  typedef Ptp-invalid-unicast-grant-request-response {
    type enumeration {
      enum "reduce" {
        value 0;
        description
          "Reduce grant parameters";
      }
      enum "deny" {
        value 1;
        description
          "Deny grant";
      }
    }
    description
      "Ptp invalid unicast grant request response";
  }

  typedef Ptp-telecom-clock {
    type enumeration {
      enum "telecom-grandmaster" {
        value 0;
        description
          "Telecom grandmaster clock";
      }
      enum "telecom-boundary" {
        value 1;
        description
          "Telecom boundary clock";
      }
      enum "telecom-slave" {
        value 2;
        description
          "Telecom slave clock";
      }
    }
    description
      "Ptp telecom clock";
  }
}
