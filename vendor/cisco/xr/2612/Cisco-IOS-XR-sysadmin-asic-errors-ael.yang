module Cisco-IOS-XR-sysadmin-asic-errors-ael {
  namespace "http://www.cisco.com/ns/yang/Cisco-IOS-XR-sysadmin-asic-errors-ael";
  prefix ael;

  import tailf-common {
    prefix tailf;
  }
  import Cisco-IOS-XR-sysadmin-types {
    prefix calvados;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2019-04-15 {
    description
      "Establish semantic version baseline.";
    semver:module-version "1.0.0";
  }
  revision 2017-07-05 {
    description
      "Namespace change to fix comply with Cisco guidelines on namespace";
  }
  revision 2017-05-01 {
    description
      "Namespace change to comply with Cisco guidelines on namespace";
  }

  grouping clear-asic-errors {
    tailf:action "counter";
  }

  grouping ael-history-ap-grp {
    container history {
      list location {
        key "location-name";
        leaf location-name {
          type calvados:location-id;
        }
        uses clear-asic-errors;
      }
    }
  }

  grouping ael-history-grp {
    container history {
      list location {
        key "location-name";
        leaf location-name {
          type calvados:location-id;
        }
        list log-lst {
          leaf log-line {
            type string;
          }
        }
      }
    }
  }

  grouping ael-non-history-grp {
    list location {
      key "location-name";
      leaf location-name {
        type calvados:location-id;
      }
      list log-lst {
        leaf log-line {
          type string;
        }
      }
    }
  }

  grouping ael-save-option-grp {
    container save-all-inst-asic-errors {
      uses ael-non-history-grp;
    }
  }

  grouping ael-non-history-ap-grp {
    list location {
      key "location-name";
      leaf location-name {
        type calvados:location-id;
      }
      uses clear-asic-errors;
    }
  }

  grouping ael-all-error-types-grp {
    container sbe {
      uses ael-non-history-grp;
    }
    container mbe {
      uses ael-non-history-grp;
    }
    container parity {
      uses ael-non-history-grp;
    }
    container generic {
      uses ael-non-history-grp;
    }
    container crc {
      uses ael-non-history-grp;
    }
    container reset {
      uses ael-non-history-grp;
    }
    container barrier {
      uses ael-non-history-grp;
    }
    container unexpected {
      uses ael-non-history-grp;
    }
    container link {
      uses ael-non-history-grp;
    }
    container oor-thresh {
      uses ael-non-history-grp;
    }
    container bp {
      uses ael-non-history-grp;
    }
    container io {
      uses ael-non-history-grp;
    }
    container ucode {
      uses ael-non-history-grp;
    }
    container config {
      uses ael-non-history-grp;
    }
    container indirect {
      uses ael-non-history-grp;
    }
    container nonerr {
      uses ael-non-history-grp;
    }
    container summary {
      uses ael-non-history-grp;
    }
    container all {
      uses ael-save-option-grp;
      uses ael-history-grp;
      uses ael-non-history-grp;
    }
  }

  grouping ael-all-error-types-wo-history-grp {
    container sbe {
      uses ael-non-history-grp;
    }
    container mbe {
      uses ael-non-history-grp;
    }
    container parity {
      uses ael-non-history-grp;
    }
    container generic {
      uses ael-non-history-grp;
    }
    container crc {
      uses ael-non-history-grp;
    }
    container reset {
      uses ael-non-history-grp;
    }
    container barrier {
      uses ael-non-history-grp;
    }
    container unexpected {
      uses ael-non-history-grp;
    }
    container link {
      uses ael-non-history-grp;
    }
    container oor-thresh {
      uses ael-non-history-grp;
    }
    container bp {
      uses ael-non-history-grp;
    }
    container io {
      uses ael-non-history-grp;
    }
    container ucode {
      uses ael-non-history-grp;
    }
    container config {
      uses ael-non-history-grp;
    }
    container indirect {
      uses ael-non-history-grp;
    }
    container nonerr {
      uses ael-non-history-grp;
    }
    container summary {
      uses ael-non-history-grp;
    }
    container all {
      uses ael-save-option-grp;
      uses ael-non-history-grp;
    }
  }

  grouping ael-all-error-types-ap-grp {
    container sbe {
      uses ael-non-history-ap-grp;
    }
    container mbe {
      uses ael-non-history-ap-grp;
    }
    container parity {
      uses ael-non-history-ap-grp;
    }
    container generic {
      uses ael-non-history-ap-grp;
    }
    container crc {
      uses ael-non-history-ap-grp;
    }
    container reset {
      uses ael-non-history-ap-grp;
    }
    container barrier {
      uses ael-non-history-ap-grp;
    }
    container unexpected {
      uses ael-non-history-ap-grp;
    }
    container link {
      uses ael-non-history-ap-grp;
    }
    container oor-thresh {
      uses ael-non-history-ap-grp;
    }
    container bp {
      uses ael-non-history-ap-grp;
    }
    container io {
      uses ael-non-history-ap-grp;
    }
    container ucode {
      uses ael-non-history-ap-grp;
    }
    container config {
      uses ael-non-history-ap-grp;
    }
    container indirect {
      uses ael-non-history-ap-grp;
    }
    container nonerr {
      uses ael-non-history-ap-grp;
    }
    container summary {
      uses ael-non-history-ap-grp;
    }
    container all {
      uses ael-save-option-grp;
      uses ael-history-ap-grp;
      uses ael-non-history-ap-grp;
    }
  }

  grouping ael-show-asic-errors-grp {
    list asic-errors {
      key "device-name";
      config false;
      leaf device-name {
        type string;
      }
      list instance {
        key "instance-num";
        leaf instance-num {
          type uint32;
        }
        uses ael-all-error-types-grp;
      }
      container show-all-instances {
        uses ael-all-error-types-wo-history-grp;
      }
    }
  }

  grouping ael-clear-asic-errors-grp {
    container clear-asic-errors-grp {
      list clear-device {
        key "device-name";
        config false;
        leaf device-name {
          type string;
        }
        list instance {
          key "instance-num";
          leaf instance-num {
            type uint32;
          }
          uses ael-all-error-types-ap-grp;
        }
        container all-instances {
          uses ael-all-error-types-ap-grp;
        }
      }
    }
  }

  uses ael-show-asic-errors-grp;
}
