submodule Cisco-IOS-XR-dot1x-portauth-oper-sub1 {
  belongs-to Cisco-IOS-XR-dot1x-portauth-oper {
    prefix Cisco-IOS-XR-dot1x-portauth-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR dot1x-portauth package operational data.
     
     Copyright (c) 2013-2025 by Cisco Systems, Inc.
     All rights reserved.";

  revision 2025-03-04 {
    description
      "Introduced support for dot1x portauth statistics";
    semver:module-version "1.0.0";
  }
  revision 2024-12-12 {
    description
      "Addition of dot1x portauth oper model";
  }
  revision 2019-04-05 {
    description
      "Establish semantic version baseline.";
  }
  revision 2015-11-09 {
    description
      "IOS XR 6.0 revision.";
  }

  grouping DOT1X-COA-STATS {
    description
      "Dot1x Change of authorization statistics";
    leaf total-coa-request-received-count {
      type uint64;
      description
        "Total COA request received count";
    }
    leaf total-coa-ack-count {
      type uint64;
      description
        "Total COA ack count";
    }
    leaf total-coa-nak-count {
      type uint64;
      description
        "Total COA nak count";
    }
    leaf total-coa-req-reauth-last-count {
      type uint64;
      description
        "Total COA Req Reauth last count";
    }
    leaf total-coa-ack-reauth-last-count {
      type uint64;
      description
        "Total COA ACK Reauth last count";
    }
    leaf total-coa-nak-reauth-last-count {
      type uint64;
      description
        "Total COA NAK Reauth last count";
    }
    leaf total-coa-req-reauth-rerun-count {
      type uint64;
      description
        "Total COA Req Reauth rerun count";
    }
    leaf total-coa-ack-reauth-rerun-count {
      type uint64;
      description
        "Total COA ACK Reauth rerun count";
    }
    leaf total-coa-nak-reauth-rerun-count {
      type uint64;
      description
        "Total COA NAK Reauth rerun count";
    }
    leaf total-coa-nak-due-to-rate-limit {
      type uint64;
      description
        "Total number of COA NAKs sent due to multiple
         requests being rate-limited";
    }
    leaf total-coa-ack-send-fail-count {
      type uint64;
      description
        "Total COA ACK Send Fail count";
    }
    leaf total-coa-nak-send-fail-count {
      type uint64;
      description
        "Total COA NAK Send Fail count";
    }
    leaf total-coa-req-invalid-calling-station-id-count {
      type uint64;
      description
        "Total COA Req Invalid Calling Station Id count";
    }
    leaf total-coa-req-invalid-nas-port-id-count {
      type uint64;
      description
        "Total COA Req Invalid NAS Port Id count";
    }
    leaf total-coa-req-invalid-cmd-count {
      type uint64;
      description
        "Total COA Req Invalid command count";
    }
    leaf total-coa-req-sent-to-nodes-count {
      type uint64;
      description
        "Total COA req sent to Nodes count";
    }
    leaf total-coa-ack-from-nodes-count {
      type uint64;
      description
        "Total COA ACK from Nodes count";
    }
    leaf total-coa-nak-from-nodes-count {
      type uint64;
      description
        "Total COA NAK from Nodes count";
    }
    leaf total-coa-client-not-found-from-nodes-count {
      type uint64;
      description
        "Total COA Client Not Found from nodes count";
    }
    leaf total-coa-req-internal-err-count {
      type uint64;
      description
        "Total COA req internal processing error count";
    }
    leaf total-coa-rsp-timeout-count {
      type uint64;
      description
        "Total number of COA response timeouts from
         internal nodes";
    }
    leaf total-coa-ctx-not-found-count {
      type uint64;
      description
        "Total number of COA context Not Found error
         count";
    }
    leaf total-coa-ctx-tid-mismatch-count {
      type uint64;
      description
        "Total number of COA context tid mismatch error
         count";
    }
    leaf total-coa-nak-due-to-client-not-found {
      type uint64;
      description
        "Total number of COA NAKs sent due to request
         received with unknown Calling-Station-Id";
    }
    leaf total-coa-ctx-active-count {
      type uint64;
      description
        "Total number of Active COA context count";
    }
    leaf max-coa-request-rate-limit {
      type uint64;
      description
        "Maximum allowed COA Requests per minute";
    }
  }

  grouping DOT1X-PORT-AUTH-STATS {
    description
      "DOT1X PORT AUTH STATS";
    container change-of-authorization-statistics {
      description
        "Dot1x Change of Authorization Statistics";
      uses DOT1X-COA-STATS;
    }
  }

  grouping DOT1X-PORT-AUTH-CLIENT-COA-STATS {
    description
      "Dot1x PortAuth Client Change of authorization
       statistics";
    leaf total-coa-request-received-count {
      type uint64;
      description
        "Total COA request received count";
    }
    leaf total-coa-ack-count {
      type uint64;
      description
        "Total COA ack count";
    }
    leaf total-coa-nak-count {
      type uint64;
      description
        "Total COA nak count";
    }
    leaf total-coa-req-reauth-last-count {
      type uint64;
      description
        "Total COA Req Reauth last count";
    }
    leaf total-coa-ack-reauth-last-count {
      type uint64;
      description
        "Total COA ACK Reauth last count";
    }
    leaf total-coa-nak-reauth-last-count {
      type uint64;
      description
        "Total COA NAK Reauth last count";
    }
    leaf total-coa-req-reauth-rerun-count {
      type uint64;
      description
        "Total COA Req Reauth rerun count";
    }
    leaf total-coa-ack-reauth-rerun-count {
      type uint64;
      description
        "Total COA ACK Reauth rerun count";
    }
    leaf total-coa-nak-reauth-rerun-count {
      type uint64;
      description
        "Total COA NAK Reauth rerun count";
    }
  }

  grouping DOT1X-PORT-AUTH-CLIENT-STATS {
    description
      "Dot1x PortAuth Client Statistics";
    container change-of-authorization-statistics {
      description
        "Client specific Change of Authorization
         Statistics";
      uses DOT1X-PORT-AUTH-CLIENT-COA-STATS;
    }
    leaf client-mac {
      type string;
      description
        "Formatted Client MAC Address";
    }
  }

  grouping DOT1X-PORT-AUTH-IF-STATS {
    description
      "Dot1x PortAuth Interface Statistics";
    leaf interface-short-name {
      type string;
      description
        "Interface short name";
    }
    list client-stat {
      description
        "DOT1X Clients statistics";
      uses DOT1X-PORT-AUTH-CLIENT-STATS;
    }
  }

  grouping DOT1X-PORT-AUTH-CLIENT-INFO {
    description
      "DOT1X PORT AUTH CLIENT INFO";
    leaf client-mac {
      type string;
      description
        "Formatted Client MAC Address";
    }
    list auth-method {
      description
        "Port Authentication method, dot1x(EAPOL) or MAB";
      uses DOT1X-PORT-AUTH-METHOD;
    }
  }

  grouping DOT1X-PORT-AUTH-SUMMARY {
    description
      "DOT1X PORT AUTH SUMMARY";
    leaf interface-short-name {
      type string;
      description
        "Interface short name";
    }
    list client-info {
      description
        "Information on Dot1x and MAB Clients";
      uses DOT1X-PORT-AUTH-CLIENT-INFO;
    }
  }

  grouping DOT1X-PORT-AUTH-METHOD {
    description
      "DOT1X PORT AUTH METHOD";
    leaf method {
      type string;
      description
        "Authentication method dot1x or MAB";
    }
    leaf status {
      type string;
      description
        "Authentication method status";
    }
  }

  grouping DOT1X-PORT-AUTH-CLIENT-INFO-DETAIL {
    description
      "DOT1X PORT AUTH CLIENT INFO DETAIL";
    leaf client-mac {
      type string;
      description
        "Formatted Client MAC Address";
    }
    leaf status {
      type string;
      description
        "Client Authentication status";
    }
    leaf programming-status {
      type string;
      description
        "Programming Status";
    }
    leaf unauthorized-timeout {
      type uint32;
      units "second";
      description
        "Authentication Lockout Timer duration in seconds";
    }
    leaf unauthorized-timer {
      type string;
      description
        "Authentication Lockout Timer Status";
    }
    list auth-method {
      description
        "Port Authentication method, dot1x(EAPOL) or MAB";
      uses DOT1X-PORT-AUTH-METHOD;
    }
  }

  grouping DOT1X-PORT-AUTH-DETAIL {
    description
      "DOT1X PORT AUTH DETAIL";
    leaf interface-short-name {
      type string;
      description
        "Interface short name";
    }
    leaf interface-handle {
      type xr:Hex-integer;
      description
        "Interface Handle";
    }
    leaf interface-state {
      type string;
      description
        "Interface State, Up or Down";
    }
    leaf port-status {
      type string;
      description
        "Authorization Status for clients on this Port";
    }
    leaf dot1x-profile {
      type string;
      description
        "Dot1x Profile";
    }
    leaf method-list {
      type string;
      description
        "Authentication Method List";
    }
    list client-info {
      description
        "Detailed Information on Dot1x and MAB Clients";
      uses DOT1X-PORT-AUTH-CLIENT-INFO-DETAIL;
    }
  }
}
