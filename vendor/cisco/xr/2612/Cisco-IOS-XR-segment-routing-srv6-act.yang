module Cisco-IOS-XR-segment-routing-srv6-act {
  namespace "http://cisco.com/ns/yang/Cisco-IOS-XR-segment-routing-srv6-act";
  prefix segment-routing-srv6-act;

  import cisco-semver {
    prefix semver;
  }
  import Cisco-IOS-XR-types {
    prefix csc;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR segment-routing srv6 action commands.
     
     Copyright (c) 2025 by Cisco Systems, Inc., and/or its affiliates.
     All rights reserved.";

  revision 2025-09-23 {
    description
      "Added an RPC to clear segment-routing srv6 sid.";
    semver:module-version "1.0.0";
  }

  rpc clear-segment-routing-srv6-sid {
    description
      "Clear segment-routing srv6 sid";
    input {
      leaf sid-address {
        type inet:ip-address-no-zone;
        mandatory true;
        description
          "Specify the SID address to be cleared";
      }
    }
    csc:xr-task "rib";
    csc:cli-command "clear segment-routing srv6 sid <sid-address>";
  }
}
