module Cisco-IOS-XR-fretta-bcm-dpa-qos-rate-profile-resources-oper {
  namespace "http://cisco.com/ns/yang/Cisco-IOS-XR-fretta-bcm-dpa-qos-rate-profile-resources-oper";
  prefix fretta-bcm-dpa-qos-rate-profile-resources-oper;

  import Cisco-IOS-XR-types {
    prefix xr;
  }
  import cisco-semver {
    prefix semver;
  }
  include Cisco-IOS-XR-fretta-bcm-dpa-qos-rate-profile-resources-oper-sub1 {
    revision-date 2023-06-06;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fretta-bcm-dpa-qos-rate-profile-resources package operational data.
     
     This module contains definitions
     for the following management objects:
       dpa-qos: QOS hw resources data
     
     Copyright (c) 2013-2023 by Cisco Systems, Inc.
     All rights reserved.";

  revision 2023-06-06 {
    description
      "Added schema for qos rate profile resource utilization cli";
    semver:module-version "1.0.0";
  }
  revision 2019-04-05 {
    description
      "Establish semantic version baseline.";
  }
  revision 2015-11-09 {
    description
      "IOS XR 6.0 revision.";
  }

  container dpa-qos {
    config false;
    description
      "QOS hw resources data";
    container nodes {
      description
        "QOS hw resources data for available nodes";
      list node {
        key "node-name";
        description
          "QOS hw resources data for a particular node";
        container qos-rate-profile-res-datas {
          description
            "QOS Rate Profile Resources";
          list qos-rate-profile-res-data {
            key "npu-id";
            description
              "QoS rate profile resource data for a
               particular NPU";
            leaf npu-id {
              type uint32;
              description
                "NPU number";
            }
            uses BCMDPA-QOS-RATE-PROFILE-RESOURCES-INFO;
          }
        }
        leaf node-name {
          type xr:Node-id;
          description
            "Node ID";
        }
      }
    }
  }
}
