module Cisco-IOS-XR-um-cdp-cfg {
  namespace "http://cisco.com/ns/yang/Cisco-IOS-XR-um-cdp-cfg";
  prefix um-cdp-cfg;

  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cdp package configuration.
     
     This YANG module augments the
     modules with configuration data.
     
     Copyright (c) 2020-2025 by Cisco Systems, Inc., and/or its affiliates.
     All rights reserved.";

  revision 2022-07-11 {
    description
      "Added missing description statement to nodes";
    semver:module-version "1.1.0";
  }
  revision 2020-09-03 {
    description
      "Initial release";
    semver:module-version "1.0.0";
  }

  grouping IF-BODY {
    description
      "Grouping for interface";
    container cdp {
      presence "Indicates a cdp node is configured.";
      description
        "Enable CDP on an interface";
    }
    container cdp-mac-address {
      description
        "Configure CDP MAC address on interface";
      container ethernet-slow-protocols-mac {
        presence "Indicates a ethernet-slow-protocols-mac node is configured.";
        description
          "Ethernet Slow-Protocols MAC, 01:80:c2:00:00:02";
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  container cdp {
    description
      "Configure global CDP subcommands";
    container enable {
      presence "Indicates an enable node is configured.";
      description
        "Enable CDP";
    }
    leaf holdtime {
      type uint32 {
        range "10..255" {
          description
            "Length of time (in sec) that receiver must keep this packet";
        }
      }
      description
        "Specify the holdtime (in sec) to be sent in packets";
    }
    leaf timer {
      type uint32 {
        range "5..254" {
          description
            "Rate at which CDP packets are sent (in sec)";
        }
      }
      description
        "Specify the rate at which CDP packets are sent (in sec)";
    }
    container advertise {
      description
        "Specify the version of CDP advertisements";
      container v1 {
        presence "Indicates a v1 node is configured.";
        description
          "CDP sends version-1 advertisements only";
      }
    }
    container log {
      description
        "Configure CDP to log Events";
      container adjacency {
        description
          "Configure CDP to log adjacency data";
        container changes {
          presence "Indicates a changes node is configured.";
          description
            "Configure CDP to log changes to adjacency table";
        }
      }
    }
  }
}
