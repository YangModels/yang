module Cisco-IOS-XR-um-asr9k-hw-module-port-cfg {
  namespace "http://cisco.com/ns/yang/Cisco-IOS-XR-um-asr9k-hw-module-port-cfg";
  prefix um-asr9k-hw-module-port-cfg;

  import Cisco-IOS-XR-types {
    prefix xr;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-hw-module-port package configuration.
     
     This YANG module augments the
     modules with configuration data.
     
     Copyright (c) 2020-2025 by Cisco Systems, Inc., and/or its affiliates.
     All rights reserved.";

  revision 2023-03-09 {
    description
      "Added missing statement for 2x100, 3x100, 4x100
       2022-07-11
         Added missing description statement to nodes
       2022-03-10
         Updated the must statement under list port";
    semver:module-version "1.1.0";
  }
  revision 2020-12-14 {
    description
      "Initial release";
    semver:module-version "1.0.0";
  }

  grouping LOCATION-BODY {
    description
      "Grouping for location";
    container breakout {
      description
        "breakout interface types";
      container ports {
        description
          "Optics port configuration";
        list port {
          must
            "forty-gig-e-x2 or forty-gig-e-x1
              or ten-gig-e-x4 or twenty-five-gig-e-x4
              or four-hundred-gig-e-x1 or fifty-gig-e-x8
              or hundred-gig-e-x4 or hundred-gig-e-x2
              or hundred-gig-e-x3 or hundred-gig-e-x1
              or ten-gig-e-x10";
          key "port-number";
          description
            "Optics port configuration";
          leaf port-number {
            type uint32 {
              range "0..21" {
                description
                  "Optics port number";
              }
            }
            description
              "Optics port configuration";
          }
          container ten-gig-e-x10 {
            must
              "not(../forty-gig-e-x2 or ../forty-gig-e-x1
               or ../ten-gig-e-x4 or ../twenty-five-gig-e-x4
               or ../four-hundred-gig-e-x1 or ../fifty-gig-e-x8
               or ../hundred-gig-e-x4 or ../hundred-gig-e-x2
               or ../hundred-gig-e-x3 or ../hundred-gig-e-x1)";
            presence "Indicates a ten-gig-e-x10 node is configured.";
            description
              "10 TenGigE interfaces";
          }
          container forty-gig-e-x2 {
            must
              "not(../ten-gig-e-x10 or ../forty-gig-e-x1
               or ../ten-gig-e-x4 or ../twenty-five-gig-e-x4
               or ../four-hundred-gig-e-x1 or ../fifty-gig-e-x8
               or ../hundred-gig-e-x4 or ../hundred-gig-e-x2
               or ../hundred-gig-e-x3 or ../hundred-gig-e-x1)";
            presence "Indicates a forty-gig-e-x2 node is configured.";
            description
              "2 FortyGigE interfaces";
          }
          container forty-gig-e-x1 {
            must
              "not(../ten-gig-e-x10 or ../forty-gig-e-x2
               or ../ten-gig-e-x4 or ../twenty-five-gig-e-x4
               or ../four-hundred-gig-e-x1 or ../fifty-gig-e-x8
               or ../hundred-gig-e-x4 or ../hundred-gig-e-x2
               or ../hundred-gig-e-x3 or ../hundred-gig-e-x1)";
            presence "Indicates a forty-gig-e-x1 node is configured.";
            description
              "1 FortyGigE interface";
          }
          container ten-gig-e-x4 {
            must
              "not(../ten-gig-e-x10 or ../forty-gig-e-x2
               or ../forty-gig-e-x1 or ../twenty-five-gig-e-x4
               or ../four-hundred-gig-e-x1 or ../fifty-gig-e-x8
               or ../hundred-gig-e-x4 or ../hundred-gig-e-x2
               or ../hundred-gig-e-x3 or ../hundred-gig-e-x1)";
            presence "Indicates a ten-gig-e-x4 node is configured.";
            description
              "4 TenGigE interface";
          }
          container twenty-five-gig-e-x4 {
            must
              "not(../ten-gig-e-x10 or ../forty-gig-e-x2
               or ../forty-gig-e-x1 or ../ten-gig-e-x4
               or ../four-hundred-gig-e-x1 or ../fifty-gig-e-x8
               or ../hundred-gig-e-x4 or ../hundred-gig-e-x2
               or ../hundred-gig-e-x3 or ../hundred-gig-e-x1)";
            presence "Indicates a twenty-five-gig-e-x4 node is configured.";
            description
              "4 TwentyFiveGigE interface";
          }
          container four-hundred-gig-e-x1 {
            must
              "not(../ten-gig-e-x10 or ../forty-gig-e-x2
               or ../forty-gig-e-x1 or ../ten-gig-e-x4
               or ../twenty-five-gig-e-x4 or ../fifty-gig-e-x8
               or ../hundred-gig-e-x4 or ../hundred-gig-e-x2
               or ../hundred-gig-e-x3 or ../hundred-gig-e-x1)";
            presence "Indicates a four-hundred-gig-e-x1 node is configured.";
            description
              "1 FourHundredGigE interface";
          }
          container fifty-gig-e-x8 {
            must
              "not(../ten-gig-e-x10 or ../forty-gig-e-x2
               or ../forty-gig-e-x1 or ../ten-gig-e-x4
               or ../twenty-five-gig-e-x4 or ../four-hundred-gig-e-x1
               or ../hundred-gig-e-x4 or ../hundred-gig-e-x2
               or ../hundred-gig-e-x3 or ../hundred-gig-e-x1)";
            presence "Indicates a fifty-gig-e-x8 node is configured.";
            description
              "8 FiftyGigE interface";
          }
          container hundred-gig-e-x4 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x2
               or ../hundred-gig-e-x3 or ../hundred-gig-e-x1)";
            presence "Indicates a hundred-gig-e-x4 node is configured.";
            description
              "4 HundredGigE interface";
          }
          container hundred-gig-e-x2 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x4
               or ../hundred-gig-e-x3 or ../hundred-gig-e-x1)";
            presence "Indicates a hundred-gig-e-x2 node is configured.";
            description
              "2 HundredGigE interface";
          }
          container hundred-gig-e-x3 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x4
               or ../hundred-gig-e-x2 or ../hundred-gig-e-x1)";
            presence "Indicates a hundred-gig-e-x3 node is configured.";
            description
              "3 HundredGigE interface";
          }
          container hundred-gig-e-x1 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x4
               or ../hundred-gig-e-x2 or ../hundred-gig-e-x3)";
            presence "Indicates a hundred-gig-e-x1 node is configured.";
            description
              "1 HundredGigE interface";
          }
        }
      }
      container bays {
        description
          "Breakout/port-mode bay configuration";
        list bay {
          key "bay-number port-number";
          description
            "Breakout/port-mode bay configuration";
          leaf bay-number {
            type uint32 {
              range "0..1" {
                description
                  "Breakout/port-mode bay number";
              }
            }
            description
              "Breakout/port-mode bay configuration";
          }
          leaf port-number {
            type uint32 {
              range "0..19" {
                description
                  "Breakout/port-mode port number";
              }
            }
            description
              "Breakout/port-mode port configuration";
          }
          container ten-gig-e-x10 {
            must
              "not(../forty-gig-e-x2 or ../forty-gig-e-x1
               or ../ten-gig-e-x4 or ../twenty-five-gig-e-x4
               or ../four-hundred-gig-e-x1 or ../fifty-gig-e-x8
               or ../hundred-gig-e-x4 or ../hundred-gig-e-x2
               or ../hundred-gig-e-x3 or ../hundred-gig-e-x1)";
            presence "Indicates a ten-gig-e-x10 node is configured.";
            description
              "10 TenGigE interfaces";
          }
          container forty-gig-e-x2 {
            must
              "not(../ten-gig-e-x10 or ../forty-gig-e-x1
               or ../ten-gig-e-x4 or ../twenty-five-gig-e-x4
               or ../four-hundred-gig-e-x1 or ../fifty-gig-e-x8
               or ../hundred-gig-e-x4 or ../hundred-gig-e-x2
               or ../hundred-gig-e-x3 or ../hundred-gig-e-x1)";
            presence "Indicates a forty-gig-e-x2 node is configured.";
            description
              "2 FortyGigE interfaces";
          }
          container forty-gig-e-x1 {
            must
              "not(../ten-gig-e-x10 or ../forty-gig-e-x2
               or ../ten-gig-e-x4 or ../twenty-five-gig-e-x4
               or ../four-hundred-gig-e-x1 or ../fifty-gig-e-x8
               or ../hundred-gig-e-x4 or ../hundred-gig-e-x2
               or ../hundred-gig-e-x3 or ../hundred-gig-e-x1)";
            presence "Indicates a forty-gig-e-x1 node is configured.";
            description
              "1 FortyGigE interface";
          }
          container ten-gig-e-x4 {
            must
              "not(../ten-gig-e-x10 or ../forty-gig-e-x2
               or ../forty-gig-e-x1 or ../twenty-five-gig-e-x4
               or ../four-hundred-gig-e-x1 or ../fifty-gig-e-x8
               or ../hundred-gig-e-x4 or ../hundred-gig-e-x2
               or ../hundred-gig-e-x3 or ../hundred-gig-e-x1)";
            presence "Indicates a ten-gig-e-x4 node is configured.";
            description
              "4 TenGigE interface";
          }
          container twenty-five-gig-e-x4 {
            must
              "not(../ten-gig-e-x10 or ../forty-gig-e-x2
               or ../forty-gig-e-x1 or ../ten-gig-e-x4
               or ../four-hundred-gig-e-x1 or ../fifty-gig-e-x8
               or ../hundred-gig-e-x4 or ../hundred-gig-e-x2
               or ../hundred-gig-e-x3 or ../hundred-gig-e-x1)";
            presence "Indicates a twenty-five-gig-e-x4 node is configured.";
            description
              "4 TwentyFiveGigE interface";
          }
          container four-hundred-gig-e-x1 {
            must
              "not(../ten-gig-e-x10 or ../forty-gig-e-x2
               or ../forty-gig-e-x1 or ../ten-gig-e-x4
               or ../twenty-five-gig-e-x4 or ../fifty-gig-e-x8
               or ../hundred-gig-e-x4 or ../hundred-gig-e-x2
               or ../hundred-gig-e-x3 or ../hundred-gig-e-x1)";
            presence "Indicates a four-hundred-gig-e-x1 node is configured.";
            description
              "1 FourHundredGigE interface";
          }
          container fifty-gig-e-x8 {
            must
              "not(../ten-gig-e-x10 or ../forty-gig-e-x2
               or ../forty-gig-e-x1 or ../ten-gig-e-x4
               or ../twenty-five-gig-e-x4 or ../four-hundred-gig-e-x1
               or ../hundred-gig-e-x4 or ../hundred-gig-e-x2
               or ../hundred-gig-e-x3 or ../hundred-gig-e-x1)";
            presence "Indicates a fifty-gig-e-x8 node is configured.";
            description
              "8 FiftyGigE interface";
          }
          container hundred-gig-e-x1 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x4
               or ../hundred-gig-e-x2 or ../hundred-gig-e-x3)";
            presence "Indicates a hundred-gig-e-x1 node is configured.";
            description
              "1 HundredGigE interface";
          }
          container hundred-gig-e-x2 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x4
               or ../hundred-gig-e-x3 or ../hundred-gig-e-x1)";
            presence "Indicates a hundred-gig-e-x2 node is configured.";
            description
              "2 HundredGigE interface";
          }
          container hundred-gig-e-x3 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x4
               or ../hundred-gig-e-x2 or ../hundred-gig-e-x1)";
            presence "Indicates a hundred-gig-e-x3 node is configured.";
            description
              "3 HundredGigE interface";
          }
          container hundred-gig-e-x4 {
            must
              "not(../ten-gig-e-x10 or ../forty-gig-e-x2
               or ../forty-gig-e-x1 or ../ten-gig-e-x4
               or ../twenty-five-gig-e-x4 or ../four-hundred-gig-e-x1
               or ../fifty-gig-e-x8 or ../hundred-gig-e-x2
               or ../hundred-gig-e-x3 or ../hundred-gig-e-x1)";
            presence "Indicates a hundred-gig-e-x4 node is configured.";
            description
              "4 HundredGigE interface";
          }
        }
      }
    }
    container bay-port-mode {
      description
        "Configure port mode of operation for EP";
      container bays {
        description
          "Breakout/port-mode bay configuration";
        list bay {
          must "hundred-gig-e-16qam-x2 or hundred-gig-e-8qam-x2";
          key "bay-number port-number";
          description
            "Breakout/port-mode bay configuration";
          leaf bay-number {
            type uint32 {
              range "0..1" {
                description
                  "Breakout/port-mode bay number";
              }
            }
            description
              "Breakout/port-mode bay configuration";
          }
          leaf port-number {
            type uint32 {
              range "0..19" {
                description
                  "Breakout/port-mode port number";
              }
            }
            description
              "Breakout/port-mode port configuration";
          }
          container hundred-gig-e-16qam-x2 {
            must "not(../hundred-gig-e-8qam-x2)";
            presence "Indicates a hundred-gig-e-16qam-x2 node is configured.";
            description
              "Configure 200G 16QAM port mode for EP";
          }
          container hundred-gig-e-8qam-x2 {
            must "not(../hundred-gig-e-16qam-x2)";
            presence "Indicates a hundred-gig-e-8qam-x2 node is configured.";
            description
              "Configure 200G 8QAM port mode for EP";
          }
        }
      }
    }
    leaf port-mode {
      type xr:Cisco-ios-xr-string {
        length "1..800" {
          description
            "Input a string with number of characters between 4 and 64";
        }
        pattern "[a-zA-Z0-9_.{}, ]+";
      }
      description
        "RXS: Configure R(consecutive N number of same speed ports)xS(speed 1 for 1G or 10 for 10G):48x10";
    }
  }

  augment "/location:locations/location:location" {
    description
      "This augment extends active nodes configuration";
    uses LOCATION-BODY;
  }
  augment "/location:locations/location:preconfigured-location" {
    description
      "This augment extends preconfigured nodes
       configuration";
    uses LOCATION-BODY;
  }
  container hw-module {
    description
      "Configure h/w module";
    container port-control {
      description
        "Conifugre port-control of linecard";
      container license {
        description
          "Apply license for full bandwidth";
        list location {
          key "location-name";
          description
            "Location of the node";
          leaf location-name {
            type xr:Node-id;
            description
              "Fully qualified location specification";
          }
        }
      }
      container non-combo-mode {
        description
          "Configure non-combo mode of operation";
        list location {
          key "location-name";
          description
            "Location of the node";
          leaf location-name {
            type xr:Node-id;
            description
              "Fully qualified location specification";
          }
        }
      }
    }
  }
}
