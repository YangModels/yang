module Cisco-IOS-XR-attestation-agent-cfg {
  namespace "http://cisco.com/ns/yang/Cisco-IOS-XR-attestation-agent-cfg";
  prefix attestation-agent-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR attestation-agent package configuration.
     
     This module contains definitions
     for the following management objects:
       attestation: Attestation Agent configuration
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container attestation {
    description
      "Attestation Agent configuration";
    container ima {
      description
        "Runtime Integrity configuration";
      container cache {
        description
          "IMA cache related configuration";
        container job {
          description
            "Cache CRON Job configuration";
          leaf disable {
            type boolean;
            default "false";
            description
              "Disable the cache job";
          }
          leaf interval {
            type uint32 {
              range "5..1440";
            }
            default "240";
            description
              "Interval for CRON Job 5-1440 mins, must be
               multiple or factor of 60, default 240";
          }
        }
      }
    }
  }
}
