/* ----------------------------------------------------------------------------
 * openconfig-yiny-it-pre.yang - YANG OC Schema definitions for Preconfig IT
 *
 * September 2023, Anthony Thompson-Nutt
 *
 * Copyright (c) 2023-2025 by Cisco Systems, Inc., and/or its affiliates.
 * All rights reserved.
 * ----------------------------------------------------------------------------
 */

module openconfig-yiny-it-pre {
  namespace "http://openconfig.net/yang/yiny-it-pre";
  prefix "oc-yiny-it-pre";

  import openconfig-interfaces { prefix "oc-if"; }

  revision "2023-09-19" {
    description "Initial release";
  }

  grouping preconfig-grouping {
    leaf preconfig-leaf { type string; }
  }

  augment "/oc-if:interfaces/oc-if:interface" {
    container preconfig-cont {
      container config {
        uses preconfig-grouping;
      }

      container state {
        config false;
        uses preconfig-grouping;
      }
    }
  }
}
