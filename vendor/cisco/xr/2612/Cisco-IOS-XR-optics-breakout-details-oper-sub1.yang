submodule Cisco-IOS-XR-optics-breakout-details-oper-sub1 {
  belongs-to Cisco-IOS-XR-optics-breakout-details-oper {
    prefix Cisco-IOS-XR-optics-breakout-details-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR optics-breakout-details package operational data.
     
     Copyright (c) 2013-2022 by Cisco Systems, Inc.
     All rights reserved.";

  revision 2022-08-21 {
    description
      "Schema added.";
    semver:module-version "1.0.0";
  }
  revision 2019-04-05 {
    description
      "Establish semantic version baseline.";
  }
  revision 2015-11-09 {
    description
      "IOS XR 6.0 revision.";
  }

  typedef Breakout-speed {
    type enumeration {
      enum "zero-gig" {
        value 0;
        description
          "zero gig";
      }
      enum "one-gig" {
        value 1;
        description
          "one gig";
      }
      enum "ten-gig" {
        value 2;
        description
          "ten gig";
      }
      enum "twenty-five-gig" {
        value 3;
        description
          "twenty five gig";
      }
      enum "forty-gig" {
        value 4;
        description
          "forty gig";
      }
      enum "fifty-gig" {
        value 5;
        description
          "fifty gig";
      }
      enum "hundred-gig" {
        value 6;
        description
          "hundred gig";
      }
      enum "one-fifty-gig" {
        value 7;
        description
          "one fifty gig";
      }
      enum "two-hundred-gig" {
        value 8;
        description
          "two hundred gig";
      }
      enum "four-hundred-gig" {
        value 9;
        description
          "four hundred gig";
      }
    }
    description
      "Breakout speed";
  }

  grouping BREAKOUT-DETAILS-OP {
    description
      "Breakout Details";
    leaf num-of-breakouts {
      type uint8;
      description
        " No:of breakouts";
    }
    leaf breakout-speed {
      type Breakout-speed;
      description
        " Breakout Speed";
    }
    leaf num-of-physical-channels {
      type uint8;
      description
        " No:of Physical channels";
    }
  }
}
