submodule Cisco-IOS-XR-fib-common-oper-sub8 {
  belongs-to Cisco-IOS-XR-fib-common-oper {
    prefix Cisco-IOS-XR-fib-common-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2026 by Cisco Systems, Inc.
     All rights reserved.";

  revision 2026-04-09 {
    description
      "Changed AS Path string from fixed size to dynamic
       2026-01-19
         Changed encap-id-conflict-count to 64 bits and added encap-id-conflict-cleared
       2025-12-20
         Added Sync Marker event history
       2025-12-11
         Added LDI transition counter to misc container
       2025-12-01
         Extended show of SRv6-Global params to display encap SA with add-entropy flowlabel info
       2025-11-19
         Added OC AFT state-sync feature info in show cef misc
       2025-11-17
         Added Counters and Timestamps for OOR Notification for FIB cef summary
       2025-11-14
         Added local-label conflict DataBase entry type and flags
       2025-10-10
         Added SRv6 dualsid-combo info in show of SRv6-Global
       2025-09-25
         Added SRv6 accounting egress path counter status
       2025-09-23
         Added support for GUE V1 tunnel TEP entry
       2025-09-11
         Added support for Displaying Per table PL and Encap-id Sharing Capabilities
       2025-09-08
         Added fields in fib leaf bag for IP2MPLS
       2025-08-20
         Added fpc_collapse_con_ip_ldi field
       2025-07-15
         Added NexthopID to FIB RTEP entry
       2025-06-29
         Added UDP source port to FIB path TEP entry.
       2025-06-17
         Added error counters in cef summary
       2025-06-06
         Added EncapID to next-hop bag
       2025-04-01
         Added support for the global object-id allocation statistics
       2025-03-17
         Added Overlay Proto, DSCP, and TTL to FIB RTEP entry. Added OC encap type UDP, UDPV4 and UDPV6
       2025-03-10
         Added support for ViaFibNextHopGroup flag in FIB table entry
       2025-03-04
         Added pre-program nexthop group information under fib-sh-tbl-fib and fib-sh-tbl-fib-internal. Added new-trans-id-timestamp under fib-sh-tbl-fib
       2025-02-14
         Added pre-program nexthop group information
       2025-01-30
         Added UDP port global bag
       2025-01-24
         Added counter for ignoring FRR event
       2025-01-17
         Added number of allocated bytes to per protocol debug stats
       2025-01-09
         Added GUE V1 tunnel type
       2024-12-02
         Added Event History for NextHop Group Make-before-break
       2024-10-29
         Added tunnel encapsulation flag in route table information and added a new list of tunnel encapsulation data in route path information
       2024-10-10
         Added EncapID event history
       2024-09-24
         Added nexthop group named table
       2024-09-20
         Added backup-active leaf to next-hop-group/state container
       2024-09-17
         Added SRv6 prefix support for BSID accounting
       2024-09-11
         Moved misc container to global container instead of protocol container
       2024-09-10
         Added EncapID programming related fields
       2024-08-21
         Added time-of-last-rsrc-msg-update-in-msec and time-of-last-rsrc-nfn-update-in-msec to object counters
       2024-08-19
         Added viability info to FIB external-client instances
       2024-08-16
         Added FIB oor prevention support to FIB cef summary
       2024-08-12
         Added support for information display of PWHE Interfaces, added new entry (gil-interface-name) to key of RTEP table and modified existing entry type (tunnel-interface-name) of RTEP table
       2024-08-09
         Added aysnc error notify capability
       2024-07-26
         Added per-NHOP nh-idb-usable and per-interface usable elements
       2024-06-28
         Added key to route summary counters
       2024-06-26
         Removed oor-resource-counter
       2024-06-24
         Added misc/per-protocol-debug-statistics/bcdlv2-stats
       2024-06-20
         Added route summary counters per protocol
       2024-05-28
         Added l3-unequal-cost-ip-route-paths-count to platform capabilities
       2024-05-23
         Standardize naming of ipvpn-tunnel-type and add new ipvpn-tunnel-type-nh type
       2024-05-23
         Add is-loadinfo-collapsed flag to basic FIB table information
       2024-05-02
         Added rtep-source, tunnel-id, tunnel-ifh and overlay-proto keys to tunnel tables
       2024-01-25
         Increased ECMP/UCMP capability
       2024-01-12
         Add back error/oor state for telemetry in oc-aft-l3 model
       2023-12-01
         Add platform-pbtsv6-support to platform capabilities
       2023-11-29
         Added Nexthop group ID information
       2023-11-27
         Optimized schema for linklocal. Added is-non-recursive field to IP prefixes.
       2023-10-25
         Added GIL ID in PWHE information and Interface List attribute
       2023-10-24
         Consolidated nh-info tables by type
       2023-10-19
         Added NextHop group ID to ext client output
       2023-10-11
         Added schema for external client, fixed schema for hardware egress/ingress
       2023-10-10
         Added and modified NPU mask and PWHE information
       2023-10-04
         Added encap-id and stat-id to recursive-nexthop dependents.
       2023-10-02
         Added VXLAN TEP tables.
       2023-09-21
         Eliminate name conflicts between keys and values
       2023-09-18
         Separated schema of linklocal prefix table from generic prefix table.
       2023-09-14
         Added via-nexthop-group to show cef output
       2023-08-15
         Added new errors sub-tree.
       2023-07-31
         Made hierarchical-loadbalancing parameters mandatory
       2023-07-28
         Internal cleanup, some type name changes.
       2023-07-26
         Fixed schema for exact-route and linklocal
       2023-07-17
         Changed pbts related variable type from static to dynamic array
       2023-07-13
         Added is-unresolved and is-frr to prefix tables
       2023-07-07
         Standardized leaf names and types throughout.
       2023-06-26
         Fix schema for hardware egress/ingress option
       2023-06-15
         Changed vni-info-key-type to an enum and added tblid-vni-key to vni-info-key-type
       2023-06-02
         Two Stage platform ObjectId capability added for cef-misc
       2023-06-01
         Added new field to ltep-nve-tunnels in order keep track of destination address protocol
       2023-05-31
         SRv6 accounting support added for FIB cef
       2023-05-25
         SRv6 accounting support added for FIB cef-accounting
       2023-05-24
         Added new detail field for hardware egress/ingress option
       2023-05-11
         Added class-id to support full exact-route functionality
       2023-05-08
         Remove oc-aft model from fib oper model
       2023-05-04
         Added new field to rtep-tunnels in order keep track of destination address protocol
       2023-04-24
         Combined separate evni tables for BGP and RTEP-ID to single evni table
       2023-04-15
         Added changes for show cef Interface
       2023-04-14
         Added hardware ingress and egress path for evni
       2023-04-05
         Added srv6_hardware ingress/egress
       2023-03-31
         Added resource-summary-infos and modified ip-prefix-detail
       2023-03-29
         Changed recursive nexthop display to be generic for address types
       2023-03-28
         Modified Interface List ID size from 16-bit to 32-bit
       2023-03-28
         Modifed fib_sh_policy_rl_entry rate field to uint64_t
       2023-03-20
         Added some preprograming related fields.
       2023-03-18
         Removed node tag from cef-accounting container.
       2023-03-06
         Added global policy table
       2023-02-07
         Added Exact route schema changes
       2023-02-06
         Added proto-retry-db-summary.
       2023-02-06
         Added disable-rfc5549-ipv4-over-ipv6-nexthop platform capability.
       2023-01-27
         Updated schema for ResourceHardwareIngress and Egress support
       2023-01-27
         Added exceptions-v4, exceptions-v6 and exceptions-mpls.
       2023-01-25
         Added global-retry-db-summary.
       2023-01-24
         Added cef-table-summary, drops-v6 and drops-mpls.
       2023-01-23
         srv6 accounting support
       2023-01-20
         Summary statistics: Added udp-src-port-msb information
       2023-01-04
         Updated evni-tunnel-bgp keys for VxLAN support
       2022-12-20
         Added changes for NHInfoHardwareIngress and NHInfoHardwareEgress in schema file.
       2022-12-06
         Added destionation address to Tunnel Decap, added destination address and underlay table id to Tunnel Decap-NVE
       2022-11-07
         protocol origin changes
       2022-11-01
         Updated FIB ext-client info bag to support ECD LTEP registrations
       2022-10-17
         CNHG changes
       2022-10-05
         Added PWHE and NPU mask for interface details
       2022-10-04
         Tunnel Encap/Decap: Added Prefix Length to the source and destination addresses
       2022-09-22
         Rate limiter statistics: Added drop stats
       2022-09-15
         Added Internal ID in PW-HE extension
       2022-08-29
         Summary statistics: Added udp-port information
       2022-07-19
         Added async-ack-support to FIB-SH-PLAT-CAPABILITIES, and ack-status, ack-latency, to FIB-GRIBI-ENTRY-INFO and FIB-GLOBAL-GRIBI-ENTRY.
       2022-07-07
         Added VRF base filtering for MPLS label stats
       2022-06-14
         Added program id, dst_ip and src_ip in next-hop and nhg fib.bag
       2022-06-13
         Added destination address to nve-ltep bag
       2022-05-13
         Added aft vrf-id to gribi bags
       2022-04-27
         Added vxlan-vni-id to ltep-tunnel
       2022-04-25
         Added RNH state
       2022-04-08
         Added table statistics
       2022-03-31
         Added sr-frr-nhid to frr-nhinfo-pending
       2022-03-24
         Added retry counts to object summary attributes
       2022-03-15
         Added vxlan-tunnels
       2022-03-01
         Added policy and hardware ingress and egress paths
       2022-02-16
         Added some SRv6 SIDs data
       2021-12-14
         Added gribi-table and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "5.0.0";
  }
  revision 2021-10-17 {
    description
      "Modify the type of list fsum-attr-cnt
       2021-09-17
          Rename lists unicast-prefix, broadcast-prefix and leafs num-retry-objects, old-unresolved-entries, new-unresolved-entries, unresolved-entries
       2021-07-30
          Added evpn bridge ID and SHG ID to srv6-information-for-path bag
       2021-07-06
          Added global-main subtree and support show CLIs for FIB IPC infra
       2021-05-25
          Migrate NHINFO to TI infra";
    semver:module-version "4.0.0";
  }
  revision 2020-12-02 {
    description
      "Adding per-object accounting.
       2020-10-20
           NBC documentation of CSCvu06764, CSCvv14573,CSCvv76648
       2020-05-26
           Update SRv6 Block Space naming convention
       2020-05-05
           changes related to treat SRv6 and SID as well-known when parsing XML for yang";
    semver:module-version "3.0.0";
  }
  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  grouping FIB-STATISTICS-BAG-EXCEPTIONS {
    description
      "FIB exception statistics";
    leaf packet-switched-counter {
      type uint64;
      description
        "FIB switched the packet";
    }
    leaf punt-due-to-receive-counter {
      type uint64;
      description
        "Punt due to receive";
    }
    leaf broadcast-counter {
      type uint64;
      description
        "Special processing for bcast";
    }
    leaf max-deliver-counter {
      type uint64;
      description
        "End of deliver on failure";
    }
    leaf no-route-counter {
      type uint64;
      description
        "Punt to generate unreachable";
    }
    leaf ttl-expired-counter {
      type uint64;
      description
        "Punt bad checksum or ttl";
    }
    leaf redirect-counter {
      type uint64;
      description
        "Punt to generate redirect";
    }
    leaf df-unreachable-counter {
      type uint64;
      description
        "Punt generate DF unreachable";
    }
    leaf icmp-failures-counter {
      type uint64;
      description
        "End of ICMP related failures";
    }
    leaf ip-options-counter {
      type uint64;
      description
        "Punt due to option in packet";
    }
    leaf unsupported-feature-counter {
      type uint64;
      description
        "Punt unsupported feature";
    }
    leaf punt-failure-counter {
      type uint64;
      description
        "End of punt on failure";
    }
    leaf fragmented-packet-counter {
      type uint64;
      description
        "Packet required fragmenting";
    }
    leaf slow-encap-counter {
      type uint64;
      description
        "Encap skip could not be done";
    }
    leaf packet-consumed-counter {
      type uint64;
      description
        "Pkt consumed by external fn";
    }
  }

  grouping FIB-STATISTICS-BAG-DROPS {
    description
      "FIB drop statistics";
    leaf no-route-packets {
      type uint64;
      description
        "Fib stats for no route pkts";
    }
    leaf punt-unreachable-packets {
      type uint64;
      description
        "Punt generate unreach pkt";
    }
    leaf df-unreachable-packets {
      type uint64;
      description
        "DF unreachable pkt";
    }
    leaf encapsulation-failure-packets {
      type uint64;
      description
        "Fib stats for encapsulation failure pkts";
    }
    leaf incomplete-adjacency-packets {
      type uint64;
      description
        "Fib stats for incomplete adjacency pkts";
    }
    leaf unresolved-prefix-packets {
      type uint64;
      description
        "Fib stats for unresolved prefix pkts";
    }
    leaf unsupported-feature-packets {
      type uint64;
      description
        "Fib stats for unsupported feature pkt";
    }
    leaf discard-packets {
      type uint64;
      description
        "Fib stats for discarded pkts";
    }
    leaf checksum-error-packets {
      type uint64;
      description
        "Fib stats for checksum error pkts";
    }
    leaf fragmenation-consumed-packets {
      type uint64;
      description
        "frag consumed packet pkt";
    }
    leaf fragmenation-failure-packets {
      type uint64;
      description
        "Fib stats for fragmenation failure pkt";
    }
    leaf null-packets {
      type uint64;
      description
        "null0 pkt";
    }
    leaf rpf-check-failure-packets {
      type uint64;
      description
        "RPF check failures pkt";
    }
    leaf acl-in-rpf-packets {
      type uint64;
      description
        "ACL in RPF pkt";
    }
    leaf rp-destination-drop-packets {
      type uint64;
      description
        "rp dest drop pkt";
    }
    leaf total-number-of-drop-packets {
      type uint64;
      description
        "Fib stats for the total number of dropped pkts";
    }
    leaf mpls-disabled-interface {
      type uint64;
      description
        "Fib number of drops for mpls disabled interfaces";
    }
    leaf gre-lookup-failed-drop {
      type uint64;
      description
        "GRE tunnel lookup failed drop pkt";
    }
    leaf gre-error-drop {
      type uint64;
      description
        "GRE processing errors";
    }
    leaf lisp-punt-drops {
      type uint64;
      description
        "LISP Punt drops";
    }
    leaf lisp-encap-error-drops {
      type uint64;
      description
        "Fib stats for Lisp encap error drops";
    }
    leaf lisp-decap-error-drops {
      type uint64;
      description
        "Fib stats for Lisp decap error drops";
    }
    leaf multi-label-drops {
      type uint64;
      description
        "Drops for the packets with multi[le labels";
    }
    leaf unreachable-sr-label-drops {
      type uint64;
      description
        "No route or unresolved route of MPLS SR labels";
    }
    leaf ttl-expired-sr-label-drops {
      type uint64;
      description
        "TTL expired drops of MPLS SR labels";
    }
  }
}
