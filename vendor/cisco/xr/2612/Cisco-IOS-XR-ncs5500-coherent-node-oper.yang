module Cisco-IOS-XR-ncs5500-coherent-node-oper {
  namespace "http://cisco.com/ns/yang/Cisco-IOS-XR-ncs5500-coherent-node-oper";
  prefix ncs5500-coherent-node-oper;

  import Cisco-IOS-XR-types {
    prefix xr;
  }
  import cisco-semver {
    prefix semver;
  }
  include Cisco-IOS-XR-ncs5500-coherent-node-oper-sub1 {
    revision-date 2023-11-02;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs5500-coherent-node package operational data.
     
     This module contains definitions
     for the following management objects:
       coherent: Coherent node  operational data
     
     Copyright (c) 2013-2023 by Cisco Systems, Inc.
     All rights reserved.";

  revision 2023-11-02 {
    description
      "Added a leaf optics subtype
       2022-03-24
         Increase in interface name length";
    semver:module-version "1.1.0";
  }
  revision 2019-04-05 {
    description
      "Establish semantic version baseline.";
    semver:module-version "1.0.0";
  }
  revision 2015-11-09 {
    description
      "IOS XR 6.0 revision.";
  }

  container coherent {
    config false;
    description
      "Coherent node  operational data";
    container nodes {
      description
        "Coherent list of nodes";
      list node {
        key "node-name";
        description
          "Coherent discovery operational data for a
           particular node";
        container coherent-time-stats {
          description
            "Coherent driver performace information";
          uses COH-TIME-STATS;
        }
        container coherenthealth {
          description
            "Coherent node data for driver health";
          uses COH-HEALTH-DATA;
        }
        leaf node-name {
          type xr:Node-id;
          description
            "The node name";
        }
      }
    }
  }
}
