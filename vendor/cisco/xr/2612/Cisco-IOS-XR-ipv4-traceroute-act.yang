submodule Cisco-IOS-XR-ipv4-traceroute-act {
  belongs-to Cisco-IOS-XR-traceroute-act {
    prefix traceroute-act;
  }

  import cisco-semver {
    prefix semver;
  }
  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR IPv4 traceroute action package configuration.
     
     Copyright (c) 2016-2025 by Cisco Systems, Inc., and/or its affiliates.
     All rights reserved.";

  revision 2025-01-08 {
    description
      "Add extended-diagnostics response details
       2023-10-31
         Addition of dscp leaf
       2022-12-06
         Additional leaves for google_b4_traceroute";
    semver:module-version "1.2.0";
  }
  revision 2021-03-05 {
    description
      "Removed support for use-srv6-op-sid";
    semver:module-version "1.1.0";
  }
  revision 2019-10-01 {
    description
      "Made changes to be RFC6087 compliant";
    semver:module-version "1.1.0";
  }
  revision 2019-04-05 {
    description
      "Establish semantic version baseline.";
    semver:module-version "1.0.0";
  }
  revision 2016-09-17 {
    description
      "IOS XR 6.2.1 revision.";
  }

  grouping TRACEROUTE-OPTIONS {
    description
      "Traceroute options";
    leaf destination {
      type string;
      mandatory true;
      description
        "Destination address or hostname";
    }
    leaf source {
      type string;
      description
        "Source address or interface";
    }
    leaf timeout {
      type uint32 {
        range "0..36";
      }
      default "3";
      description
        "Timeout in seconds";
    }
    leaf probe {
      type uint16 {
        range "1..64";
      }
      default "3";
      description
        "Probe count";
    }
    leaf numeric {
      type boolean;
      description
        "Numeric display only";
    }
    leaf vrf-name {
      type string;
      description
        "VRF name";
    }
    leaf min-ttl {
      type uint16 {
        range "0..255";
      }
      default "1";
      description
        "minimum time to live";
    }
    leaf max-ttl {
      type uint16 {
        range "0..255";
      }
      default "30";
      description
        "maximum time to live";
    }
    leaf port {
      type uint32 {
        range "0..65535";
      }
      description
        "Port numbe";
    }
    leaf verbose {
      type boolean;
      description
        "verbose output";
    }
    leaf dscp {
      type enumeration {
        enum "CS0" {
          value 0;
          description
            "Class Selector default precedence";
        }
        enum "CS1" {
          value 8;
          description
            "Class Selector precedence 1";
        }
        enum "AF11" {
          value 10;
          description
            "Class 1 low drop precedence";
        }
        enum "AF12" {
          value 12;
          description
            "Class 1 medium drop precedence";
        }
        enum "AF13" {
          value 14;
          description
            "Class 1 high drop precedence";
        }
        enum "CS2" {
          value 16;
          description
            "Class Selector precedence 2";
        }
        enum "AF21" {
          value 18;
          description
            "Class 2 low drop precedence";
        }
        enum "AF22" {
          value 20;
          description
            "Class 2 medium drop precedence";
        }
        enum "AF23" {
          value 22;
          description
            "Class 2 high drop precedence";
        }
        enum "CS3" {
          value 24;
          description
            "Class Selector precedence 3";
        }
        enum "AF31" {
          value 26;
          description
            "Class 3 low drop precedence";
        }
        enum "AF32" {
          value 28;
          description
            "Class 3 medium drop precedence";
        }
        enum "AF33" {
          value 30;
          description
            "Class 3 high drop precedence";
        }
        enum "CS4" {
          value 32;
          description
            "Class Selector precedence 4";
        }
        enum "AF41" {
          value 34;
          description
            "Class 4 low drop precedence";
        }
        enum "AF42" {
          value 36;
          description
            "Class 4 medium drop precedence";
        }
        enum "AF43" {
          value 38;
          description
            "Class 4 high drop precedence";
        }
        enum "CS5" {
          value 40;
          description
            "Class Selector precedence 5";
        }
        enum "VA" {
          value 44;
          description
            "Voice admit";
        }
        enum "EF" {
          value 46;
          description
            "Expedited Forwarding";
        }
        enum "CS6" {
          value 48;
          description
            "Class Selector precedence 6";
        }
        enum "CS7" {
          value 56;
          description
            "Class Selector precedence 7";
        }
      }
      description
        "Set IP Differentiated Services CodePoint";
    }
  }

  grouping DIAG-EXT-INTERFACE {
    description
      "Interface identified by diagnostic extensions";
    leaf name {
      type xr:Interface-name;
      description
        "Interface name";
    }
    leaf address {
      type inet:ip-address-no-zone;
      description
        "IPv4 or IPv6 address";
    }
    leaf mtu {
      type uint32;
      description
        "Layer 3 MTU";
    }
  }

  grouping TRACEROUTE-OUTPUT {
    description
      "Traceroute output";
    leaf destination {
      type string;
      description
        "Destination address or hostname";
    }
    leaf data-size {
      type uint32;
      description
        "size of the packet";
    }
    leaf dest-hostname {
      type string;
      description
        "Destination hostname";
    }
    container hops {
      description
        "Hops info";
      list hop {
        key "hop-index";
        description
          "Hop info";
        leaf hop-index {
          type uint32;
          description
            "Index of the hop";
        }
        leaf hop-address {
          type string;
          description
            "Address of the hop";
        }
        leaf hop-hostname {
          type string;
          description
            "Hostname of the hop";
        }
        container probes {
          description
            "Probes info";
          list probe {
            key "probe-index";
            description
              "Probe info";
            leaf probe-index {
              type uint32;
              description
                "Index of the probe";
            }
            leaf result {
              type string;
              description
                "Response for each probe";
            }
            leaf delta-time {
              type uint32;
              description
                "Delta time in seconds";
            }
            leaf hop-address {
              type string;
              description
                "Address of the hop";
            }
            leaf state {
              type int32;
              description
                "state of the probe";
            }
            leaf icmp-code {
              type int32;
              description
                "icmp code of the probe";
            }
            leaf hop-hostname {
              type string;
              description
                "Hostname of the hop";
            }
            container srv6-header {
              description
                "SRV6 header";
              leaf destination-address {
                type uint32;
                description
                  "Destination address for srv6 header";
              }
              leaf segments-left {
                type uint32;
                description
                  "Number of segments left";
              }
              container segments {
                description
                  "Segments";
                leaf-list segment {
                  type string;
                  description
                    "sid in sidlist";
                }
              }
            }
            container ingress-interface {
              description
                "Interface through which original packet was received";
              uses DIAG-EXT-INTERFACE;
            }
            container forwarding-interface {
              description
                "Interface through which original packet would have
                 been forwarded, if it was forwardable";
              uses DIAG-EXT-INTERFACE;
            }
            leaf next-hop-address {
              type inet:ip-address-no-zone;
              description
                "Next hop to which the original packet would have
                 been forwarded, if it was forwardable";
            }
          }
        }
      }
    }
    leaf verbose-output {
      type string;
      description
        "Verbose output";
    }
  }
}
