module Cisco-IOS-XR-um-mac-persist-cfg {
  namespace "http://cisco.com/ns/yang/Cisco-IOS-XR-um-mac-persist-cfg";
  prefix um-mac-persist-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mac-persist package configuration.
     
     This YANG module augments the
     modules with configuration data.
     
     Copyright (c) 2022-2025 by Cisco Systems, Inc., and/or its affiliates.
     All rights reserved.";

  revision 2022-09-22 {
    description
      "Initial release";
    semver:module-version "1.0.0";
  }

  container bundle {
    description
      "Bundle global command";
    container mac-address {
      description
        "MAC address for LACP bundles";
      container persist {
        presence "Indicates a persist node is configured.";
        description
          "Persist mac-address for the bundles";
      }
    }
  }
}
