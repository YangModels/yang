module Cisco-IOS-XR-um-conflict-policy-cfg {
  namespace "http://cisco.com/ns/yang/Cisco-IOS-XR-um-conflict-policy-cfg";
  prefix um-conflict-policy-cfg;

  import Cisco-IOS-XR-types {
    prefix xr;
  }
  import Cisco-IOS-XR-um-vrf-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR conflict-policy package configuration.
     
     This YANG module augments the
     modules with configuration data.
     
     Copyright (c) 2020-2021 by Cisco Systems, Inc.
     All rights reserved.";

  revision 2021-05-04 {
    description
      "Removed presence statement under conflict-policy";
    semver:module-version "1.1.0";
  }
  revision 2020-04-20 {
    description
      "Initial release";
    semver:module-version "1.0.0";
  }

  grouping VRF-BODY {
    container mhost {
      description
        "Multicast host stack options";
      container ipv4 {
        description
          "IPv4 specific";
        leaf default-interface {
          type xr:Interface-name;
          description
            "default multicast interface";
        }
      }
      container ipv6 {
        description
          "IPv6 specific";
        leaf default-interface {
          type xr:Interface-name;
          description
            "default multicast interface";
        }
      }
    }
  }

  augment "/a1:vrfs/a1:vrf" {
    uses VRF-BODY;
  }
  container ipv4 {
    description
      "Global IPv4 configuration commands";
    container conflict-policy {
      description
        "ipv4 address conflict algorithm selection";
      container static {
        must "not(../longest-prefix or ../highest-ip)";
        presence "Indicates a static node is configured.";
        description
          "Keeps the existing interface UP across new address configs";
      }
      container longest-prefix {
        must "not(../static or ../highest-ip)";
        presence "Indicates a longest-prefix node is configured.";
        description
          "Keeps the longest prefix match in the conflict set UP";
      }
      container highest-ip {
        must "not(../static or ../longest-prefix)";
        presence "Indicates a highest-ip node is configured.";
        description
          "Keeps the highest ip address in the conflict set UP";
      }
    }
  }
  container ipv6 {
    description
      "Global IPv6 configuration commands";
    container conflict-policy {
      description
        "ipv6 address conflict policy selection";
      container static {
        must "not(../longest-prefix or ../highest-ip)";
        presence "Indicates a static node is configured.";
        description
          "Keeps the existing interface UP across new address configs";
      }
      container longest-prefix {
        must "not(../static or ../highest-ip)";
        presence "Indicates a longest-prefix node is configured.";
        description
          "Keeps the longest prefix match in the conflict set UP";
      }
      container highest-ip {
        must "not(../static or ../longest-prefix)";
        presence "Indicates a highest-ip node is configured.";
        description
          "Keeps the highest ip address in the conflict set UP";
      }
    }
  }
  container mhost {
    description
      "Multicast host stack options";
    container ipv4 {
      description
        "IPv4 specific";
      leaf default-interface {
        type xr:Interface-name;
        description
          "default multicast interface";
      }
    }
    container ipv6 {
      description
        "IPv6 specific";
      leaf default-interface {
        type xr:Interface-name;
        description
          "default multicast interface";
      }
    }
  }
}
