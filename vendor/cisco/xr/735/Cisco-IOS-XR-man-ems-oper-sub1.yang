submodule Cisco-IOS-XR-man-ems-oper-sub1 {
  belongs-to Cisco-IOS-XR-man-ems-oper {
    prefix Cisco-IOS-XR-man-ems-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR man-ems package operational data.
     
     Copyright (c) 2013-2022 by Cisco Systems, Inc.
     All rights reserved.";

  revision 2022-07-07 {
    description
      "Added support for TTL flag
       2021-09-13
         Added status string to reflect unavailable port state.
       2021-06-18
         Added support for local-connection
       2021-06-10
         Added gRPC tunnel.";
    semver:module-version "1.2.0";
  }
  revision 2020-03-19 {
    description
      "Added grpc server status.";
    semver:module-version "1.1.0";
  }
  revision 2019-04-05 {
    description
      "Establish semantic version baseline.";
    semver:module-version "1.0.1";
  }
  revision 2019-02-22 {
    description
      "Fixed yang evaluator warnings.";
  }
  revision 2015-11-09 {
    description
      "IOS XR 6.0 revision.";
  }

  typedef Grpc-tls-cipher-default {
    type enumeration {
      enum "none" {
        value 0;
        description
          "Not configured";
      }
      enum "disable" {
        value 1;
        description
          "Disable all ciphers";
      }
      enum "enable" {
        value 2;
        description
          "Enable all ciphers";
      }
    }
    description
      "Grpc tls cipher default";
  }

  typedef Certauth-state {
    type enumeration {
      enum "disabled" {
        value 0;
        description
          "Certificate authentication is disabled";
      }
      enum "enabled" {
        value 1;
        description
          "Certificate authentication is enabled";
      }
    }
    description
      "Certauth state";
  }

  typedef Tls-mutual-state {
    type enumeration {
      enum "disabled" {
        value 0;
        description
          "TLS mutual is disabled";
      }
      enum "enabled" {
        value 1;
        description
          "TLS mutual is enabled";
      }
    }
    description
      "Tls mutual state";
  }

  typedef Tls-state {
    type enumeration {
      enum "disabled" {
        value 0;
        description
          "TLS is disabled";
      }
      enum "enabled" {
        value 1;
        description
          "TLS is enabled";
      }
    }
    description
      "Tls state";
  }

  typedef Af {
    type enumeration {
      enum "ipv4" {
        value 0;
        description
          "IPv4";
      }
      enum "ipv6" {
        value 1;
        description
          "IPv6";
      }
      enum "dual" {
        value 2;
        description
          "Dual";
      }
    }
    description
      "Af";
  }

  grouping GRPC-STATISTICS-INFO-B {
    description
      "gRPC statistics";
    leaf ct-show-cmd-txt-req-recv {
      type uint64;
      description
        "CounterShowCmdTxtReqRecv";
    }
    leaf ct-show-cmd-txt-res-sent {
      type uint64;
      description
        "CounterShowCmdTxtResSent";
    }
    leaf ct-get-config-req-recv {
      type uint64;
      description
        "CounterGetConfigReqRecv";
    }
    leaf ct-get-config-res-sent {
      type uint64;
      description
        "CounterGetConfigResSent";
    }
    leaf ct-cli-config-req-recv {
      type uint64;
      description
        "CounterCliConfigReqRecv";
    }
    leaf ct-cli-config-res-sent {
      type uint64;
      description
        "CounterCliConfigResSent";
    }
    leaf ct-merge-config-req-recv {
      type uint64;
      description
        "CounterMergeConfigReq";
    }
    leaf ct-merge-config-res-sent {
      type uint64;
      description
        "CounterMergeConfigRes";
    }
    leaf ct-commit-replace-req-recv {
      type uint64;
      description
        "CounterCommitReplaceReq";
    }
    leaf ct-commit-replace-res-sent {
      type uint64;
      description
        "CounterCommitReplaceRes";
    }
    leaf ct-delete-config-req-recv {
      type uint64;
      description
        "CounterDeleteConfigReq";
    }
    leaf ct-delete-config-res-sent {
      type uint64;
      description
        "CounterDeleteConfigRes";
    }
    leaf ct-remove-config-req-recv {
      type uint64;
      description
        "CounterRemoveConfigReq";
    }
    leaf ct-remove-config-res-sent {
      type uint64;
      description
        "CounterRemoveConfigRes";
    }
    leaf ct-replace-config-req-recv {
      type uint64;
      description
        "CounterReplaceConfigReq";
    }
    leaf ct-replace-config-res-sent {
      type uint64;
      description
        "CounterReplaceConfigSent";
    }
    leaf ct-get-oper-req-recv {
      type uint64;
      description
        "CounterGetOperReqRecv";
    }
    leaf ct-get-oper-res-sent {
      type uint64;
      description
        "CounterGetOperResSent";
    }
    leaf ct-get-current-session {
      type uint32;
      description
        "CounterGetCurrentSession";
    }
    leaf ct-commit-config-req-recv {
      type uint64;
      description
        "CounterForHowManyCommitConfigRequests";
    }
    leaf ct-commit-config-res-sent {
      type uint64;
      description
        "CounterForHowManyCommitConfigResponses";
    }
    leaf ct-action-json-req-recv {
      type uint64;
      description
        "CounterForHowManyActionJsonRequests";
    }
    leaf ct-action-json-res-sent {
      type uint64;
      description
        "CounterForHowManyActionJsonResponses";
    }
  }

  grouping GRPC-STATUS-INFO-B {
    description
      "gRPC status";
    leaf transport {
      type string;
      description
        "GRPCTransport";
    }
    leaf address-family {
      type string;
      description
        "Address family : ipv4 or ipv6";
    }
    leaf tls {
      type string;
      description
        "GRPCTLS";
    }
    leaf trustpoint {
      type string;
      description
        "GRPCTrustpoint";
    }
    leaf listening-port {
      type int32;
      description
        "GRPCListeningPort";
    }
    leaf vrf-socket-ns-path {
      type string;
      description
        "VrfSocketNamespacePath";
    }
    leaf max-req-per-user {
      type uint32;
      description
        "MaxReqPerUser";
    }
    leaf max-req-total {
      type uint32;
      description
        "MaxReqTotal";
    }
    leaf max-streams {
      type uint32;
      description
        "Maximum number of streaming gRPCs";
    }
    leaf max-streams-per-user {
      type uint32;
      description
        "Maximum number of streaming gRPCs per user";
    }
    leaf min-client-ka-intvl {
      type uint32;
      description
        "Minimum client keep alive interval";
    }
    leaf local-connection {
      type string;
      description
        "gRPC Server Unix socket";
    }
  }

  grouping GRPC-STATE {
    description
      "gRPC state";
    leaf address-family {
      type Af;
      description
        "gRPC address family";
    }
    leaf port {
      type uint32;
      description
        "gRPC port";
    }
    leaf vrf {
      type string;
      description
        "gRPC VRF";
    }
    leaf tls {
      type Tls-state;
      description
        "gRPC TLS state";
    }
    leaf tls-mutual {
      type Tls-mutual-state;
      description
        "gRPC TLS mutual";
    }
    leaf trustpoint {
      type string;
      description
        "gRPC trustpoint";
    }
    leaf cert-auth {
      type Certauth-state;
      description
        "gRPC Certificate Authentication";
    }
    leaf max-requests {
      type uint32;
      description
        "Maximum number of requests";
    }
    leaf max-requests-per-user {
      type uint32;
      description
        "Maximum number of requests per user";
    }
    leaf max-streams {
      type uint32;
      description
        "Maximum number of streaming gRPCs";
    }
    leaf max-streams-per-user {
      type uint32;
      description
        "Maximum number of streaming gRPCs per user";
    }
    leaf dscp {
      type uint8;
      description
        "QoS marking DSCP on transmitted gRPC";
    }
    leaf cipher-default {
      type Grpc-tls-cipher-default;
      description
        "Default of all ciphers";
    }
    leaf cipher-enable {
      type string;
      description
        "Comma separated list of enable ciphers, if
         cipher-default is disabled'";
    }
    leaf cipher-disable {
      type string;
      description
        "Comma separated list of disable ciphers, if
         cipher-default is enabled'";
    }
    leaf oper-cipher-enable {
      type string;
      description
        "Comma separated list of enable ciphers based on
         cipher default, disable, and enable";
    }
    leaf oper-cipher-disable {
      type string;
      description
        "Comma separated list of disable ciphers based on
         cipher default, disable, and enable";
    }
    leaf server {
      type uint32;
      description
        "Server SHUT state";
    }
    leaf server-disable-reason {
      type uint32;
      description
        "Server SHUT reason";
    }
    leaf ttl {
      type uint8;
      description
        "TTL settings for transmitted gRPC";
    }
  }
}
