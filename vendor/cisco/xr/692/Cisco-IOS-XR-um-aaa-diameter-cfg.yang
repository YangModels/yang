module Cisco-IOS-XR-um-aaa-diameter-cfg {
  namespace "http://cisco.com/ns/yang/Cisco-IOS-XR-um-aaa-diameter-cfg";
  prefix um-aaa-diameter-cfg;

  import Cisco-IOS-XR-types {
    prefix xr;
  }
  import ietf-inet-types {
    prefix inet;
  }
  import Cisco-IOS-XR-um-snmp-server-cfg {
    prefix a1;
  }
  import Cisco-IOS-XR-um-aaa-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-diameter package configuration.
     
     This YANG module augments the
     modules with configuration data.
     
     Copyright (c) 2021 by Cisco Systems, Inc.
     All rights reserved.";

  revision 2021-02-04 {
    description
      "Initial release";
    semver:module-version "1.0.0";
  }

  augment "/a1:snmp-server/a1:traps" {
    container diameter {
      description
        "Enable SNMP diameter traps";
      container protocolerror {
        presence "Indicates a protocolerror node is configured.";
        description
          "Enable protocol error notifications";
      }
      container transientfail {
        presence "Indicates a transientfail node is configured.";
        description
          "Enable transient failure notification";
      }
      container permanentfail {
        presence "Indicates a permanentfail node is configured.";
        description
          "Enable permanent failure notification";
      }
      container peerdown {
        presence "Indicates a peerdown node is configured.";
        description
          "Enable peer connection down notification";
      }
      container peerup {
        presence "Indicates a peerup node is configured.";
        description
          "Enable peer connection up notification";
      }
    }
  }
  augment "/a2:aaa" {
    container group {
      description
        "AAA group definitions";
      container server {
        description
          "AAA Server group definition";
        container diameter {
          description
            "DIAMETER server-group definition";
          container server-groups {
            description
              "Server group name";
            list server-group {
              key "server-group-name";
              description
                "Server group name";
              leaf server-group-name {
                type xr:Cisco-ios-xr-string {
                  length "1..800" {
                    description
                      "Server group name";
                  }
                }
                description
                  "Server group name";
              }
              container servers {
                description
                  "Specify a DIAMETER server";
                list server {
                  key "server-name";
                  description
                    "Specify a DIAMETER server";
                  leaf server-name {
                    type xr:Cisco-ios-xr-string {
                      length "1..800" {
                        description
                          "Hostname of DIAMETER server";
                      }
                    }
                    description
                      "Specify a DIAMETER server";
                  }
                }
              }
            }
          }
        }
      }
    }
    container diameter {
      description
        "DIAMETER server definition";
      container peers {
        description
          "Peer configuration";
        list peer {
          key "peer-name";
          description
            "Name for the diameter peer configuration";
          leaf peer-name {
            type string {
              length "1..800" {
                description
                  "Name for the diameter peer configuration";
              }
            }
            description
              "Name for the diameter peer configuration";
          }
          container address {
            description
              "Specify a Diameter peer address";
            leaf ipv4 {
              type inet:ipv4-address-no-zone;
              description
                "IPv4 Address";
            }
            leaf ipv6 {
              type inet:ipv6-address-no-zone;
              description
                "IPv6 Address";
            }
          }
          container destination {
            description
              "Peer information";
            leaf host {
              type xr:Cisco-ios-xr-string {
                length "1..256" {
                  description
                    "Host name in FQDN format";
                }
              }
              description
                "host information";
            }
            leaf realm {
              type xr:Cisco-ios-xr-string {
                length "1..256" {
                  description
                    "Realm to which the peer belongs to";
                }
              }
              description
                "realm information";
            }
          }
          container ip {
            description
              "IP specific commands";
            container vrf {
              description
                "VRF the peer belongs to";
              leaf forwarding {
                type xr:Cisco-ios-xr-string {
                  length "1..800" {
                    description
                      "VRF Table name";
                  }
                }
                description
                  "Forwarding table";
              }
            }
          }
          container timer {
            description
              "Timers used for the peer";
            leaf connection {
              type uint32 {
                range "6..1000" {
                  description
                    "Timer value in seconds";
                }
              }
              description
                "Connection retry timer";
            }
            leaf transaction {
              type uint32 {
                range "6..1000" {
                  description
                    "Timer value in seconds";
                }
              }
              description
                "Transaction timer";
            }
            leaf watchdog {
              type uint32 {
                range "6..1000" {
                  description
                    "Timer value in seconds";
                }
              }
              description
                "Watchdog timer";
            }
          }
          container transport {
            description
              "Specify a Diameter transport";
            container tcp {
              description
                "Specify a Diameter transport protocol";
              leaf port {
                type uint32 {
                  range "1..65535" {
                    description
                      "Port number";
                  }
                }
                description
                  "Port number on which the peer is running(default is 3868)";
              }
            }
            container security-type {
              description
                "Specify a Diameter security type";
              container tls {
                presence "Indicates a tls node is configured.";
                description
                  "Use tls for Diameter transport";
              }
            }
          }
          leaf source-interface {
            type xr:Interface-name;
            description
              "Specify interface for source address in DIAMETER packets";
          }
          container peer-type {
            description
              "Peer Type";
            container server {
              presence "Indicates a server node is configured.";
              description
                "Peer is a server";
            }
          }
          container preferred-server {
            presence "Indicates a preferred-server node is configured.";
            description
              "Enable Preferred server for the peer";
          }
          container origin {
            description
              "origin sub command";
            container realms {
              description
                "origin realm information";
              list realm {
                key "realm-name";
                description
                  "origin realm information";
                leaf realm-name {
                  type xr:Cisco-ios-xr-string {
                    length "1..256" {
                      description
                        "Origin realm string";
                    }
                  }
                  description
                    "origin realm information";
                }
                container access-interfaces {
                  description
                    "Specify a access interface ";
                  list access-interface {
                    key "access-interface-name";
                    description
                      "Specify a access interface ";
                    leaf access-interface-name {
                      type xr:Interface-name;
                      description
                        "Specify a access interface ";
                    }
                  }
                }
              }
            }
          }
          container auth-session-stateless {
            presence "Indicates a auth-session-stateless node is configured.";
            description
              "Maintain NASREQ session stateless";
          }
        }
      }
      container origin {
        description
          "Origin sub commands";
        leaf host {
          type xr:Cisco-ios-xr-string {
            length "1..256" {
              description
                "Host name in FQDN format";
            }
          }
          description
            "host information";
        }
        leaf realm {
          type xr:Cisco-ios-xr-string {
            length "1..256" {
              description
                "Origin realm string";
            }
          }
          description
            "Realm information ";
        }
      }
      container timer {
        description
          "Timers used for the peer";
        leaf connection {
          type uint32 {
            range "6..1000" {
              description
                "Timer value in seconds";
            }
          }
          description
            "Connection retry timer";
        }
        leaf transaction {
          type uint32 {
            range "6..1000" {
              description
                "Timer value in seconds";
            }
          }
          description
            "Transaction timer";
        }
        leaf watchdog {
          type uint32 {
            range "6..1000" {
              description
                "Timer value in seconds";
            }
          }
          description
            "Watchdog timer";
        }
      }
      container service {
        description
          "Peer configuration";
        list peer {
          key "peer-name";
          description
            "Name for the diameter peer configuration";
          leaf peer-name {
            type string {
              length "1..800" {
                description
                  "Name for the diameter peer configuration";
              }
            }
            description
              "Name for the diameter peer configuration";
          }
          leaf monitoring-key {
            type xr:Cisco-ios-xr-string {
              length "1..800" {
                description
                  "Name for the diameter peer configuration";
              }
            }
            description
              "Peer configuration";
          }
        }
      }
      leaf source-interface {
        type xr:Interface-name;
        description
          "Specify interface for source address in DIAMETER packets";
      }
      container vendor {
        description
          "Vendor specific";
        container supported {
          description
            "Supported vendors";
          container threegpp {
            presence "Indicates a threegpp node is configured.";
            description
              "3GPP attribute support";
          }
          container cisco {
            presence "Indicates a cisco node is configured.";
            description
              "Cisco attribute support";
          }
          container vodafone {
            presence "Indicates a vodafone node is configured.";
            description
              "Vodafone attribute support";
          }
          container etsi {
            presence "Indicates a etsi node is configured.";
            description
              "Etsi attribute support";
          }
        }
      }
      container tls {
        description
          "TLS sub commands";
        leaf trustpoint {
          type xr:Cisco-ios-xr-string {
            length "1..800" {
              description
                "trustpoint label to be used";
            }
          }
          description
            "trustpoint information";
        }
      }
      container subscription-id {
        description
          "Subscription-Id AVP, to identify the end user's subscription";
        leaf type {
          type uint32 {
            range "0..4" {
              description
                "[END_USER_E164(0), END_USER_IMSI(1), END_USER_SIP_URI(2), END_USER_NAI(3), END_USER_PRIVATE(4)]";
            }
          }
          description
            "Type of indentifier carried by subscription-Id AVP";
        }
      }
      container gx {
        description
          "Start diameter policy-if";
        container enable {
          presence "Indicates an enable node is configured.";
        }
        leaf tx-timer {
          type uint32 {
            range "6..1000" {
              description
                "Timer value in seconds";
            }
          }
          description
            "Set transaction timer";
        }
        leaf retransmit {
          type uint32 {
            range "1..10" {
              description
                "Timer value in seconds";
            }
          }
          description
            "Set retransmit count";
        }
        leaf dest-host {
          type xr:Cisco-ios-xr-string {
            length "1..256" {
              description
                "Destination Host name in FQDN format";
            }
          }
          description
            "Set retransmit count";
        }
      }
      container gy {
        description
          "Start diameter prepaid service";
        container enable {
          presence "Indicates an enable node is configured.";
        }
        leaf tx-timer {
          type uint32 {
            range "6..1000" {
              description
                "Timer value in seconds";
            }
          }
          description
            "Set transaction timer";
        }
        leaf retransmit {
          type uint32 {
            range "1..10" {
              description
                "Timer value in seconds";
            }
          }
          description
            "Set retransmit count";
        }
        leaf dest-host {
          type xr:Cisco-ios-xr-string {
            length "1..256" {
              description
                "Destination Host name in FQDN format";
            }
          }
          description
            "Set destination host";
        }
        leaf service-context-id {
          type xr:Cisco-ios-xr-string {
            length "1..256" {
              description
                "Service Context ID ";
            }
          }
          description
            "Set service context id";
        }
      }
      container nas {
        description
          "Start diameter Nas";
        container enable {
          presence "Indicates an enable node is configured.";
        }
        leaf dest-host {
          type xr:Cisco-ios-xr-string {
            length "1..256" {
              description
                "Destination Host name in FQDN format";
            }
          }
          description
            "Set destination host for NAS";
        }
      }
      container quota-high-usage {
        description
          "To disable quota high usage disconnect (applicable only for GX_PLUS)";
        container disconnect-disable {
          presence "Indicates a disconnect-disable node is configured.";
          description
            "To disable quota high usage disconnect (applicable only for GX_PLUS)";
        }
      }
      container attribute {
        description
          "Attribute list configuration for test command";
        container lists {
          description
            "attribute list configuration";
          list list {
            key "attribute-list-number";
            description
              "attribute list number";
            leaf attribute-list-number {
              type uint32 {
                range "0..99" {
                  description
                    "attribute list number";
                }
              }
              description
                "attribute list number";
            }
            container attribute {
              description
                "Specify an attribute definition";
              container attribute-lists {
                list attribute-list {
                  key "attribute-id";
                  leaf attribute-id {
                    type uint32 {
                      range "1..65535" {
                        description
                          "Attribute id";
                      }
                    }
                    description
                      "Attribute id";
                  }
                  leaf address {
                    type inet:ipv4-address-no-zone;
                    description
                      "Address format";
                  }
                  leaf binary {
                    type xr:Cisco-ios-xr-string {
                      length "1..1024" {
                        description
                          "value in hex format";
                      }
                    }
                    description
                      "Binary type";
                  }
                  leaf boolean {
                    type uint32 {
                      range "0..4294967295" {
                        description
                          "attribute value number";
                      }
                    }
                    description
                      "Boolean type";
                  }
                  leaf diameter-identity {
                    type xr:Cisco-ios-xr-string {
                      length "1..1024" {
                        description
                          "value in string format";
                      }
                    }
                    description
                      "diameter identity";
                  }
                  leaf enum {
                    type uint32 {
                      range "0..4294967295" {
                        description
                          "attribute value number";
                      }
                    }
                    description
                      "Enumeration type";
                  }
                  leaf grouped {
                    type uint32 {
                      range "0..99" {
                        description
                          "the attr list id for sub-attrs";
                      }
                    }
                    description
                      "Grouped attribute";
                  }
                  leaf string {
                    type xr:Cisco-ios-xr-string {
                      length "1..1024" {
                        description
                          "value in string format";
                      }
                    }
                    description
                      "String type";
                  }
                  leaf ulong {
                    type uint32 {
                      range "0..4294967295" {
                        description
                          "attribute value number";
                      }
                    }
                    description
                      "Numeric type";
                  }
                  leaf ulonglong {
                    type uint32 {
                      range "0..4294967295" {
                        description
                          "attribute value number";
                      }
                    }
                    description
                      "Numeric type";
                  }
                  leaf utc {
                    type uint32 {
                      range "0..4294967295" {
                        description
                          "value in utc format";
                      }
                    }
                    description
                      "Numeric type";
                  }
                  container mandatory {
                    presence "Indicates a mandatory node is configured.";
                    description
                      "specify if the attribute is mandatory";
                  }
                }
              }
              container vendor-id-attribute-lists {
                list vendor-id-attribute-list {
                  key "attribute-id vendor-id";
                  leaf attribute-id {
                    type uint32 {
                      range "1..65535" {
                        description
                          "Attribute id";
                      }
                    }
                    description
                      "Attribute id";
                  }
                  leaf vendor-id {
                    type uint32 {
                      range "0..4294967295" {
                        description
                          "value for vendor id";
                      }
                    }
                    description
                      "vendor id";
                  }
                  leaf address {
                    type inet:ipv4-address-no-zone;
                    description
                      "Address format";
                  }
                  leaf binary {
                    type xr:Cisco-ios-xr-string {
                      length "1..1024" {
                        description
                          "value in hex format";
                      }
                    }
                    description
                      "Binary type";
                  }
                  leaf boolean {
                    type uint32 {
                      range "0..4294967295" {
                        description
                          "attribute value number";
                      }
                    }
                    description
                      "Boolean type";
                  }
                  leaf diameter-identity {
                    type xr:Cisco-ios-xr-string {
                      length "1..1024" {
                        description
                          "value in string format";
                      }
                    }
                    description
                      "diameter identity";
                  }
                  leaf enum {
                    type uint32 {
                      range "0..4294967295" {
                        description
                          "attribute value number";
                      }
                    }
                    description
                      "Enumeration type";
                  }
                  leaf grouped {
                    type uint32 {
                      range "0..99" {
                        description
                          "the attr list id for sub-attrs";
                      }
                    }
                    description
                      "Grouped attribute";
                  }
                  leaf string {
                    type xr:Cisco-ios-xr-string {
                      length "1..1024" {
                        description
                          "value in string format";
                      }
                    }
                    description
                      "String type";
                  }
                  leaf ulong {
                    type uint32 {
                      range "0..4294967295" {
                        description
                          "attribute value number";
                      }
                    }
                    description
                      "Numeric type";
                  }
                  leaf ulonglong {
                    type uint32 {
                      range "0..4294967295" {
                        description
                          "attribute value number";
                      }
                    }
                    description
                      "Numeric type";
                  }
                  leaf utc {
                    type uint32 {
                      range "0..4294967295" {
                        description
                          "value in utc format";
                      }
                    }
                    description
                      "Numeric type";
                  }
                  container mandatory {
                    presence "Indicates a mandatory node is configured.";
                    description
                      "specify if the attribute is mandatory";
                  }
                }
              }
            }
          }
        }
      }
    }
  }
}
