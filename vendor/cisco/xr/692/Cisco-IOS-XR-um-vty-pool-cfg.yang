module Cisco-IOS-XR-um-vty-pool-cfg {
  namespace "http://cisco.com/ns/yang/Cisco-IOS-XR-um-vty-pool-cfg";
  prefix um-vty-pool-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR vty-pool package configuration.
     
     This YANG module augments the
     modules with configuration data.
     
     Copyright (c) 2020 by Cisco Systems, Inc.
     All rights reserved.";

  revision 2020-12-15 {
    description
      "Initial release";
    semver:module-version "1.0.0";
  }

  container vty-pool {
    description
      "VTY Pools";
    container default {
      presence "Indicates a default node is configured.";
      description
        "Default VTY Pool.";
      leaf first-vty-number {
        type uint32 {
          range "0" {
            description
              "First VTY number";
          }
        }
        mandatory true;
        description
          "Default VTY Pool.";
      }
      leaf last-vty-number {
        type uint32 {
          range "4..99" {
            description
              "Last VTY number";
          }
        }
        mandatory true;
        description
          "Last VTY number";
      }
      leaf line-template {
        type xr:Cisco-ios-xr-string {
          length "1..800" {
            description
              "Name of line template";
          }
        }
        description
          "Name of line template";
      }
    }
    container eem {
      presence "Indicates a eem node is configured.";
      description
        "Event Manager VTY Pool.";
      leaf first-vty-number {
        type uint32 {
          range "100" {
            description
              "First VTY number";
          }
        }
        mandatory true;
        description
          "eem VTY Pool.";
      }
      leaf last-vty-number {
        type uint32 {
          range "105" {
            description
              "Last VTY number";
          }
        }
        mandatory true;
        description
          "Last VTY number";
      }
      leaf line-template {
        type xr:Cisco-ios-xr-string {
          length "1..800" {
            description
              "Name of line template";
          }
        }
        description
          "Name of line template";
      }
    }
    container pools {
      description
        "User defined VTY Pool";
      list pool {
        key "pool-name";
        description
          "First VTY number";
        leaf pool-name {
          type xr:Cisco-ios-xr-string {
            length "1..1024" {
              description
                "Name of user defined VTY Pool";
            }
          }
          description
            "Name of user defined VTY Pool";
        }
        leaf first-vty-number {
          type uint32 {
            range "5..99" {
              description
                "First VTY number";
            }
          }
          mandatory true;
          description
            "First VTY number";
        }
        leaf last-vty-number {
          type uint32 {
            range "5..99" {
              description
                "Last VTY number";
            }
          }
          mandatory true;
          description
            "Last VTY number";
        }
        leaf line-template {
          type xr:Cisco-ios-xr-string {
            length "1..800" {
              description
                "Name of line template";
            }
          }
          description
            "Name of line template";
        }
      }
    }
  }
}
