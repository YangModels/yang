module Cisco-IOS-XR-asr9k-lc-ep-breakout-port-cfg {
  namespace "http://cisco.com/ns/yang/Cisco-IOS-XR-asr9k-lc-ep-breakout-port-cfg";
  prefix asr9k-lc-ep-breakout-port-cfg;

  import cisco-semver {
    prefix semver;
  }
  import Cisco-IOS-XR-config-mda-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-lc-ep-breakout-port package configuration.
     
     This YANG module augments the
       Cisco-IOS-XR-config-mda-cfg
     module with configuration data.
     
     Copyright (c) 2013-2020 by Cisco Systems, Inc.
     All rights reserved.";

  revision 2020-08-25 {
    description
      "Added support for EP breakout bay port config through yang model.";
    semver:module-version "1.0.0";
  }
  revision 2019-04-05 {
    description
      "Establish semantic version baseline.";
  }
  revision 2015-11-09 {
    description
      "IOS XR 6.0 revision.";
  }

  typedef Hw-module-ep-breakout-if {
    type enumeration {
      enum "1x-hundred-gig-e" {
        value 0;
        description
          "HundredGigE interfaces";
      }
      enum "10x-ten-gig-e" {
        value 1;
        description
          "TenGigE interfaces";
      }
      enum "2x-forty-gig-e" {
        value 2;
        description
          "FortyGigE interfaces";
      }
      enum "1x-forty-gig-e" {
        value 3;
        description
          "FortyGigE interfaces";
      }
      enum "4x-ten-gig-e" {
        value 4;
        description
          "TenGigE interfaces";
      }
      enum "4x-twenty-five-gig-e" {
        value 5;
        description
          "TwentyFiveGigE interfaces";
      }
      enum "1x-four-hundred-gig-e" {
        value 6;
        description
          "FourHundredGigE interfaces";
      }
      enum "8x-fifty-gig-e" {
        value 7;
        description
          "FiftyGigE interfaces";
      }
    }
    description
      "Hw module ep breakout if";
  }

  grouping HW-MODULE-EP-BREAKOUT {
    description
      "Common node of active-node, preconfigured-node";
    container hw-module-ep-breakout {
      description
        "HW module EP breakout config";
      container bays {
        description
          "configuration for EP bay number";
        list bay {
          key "bay-number";
          description
            "EP Bay number";
          container ports {
            description
              "Optics port configuration";
            list port {
              key "port-number";
              description
                "Optics port number";
              leaf iftype {
                type Hw-module-ep-breakout-if;
                description
                  "EP Breakout iftype";
              }
              leaf port-number {
                type uint32 {
                  range "0..19";
                }
                description
                  "Optics port number";
              }
            }
          }
          leaf bay-number {
            type uint32 {
              range "0..1";
            }
            description
              "bay number";
          }
        }
      }
    }
  }

  augment "/a1:preconfigured-nodes/a1:preconfigured-node" {
    description
      "This augment extends the configuration data of
       'Cisco-IOS-XR-config-mda-cfg'";
    uses HW-MODULE-EP-BREAKOUT;
  }
  augment "/a1:active-nodes/a1:active-node" {
    description
      "This augment extends the configuration data of
       'Cisco-IOS-XR-config-mda-cfg'";
    uses HW-MODULE-EP-BREAKOUT;
  }
}
