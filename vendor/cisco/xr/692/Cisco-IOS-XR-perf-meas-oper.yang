module Cisco-IOS-XR-perf-meas-oper {
  namespace "http://cisco.com/ns/yang/Cisco-IOS-XR-perf-meas-oper";
  prefix perf-meas-oper;

  import Cisco-IOS-XR-types {
    prefix xr;
  }
  import cisco-semver {
    prefix semver;
  }
  include Cisco-IOS-XR-perf-meas-oper-sub2 {
    revision-date 2021-11-18;
  }
  include Cisco-IOS-XR-perf-meas-oper-sub1 {
    revision-date 2021-11-18;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR perf-meas package operational data.
     
     This module contains definitions
     for the following management objects:
       performance-measurement: Performance Measurement operational
         data
       performance-measurement-responder: Performance Measurement
         operational data
     
     Copyright (c) 2013-2021 by Cisco Systems, Inc.
     All rights reserved.";

  revision 2021-11-18 {
    description
      "Added transport specific parameters to profile information.
       2021-10-27
         Added tx-interval to profile information.";
    semver:module-version "5.0.0";
  }
  revision 2021-06-02 {
    description
      "Added session id to endpoint liveness bag.
       2021-04-17
       Removed liveness parameters from delay profile bag.
       2021-02-26
       Remove PM hidden show cli, loss, history packet.
       2021-02-16
       Remove liveness history and liveness detection verbose from sr-policy delay schema.
       2021-01-08
       Added srpolicy liveness schema.
       2021-01-08
       Added srpolicy liveness history schema and renamed liveness detection schema.
       2020-12-19
       Added schema for endpoint liveness profile.
       2020-12-02
       Add sr-policy liveness profile bag and oper schema.
       2020-11-26
       Update endpoint show command bags in order to support liveness-detection.
       2020-11-17
       Added new bag for PPS info. IosSetYangSchemaRev Cisco-IOS-XR-perf-meas-oper
       2020-10-27
       Added anomaly support for sr-policy min delay metrics.
       2020-10-27
       Added all endpoint show commands support and respective bags.
       2020-10-15
       Update probe running reason name for link down.
       2020-10-02
       Added anomaly support for interface min delay metrics.
       2020-08-06
       Added liveness session state history information.
       2020-07-23
       Fixed typos in perf-meas oper bag.";
    semver:module-version "4.0.0";
  }
  revision 2020-06-24 {
    description
      "Update perf-meas oper schema task group.
       2020-04-10
       Added new TX error counter for next hop MAC missing.
       2020-03-31
       721 nohelp CLI for liveness, loopback, endpoint, src-port, named profile, distribution.
       2020-03-25
       Add trace id in PM session bag.
       2020-03-17
       Added new types counters to count different types of PM DM sessions.
       2020-03-09
       Added new types of probe running errors and counters for probe running errors.
       2020-02-24
       Modifid type of service knobs from array to integer.
       2020-02-21
       Modify router alert type
       2020-02-19
       Modifiy periodic minimum change value.
       2020-02-13
       Modifiy delay-measurement hisotry key words.
       2020-01-22
       Added a new advertisement reason for interface delay-measurement.
       2019-12-16
       Revision IOS XR 7.2.1 Added responder src address and num of hops for PM DM.
       2019-12-09
       Added new reason for DM probe not running.
       2019-11-18
       Revision IOS XR 7.2.1 Added EDT for Liveness state for SR Policy Candidate path atmoic path.";
    semver:module-version "3.0.0";
  }
  revision 2019-10-19 {
    description
      "Added burst-interval-effective to oper data.";
    semver:module-version "2.0.0";
  }
  revision 2019-04-05 {
    description
      "Establish semantic version baseline.";
    semver:module-version "1.0.0";
  }
  revision 2018-12-13 {
    description
      "Revision IOS XR 7.0.1 Added delay measurment for SR Policy and RSVP-TE LSP.";
  }
  revision 2017-10-17 {
    description
      "Revision Zero.";
  }
  revision 2015-11-09 {
    description
      "IOS XR 6.0 revision.";
  }

  container performance-measurement {
    config false;
    description
      "Performance Measurement operational data";
    container nodes {
      description
        "Node table for node-specific operational data";
      list node {
        key "node";
        description
          "Node-specific data for a particular node";
        container sr-policies {
          description
            "SR Policies";
          container sr-policy-details {
            description
              "Table of SR Policies detail info";
            list sr-policy-detail {
              key "policy-name";
              description
                "SR Policy information";
              leaf policy-name {
                type xr:Cisco-ios-xr-string;
                description
                  "Policy name";
              }
              uses PM-SRPOLICY-BAG;
            }
          }
          container sr-policy-delay {
            description
              "SR Policy Delay-measurement information";
            container sr-policy-last-advertisements {
              description
                "Table of last advertisement metrics";
              list sr-policy-last-advertisement {
                key "sr-policy-name";
                description
                  "Last advertisement metrics information";
                leaf sr-policy-name {
                  type xr:Cisco-ios-xr-string;
                  description
                    "SR Policy name";
                }
                uses PM-SRPOLICY-METRICS-BAG;
              }
            }
            container sr-policy-probe-computation-histories {
              description
                "Table of probe computation history";
              list sr-policy-probe-computation-history {
                key "sr-policy-name";
                description
                  "Probe computation history information";
                leaf sr-policy-name {
                  type xr:Cisco-ios-xr-string;
                  description
                    "SR Policy name";
                }
                uses PM-SRPOLICY-HISTORY-BAG;
              }
            }
            container sr-policy-advertisement-histories {
              description
                "Table of advertisement history";
              list sr-policy-advertisement-history {
                key "sr-policy-name";
                description
                  "Advertisement history information";
                leaf sr-policy-name {
                  type xr:Cisco-ios-xr-string;
                  description
                    "SR Policy name";
                }
                uses PM-SRPOLICY-HISTORY-BAG;
              }
            }
            container sr-policy-last-probe-verboses {
              description
                "Table of last probe metrics verbose";
              list sr-policy-last-probe-verbose {
                key "sr-policy-name";
                description
                  "Last probe verbose information";
                leaf sr-policy-name {
                  type xr:Cisco-ios-xr-string;
                  description
                    "SR Policy name";
                }
                uses PM-SRPOLICY-METRICS-BAG;
              }
            }
            container sr-policy-last-advertisement-verboses {
              description
                "Table of last advertisement verbose
                 information";
              list sr-policy-last-advertisement-verbose {
                key "sr-policy-name";
                description
                  "Last advertisement verbose metrics
                   information";
                leaf sr-policy-name {
                  type xr:Cisco-ios-xr-string;
                  description
                    "SR Policy name";
                }
                uses PM-SRPOLICY-METRICS-BAG;
              }
            }
            container sr-policy-last-probes {
              description
                "Table of last probe metrics";
              list sr-policy-last-probe {
                key "sr-policy-name";
                description
                  "Last probe information";
                leaf sr-policy-name {
                  type xr:Cisco-ios-xr-string;
                  description
                    "SR Policy name";
                }
                uses PM-SRPOLICY-METRICS-BAG;
              }
            }
            container sr-policy-last-aggregation-verboses {
              description
                "Table of last probe aggregation verbose";
              list sr-policy-last-aggregation-verbose {
                key "sr-policy-name";
                description
                  "Last probe aggregation verbose information";
                leaf sr-policy-name {
                  type xr:Cisco-ios-xr-string;
                  description
                    "SR Policy name";
                }
                uses PM-SRPOLICY-METRICS-BAG;
              }
            }
            container sr-policy-aggregation-histories {
              description
                "Table of aggregation history";
              list sr-policy-aggregation-history {
                key "sr-policy-name";
                description
                  "Aggregation history information";
                leaf sr-policy-name {
                  type xr:Cisco-ios-xr-string;
                  description
                    "SR Policy name";
                }
                uses PM-SRPOLICY-HISTORY-BAG;
              }
            }
            container sr-policy-last-aggregations {
              description
                "Table of last aggregation";
              list sr-policy-last-aggregation {
                key "sr-policy-name";
                description
                  "Last aggregation information";
                leaf sr-policy-name {
                  type xr:Cisco-ios-xr-string;
                  description
                    "SR Policy name";
                }
                uses PM-SRPOLICY-METRICS-BAG;
              }
            }
          }
          container sr-policy-liveness {
            description
              "SR Policy Liveness-Detection information";
            container pm-sr-policy-last-liveness-detection-verboses {
              description
                "Table of last liveness detection information";
              list pm-sr-policy-last-liveness-detection-verbose {
                key "sr-policy-name";
                description
                  "Last liveness verbose information";
                leaf sr-policy-name {
                  type xr:Cisco-ios-xr-string;
                  description
                    "SR Policy name";
                }
                uses PM-SRPOLICY-LIVENESS;
              }
            }
            container pm-sr-policy-liveness-session-state-histories {
              description
                "Table of liveness session state history";
              list pm-sr-policy-liveness-session-state-history {
                key "sr-policy-name";
                description
                  "Liveness session state history information";
                leaf sr-policy-name {
                  type xr:Cisco-ios-xr-string;
                  description
                    "SR Policy name";
                }
                uses PM-SRPOLICY-HISTORY-BAG;
              }
            }
          }
          container sr-policy-counters {
            description
              "Table of SR Policies counters info";
            list sr-policy-counter {
              key "policy-name";
              description
                "SR Policy counter information";
              leaf policy-name {
                type xr:Cisco-ios-xr-string;
                description
                  "Policy name";
              }
              uses PM-SRPOLICY-COUNTERS-BAG;
            }
          }
        }
        container rsvpte-tunnels {
          description
            "RSVP-TE tunnels";
          container rsvpte-counters {
            description
              "Table of RSVP-TE tunnel counters info";
            list rsvpte-counter {
              key "tunnel-name";
              description
                "RSVP-TE counter information";
              leaf tunnel-name {
                type xr:Interface-name;
                description
                  "Tunnel name";
              }
              uses PM-RSVPTE-COUNTERS-BAG;
            }
          }
          container rsvpte-details {
            description
              "Table of RSVP-TE tunnels detail info";
            list rsvpte-detail {
              key "tunnel-name";
              description
                "RSVP-TE information";
              leaf tunnel-name {
                type xr:Interface-name;
                description
                  "Tunnel name";
              }
              uses PM-RSVPTE-BAG;
            }
          }
          container rsvpte-delay {
            description
              "RSVP-TE tunnel delay-measurement information";
            container rsvpte-last-advertisements {
              description
                "Table of last advertisement metrics";
              list rsvpte-last-advertisement {
                key "tunnel-name";
                description
                  "Last advertisement metrics information";
                leaf tunnel-name {
                  type xr:Interface-name;
                  description
                    "Tunnel name";
                }
                uses PM-RSVPTE-DELAY-METRICS-BAG;
              }
            }
            container rsvpte-last-aggregations {
              description
                "Table of last probe aggregation";
              list rsvpte-last-aggregation {
                key "tunnel-name";
                description
                  "Last probe aggregation information";
                leaf tunnel-name {
                  type xr:Interface-name;
                  description
                    "SR Policy name";
                }
                uses PM-RSVPTE-DELAY-METRICS-BAG;
              }
            }
            container rsvpte-aggregation-histories {
              description
                "Table of aggregation history";
              list rsvpte-aggregation-history {
                key "tunnel-name";
                description
                  "Aggregation history information";
                leaf tunnel-name {
                  type xr:Interface-name;
                  description
                    "Tunnel name";
                }
                uses PM-RSVPTE-HISTORY-BAG;
              }
            }
            container rsvpte-last-probes {
              description
                "Table of last probe metrics";
              list rsvpte-last-probe {
                key "tunnel-name";
                description
                  "Last probe information";
                leaf tunnel-name {
                  type xr:Interface-name;
                  description
                    "Tunnel name";
                }
                uses PM-RSVPTE-DELAY-METRICS-BAG;
              }
            }
            container rsvpte-advertisement-histories {
              description
                "Table of advertisement history for the
                 RSVP-TE LSP";
              list rsvpte-advertisement-history {
                key "tunnel-name";
                description
                  "Advertisement history information for the
                   RSVP-TE LSP";
                leaf tunnel-name {
                  type xr:Interface-name;
                  description
                    "Tunnel name";
                }
                uses PM-RSVPTE-HISTORY-BAG;
              }
            }
            container rsvpte-probe-computation-histories {
              description
                "Table of probe computation history";
              list rsvpte-probe-computation-history {
                key "tunnel-name";
                description
                  "Probe computation history information";
                leaf tunnel-name {
                  type xr:Interface-name;
                  description
                    "Tunnel name";
                }
                uses PM-RSVPTE-HISTORY-BAG;
              }
            }
          }
        }
        container local-capability-info {
          description
            "Capability information for the local hardware";
          uses PM-CAPABILITY-BAG;
        }
        container endpoints {
          description
            "Endpoints";
          container endpoint-liveness {
            description
              "Endpoint Liveness-Detection information";
            container endpoint-last-liveness-detection-verboses {
              description
                "Table of last liveness detection information";
              list endpoint-last-liveness-detection-verbose {
                key "endpoint-name";
                description
                  "Last liveness verbose information";
                leaf endpoint-name {
                  type xr:Cisco-ios-xr-string;
                  description
                    "Endpoint name";
                }
                uses PM-ENDPOINT-LIVENESS;
              }
            }
          }
          container endpoint-delay {
            description
              "Endpoint Delay-measurement information";
            container endpoint-last-probe-verboses {
              description
                "Table of last probe metrics verbose";
              list endpoint-last-probe-verbose {
                key "endpoint-name";
                description
                  "Last probe verbose information";
                leaf endpoint-name {
                  type xr:Cisco-ios-xr-string;
                  description
                    "Endpoint name";
                }
                uses PM-ENDPOINT-METRICS-BAG;
              }
            }
            container endpoint-probe-computation-histories {
              description
                "Table of probe computation history";
              list endpoint-probe-computation-history {
                key "endpoint-name";
                description
                  "Probe computation history information";
                leaf endpoint-name {
                  type xr:Cisco-ios-xr-string;
                  description
                    "Endpoint name";
                }
                uses PM-ENDPOINT-HISTORY-BAG;
              }
            }
            container endpoint-last-advertisements {
              description
                "Table of last advertisement metrics";
              list endpoint-last-advertisement {
                key "endpoint-name";
                description
                  "Last advertisement metrics information";
                leaf endpoint-name {
                  type xr:Cisco-ios-xr-string;
                  description
                    "Endpoint name";
                }
                uses PM-ENDPOINT-METRICS-BAG;
              }
            }
            container endpoint-last-probes {
              description
                "Table of last probe metrics";
              list endpoint-last-probe {
                key "endpoint-name";
                description
                  "Last probe information";
                leaf endpoint-name {
                  type xr:Cisco-ios-xr-string;
                  description
                    "Endpoint name";
                }
                uses PM-ENDPOINT-METRICS-BAG;
              }
            }
            container endpoint-last-aggregations {
              description
                "Table of Endpoint last aggregation";
              list endpoint-last-aggregation {
                key "endpoint-name";
                description
                  "Last aggregation information";
                leaf endpoint-name {
                  type xr:Cisco-ios-xr-string;
                  description
                    "Endpoint name";
                }
                uses PM-ENDPOINT-METRICS-BAG;
              }
            }
            container endpoint-last-advertisement-verboses {
              description
                "Table of last advertisement verbose
                 information";
              list endpoint-last-advertisement-verbose {
                key "endpoint-name";
                description
                  "Last advertisement verbose metrics
                   information";
                leaf endpoint-name {
                  type xr:Cisco-ios-xr-string;
                  description
                    "Endpoint name";
                }
                uses PM-ENDPOINT-METRICS-BAG;
              }
            }
            container endpoint-last-aggregationverboses {
              description
                "Table of last probe aggregation verbose";
              list endpoint-last-aggregationverbose {
                key "endpoint-name";
                description
                  "Last probe aggregation verbose information";
                leaf endpoint-name {
                  type xr:Cisco-ios-xr-string;
                  description
                    "Endpoint name";
                }
                uses PM-ENDPOINT-METRICS-BAG;
              }
            }
            container endpoint-aggregation-histories {
              description
                "Table of aggregation history";
              list endpoint-aggregation-history {
                key "endpoint-name";
                description
                  "Aggregation history information";
                leaf endpoint-name {
                  type xr:Cisco-ios-xr-string;
                  description
                    "Endpoint name";
                }
                uses PM-ENDPOINT-HISTORY-BAG;
              }
            }
            container endpoint-advertisement-histories {
              description
                "Table of advertisement history";
              list endpoint-advertisement-history {
                key "endpoint-name";
                description
                  "Advertisement history information";
                leaf endpoint-name {
                  type xr:Cisco-ios-xr-string;
                  description
                    "Endpoint name";
                }
                uses PM-ENDPOINT-HISTORY-BAG;
              }
            }
          }
          container endpoint-counters {
            description
              "Table of Endpoint counters info";
            list endpoint-counter {
              key "endpoint-name";
              description
                "Endpoint counter information";
              leaf endpoint-name {
                type xr:Cisco-ios-xr-string;
                description
                  "Endpoint name";
              }
              uses PM-ENDPOINT-COUNTERS-BAG;
            }
          }
          container endpoint-commons {
            description
              "Table of Endpoint common info";
            list endpoint-common {
              key "endpoint-name";
              description
                "Endpoint information";
              leaf endpoint-name {
                type xr:Cisco-ios-xr-string;
                description
                  "Endpoint name";
              }
              uses PM-ENDPOINT-COMMON;
            }
          }
        }
        container sessions {
          description
            "Table of sessions";
          list session {
            key "session-id";
            description
              "Session information";
            leaf session-id {
              type uint32;
              description
                "Session ID";
            }
            uses PM-SESSION-BAG;
          }
        }
        container summary {
          description
            "Summary information for all the measurement
             and transportation type on querier";
          uses PM-SUMMARY-BAG;
        }
        container interfaces {
          description
            "Physical and bundle interfaces";
          container interface-details {
            description
              "Interface detailed table";
            list interface-detail {
              key "interface-name";
              description
                "Detailed interface information";
              leaf interface-name {
                type xr:Interface-name;
                description
                  "Interface name";
              }
              uses PM-INTF-BAG;
            }
          }
          container interface-delay {
            description
              "Delay-measurement information";
            container interface-probe-computation-histories {
              description
                "Table of probe computation history";
              list interface-probe-computation-history {
                key "interface-name";
                description
                  "Probe computation history information";
                leaf interface-name {
                  type xr:Interface-name;
                  description
                    "Interface name";
                }
                uses PM-INTF-HISTORY-BAG;
              }
            }
            container interface-aggregation-histories {
              description
                "Table of aggregation history";
              list interface-aggregation-history {
                key "interface-name";
                description
                  "Aggregation history information";
                leaf interface-name {
                  type xr:Interface-name;
                  description
                    "Interface name";
                }
                uses PM-INTF-HISTORY-BAG;
              }
            }
            container interface-advertisement-histories {
              description
                "Table of advertisement history information";
              list interface-advertisement-history {
                key "interface-name";
                description
                  "Advertisement history information";
                leaf interface-name {
                  type xr:Interface-name;
                  description
                    "Interface name";
                }
                uses PM-INTF-HISTORY-BAG;
              }
            }
            container interface-last-aggregations {
              description
                "Table of last aggregation";
              list interface-last-aggregation {
                key "interface-name";
                description
                  "Last aggregation information";
                leaf interface-name {
                  type xr:Interface-name;
                  description
                    "Interface name";
                }
                uses PM-INTF-LAST-AGGR-BAG;
              }
            }
            container interface-last-probes {
              description
                "Table of last probes";
              list interface-last-probe {
                key "interface-name";
                description
                  "Last measurement information";
                leaf interface-name {
                  type xr:Interface-name;
                  description
                    "Interface name";
                }
                uses PM-INTF-LAST-PROBE-BAG;
              }
            }
            container interface-last-advertisements {
              description
                "Table of last advertisements";
              list interface-last-advertisement {
                key "interface-name";
                description
                  "Last advertisement information";
                leaf interface-name {
                  type xr:Interface-name;
                  description
                    "Interface name";
                }
                uses PM-INTF-LAST-ADVERT-BAG;
              }
            }
          }
        }
        container profile {
          description
            "Profile information for all the measurement
             and transportation type on querier";
          uses PM-PROFILE-BAG;
        }
        container pps-summary {
          description
            "Summary information for PPS on querier";
          uses PM-PPS-SUMMARY-BAG;
        }
        container distribution-records {
          description
            "Table of linecard session distribution records";
          list distribution-record {
            key "record-name";
            description
              "linecard session distribution record";
            leaf record-name {
              type xr:Cisco-ios-xr-string;
              description
                "Distribution record name";
            }
            uses PM-DR-INFO;
          }
        }
        container name-profile {
          description
            "Profile Name";
          container delay-profile-rsvptes {
            description
              "RSVP-TE profile name table";
            list delay-profile-rsvpte {
              key "profile-name";
              description
                "RSVP-TE delay profile name";
              leaf profile-name {
                type xr:Cisco-ios-xr-string;
                description
                  "Profile name";
              }
              uses PM-NAME-PROFILE-BAG;
            }
          }
          container delay-profiles {
            description
              "Delay profile name table";
            list delay-profile {
              key "profile-name";
              description
                "Delay profile name";
              leaf profile-name {
                type xr:Cisco-ios-xr-string;
                description
                  "Profile name";
              }
              uses PM-NAME-PROFILE-BAG;
            }
          }
          container delay-profile-endpoints {
            description
              "Endpoint profile name table";
            list delay-profile-endpoint {
              key "profile-name";
              description
                "Endpoint delay profile name";
              leaf profile-name {
                type xr:Cisco-ios-xr-string;
                description
                  "Profile name";
              }
              uses PM-NAME-PROFILE-BAG;
            }
          }
          container liveness-profile-endpoints {
            description
              "Endpoint liveness profile name table";
            list liveness-profile-endpoint {
              key "profile-name";
              description
                "Endpoint liveness profile name";
              leaf profile-name {
                type xr:Cisco-ios-xr-string;
                description
                  "Profile name";
              }
              uses PM-NAME-PROFILE-BAG;
            }
          }
          container liveness-profiles {
            description
              "Liveness profile name table";
            list liveness-profile {
              key "profile-name";
              description
                "Liveness profile name";
              leaf profile-name {
                type xr:Cisco-ios-xr-string;
                description
                  "Profile name";
              }
              uses PM-NAME-PROFILE-BAG;
            }
          }
          container delay-profile-sr-policies {
            description
              "SR Policy profile name table";
            list delay-profile-sr-policy {
              key "profile-name";
              description
                "SR Policy delay profile name";
              leaf profile-name {
                type xr:Cisco-ios-xr-string;
                description
                  "Profile name";
              }
              uses PM-NAME-PROFILE-BAG;
            }
          }
          container delay-profile-interfaces {
            description
              "Interface profile name table";
            list delay-profile-interface {
              key "profile-name";
              description
                "Interface delay profile name";
              leaf profile-name {
                type xr:Cisco-ios-xr-string;
                description
                  "Profile name";
              }
              uses PM-NAME-PROFILE-BAG;
            }
          }
          container liveness-profile-sr-policies {
            description
              "SR Policy profile name table";
            list liveness-profile-sr-policy {
              key "profile-name";
              description
                "SR Policy liveness profile name";
              leaf profile-name {
                type xr:Cisco-ios-xr-string;
                description
                  "Profile name";
              }
              uses PM-NAME-PROFILE-BAG;
            }
          }
        }
        leaf node {
          type xr:Node-id;
          description
            "Node";
        }
      }
    }
  }
  container performance-measurement-responder {
    config false;
    description
      "Performance Measurement operational data";
    container nodes {
      description
        "Node table for node-specific operational data";
      list node {
        key "node";
        description
          "Node-specific data for a particular node";
        container summary {
          description
            "Summary information for all the measurement
             and transportation type on responder";
          uses PM-RESP-SUMMARY-BAG;
        }
        container interfaces {
          description
            "Table of interfaces";
          list interface {
            key "interface-name";
            description
              "Interface information";
            leaf interface-name {
              type xr:Interface-name;
              description
                "Interface name";
            }
            uses PM-RESP-INTF-BAG;
          }
        }
        leaf node {
          type xr:Node-id;
          description
            "Node";
        }
      }
    }
  }
}
