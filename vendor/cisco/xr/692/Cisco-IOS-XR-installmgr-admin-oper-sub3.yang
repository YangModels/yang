submodule Cisco-IOS-XR-installmgr-admin-oper-sub3 {
  belongs-to Cisco-IOS-XR-installmgr-admin-oper {
    prefix Cisco-IOS-XR-installmgr-admin-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR installmgr-admin package operational data.
     
     Copyright (c) 2013-2019 by Cisco Systems, Inc.
     All rights reserved.";

  revision 2019-04-05 {
    description
      "Establish semantic version baseline.";
    semver:module-version "1.0.0";
  }
  revision 2019-01-03 {
    description
      "Fixing backward compatibility error in modules.";
  }
  revision 2015-11-09 {
    description
      "IOS XR 6.0 revision.";
  }

  typedef Instmgr-ism-fsm-state {
    type enumeration {
      enum "idle" {
        value 0;
        description
          "No ISSU in progress";
      }
      enum "init-done" {
        value 1;
        description
          "LOAD init";
      }
      enum "load-shut" {
        value 2;
        description
          "LOAD preparation";
      }
      enum "load-wait" {
        value 3;
        description
          "LOAD wait";
      }
      enum "load-stp-root-before" {
        value 4;
        description
          "LOAD root SC FO";
      }
      enum "load-standby-root-sc-upgrade" {
        value 5;
        description
          "LOAD standby ROOT SC Upgrade";
      }
      enum "load-standby-management-upgrade" {
        value 6;
        description
          "LOAD standby management upgrade";
      }
      enum "load-stp-root-after" {
        value 7;
        description
          "LOAD NDSC FO";
      }
      enum "load-fabric-upgrade" {
        value 8;
        description
          "LOAD fabric upgrade";
      }
      enum "load-management-issu-ready" {
        value 9;
        description
          "LOAD ISSU ready";
      }
      enum "load-done" {
        value 10;
        description
          "LOAD done";
      }
      enum "run-prep" {
        value 11;
        description
          "RUN preparation";
      }
      enum "run-wait" {
        value 12;
        description
          "RUN wait";
      }
      enum "runi-mdr-prep" {
        value 13;
        description
          "RUN iMDR preparation";
      }
      enum "runi-mdr-start" {
        value 14;
        description
          "RUN iMDR start";
      }
      enum "runi-mdr-complete" {
        value 15;
        description
          "RUN iMDR complete";
      }
      enum "run-make-standby-ready" {
        value 16;
        description
          "RUN make standby ready";
      }
      enum "run-root-scfo" {
        value 17;
        description
          "RUN root SC FO";
      }
      enum "run-ndscfo" {
        value 18;
        description
          "RUN NDSC FO";
      }
      enum "run-transient1" {
        value 19;
        description
          "RUN transient1";
      }
      enum "run-dscfo" {
        value 20;
        description
          "RUN DSC FO";
      }
      enum "run-fo-complete" {
        value 21;
        description
          "RUN FO compelte";
      }
      enum "run-stp-root-return" {
        value 22;
        description
          "Run STP Root Return";
      }
      enum "runi-mdr-continue" {
        value 23;
        description
          "RUN iMDR continue";
      }
      enum "run-am-i-ready-afteri-mdr" {
        value 24;
        description
          "RUN I am ready after iMDR";
      }
      enum "run-nsf-ready" {
        value 25;
        description
          "RUN NSF ready";
      }
      enum "run-nsf-begin" {
        value 26;
        description
          "RUN iMDR begin";
      }
      enum "runi-mdr-done" {
        value 27;
        description
          "RUN iMDR done";
      }
      enum "run-management-issu-ready" {
        value 28;
        description
          "RUN mgmt issu ready";
      }
      enum "run-un-shut" {
        value 29;
        description
          "RUN unshut";
      }
      enum "run-is-done" {
        value 30;
        description
          "RUN done";
      }
      enum "state-max" {
        value 31;
        description
          "Max ISSU state";
      }
    }
    description
      "Install manager FSM state";
  }

  typedef Installmgr-ism-node-conforming {
    type enumeration {
      enum "conforming" {
        value 0;
        description
          "Conforming Nodes";
      }
      enum "none-conforming" {
        value 1;
        description
          "Non-conforming nodes";
      }
      enum "upgrade-fail" {
        value 2;
        description
          "Node Upgrade failed";
      }
      enum "none-conforming-spa" {
        value 3;
        description
          "Non-conforming SPAs";
      }
      enum "spa-upgrade-fail" {
        value 4;
        description
          "SPA Upgrade failed";
      }
    }
    description
      "ISSU manage node inventory type";
  }

  typedef Instmgr-ism-node-state {
    type enumeration {
      enum "none" {
        value 0;
        description
          "No ISSU in progress";
      }
      enum "issu-node-gsp-ready" {
        value 1;
        description
          "Node GSP ready";
      }
      enum "load-shut-done" {
        value 2;
        description
          "Load shut done";
      }
      enum "standby-management-upgrade-done" {
        value 3;
        description
          "Standby management nodes upgrade done";
      }
      enum "fabric-upgrade-done" {
        value 4;
        description
          "Fabric nodes upgrade done";
      }
      enum "imdr-preparation-ack-received" {
        value 5;
        description
          "iMDR preparation ACK received";
      }
      enum "imdr-preparation-failed" {
        value 6;
        description
          "iMDR preparation ACK failed";
      }
      enum "imdr-start-ack-received" {
        value 7;
        description
          "iMDR start AVK received";
      }
      enum "imdr-start-failed" {
        value 8;
        description
          "iMDR start failed";
      }
      enum "imdr-complete-ack-received" {
        value 9;
        description
          "iMDR complete ACK received";
      }
      enum "imdr-complete-failed" {
        value 10;
        description
          "iMDR complete failed";
      }
      enum "standby-management-ready" {
        value 11;
        description
          "Standby management nodes ready";
      }
      enum "fo-acknowledged" {
        value 12;
        description
          "FO acked";
      }
      enum "fo-complete" {
        value 13;
        description
          "FO complete";
      }
      enum "standby-ready-after-fo" {
        value 14;
        description
          "Standby nodes ready after FO";
      }
      enum "iam-ready-afteri-mdr" {
        value 15;
        description
          "Node is ready after iMDR";
      }
      enum "nsf-ready" {
        value 16;
        description
          "NSF ready";
      }
      enum "nsf-begin-ack-received" {
        value 17;
        description
          "NSF begin ACK received";
      }
      enum "imdr-done" {
        value 18;
        description
          "iMDR done";
      }
      enum "unshut-done" {
        value 19;
        description
          "Unshut done";
      }
      enum "run-done" {
        value 20;
        description
          "Run done";
      }
      enum "imdr-abort-sent" {
        value 21;
        description
          "iMDR abort sent";
      }
      enum "imdr-abort-ack-received" {
        value 22;
        description
          "iMDR abort ACK Received";
      }
      enum "imdr-abort-failed" {
        value 23;
        description
          "iMDR abort failed";
      }
      enum "standby-management-downgrade-done" {
        value 24;
        description
          "Standby management nodes downgrade done";
      }
      enum "fabric-downgrade-done" {
        value 25;
        description
          "Fabric nodes downgrade done";
      }
      enum "reload-during-issu" {
        value 26;
        description
          "Node reloaded during ISSU";
      }
      enum "timneout" {
        value 27;
        description
          "Node time out";
      }
      enum "fabric-upgrade-failed" {
        value 28;
        description
          "Fabric upgrade failed";
      }
      enum "unsupported-hw" {
        value 29;
        description
          "Unsupported hardware";
      }
      enum "not-reachable" {
        value 30;
        description
          "Node unreachable";
      }
      enum "max" {
        value 32;
        description
          "Max node state";
      }
    }
    description
      "ISSU manager node state";
  }

  typedef Instmgr-pi-card {
    type enumeration {
      enum "type-rp" {
        value 0;
        description
          "Card type RP";
      }
      enum "type-drp" {
        value 1;
        description
          "Card Type DRP";
      }
      enum "type-lc" {
        value 2;
        description
          "Card type  LC";
      }
      enum "type-sc" {
        value 3;
        description
          "Card type SC";
      }
      enum "type-sp" {
        value 4;
        description
          "Card type SP";
      }
      enum "type-other" {
        value 5;
        description
          "Card type other";
      }
    }
    description
      "PI card types";
  }

  typedef Instmgr-node-role {
    type enumeration {
      enum "redundency-unknown" {
        value 0;
        description
          "Redundency unknown";
      }
      enum "redundency-active" {
        value 1;
        description
          "Redundency active";
      }
      enum "redundency-standby" {
        value 2;
        description
          "Redundency standby";
      }
      enum "redundency-unusable" {
        value 3;
        description
          "Redundency unusable";
      }
    }
    description
      "Node role";
  }

  typedef Instmgr-card-state {
    type enumeration {
      enum "instmgr-card-not-present" {
        value 0;
        description
          "instmgr card not present";
      }
      enum "instmgr-card-present" {
        value 1;
        description
          "instmgr card present";
      }
      enum "instmgr-card-reset" {
        value 2;
        description
          "instmgr card reset";
      }
      enum "instmgr-card-booting" {
        value 3;
        description
          "instmgr card booting";
      }
      enum "instmgr-card-mbi-booting" {
        value 4;
        description
          "instmgr card mbi booting";
      }
      enum "instmgr-card-running-mbi" {
        value 5;
        description
          "instmgr card running mbi";
      }
      enum "instmgr-card-running-ena" {
        value 6;
        description
          "instmgr card running ena";
      }
      enum "instmgr-card-bring-down" {
        value 7;
        description
          "instmgr card bring down";
      }
      enum "instmgr-card-ena-failure" {
        value 8;
        description
          "instmgr card ena failure";
      }
      enum "instmgr-card-f-diag-run" {
        value 9;
        description
          "instmgr card f diag run";
      }
      enum "instmgr-card-f-diag-failure" {
        value 10;
        description
          "instmgr card f diag failure";
      }
      enum "instmgr-card-powered" {
        value 11;
        description
          "instmgr card powered";
      }
      enum "instmgr-card-unpowered" {
        value 12;
        description
          "instmgr card unpowered";
      }
      enum "instmgr-card-mdr" {
        value 13;
        description
          "instmgr card mdr";
      }
      enum "instmgr-card-mdr-running-mbi" {
        value 14;
        description
          "instmgr card mdr running mbi";
      }
      enum "instmgr-card-main-t-mode" {
        value 15;
        description
          "instmgr card main t mode";
      }
      enum "instmgr-card-admin-down" {
        value 16;
        description
          "instmgr card admin down";
      }
      enum "instmgr-card-no-mon" {
        value 17;
        description
          "instmgr card no mon";
      }
      enum "instmgr-card-unknown" {
        value 18;
        description
          "instmgr card unknown";
      }
      enum "instmgr-card-failed" {
        value 19;
        description
          "instmgr card failed";
      }
      enum "instmgr-card-ok" {
        value 20;
        description
          "instmgr card ok";
      }
      enum "instmgr-card-missing" {
        value 21;
        description
          "instmgr card missing";
      }
      enum "instmgr-card-field-diag-downloading" {
        value 22;
        description
          "instmgr card field diag downloading";
      }
      enum "instmgr-card-field-diag-unmonitor" {
        value 23;
        description
          "instmgr card field diag unmonitor";
      }
      enum "instmgr-card-fabric-field-diag-unmonitor" {
        value 24;
        description
          "instmgr card fabric field diag unmonitor";
      }
      enum "instmgr-card-field-diag-rp-launching" {
        value 25;
        description
          "instmgr card field diag rp launching";
      }
      enum "instmgr-card-field-diag-running" {
        value 26;
        description
          "instmgr card field diag running";
      }
      enum "instmgr-card-field-diag-pass" {
        value 27;
        description
          "instmgr card field diag pass";
      }
      enum "instmgr-card-field-diag-fail" {
        value 28;
        description
          "instmgr card field diag fail";
      }
      enum "instmgr-card-field-diag-timeout" {
        value 29;
        description
          "instmgr card field diag timeout";
      }
      enum "instmgr-card-disabled" {
        value 30;
        description
          "instmgr card disabled";
      }
      enum "instmgr-card-spa-booting" {
        value 31;
        description
          "instmgr card spa booting";
      }
      enum "instmgr-card-not-allowed-online" {
        value 32;
        description
          "instmgr card not allowed online";
      }
      enum "instmgr-card-stopped" {
        value 33;
        description
          "instmgr card stopped";
      }
      enum "instmgr-card-incompatible-fw-ver" {
        value 34;
        description
          "instmgr card incompatible fw ver";
      }
      enum "instmgr-card-fpd-hold" {
        value 35;
        description
          "instmgr card fpd hold";
      }
      enum "instmgr-card-updating-fpd" {
        value 37;
        description
          "instmgr card updating fpd";
      }
      enum "instmgr-card-num-states" {
        value 38;
        description
          "instmgr card num states";
      }
    }
    description
      "Instmgr card state";
  }

  grouping NODE-LIST {
    description
      "List of nodes identifiers";
    list node {
      description
        "node";
      leaf entry {
        type xr:Node-id;
        description
          "entry";
      }
    }
  }

  grouping INSTALL-ISSU-STAGE {
    description
      "stage details for an install ISSU op";
    container node-in-progress {
      description
        "Progress of issu stage node";
      uses NODE-LIST;
    }
    container nodes-in-load {
      description
        "Node in LOAD phase";
      uses NODE-LIST;
    }
    container nodes-in-run {
      description
        "Node in RUN phase";
      uses NODE-LIST;
    }
    container nc-nodes {
      description
        "None-conforming nodes";
      uses NODE-LIST;
    }
    leaf issu-state {
      type string;
      description
        "Current ISSU state";
    }
    leaf issu-op-id {
      type uint32;
      description
        "ISSU operational ID";
    }
    leaf percentage {
      type uint32;
      units "percentage";
      description
        "ISSU progress percentage";
    }
    leaf is-issu-aborted {
      type boolean;
      description
        "ISSU aborted?";
    }
    leaf is-issu-aborted-by-ism {
      type boolean;
      description
        "ISSU aborted by ISM?";
    }
    leaf issu-manager-fsm-state {
      type Instmgr-ism-fsm-state;
      description
        "ISM FSM state";
    }
    leaf participating-node-all {
      type uint32;
      description
        "Number of participating nodes";
    }
    leaf num-nodes-in-progress {
      type uint32;
      description
        "Number of  issu node in progress";
    }
    leaf num-of-nodes-in-load {
      type uint32;
      description
        "Number of nodes in LOAD phase";
    }
    leaf num-of-nodes-in-run {
      type uint32;
      description
        "Number of nodes in RUN phase";
    }
    leaf numof-nc-nodes {
      type uint32;
      description
        "Number of none-conforming nodes";
    }
  }

  grouping ISM-CARD-STATUS {
    description
      "ism card status td";
    leaf node-name {
      type xr:Node-id;
      description
        "Identifier of node";
    }
    leaf partner-node-name {
      type xr:Node-id;
      description
        "Partner Node IDs";
    }
    leaf node-state {
      type Instmgr-card-state;
      description
        "Node state status";
    }
    leaf node-role {
      type Instmgr-node-role;
      description
        "Node roll";
    }
    leaf node-type-pi {
      type Instmgr-pi-card;
      description
        "PI Node type";
    }
    leaf node-type-issu {
      type string;
      description
        "ISSU node type";
    }
    leaf node-current-state {
      type Instmgr-ism-node-state;
      description
        "Current node ISSU state";
    }
    leaf node-expected-state {
      type Instmgr-ism-node-state;
      description
        "Expected ISSU state";
    }
    leaf node-failure-reason {
      type string;
      description
        " ISM card Node failure reason";
    }
    leaf is-conforming-node {
      type Installmgr-ism-node-conforming;
      description
        "Node none-cnforming";
    }
    leaf attempts {
      type uint32;
      description
        "Number of attempts made";
    }
    leaf is-node-upgraded {
      type boolean;
      description
        "Is ism card node upgraded?";
    }
  }

  grouping ISM-CARD-INVENTORY-SUMMARY {
    description
      "ISM inventory summary for a given card type";
    list summary {
      description
        "node state for all nodes";
      uses ISM-CARD-STATUS;
    }
  }
}
