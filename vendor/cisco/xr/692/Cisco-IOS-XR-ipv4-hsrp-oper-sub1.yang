submodule Cisco-IOS-XR-ipv4-hsrp-oper-sub1 {
  belongs-to Cisco-IOS-XR-ipv4-hsrp-oper {
    prefix Cisco-IOS-XR-ipv4-hsrp-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-hsrp package operational data.
     
     Copyright (c) 2013-2019 by Cisco Systems, Inc.
     All rights reserved.";

  revision 2019-04-05 {
    description
      "Establish semantic version baseline.";
    semver:module-version "1.0.0";
  }
  revision 2018-12-07 {
    description
      "Moved group numbers to a range.";
  }
  revision 2017-09-07 {
    description
      "Fixed type translation error.";
  }
  revision 2015-11-09 {
    description
      "IOS XR 6.0 revision.";
  }

  typedef Hsrp-vmac-state {
    type enumeration {
      enum "stored" {
        value 0;
        description
          "VMAC stored locally";
      }
      enum "reserved" {
        value 1;
        description
          "VMAC reserved in mac table";
      }
      enum "active" {
        value 2;
        description
          "VMAC active in mac table";
      }
      enum "reserving" {
        value 3;
        description
          "VMAC not yet reserved in mac table";
      }
    }
    description
      "Hsrp vmac state";
  }

  typedef Hsrp-state-change-reason {
    type enumeration {
      enum "state-change-bfd-down" {
        value 0;
        description
          "BFD session down";
      }
      enum "state-change-vip-learnt" {
        value 1;
        description
          "Virtual IP learnt";
      }
      enum "state-change-interface-ip" {
        value 2;
        description
          "Interface IP update";
      }
      enum "state-change-delay-timer" {
        value 3;
        description
          "Delay timer expired";
      }
      enum "state-change-startup" {
        value 4;
        description
          "Ready on startup";
      }
      enum "state-change-shutdown" {
        value 5;
        description
          "HSRP shut down";
      }
      enum "state-change-interface-up" {
        value 6;
        description
          "Interface Up update";
      }
      enum "state-change-interface-down" {
        value 7;
        description
          "Interface Down update";
      }
      enum "state-change-active-timer" {
        value 8;
        description
          "Active timer expired";
      }
      enum "state-change-standby-timer" {
        value 9;
        description
          "Standby timer expired";
      }
      enum "state-change-resign" {
        value 10;
        description
          "Resign received";
      }
      enum "state-change-coup" {
        value 11;
        description
          "Coup received";
      }
      enum "state-change-higher-priority-speak" {
        value 12;
        description
          "Higher priority speak received";
      }
      enum "state-change-higher-priority-standby" {
        value 13;
        description
          "Higher priority standby received";
      }
      enum "state-change-lower-priority-standby" {
        value 14;
        description
          "Lower priority standby received";
      }
      enum "state-change-higher-priority-active" {
        value 15;
        description
          "Higher priority active received";
      }
      enum "state-change-lower-priority-active" {
        value 16;
        description
          "Lower priority active received";
      }
      enum "state-change-virtual-ip-configured" {
        value 17;
        description
          "Virtual IP configured";
      }
      enum "state-change-virtual-ip-lost" {
        value 18;
        description
          "Virtual IP lost";
      }
      enum "state-change-recovered-from-checkpoint" {
        value 19;
        description
          "Recovered from checkpoint";
      }
      enum "state-change-mac-update" {
        value 20;
        description
          "MAC address update";
      }
      enum "state-change-admin" {
        value 21;
        description
          "Forwarder Admin state change";
      }
      enum "state-change-parent" {
        value 22;
        description
          "MGO parent change";
      }
      enum "state-change-chkpt-update" {
        value 23;
        description
          "Checkpoint update from Primary HSRP instance";
      }
      enum "state-change-issu-resync" {
        value 24;
        description
          "Resync following ISSU primary event";
      }
      enum "state-change-reset-to-learn" {
        value 25;
        description
          "Reset to learn parameters";
      }
      enum "state-change-max" {
        value 26;
        description
          "Maximum reason in enumeration";
      }
    }
    description
      "Hsrp state change reason";
  }

  typedef Hsrp-bfd-session-state {
    type enumeration {
      enum "bfd-state-none" {
        value 0;
        description
          "None";
      }
      enum "bfd-state-inactive" {
        value 1;
        description
          "Inactive";
      }
      enum "bfd-state-up" {
        value 2;
        description
          "Up";
      }
      enum "bfd-state-down" {
        value 3;
        description
          "Down";
      }
    }
    description
      "Hsrp bfd session state";
  }

  typedef Standby-grp-state {
    type enumeration {
      enum "state-initial" {
        value 1;
        description
          "Initial";
      }
      enum "state-learn" {
        value 2;
        description
          "Learn";
      }
      enum "state-listen" {
        value 3;
        description
          "Listen";
      }
      enum "state-speak" {
        value 4;
        description
          "Speak";
      }
      enum "state-standby" {
        value 5;
        description
          "Standby";
      }
      enum "state-active" {
        value 6;
        description
          "Active";
      }
    }
    description
      "Standby grp state";
  }

  typedef Hsrp-version {
    type uint8;
    description
      "Hsrp version";
  }

  typedef Hsrp-b-af {
    type enumeration {
      enum "ipv4" {
        description
          "IPv4 Address Family";
      }
      enum "ipv6" {
        description
          "IPv6 Address Family";
      }
      enum "count" {
        description
          "The number of supported address families";
      }
    }
    description
      "Hsrp b af";
  }

  grouping HSRP-SUMMARY-INFO {
    description
      "HSRP summary statistics";
    leaf ipv4-sessions-active {
      type uint32;
      description
        "Number of IPv4 sessions in ACTIVE state";
    }
    leaf ipv4-sessions-standby {
      type uint32;
      description
        "Number of IPv4 sessions in STANDBY state";
    }
    leaf ipv4-sessions-speak {
      type uint32;
      description
        "Number of IPv4 sessions in SPEAK state";
    }
    leaf ipv4-sessions-listen {
      type uint32;
      description
        "Number of IPv4 sessions in LISTEN state";
    }
    leaf ipv4-sessions-learn {
      type uint32;
      description
        "Number of IPv4 sessions in LEARN state";
    }
    leaf ipv4-sessions-init {
      type uint32;
      description
        "Number of IPv4 sessions in INIT state";
    }
    leaf ipv4-slaves-active {
      type uint32;
      description
        "Number of IPv4 slaves in ACTIVE state";
    }
    leaf ipv4-slaves-standby {
      type uint32;
      description
        "Number of IPv4 slaves in STANDBY state";
    }
    leaf ipv4-slaves-speak {
      type uint32;
      description
        "Number of IPv4 slaves in SPEAK state";
    }
    leaf ipv4-slaves-listen {
      type uint32;
      description
        "Number of IPv4 slaves in LISTEN state";
    }
    leaf ipv4-slaves-learn {
      type uint32;
      description
        "Number of IPv4 slaves in LEARN state";
    }
    leaf ipv4-slaves-init {
      type uint32;
      description
        "Number of IPv4 slaves in INIT state";
    }
    leaf ipv4-virtual-ip-addresses-active-up {
      type uint32;
      description
        "Number of UP IPv4 Virtual IP Addresses on groups
         in ACTIVE state";
    }
    leaf ipv4-virtual-ip-addresses-active-down {
      type uint32;
      description
        "Number of DOWN IPv4 Virtual IP Addresses on
         groups in ACTIVE state";
    }
    leaf ipv4-virtual-ip-addresses-standby-up {
      type uint32;
      description
        "Number of UP IPv4 Virtual IP Addresses on groups
         in STANDBY state";
    }
    leaf ipv4-virtual-ip-addresses-standby-down {
      type uint32;
      description
        "Number of DOWN IPv4 Virtual IP Addresses on
         groups in STANDBY state";
    }
    leaf ipv4-virtual-ip-addresses-speak-up {
      type uint32;
      description
        "Number of UP IPv4 Virtual IP Addresses on groups
         in SPEAK state";
    }
    leaf ipv4-virtual-ip-addresses-speak-down {
      type uint32;
      description
        "Number of DOWN IPv4 Virtual IP Addresses on
         groups in SPEAK state";
    }
    leaf ipv4-virtual-ip-addresses-listen-up {
      type uint32;
      description
        "Number of UP IPv4 Virtual IP Addresses on groups
         in LISTEN state";
    }
    leaf ipv4-virtual-ip-addresses-listen-down {
      type uint32;
      description
        "Number of DOWN IPv4 Virtual IP Addresses on
         groups in LISTEN state";
    }
    leaf ipv4-virtual-ip-addresses-learn-up {
      type uint32;
      description
        "Number of UP IPv4 Virtual IP Addresses on groups
         in LEARN state";
    }
    leaf ipv4-virtual-ip-addresses-learn-down {
      type uint32;
      description
        "Number of DOWN IPv4 Virtual IP Addresses on
         groups in LEARN state";
    }
    leaf ipv4-virtual-ip-addresses-init-up {
      type uint32;
      description
        "Number of UP IPv4 Virtual IP Addresses on groups
         in INIT state";
    }
    leaf ipv4-virtual-ip-addresses-init-down {
      type uint32;
      description
        "Number of DOWN IPv4 Virtual IP Addresses on
         groups in INIT state";
    }
    leaf ipv6-sessions-active {
      type uint32;
      description
        "Number of IPv6 sessions in ACTIVE state";
    }
    leaf ipv6-sessions-standby {
      type uint32;
      description
        "Number of IPv6 sessions in STANDBY state";
    }
    leaf ipv6-sessions-speak {
      type uint32;
      description
        "Number of IPv6 sessions in SPEAK state";
    }
    leaf ipv6-sessions-listen {
      type uint32;
      description
        "Number of IPv6 sessions in LISTEN state";
    }
    leaf ipv6-sessions-learn {
      type uint32;
      description
        "Number of IPv6 sessions in LEARN state";
    }
    leaf ipv6-sessions-init {
      type uint32;
      description
        "Number of IPv6 sessions in INIT state";
    }
    leaf ipv6-slaves-active {
      type uint32;
      description
        "Number of IPv6 slaves in ACTIVE state";
    }
    leaf ipv6-slaves-standby {
      type uint32;
      description
        "Number of IPv6 slaves in STANDBY state";
    }
    leaf ipv6-slaves-speak {
      type uint32;
      description
        "Number of IPv6 slaves in SPEAK state";
    }
    leaf ipv6-slaves-listen {
      type uint32;
      description
        "Number of IPv6 slaves in LISTEN state";
    }
    leaf ipv6-slaves-learn {
      type uint32;
      description
        "Number of IPv6 slaves in LEARN state";
    }
    leaf ipv6-slaves-init {
      type uint32;
      description
        "Number of IPv6 slaves in INIT state";
    }
    leaf ipv6-virtual-ip-addresses-active-up {
      type uint32;
      description
        "Number of UP IPv6 Virtual IP Addresses on groups
         in ACTIVE state";
    }
    leaf ipv6-virtual-ip-addresses-active-down {
      type uint32;
      description
        "Number of DOWN IPv6 Virtual IP Addresses on
         groups in ACTIVE state";
    }
    leaf ipv6-virtual-ip-addresses-standby-up {
      type uint32;
      description
        "Number of UP IPv6 Virtual IP Addresses on groups
         in STANDBY state";
    }
    leaf ipv6-virtual-ip-addresses-standby-down {
      type uint32;
      description
        "Number of DOWN IPv6 Virtual IP Addresses on
         groups in STANDBY state";
    }
    leaf ipv6-virtual-ip-addresses-speak-up {
      type uint32;
      description
        "Number of UP IPv6 Virtual IP Addresses on groups
         in SPEAK state";
    }
    leaf ipv6-virtual-ip-addresses-speak-down {
      type uint32;
      description
        "Number of DOWN IPv6 Virtual IP Addresses on
         groups in SPEAK state";
    }
    leaf ipv6-virtual-ip-addresses-listen-up {
      type uint32;
      description
        "Number of UP IPv6 Virtual IP Addresses on groups
         in LISTEN state";
    }
    leaf ipv6-virtual-ip-addresses-listen-down {
      type uint32;
      description
        "Number of DOWN IPv6 Virtual IP Addresses on
         groups in LISTEN state";
    }
    leaf ipv6-virtual-ip-addresses-learn-up {
      type uint32;
      description
        "Number of UP IPv6 Virtual IP Addresses on groups
         in LEARN state";
    }
    leaf ipv6-virtual-ip-addresses-learn-down {
      type uint32;
      description
        "Number of DOWN IPv6 Virtual IP Addresses on
         groups in LEARN state";
    }
    leaf ipv6-virtual-ip-addresses-init-up {
      type uint32;
      description
        "Number of UP IPv6 Virtual IP Addresses on groups
         in INIT state";
    }
    leaf ipv6-virtual-ip-addresses-init-down {
      type uint32;
      description
        "Number of DOWN IPv6 Virtual IP Addresses on
         groups in INIT state";
    }
    leaf interfaces-ipv4-state-up {
      type uint32;
      description
        "Number of HSRP interfaces with IPv4 caps in UP
         state";
    }
    leaf interfaces-ipv4-state-down {
      type uint32;
      description
        "Number of HSRP interfaces with IPv4 caps in DOWN
         state";
    }
    leaf tracked-interfaces-ipv4-state-up {
      type uint32;
      description
        "Number of tracked interfaces with IPv4 caps in
         UP state";
    }
    leaf tracked-interfaces-ipv4-state-down {
      type uint32;
      description
        "Number of tracked interfaces with IPv4 caps in
         DOWN state";
    }
    leaf tracked-objects-up {
      type uint32;
      description
        "Number of tracked objects in UP state";
    }
    leaf tracked-objects-down {
      type uint32;
      description
        "Number of tracked objects in DOWN state";
    }
    leaf interfaces-ipv6-state-up {
      type uint32;
      description
        "Number of HSRP interfaces with IPv6 caps in UP
         state";
    }
    leaf interfaces-ipv6-state-down {
      type uint32;
      description
        "Number of HSRP interfaces with IPv6 caps in DOWN
         state";
    }
    leaf tracked-interfaces-ipv6-state-up {
      type uint32;
      description
        "Number of tracked interfaces with IPv6 caps in
         UP state";
    }
    leaf tracked-interfaces-ipv6-state-down {
      type uint32;
      description
        "Number of tracked interfaces with IPv6 caps in
         DOWN state";
    }
    leaf bfd-sessions-up {
      type uint32;
      description
        "Number of HSRP BFD sessions in UP state";
    }
    leaf bfd-sessions-down {
      type uint32;
      description
        "Number of HSRP BFD sessions in DOWN state";
    }
    leaf bfd-session-inactive {
      type uint32;
      description
        "Number of HSRP BFD sessions in INACTIVE state";
    }
  }

  grouping HSRP-BFD-GROUP-INFO {
    description
      "BFD Group Information";
    leaf interface-name {
      type string {
        length "0..64";
      }
      description
        "Interface Name";
    }
    leaf hsrp-group-number {
      type uint32;
      description
        "HSRP Group number";
    }
  }

  grouping STANDBY-BFD-INFO {
    description
      "BFD session information";
    leaf bfd-interface-name {
      type string {
        length "0..64";
      }
      description
        "BFD Interface Name";
    }
    leaf session-address-family {
      type Hsrp-b-af;
      description
        "Session Address family";
    }
    leaf destination-address {
      type inet:ipv4-address;
      description
        "BFD destination address";
    }
    leaf destination-ipv6-address {
      type inet:ipv6-address;
      description
        "BFD IPv6 destination address";
    }
    leaf bfd-session-state {
      type Hsrp-bfd-session-state;
      description
        "BFD session state";
    }
    leaf bfd-interval {
      type uint32;
      description
        "BFD packet send interval";
    }
    leaf bfd-multiplier {
      type uint32;
      description
        "BFD multiplier";
    }
    list group {
      description
        "HSRP Groups tracking the BFD session";
      uses HSRP-BFD-GROUP-INFO;
    }
  }

  grouping HSRP-SLAVE-INFO-TYPE {
    description
      "Slave info";
    leaf slave-group-interface {
      type string {
        length "0..64";
      }
      description
        "Interface of slave group";
    }
    leaf slave-group-number {
      type uint32;
      description
        "Group number of slave group";
    }
  }

  grouping HSRP-MGO-INFO {
    description
      "MGO group data";
    leaf primary-session-name {
      type string {
        length "0..16";
      }
      description
        "Session Name";
    }
    leaf primary-session-interface {
      type xr:Interface-name;
      description
        "Interface of primary session";
    }
    leaf primary-af-name {
      type Hsrp-b-af;
      description
        "Address family of primary session";
    }
    leaf primary-session-number {
      type uint32;
      description
        "Group number of primary session";
    }
    leaf primary-session-state {
      type Standby-grp-state;
      description
        "State of primary session";
    }
    list slave {
      description
        "List of slaves following this primary session";
      uses HSRP-SLAVE-INFO-TYPE;
    }
  }

  grouping HSRP-IF-STATS-TYPE {
    description
      "HSRP Interface Statistics";
    leaf advert-packets-sent {
      type uint32;
      description
        "Number of advertisement packets sent";
    }
    leaf advert-packets-received {
      type uint32;
      description
        "Number of advertisement packets received";
    }
    leaf long-packets-received {
      type uint32;
      description
        "Number of packets received that were too Long";
    }
    leaf short-packets-received {
      type uint32;
      description
        "Number of packets received that were too short";
    }
    leaf invalid-version-received {
      type uint32;
      description
        "Number of packets received with invalid version";
    }
    leaf invalid-operation-code-received {
      type uint32;
      description
        "Number of packets received with invalid
         operation code";
    }
    leaf unknown-group-received {
      type uint32;
      description
        "Number of packets received for an unknown group
         id";
    }
    leaf inoperational-group-received {
      type uint32;
      description
        "Number of packets received for an inoperational
         group";
    }
    leaf conflict-source-ip-address-received {
      type uint32;
      description
        "Number of packets received from a conflicting
         Source IP address";
    }
  }

  grouping STANDBY-IF-INFO {
    description
      "Use burnt in mac address information";
    container statistics {
      description
        "HSRP Interface Statistics";
      uses HSRP-IF-STATS-TYPE;
    }
    leaf interface {
      type xr:Interface-name;
      description
        "IM Interface";
    }
    leaf use-bia-flag {
      type boolean;
      description
        "Use burnt in mac address flag";
    }
  }

  grouping STANDBY-TRACKEDIF-INFO {
    description
      "Interface tracking information";
    leaf interface {
      type xr:Interface-name;
      description
        "IM Interface";
    }
    leaf hsrp-group-number {
      type uint32;
      description
        "HSRP Group number";
    }
    leaf priority-decrement {
      type uint32;
      description
        "Priority weighting";
    }
    leaf interface-up-flag {
      type boolean;
      description
        "Interface up flag";
    }
    leaf tracked-interface-name-xr {
      type string {
        length "0..64";
      }
      description
        "Tracked Interface Name";
    }
    leaf is-object {
      type boolean;
      description
        "Tracked Object Flag";
    }
  }

  grouping HSRP-GROUP-STATS-TYPE {
    description
      "HSRP Group Statistics";
    leaf active-transitions {
      type uint32;
      description
        "Number of transitions to Active State";
    }
    leaf standby-transitions {
      type uint32;
      description
        "Number of transitions to Standby State";
    }
    leaf speak-transitions {
      type uint32;
      description
        "Number of transitions to Speak State";
    }
    leaf listen-transitions {
      type uint32;
      description
        "Number of transitions to Listen State";
    }
    leaf learn-transitions {
      type uint32;
      description
        "Number of transitions to Learn State";
    }
    leaf init-transitions {
      type uint32;
      description
        "Number of transitions to Init State";
    }
    leaf hello-packets-sent {
      type uint32;
      description
        "Number of Hello Packets sent (NB: Bundles only)";
    }
    leaf resign-packets-sent {
      type uint32;
      description
        "Number of Resign Packets sent";
    }
    leaf coup-packets-sent {
      type uint32;
      description
        "Number of Coup Packets sent";
    }
    leaf hello-packets-received {
      type uint32;
      description
        "Number of Hello Packets received";
    }
    leaf resign-packets-received {
      type uint32;
      description
        "Number of Resign Packets received";
    }
    leaf coup-packets-received {
      type uint32;
      description
        "Number of Coup Packets received";
    }
    leaf auth-fail-received {
      type uint32;
      description
        "Number of Packets received that failed
         authentication";
    }
    leaf invalid-timer-received {
      type uint32;
      description
        "Number of packets received with invalid Hello
         Time value";
    }
    leaf mismatch-virtual-ip-address-received {
      type uint32;
      description
        "Number of packets received with mismatching
         virtual IP address";
    }
  }

  grouping HSRP-STATE-CHANGE-INFO-TYPE {
    description
      "State change info";
    container time {
      description
        "Time of state change";
      uses HSRP-BAG-TIMESTAMP;
    }
    leaf old-state {
      type Standby-grp-state;
      description
        "Old State";
    }
    leaf new-state {
      type Standby-grp-state;
      description
        "New State";
    }
    leaf reason {
      type Hsrp-state-change-reason;
      description
        "Reason for state change";
    }
  }

  grouping HSRP-BAG-TIMESTAMP {
    description
      "Timestamp";
    leaf seconds {
      type uint32;
      units "second";
      description
        "Seconds";
    }
    leaf nanoseconds {
      type uint32;
      units "nanosecond";
      description
        "Nanoseconds";
    }
  }

  grouping IPV6-BAG-ADDR {
    description
      "IPV6 BAG ADDR";
    leaf ipv6-address {
      type inet:ipv6-address;
      description
        "IPV6Address";
    }
  }

  grouping STANDBY-GRP-INFO {
    description
      "Detailed group specfic information";
    container resign-sent-time {
      description
        "Time last resign was sent";
      uses HSRP-BAG-TIMESTAMP;
    }
    container resign-received-time {
      description
        "Time last resign was received";
      uses HSRP-BAG-TIMESTAMP;
    }
    container coup-sent-time {
      description
        "Time last coup was sent";
      uses HSRP-BAG-TIMESTAMP;
    }
    container coup-received-time {
      description
        "Time last coup was received";
      uses HSRP-BAG-TIMESTAMP;
    }
    container statistics {
      description
        "HSRP Group statistics";
      uses HSRP-GROUP-STATS-TYPE;
    }
    leaf authentication-string {
      type string {
        length "0..9";
      }
      description
        "Authentication string";
    }
    leaf virtual-mac-address {
      type yang:mac-address;
      description
        "Virtual mac address";
    }
    leaf hsrp-group-number {
      type uint32;
      description
        "HSRP Group number";
    }
    leaf address-family {
      type Hsrp-b-af;
      description
        "Address family";
    }
    leaf version {
      type Hsrp-version;
      description
        "HSRP Protocol Version";
    }
    leaf session-name {
      type string {
        length "0..16";
      }
      description
        "Session Name";
    }
    leaf slaves {
      type uint32;
      description
        "Number of slaves following state";
    }
    leaf is-slave {
      type boolean;
      description
        "Group is a slave group";
    }
    leaf followed-session-name {
      type string {
        length "0..16";
      }
      description
        "Followed Session Name";
    }
    leaf configured-priority {
      type uint8;
      description
        "Configured priority";
    }
    leaf preempt-delay {
      type uint32;
      units "second";
      description
        "Preempt delay time in seconds";
    }
    leaf preempt-timer-secs {
      type uint32;
      units "second";
      description
        "Preempt time remaining in seconds";
    }
    leaf hello-time {
      type uint32;
      units "millisecond";
      description
        "Hellotime in msecs";
    }
    leaf hold-time {
      type uint32;
      units "millisecond";
      description
        "Holdtime in msecs";
    }
    leaf learned-hello-time {
      type uint32;
      units "millisecond";
      description
        "Learned hellotime in msecs";
    }
    leaf learned-hold-time {
      type uint32;
      units "millisecond";
      description
        "Learned holdtime in msecs";
    }
    leaf min-delay-time {
      type uint32;
      units "millisecond";
      description
        "Minimum delay time in msecs";
    }
    leaf reload-delay-time {
      type uint32;
      units "millisecond";
      description
        "Reload delay time in msecs";
    }
    leaf virtual-ip-address {
      type inet:ipv4-address;
      description
        "Configured Virtual IPv4 address";
    }
    leaf virtual-linklocal-ipv6-address {
      type inet:ipv6-address;
      description
        "Virtual linklocal IPv6 address";
    }
    leaf active-ip-address {
      type inet:ipv4-address;
      description
        "Active router's IP address";
    }
    leaf active-ipv6-address {
      type inet:ipv6-address;
      description
        "Active router's IPv6 address";
    }
    leaf active-mac-address {
      type yang:mac-address;
      description
        "Active router's interface MAC address";
    }
    leaf standby-ip-address {
      type inet:ipv4-address;
      description
        "Standby router's IP address";
    }
    leaf standby-ipv6-address {
      type inet:ipv6-address;
      description
        "Standby router's IPv6 address";
    }
    leaf standby-mac-address {
      type yang:mac-address;
      description
        "Standby router's interface MAC address";
    }
    leaf hsrp-router-state {
      type Standby-grp-state;
      description
        "HSRP router state";
    }
    leaf interface-name-xr {
      type string {
        length "0..64";
      }
      description
        "Interface Name";
    }
    leaf interface {
      type xr:Interface-name;
      description
        "IM Interface";
    }
    leaf router-priority {
      type uint8;
      description
        "Priority of the router";
    }
    leaf active-priority {
      type uint8;
      description
        "Priority of the Active router";
    }
    leaf active-timer-flag {
      type boolean;
      description
        "Active timer running flag";
    }
    leaf active-timer-secs {
      type uint32;
      units "second";
      description
        "Active timer running time secs";
    }
    leaf active-timer-msecs {
      type uint32;
      units "millisecond";
      description
        "Active timer running time msecs";
    }
    leaf standby-timer-flag {
      type boolean;
      description
        "Standby timer running flag";
    }
    leaf standby-timer-secs {
      type uint32;
      units "second";
      description
        "Standby timer running time secs";
    }
    leaf standby-timer-msecs {
      type uint32;
      units "millisecond";
      description
        "Standby timer running time msecs";
    }
    leaf hello-timer-flag {
      type boolean;
      description
        "Hello timer running flag";
    }
    leaf hello-timer-secs {
      type uint32;
      units "second";
      description
        "Hello timer running time secs";
    }
    leaf hello-timer-msecs {
      type uint32;
      units "millisecond";
      description
        "Hello timer running time msecs";
    }
    leaf delay-timer-flag {
      type boolean;
      description
        "Delay timer running flag";
    }
    leaf delay-timer-secs {
      type uint32;
      units "second";
      description
        "Delay timer running time secs";
    }
    leaf delay-timer-msecs {
      type uint32;
      units "millisecond";
      description
        "Delay timer running time msecs";
    }
    leaf current-state-timer-secs {
      type uint32;
      units "second";
      description
        "Time in current state secs";
    }
    leaf state-change-count {
      type uint32;
      description
        "Number of state changes";
    }
    leaf tracked-interface-count {
      type uint32;
      description
        "Number of tracked interfaces";
    }
    leaf tracked-interface-up-count {
      type uint32;
      description
        "Number of tracked interfaces up";
    }
    leaf preempt-enabled {
      type boolean;
      description
        "Preempt enabled";
    }
    leaf use-configured-timers {
      type boolean;
      description
        "Use configured timers";
    }
    leaf use-configured-virtual-ip {
      type boolean;
      description
        "Use configured virtual IP";
    }
    leaf use-bia-configured {
      type boolean;
      description
        "Use burnt in MAC address configured";
    }
    leaf configured-timers {
      type boolean;
      description
        "Non-default timers are configured";
    }
    leaf configured-mac-address {
      type boolean;
      description
        "MAC address configured";
    }
    leaf redirects-disabled {
      type boolean;
      description
        "HSRP redirects disabled";
    }
    leaf bfd-enabled {
      type boolean;
      description
        "HSRP BFD fast failover";
    }
    leaf bfd-interface {
      type xr:Interface-name;
      description
        "BFD Interface";
    }
    leaf bfd-peer-ip-address {
      type inet:ipv4-address;
      description
        "BFD Peer IP address";
    }
    leaf bfd-peer-ipv6-address {
      type inet:ipv6-address;
      description
        "BFD Peer IPv6 address";
    }
    leaf bfd-session-state {
      type Hsrp-bfd-session-state;
      description
        "BFD session state";
    }
    leaf bfd-interval {
      type uint32;
      description
        "BFD packet send interval";
    }
    leaf bfd-multiplier {
      type uint32;
      description
        "BFD multiplier";
    }
    leaf virtual-mac-address-state {
      type Hsrp-vmac-state;
      description
        "Virtual mac address state";
    }
    leaf-list secondary-address {
      type inet:ipv4-address;
      description
        "Secondary virtual IP addresses";
    }
    list global-address {
      description
        "Global virtual IPv6 addresses";
      uses IPV6-BAG-ADDR;
    }
    list state-change-history {
      description
        "State change history";
      uses HSRP-STATE-CHANGE-INFO-TYPE;
    }
  }
}
