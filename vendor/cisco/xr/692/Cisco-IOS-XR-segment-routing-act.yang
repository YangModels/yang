module Cisco-IOS-XR-segment-routing-act {
  namespace "http://cisco.com/ns/yang/Cisco-IOS-XR-segment-routing-act";
  prefix segment-routing-act;

  import cisco-semver {
    prefix semver;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Segment Routing action package.
     
     Copyright (c) 2021 by Cisco Systems, Inc.
     All rights reserved.";

  revision 2021-05-05 {
    description
      "Initial revision.";
    reference "Segment Routing reference.";
    semver:module-version "1.0.0";
  }

  rpc segment-routing-protect-policy-override-lock {
    description
      "Execute segment routing command";
    input {
      choice sr-policy-option {
        mandatory true;
        case sr-policy-all {
          leaf all {
            type boolean;
            description
              "Attempt a switchover on all protection locked SR Policies";
          }
        }
        case sr-policy-name {
          leaf name {
            type string;
            description
              "Attempt a switchover on named protection locked SR Policy";
          }
        }
      }
    }
  }
}
