module Cisco-IOS-XR-alarmgr-server-oper {
  namespace "http://cisco.com/ns/yang/Cisco-IOS-XR-alarmgr-server-oper";
  prefix alarmgr-server-oper;

  import Cisco-IOS-XR-types {
    prefix xr;
  }
  import cisco-semver {
    prefix semver;
  }
  include Cisco-IOS-XR-alarmgr-server-oper-sub1 {
    revision-date 2021-05-06;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR alarmgr-server package operational data.
     
     This module contains definitions
     for the following management objects:
       alarms: Show Alarms associated with XR
     
     Copyright (c) 2013-2021 by Cisco Systems, Inc.
     All rights reserved.";

  revision 2021-05-06 {
    description
      "Adding new alarm groups to alarm_mgr_edm_spi.bag
       2020-12-02
         PTAH support for Fibre Channel controller.
       2020-09-02
         SNMP Trap support added for Alarm mib";
    semver:module-version "3.0.0";
  }
  revision 2020-05-29 {
    description
      "Addressing Yang inconsistency across platforms
       2019-06-28
       PTAH support for CPRI controller in Felidae 5G platform.";
    semver:module-version "2.1.0";
  }
  revision 2019-04-05 {
    description
      "Establish semantic version baseline.";
    semver:module-version "2.0.0";
  }
  revision 2015-11-09 {
    description
      "IOS XR 6.0 revision.";
  }

  container alarms {
    config false;
    description
      "Show Alarms associated with XR";
    container detail {
      description
        "A set of detail alarm commands.";
      container detail-system {
        description
          "show detail system scope alarm related data.";
        container history {
          description
            "Show the history alarms at this scope.";
          uses ALARM-MGR-SHOW-ALARM-INFO-CLI;
        }
        container conditions {
          description
            "Show the Conditions present at this scope.";
          uses ALARM-MGR-SHOW-ALARM-INFO-CLI;
        }
        container stats {
          description
            "Show the service statistics.";
          uses ALARM-MGR-SHOW-ALARM-STATS;
        }
        container clients {
          description
            "Show the clients associated with this service.";
          uses ALARM-MGR-SHOW-CLIENT-INFO;
        }
        container suppressed {
          description
            "Show the suppressed alarms at this scope.";
          uses ALARM-MGR-SHOW-ALARM-INFO-SUPPR-CLI;
        }
        container active {
          description
            "Show the active alarms at this scope.";
          uses ALARM-MGR-SHOW-ALARM-INFO-CLI;
        }
      }
      container alarm-detail {
        description
          "show detail system scope alarm related data.";
        container active-details {
          description
            "Table of ActiveDetail";
          list active-detail {
            key "aid";
            description
              "Show the active alarms at this scope.";
            leaf aid {
              type string;
              description
                "Alarm ID";
            }
            uses ALARM-MGR-SHOW-ALARM-AID-DETAIL-INFO;
          }
        }
      }
      container detail-card {
        description
          "Show detail card scope alarm related data.";
        container detail-locations {
          description
            "Table of DetailLocation";
          list detail-location {
            key "node-id";
            description
              "Specify a card location for alarms.";
            container history {
              description
                "Show the history alarms at this scope.";
              uses ALARM-MGR-SHOW-ALARM-INFO-CLI;
            }
            container conditions {
              description
                "Show the conditions present at this scope.";
              uses ALARM-MGR-SHOW-ALARM-INFO-CLI;
            }
            container stats {
              description
                "Show the service statistics.";
              uses ALARM-MGR-SHOW-ALARM-STATS;
            }
            container clients {
              description
                "Show the clients associated with this
                 service.";
              uses ALARM-MGR-SHOW-CLIENT-INFO;
            }
            container suppressed {
              description
                "Show the suppressed alarms at this scope.";
              uses ALARM-MGR-SHOW-ALARM-INFO-SUPPR-CLI;
            }
            container active {
              description
                "Show the active alarms at this scope.";
              uses ALARM-MGR-SHOW-ALARM-INFO-CLI;
            }
            leaf node-id {
              type xr:Node-id;
              description
                "NodeID of the Location";
            }
          }
        }
      }
      container detail-rack {
        description
          "Show detail rack scope alarm related data.";
        container detail-numbers {
          description
            "Table of DetailNumber";
          list detail-number {
            key "rack-num";
            description
              "Specify a rack number for alarms.";
            container history {
              description
                "Show the history alarms at this scope.";
              uses ALARM-MGR-SHOW-ALARM-INFO-CLI;
            }
            container stats {
              description
                "Show the service statistics.";
              uses ALARM-MGR-SHOW-ALARM-STATS;
            }
            container clients {
              description
                "Show the clients associated with this
                 service.";
              uses ALARM-MGR-SHOW-CLIENT-INFO;
            }
            container suppressed {
              description
                "Show the suppressed alarms at this scope.";
              uses ALARM-MGR-SHOW-ALARM-INFO-SUPPR-CLI;
            }
            container active {
              description
                "Show the active alarms at this scope.";
              uses ALARM-MGR-SHOW-ALARM-INFO-CLI;
            }
            leaf rack-num {
              type xr:Cisco-ios-xr-string;
              description
                "Rack Number";
            }
          }
        }
      }
    }
    container brief {
      description
        "A set of brief alarm commands.";
      container alarm-id {
        description
          "Show brief system scope alarm related data.";
        container active-alarms {
          description
            "Table of ActiveAlarm";
          list active-alarm {
            key "aid";
            description
              "Show the active alarms at this scope.";
            leaf aid {
              type string;
              description
                "Alarm ID";
            }
            uses ALARM-MGR-SHOW-ALARM-AID-BRIEF-INFO;
          }
        }
      }
      container brief-rack {
        description
          "Show brief rack scope alarm related data.";
        container brief-numbers {
          description
            "Table of BriefNumber";
          list brief-number {
            key "rack-num";
            description
              "Specify a rack number for alarms.";
            container history {
              description
                "Show the history alarms at this scope.";
              uses ALARM-MGR-SHOW-ALARM-BRIEF-INFO;
            }
            container suppressed {
              description
                "Show the suppressed alarms at this scope.";
              uses ALARM-MGR-SHOW-ALARM-BRIEF-SUPPR-INFO;
            }
            container active {
              description
                "Show the active alarms at this scope.";
              uses ALARM-MGR-SHOW-ALARM-BRIEF-INFO;
            }
            leaf rack-num {
              type xr:Cisco-ios-xr-string;
              description
                "Rack Number";
            }
          }
        }
      }
      container brief-system {
        description
          "Show brief system scope alarm related data.";
        container history {
          description
            "Show the history alarms at this scope.";
          uses ALARM-MGR-SHOW-ALARM-BRIEF-INFO;
        }
        container conditions {
          description
            "Show the conditions present at this scope.";
          uses ALARM-MGR-SHOW-ALARM-BRIEF-INFO;
        }
        container suppressed {
          description
            "Show the suppressed alarms at this scope.";
          uses ALARM-MGR-SHOW-ALARM-BRIEF-SUPPR-INFO;
        }
        container active {
          description
            "Show the active alarms at this scope.";
          uses ALARM-MGR-SHOW-ALARM-BRIEF-INFO;
        }
      }
      container brief-card {
        description
          "Show brief card scope alarm related data.";
        container brief-locations {
          description
            "Table of BriefLocation";
          list brief-location {
            key "node-id";
            description
              "Specify a card location for alarms.";
            container history {
              description
                "Show the history alarms at this scope.";
              uses ALARM-MGR-SHOW-ALARM-BRIEF-INFO;
            }
            container conditions {
              description
                "Show the conditions present at this scope.";
              uses ALARM-MGR-SHOW-ALARM-BRIEF-INFO;
            }
            container suppressed {
              description
                "Show the suppressed alarms at this scope.";
              uses ALARM-MGR-SHOW-ALARM-BRIEF-SUPPR-INFO;
            }
            container active {
              description
                "Show the active alarms at this scope.";
              uses ALARM-MGR-SHOW-ALARM-BRIEF-INFO;
            }
            leaf node-id {
              type xr:Node-id;
              description
                "NodeID of the Location";
            }
          }
        }
      }
    }
  }
}
