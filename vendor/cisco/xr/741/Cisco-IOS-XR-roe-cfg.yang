module Cisco-IOS-XR-roe-cfg {
  namespace "http://cisco.com/ns/yang/Cisco-IOS-XR-roe-cfg";
  prefix roe-cfg;

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR roe package configuration.
     
     This module contains definitions
     for the following management objects:
       roe: ROE configuration data
     
     Copyright (c) 2013-2021 by Cisco Systems, Inc.
     All rights reserved.";

  revision 2021-05-10 {
    description
      "Added new leaf hfn-sync-disable to list profile.
       2021-05-03
         Added mapper,demapper roe-profile parameters presync-match-threshold, resync-match-threshold, resync-mismatch-threshold of task-name cisco-support. Added demapper roe-profile parameters sync-threshold, drain-threshold, presync-match-count, resync-match-count, resync-mismatch-count of task-name cisco-support.
       2020-10-29
         Removed enum 32 from type Roe-packet-length of leaf packet-length.
       2020-09-01
         Added default statements to leaves mapper-flow-id, demapper-flow-id, order-info, mapper-type, accept-time-window, sample-width, num-of-containers, num-of-ctrl-containers, num-of-prach, num-of-fft, retimer-buffer, idle-frame-size, idle-frame-threshold of list profile. Renamed enum both to sequence-num-and-time-stamp and removed enum time-stamp from type Roe-order-info. Removed enum native-timing and native-frequency from type Roe-mapper. Added range to leaves ethlink-id and profile-id. Changed type of leaf packet-length. Changed range of leaf ethlink-identifier. Changed range of idle-frame-threshold.
       2020-08-03
         Configure RoE packet length in terms of CPRI basic frames instead of bytes. RoE profile id range set from 1 to 255. RoE ethlink profile id range set to 1 to 65535";
    semver:module-version "2.0.0";
  }
  revision 2020-02-27 {
    description
      "Initial ROE config yang";
    semver:module-version "1.0.0";
  }
  revision 2019-04-05 {
    description
      "Establish semantic version baseline.";
  }
  revision 2015-11-09 {
    description
      "IOS XR 6.0 revision.";
  }

  typedef Roe-packet-length {
    type enumeration {
      enum "2" {
        value 2;
        description
          "Two CPRI basic frames";
      }
      enum "4" {
        value 4;
        description
          "Four CPRI basic frames";
      }
      enum "8" {
        value 8;
        description
          "Eight CPRI basic frames";
      }
      enum "16" {
        value 16;
        description
          "Sixteen CPRI basic frames";
      }
    }
    description
      "Roe packet length";
  }

  typedef Roe-order-info {
    type enumeration {
      enum "sequence-num" {
        value 0;
        description
          "Sequence Number";
      }
      enum "sequence-num-and-time-stamp" {
        value 2;
        description
          "Both sequence number and timestamp";
      }
    }
    description
      "Roe order info";
  }

  typedef Roe-mapper {
    type enumeration {
      enum "structure-agnostic-tunneling" {
        value 0;
        description
          "Structure agnostic tunneling mode";
      }
      enum "structure-agnostic-wo-line-coding" {
        value 1;
        description
          "Structure agnostic without line coding mode";
      }
      enum "structure-aware" {
        value 2;
        description
          "Structure aware mode";
      }
    }
    description
      "Roe mapper";
  }

  container roe {
    description
      "ROE configuration data";
    container ethlinks {
      description
        "List of ROE Eth link profiles";
      list ethlink {
        key "ethlink-id";
        description
          "ROE Eth link configuration parameters";
        leaf enable {
          type empty;
          description
            "Enable Ethlink submode";
        }
        leaf destination-mac {
          type yang:mac-address;
          description
            "Ethlink <id> destination MAC address";
        }
        leaf source-mac {
          type yang:mac-address;
          description
            "Ethlink <id> source MAC address";
        }
        leaf ethlink-id {
          type uint32 {
            range "1..65535";
          }
          description
            "Ethlink identifier";
        }
      }
    }
    container profiles {
      description
        "List of ROE Profile";
      list profile {
        key "profile-id";
        description
          "ROE profile parameters";
        leaf enable {
          type empty;
          description
            "Enable Profile submode";
        }
        leaf demapper-sync-threshold {
          type uint32 {
            range "4..63";
          }
          description
            "Demapper sync threshold";
        }
        leaf demapper-resync-match-threshold {
          type uint32 {
            range "0..15";
          }
          default "0";
          description
            "Demapper resync match threshold";
        }
        leaf mapper-presync-match-threshold {
          type uint32 {
            range "0..15";
          }
          default "0";
          description
            "Mapper presync match threshold";
        }
        leaf demapper-resync-mismatch-threshold {
          type uint32 {
            range "0..15";
          }
          default "0";
          description
            "Demapper resync mismatch threshold";
        }
        leaf compress {
          type uint32 {
            range "0..1";
          }
          default "0";
          description
            "enable/disable compression";
        }
        leaf hfn-sync-disable {
          type empty;
          description
            "Disable HFN sync. Applicable only for
             Structure Agnostic tunneling mode(Type-0)
             mapper type config in non auto-neg CPRI port";
        }
        leaf mapper-resync-mismatch-threshold {
          type uint32 {
            range "0..15";
          }
          default "0";
          description
            "Mapper resync mismatch threshold";
        }
        leaf sample-width {
          type uint32 {
            range "0..255";
          }
          default "16";
          description
            "Sample width";
        }
        leaf mapper-resync-match-threshold {
          type uint32 {
            range "0..15";
          }
          default "0";
          description
            "Mapper resync match threshold";
        }
        leaf demapper-presync-match-threshold {
          type uint32 {
            range "0..15";
          }
          default "0";
          description
            "Demapper presync match threshold";
        }
        leaf num-of-containers {
          type uint32 {
            range "0..255";
          }
          default "0";
          description
            "Number of Containers";
        }
        leaf num-of-prach {
          type uint32 {
            range "0..255";
          }
          default "0";
          description
            "Number of PRACH";
        }
        leaf num-of-fft {
          type uint32 {
            range "0..255";
          }
          default "0";
          description
            "Number of FFT";
        }
        leaf packet-length {
          type Roe-packet-length;
          default "4";
          description
            "Packet length in terms of CPRI basic frames";
        }
        leaf demapper-flow-id {
          type uint32 {
            range "0..255";
          }
          default "0";
          description
            "Demapper flow id";
        }
        leaf demapper-drain-threshold {
          type uint32 {
            range "4..64";
          }
          description
            "Demapper drain threshold";
        }
        leaf mapper-flow-id {
          type uint32 {
            range "0..255";
          }
          default "0";
          description
            "Mapper flow id";
        }
        leaf num-of-control-containers {
          type uint32 {
            range "0..255";
          }
          default "0";
          description
            "Number of control containers";
        }
        leaf demapper-resync-mismatch-count {
          type uint32 {
            range "0..15";
          }
          default "0";
          description
            "Demapper resync mismatch count";
        }
        leaf demapper-resync-match-count {
          type uint32 {
            range "0..15";
          }
          default "0";
          description
            "Demapper resync match count";
        }
        leaf mapper-type {
          type Roe-mapper;
          default "structure-agnostic-tunneling";
          description
            "Mapper type";
        }
        leaf idle-frame-size {
          type uint32 {
            range "0..255";
          }
          default "0";
          description
            "Idle Frame Size";
        }
        leaf accept-time-window {
          type uint32 {
            range "0..536870911";
          }
          default "0";
          description
            "Accept time window";
        }
        leaf order-info {
          type Roe-order-info;
          default "sequence-num";
          description
            "Order info type";
        }
        leaf ethlink-identifier {
          type uint32 {
            range "1..65535";
          }
          description
            "Ethlink profile attached to this ROE profile";
        }
        leaf idle-frame-threshold {
          type uint32 {
            range "0..1048575";
          }
          default "0";
          description
            "Idle frame threshold (in terms of number of
             packets)";
        }
        leaf retimer-buffer {
          type uint32 {
            range "0..255";
          }
          default "0";
          description
            "Retimer buffer";
        }
        leaf encrypt {
          type uint32 {
            range "0..1";
          }
          default "0";
          description
            "enable/disable encryption";
        }
        leaf demapper-presync-match-count {
          type uint32 {
            range "0..15";
          }
          default "0";
          description
            "Demapper presync match count";
        }
        leaf profile-id {
          type uint32 {
            range "1..255";
          }
          description
            "Profile identifier";
        }
      }
    }
  }
}
