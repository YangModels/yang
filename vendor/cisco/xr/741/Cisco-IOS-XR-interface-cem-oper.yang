module Cisco-IOS-XR-interface-cem-oper {
  namespace "http://cisco.com/ns/yang/Cisco-IOS-XR-interface-cem-oper";
  prefix interface-cem-oper;

  import Cisco-IOS-XR-types {
    prefix xr;
  }
  import cisco-semver {
    prefix semver;
  }
  include Cisco-IOS-XR-interface-cem-oper-sub2 {
    revision-date 2019-04-05;
  }
  include Cisco-IOS-XR-interface-cem-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR interface-cem package operational data.
     
     This module contains definitions
     for the following management objects:
       cem: CEM operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container cem {
    config false;
    description
      "CEM operational data";
    container cem-controllers {
      description
        "List of CEM interfaces";
      list cem-controller {
        key "interface-name";
        description
          "CEM interface name";
        container cem-recovered-clock-info {
          description
            "CEM Recovered clock information";
          uses CEM-RECOVERED-CLOCK-DATA;
        }
        container cem-info {
          description
            "CEM controller information";
          uses CEM-INFO;
        }
        leaf interface-name {
          type xr:Interface-name;
          description
            "Name of the CEM Interface";
        }
      }
    }
  }
}
