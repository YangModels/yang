module Cisco-IOS-XR-interface-cem-cfg {
  namespace "http://cisco.com/ns/yang/Cisco-IOS-XR-interface-cem-cfg";
  prefix interface-cem-cfg;

  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR interface-cem package configuration.
     
     This YANG module augments the
       Cisco-IOS-XR-ifmgr-cfg
     module with configuration data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Cem-if-dummy-mode {
    type enumeration {
      enum "last-frame" {
        value 0;
        description
          "Last frame";
      }
      enum "user-defined" {
        value 1;
        description
          "User defined";
      }
    }
    description
      "Cem if dummy mode";
  }

  typedef Cem-recover-clock {
    type enumeration {
      enum "adaptive" {
        value 1;
        description
          "Adaptive recover";
      }
      enum "differential" {
        value 2;
        description
          "Differential recover";
      }
    }
    description
      "Cem recover clock";
  }

  augment "/a1:interface-configurations/a1:interface-configuration" {
    description
      "This augment extends the configuration data of
       'Cisco-IOS-XR-ifmgr-cfg'";
    container cem {
      presence "CLI submode compatibility.";
      description
        "Configure CEM interface";
      container clock {
        description
          "Configure clock for this CEM interface";
        leaf recover-clock-type {
          type Cem-recover-clock;
          description
            "Configure the Recover clock type";
        }
      }
      container idle {
        description
          "Configure idle pattern";
        leaf pattern {
          type xr:Hex-integer;
          description
            "Idle pattern from 0x0 to 0xff";
        }
      }
      container dummy {
        description
          "Configure bit-pattern for filling in lost or
           corrupted frames";
        leaf pattern {
          type xr:Hex-integer;
          description
            "User defined bit pattern from 0x0 to 0xff for
             CEM frame";
        }
        leaf mode {
          type Cem-if-dummy-mode;
          description
            "Configure mode";
        }
      }
      leaf payload {
        type uint32 {
          range "32..500000";
        }
        description
          "Payload size in bytes";
      }
      leaf class {
        type string {
          length "1..80";
        }
        description
          "Attach a CEM class to this interface";
      }
      leaf dejitter {
        type uint32 {
          range "125..500000";
        }
        description
          "Dejitter buffer size in microseconds";
      }
    }
  }
}
