module Cisco-IOS-XR-fretta-npu-bandwidth-usage-oper {
  namespace "http://cisco.com/ns/yang/Cisco-IOS-XR-fretta-npu-bandwidth-usage-oper";
  prefix fretta-npu-bandwidth-usage-oper;

  import Cisco-IOS-XR-types {
    prefix xr;
  }
  import cisco-semver {
    prefix semver;
  }
  include Cisco-IOS-XR-fretta-npu-bandwidth-usage-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fretta-npu-bandwidth-usage package operational data.
     
     This module contains definitions
     for the following management objects:
       npu-bw-usage: NPU BW Usage Data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container npu-bw-usage {
    config false;
    description
      "NPU BW Usage Data";
    container nodes {
      description
        "NPU BW usage data for available nodes";
      list node {
        key "node-name";
        description
          "NPU BW usage data for a particular node";
        container bw-usage-detail-for-npu-ids {
          description
            "NPU BW usage detail info";
          list bw-usage-detail-for-npu-id {
            key "npu-id";
            description
              "BW usage detail info for a particular npu";
            leaf npu-id {
              type uint32;
              description
                "Npu number";
            }
            uses NPU-INTF-BANDWIDTH-USAGE-DETAIL;
          }
        }
        container bw-usage-brief-for-npu-ids {
          description
            "NPU BW usage brief info";
          list bw-usage-brief-for-npu-id {
            key "npu-id";
            description
              "BW usage brief info for a particular npu";
            leaf npu-id {
              type uint32;
              description
                "Npu number";
            }
            uses NPU-INTF-BANDWIDTH-USAGE;
          }
        }
        leaf node-name {
          type xr:Node-id;
          description
            "Node ID";
        }
      }
    }
  }
}
