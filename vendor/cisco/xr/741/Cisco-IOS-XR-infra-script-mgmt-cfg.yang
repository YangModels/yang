module Cisco-IOS-XR-infra-script-mgmt-cfg {
  namespace "http://cisco.com/ns/yang/Cisco-IOS-XR-infra-script-mgmt-cfg";
  prefix infra-script-mgmt-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-script-mgmt package configuration.
     
     This module contains definitions
     for the following management objects:
       scripts: Script-mgmt configuration data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Config-checksum {
    type enumeration {
      enum "disable-checksum-security" {
        value 0;
        description
          "Disable checksum";
      }
      enum "sha256" {
        value 1;
        description
          "SHA256";
      }
    }
    description
      "Config checksum";
  }

  grouping SCRIPT-TABLE {
    description
      "Common node of exec-script, process-script";
    container scripts {
      description
        "Name of script";
      list script {
        key "script-name";
        description
          "Config Script activation item";
        container checksum {
          description
            "Checksum of script";
          leaf checksum-type {
            type Config-checksum;
            description
              "Checksum type";
          }
          leaf checksum {
            when "../checksum-type != 'disable-checksum-security'" {
              description
                "../ChecksumType != DISABLE-CHECKSUM-SECURITY";
            }
            type string;
            description
              "Checksum value";
          }
        }
        leaf script-name {
          type xr:Cisco-ios-xr-string;
          description
            "Script name";
        }
      }
    }
  }

  container scripts {
    description
      "Script-mgmt configuration data";
    container exec-script {
      description
        "Exec script";
      uses SCRIPT-TABLE;
    }
    container process-script {
      description
        "Process script";
      uses SCRIPT-TABLE;
    }
  }
}
