module Cisco-IOS-XR-sysadmin-fabric-driver-sfe {
  namespace "http://www.cisco.com/ns/yang/Cisco-IOS-XR-sysadmin-fabric-driver-sfe";
  prefix fabric_sfe;

  import Cisco-IOS-XR-sysadmin-fabric-types {
    prefix fabric-types;
  }
  import Cisco-IOS-XR-sysadmin-show-trace {
    prefix show-trace;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2021-02-05 {
    description
      "Added new header field to link-info CLI";
    semver:module-version "2.0.0";
  }
  revision 2020-01-08 {
    description
      "To display CXP and Lane info in sfe link-info CLI";
    semver:module-version "2.0.0";
  }
  revision 2019-05-20 {
    description
      "To display Near-end link's bundle and lane info in SFE link-info topo detail CLI";
    semver:module-version "2.0.0";
  }
  revision 2019-04-15 {
    description
      "Establish semantic version baseline.";
    semver:module-version "1.0.0";
  }
  revision 2018-04-09 {
    description
      "Required changes for ConfD 6.4.5";
  }
  revision 2017-09-30 {
    description
      "Add fsm-state as a leaf to ensure compilation";
  }
  revision 2017-05-01 {
    description
      "Namespace change to comply with Cisco guidelines on namespace";
  }

  grouping sfe_drvr_info {
    list drvr_info {
      key "idx";
      leaf idx {
        type int32;
      }
      leaf drv_version {
        type uint32;
      }
      leaf coeff_major_rev {
        type uint32;
      }
      leaf coeff_minor_rev {
        type uint32;
      }
      leaf func_role {
        type string;
      }
      leaf issu_role {
        type string;
      }
      leaf rack_name {
        type string;
      }
      leaf rack_type {
        type string;
      }
      leaf rack_num {
        type string;
      }
      leaf ip_address {
        type string;
      }
      leaf card_avail_mask {
        type uint32;
      }
      leaf asic_avail_mask {
        type uint64;
      }
      leaf exp_asic_avail_mask {
        type uint64;
      }
      leaf ucmc_ratio {
        type uint32;
      }
      leaf pm_conn_active {
        type boolean;
      }
      leaf platform_local_conn_active {
        type boolean;
      }
      leaf fsdb_conn_active {
        type boolean;
      }
      leaf fgid_conn_active {
        type boolean;
      }
      leaf cm_conn_active {
        type boolean;
      }
      leaf ccc_conn_active {
        type boolean;
      }
      leaf issu_mgr_conn_active {
        type boolean;
      }
      leaf peer_sfe_conn_active {
        type boolean;
      }
      leaf cxp_conn_active {
        type boolean;
      }
      leaf pm_reg_active {
        type boolean;
      }
      leaf platform_local_reg_active {
        type boolean;
      }
      leaf fsdb_reg_active {
        type boolean;
      }
      leaf fgid_reg_active {
        type boolean;
      }
      leaf cm_reg_active {
        type boolean;
      }
      leaf issu_mgr_reg_active {
        type boolean;
      }
      leaf peer_sfe_reg_active {
        type boolean;
      }
      leaf cxp_reg_active {
        type boolean;
      }
      leaf num_pm_conn_reqs {
        type uint8;
      }
      leaf num_platform_local_conn_reqs {
        type uint8;
      }
      leaf num_fsdb_conn_reqs {
        type uint8;
      }
      leaf num_fgid_conn_reqs {
        type uint8;
      }
      leaf num_fstats_conn_reqs {
        type uint8;
      }
      leaf num_cm_conn_reqs {
        type uint8;
      }
      leaf num_ccc_conn_reqs {
        type uint8;
      }
      leaf num_issu_mgr_conn_reqs {
        type uint8;
      }
      leaf num_peer_sfe_conn_reqs {
        type uint8;
      }
      leaf num_cxp_conn_reqs {
        type uint8;
      }
      leaf is_gaspp_registered {
        type boolean;
      }
      leaf is_cih_registered {
        type boolean;
      }
      leaf startup_time {
        type string;
      }
      list asic_list {
        key "asic_idx";
        leaf asic_idx {
          type uint32;
        }
        leaf asic_instance {
          type string;
        }
        leaf card_present {
          type string;
        }
        leaf card_powered {
          type string;
        }
        leaf hotplug_event {
          type uint32;
        }
        leaf asic_type {
          type string;
        }
        leaf asic_cardname {
          type string;
        }
        leaf admin-state {
          type string;
        }
        leaf oper_state {
          type string;
        }
        leaf fab_plane {
          type string;
        }
        leaf fab_group {
          type string;
        }
        leaf fgid_download {
          type string;
        }
        leaf asic_state {
          type string;
        }
        leaf asic_disconnect_signal {
          type string;
        }
        leaf last_init_cause {
          type string;
        }
        leaf num_pon_resets {
          type uint32;
        }
        leaf num_hard_resets {
          type uint32;
        }
      }
    }
  }

  grouping sfe_link_info_asic_instance {
    list instance {
      key "instance-id";
      leaf instance-id {
        type fabric-types:sfe_instance_type;
      }
      leaf nodeid_str {
        type string;
      }
      leaf is_show {
        type boolean;
      }
      list link_idx_list {
        key "link_idx";
        leaf link_idx {
          type int64;
        }
        leaf link_id_str {
          type string;
        }
        leaf phy_link {
          type string;
        }
        leaf speed {
          type string;
        }
        leaf stage {
          type string;
        }
        leaf fab_plane {
          type uint32;
        }
        leaf fab_group {
          type uint32;
        }
        leaf flap_cnt {
          type uint32;
        }
        leaf num_admin_shuts {
          type uint32;
        }
        leaf admin-state {
          type string;
        }
        leaf oper_state {
          type string;
        }
        leaf flags {
          type string;
        }
        leaf far_end_link_fsdb {
          type string;
        }
        leaf far_end_link_hw {
          type string;
        }
        leaf link_cxp_port {
          type string;
        }
        leaf link_cxp_lane {
          type string;
        }
        leaf coeff1 {
          type uint32;
        }
        leaf coeff2 {
          type uint32;
        }
        leaf TX_Control_cells_counter {
          type uint64;
        }
        leaf TX_Data_cell_counter {
          type uint64;
        }
        leaf TX_Data_byte_counter {
          type uint64;
        }
        leaf TX_BEC_retransmit {
          type uint64;
        }
        leaf TX_Asyn_fifo_rate {
          type uint64;
        }
        leaf RX_Control_cells_counter {
          type uint64;
        }
        leaf RX_Data_cell_counter {
          type uint64;
        }
        leaf RX_Data_byte_counter {
          type uint64;
        }
        leaf RX_BEC_retransmit {
          type uint64;
        }
        leaf RX_Asyn_fifo_rate {
          type uint64;
        }
        leaf RX_CRC_errors_counter {
          type uint64;
        }
        leaf RX_LFEC_FEC_correctable_error {
          type uint64;
        }
        leaf RX_LFEC_FEC_uncorrectable_errors {
          type uint64;
        }
        leaf RX_dropped_retransmitted_control {
          type uint64;
        }
        leaf fsm_state {
          type string;
        }
        list history {
          key "history_idx";
          leaf history_idx {
            type int32;
          }
          leaf time_stamp {
            type string;
          }
          leaf admin-state {
            type string;
          }
          leaf oper_state {
            type string;
          }
          leaf error_state {
            type string;
          }
          leaf down_reasons {
            type string;
          }
        }
      }
    }
  }

  grouping sfe_link_info_stats_asic_instance {
    container stats {
      container data {
        uses sfe_link_info_asic_instance;
      }
      container ctrl {
        uses sfe_link_info_asic_instance;
      }
      container all {
        uses sfe_link_info_asic_instance;
      }
    }
  }

  grouping sfe_statistics_asic_instance {
    list instance {
      key "instance-id";
      leaf instance-id {
        type fabric-types:sfe_instance_type;
      }
      leaf stats_output {
        type string;
      }
    }
  }

  grouping sfe_trace {
    container sfe_driver {
      uses show-trace:traceable;
    }
  }

  grouping sfe_parse_link_instance {
    list instance {
      key "instance-id";
      leaf instance-id {
        type fabric-types:sfe_instance_type;
      }
      leaf is_show {
        type boolean;
      }
      list link_idx_list {
        key "link_idx";
        leaf link_idx {
          type int64;
        }
        leaf rack_id_str {
          type string;
        }
        leaf slot_id_str {
          type string;
        }
        leaf asic_inst_id {
          type uint32;
        }
        leaf link_num_id {
          type uint32;
        }
        leaf log_slot {
          type uint32;
        }
        leaf phy_slot {
          type uint32;
        }
        leaf fap_id {
          type uint32;
        }
        leaf unit {
          type uint32;
        }
        leaf sfi_id {
          type uint32;
        }
        leaf ip_addr {
          type string;
        }
        leaf driver_run {
          type string;
        }
      }
    }
  }

  grouping sfe {
    container sfe {
      description
        "Fabric SFE driver commands";
      container driver {
        list rack {
          key "rack_num";
          leaf rack_num {
            type fabric-types:fabric_rack_num_type;
          }
          leaf description {
            type string;
            default "rack no.";
          }
          uses sfe_drvr_info;
        }
      }
      container statistics {
        list location {
          key "loc_str";
          leaf loc_str {
            type fabric-types:sfe_location_type;
          }
          leaf description {
            type string;
            default "location (R/S).";
          }
          list asic_types {
            key "asicname";
            leaf asicname {
              type string;
            }
            list block {
              key "blockname";
              leaf blockname {
                type string;
              }
              uses sfe_statistics_asic_instance;
            }
          }
        }
      }
      container link-info {
        list location {
          key "loc_str";
          leaf loc_str {
            type fabric-types:sfe_location_type;
          }
          leaf description {
            type string;
            default "location (R/S)";
          }
          list rx {
            key "start end";
            leaf start {
              type fabric-types:sfe_link_type;
            }
            leaf end {
              type fabric-types:sfe_link_type;
            }
            container detail {
              container topo {
                uses sfe_link_info_asic_instance;
              }
              container flap {
                uses sfe_link_info_asic_instance;
              }
            }
            container topo {
              uses sfe_link_info_asic_instance;
            }
            container flap {
              uses sfe_link_info_asic_instance;
            }
            uses sfe_link_info_stats_asic_instance;
          }
          list tx {
            key "start end";
            leaf start {
              type fabric-types:sfe_link_type;
            }
            leaf end {
              type fabric-types:sfe_link_type;
            }
            container detail {
              uses sfe_link_info_asic_instance;
            }
            uses sfe_link_info_asic_instance;
            uses sfe_link_info_stats_asic_instance;
          }
        }
      }
      container diagshell {
        list location {
          key "loc_str";
          leaf loc_str {
            type fabric-types:sfe_location_type;
          }
          leaf description {
            type string;
            default "location (R/S)";
          }
          list instance {
            key "instance_num";
            leaf instance_num {
              type fabric-types:fabric_diag_shell_instance_num_type;
            }
            list diag_cmd {
              key "cmd_str";
              leaf cmd_str {
                type fabric-types:fabric_diag_shell_cmd_type;
              }
              list bytes {
                key "byte_idx";
                leaf byte_idx {
                  type int64;
                }
                leaf data {
                  type string;
                }
              }
            }
          }
        }
      }
      container register {
        list location {
          key "loc_str";
          leaf loc_str {
            type fabric-types:sfe_location_type;
          }
          leaf description {
            type string;
            default "location (R/S)";
          }
          list instance {
            key "instance_num";
            leaf instance_num {
              type fabric-types:fabric_diag_shell_instance_num_type;
            }
            list bytes {
              key "byte_idx";
              leaf byte_idx {
                type int64;
              }
              leaf data {
                type string;
              }
            }
          }
        }
      }
      container dump-file {
        list location {
          key "loc_str";
          leaf loc_str {
            type fabric-types:sfe_location_type;
          }
          leaf description {
            type string;
            default "location (R/S)";
          }
          list file {
            key "file_name";
            leaf file_name {
              type string;
            }
            list bytes {
              key "byte_idx";
              leaf byte_idx {
                type int64;
              }
              leaf data {
                type string;
              }
            }
          }
        }
      }
      container parse {
        list location {
          key "loc_str";
          leaf loc_str {
            type fabric-types:sfe_location_type;
          }
          leaf description {
            type string;
            default "location (R/S)";
          }
          list link {
            key "start end";
            leaf start {
              type fabric-types:sfe_link_type;
            }
            leaf end {
              type fabric-types:sfe_link_type;
            }
            uses sfe_parse_link_instance;
          }
        }
      }
    }
    container sfe_trace {
      uses sfe_trace;
    }
  }
}
