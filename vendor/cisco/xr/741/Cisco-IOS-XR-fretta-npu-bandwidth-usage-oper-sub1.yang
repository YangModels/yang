submodule Cisco-IOS-XR-fretta-npu-bandwidth-usage-oper-sub1 {
  belongs-to Cisco-IOS-XR-fretta-npu-bandwidth-usage-oper {
    prefix Cisco-IOS-XR-fretta-npu-bandwidth-usage-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fretta-npu-bandwidth-usage package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping NPU-INTF-BANDWIDTH-USAGE {
    description
      "NPU INTF BANDWIDTH USAGE";
    leaf total-bw {
      type uint32;
      description
        "Total Bandwidth";
    }
    leaf used-bw {
      type uint32;
      description
        "Used Bandwidth";
    }
    leaf available-bw {
      type uint32;
      description
        "Available Bandwidth";
    }
  }

  grouping BW-USAGE-STATUS-INFO {
    description
      "BW USAGE STATUS INFO";
    leaf type {
      type string {
        length "0..32";
      }
      description
        "Bandwidth Type";
    }
    leaf status {
      type string {
        length "0..32";
      }
      description
        "Bandwidth allocation staus";
    }
  }

  grouping BW-USAGE-PORT-INFO {
    description
      "BW USAGE PORT INFO";
    leaf port-name {
      type string {
        length "0..32";
      }
      description
        "Port Name";
    }
    list bw-info {
      description
        "Port Bandwidth information";
      uses BW-USAGE-STATUS-INFO;
    }
  }

  grouping BW-USAGE-INST-INFO {
    description
      "BW USAGE INST INFO";
    list port-info {
      description
        "Port information";
      uses BW-USAGE-PORT-INFO;
    }
  }

  grouping NPU-INTF-BANDWIDTH-USAGE-DETAIL {
    description
      "NPU INTF BANDWIDTH USAGE DETAIL";
    list inst-info {
      description
        "Instance information";
      uses BW-USAGE-INST-INFO;
    }
  }
}
