module Cisco-IOS-XR-envmon-cfg {
  namespace "http://cisco.com/ns/yang/Cisco-IOS-XR-envmon-cfg";
  prefix envmon-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR envmon package configuration.
     
     This module contains definitions
     for the following management objects:
       environmental-monitoring: Environmental Monitoring Operational
         data space
     
     Copyright (c) 2013-2020 by Cisco Systems, Inc.
     All rights reserved.";

  revision 2020-09-08 {
    description
      "IOS XR 7.3.1 revision. Added Alarm port config.";
    semver:module-version "1.2.0";
  }
  revision 2019-10-15 {
    description
      "IOS XR 7.0.12 revision. Added chassis door alarm.";
    semver:module-version "1.1.0";
  }
  revision 2019-04-05 {
    description
      "Establish semantic version baseline.";
    semver:module-version "1.0.0";
  }
  revision 2015-11-09 {
    description
      "IOS XR 6.0 revision.";
  }

  typedef Description-str {
    type string {
      length "1..80";
    }
    description
      "Description str";
  }

  typedef Trigger-state {
    type enumeration {
      enum "open" {
        value 0;
        description
          "Trigger on Open";
      }
      enum "closed" {
        value 1;
        description
          "Trigger is Closed";
      }
    }
    description
      "Trigger state";
  }

  typedef Severity {
    type string {
      pattern "(minor)|(major)|(critical)";
    }
    description
      "minor: minor alarm, major: major alarm, critical:
       critical alarm";
  }

  container environmental-monitoring {
    description
      "Environmental Monitoring Operational data space";
    container fan-ctrl-optics {
      status deprecated;
      description
        "Control chassis fan status";
      leaf enable {
        type boolean;
        default "false";
        status deprecated;
        description
          "Enable or disable higher fan speed";
      }
    }
    container air-filter {
      description
        "Chassis air-filter status";
      container replaced {
        description
          "air-filter replaced date";
        leaf date {
          type string;
          description
            "CCYY-MM-DD format";
        }
      }
    }
    container chassis-door-alarm {
      description
        "Control chassis door alarm";
      leaf enable {
        type boolean;
        default "false";
        description
          "Enable or disable chassis door alarm";
      }
    }
    container alarm-contacts {
      description
        "Control alarm port behavior";
      list alarm-contact {
        key "name";
        description
          "Alarm port number";
        leaf severity {
          type Severity;
          description
            "Trigger on open or close";
        }
        leaf description {
          type Description-str;
          description
            "Description of the alarm";
        }
        leaf trigger {
          type Trigger-state;
          default "open";
          description
            "Trigger alarm on pin open or closed";
        }
        leaf name {
          type uint32;
          description
            "Alarm contact number";
        }
      }
    }
    leaf min-fan-speed {
      type uint32 {
        range "0..100";
      }
      description
        "Min default fan speed in PWM";
    }
  }
}
