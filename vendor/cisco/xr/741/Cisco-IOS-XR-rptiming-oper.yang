module Cisco-IOS-XR-rptiming-oper {
  namespace "http://cisco.com/ns/yang/Cisco-IOS-XR-rptiming-oper";
  prefix rptiming-oper;

  import Cisco-IOS-XR-types {
    prefix xr;
  }
  import cisco-semver {
    prefix semver;
  }
  include Cisco-IOS-XR-rptiming-oper-sub1 {
    revision-date 2020-05-29;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR rptiming package operational data.
     
     This module contains definitions
     for the following management objects:
       timing-card: Timing PLL status and configuration
     
     Copyright (c) 2013-2020 by Cisco Systems, Inc.
     All rights reserved.";

  revision 2020-05-29 {
    description
      "Added/Modified to clear the inconsistencies";
    semver:module-version "1.0.0";
  }
  revision 2019-04-05 {
    description
      "Establish semantic version baseline.";
  }
  revision 2015-11-09 {
    description
      "IOS XR 6.0 revision.";
  }

  container timing-card {
    config false;
    description
      "Timing PLL status and configuration";
    container nodes {
      description
        "List of nodes applicable to timing";
      list node {
        key "node-name";
        description
          "Timing operational data for a single node";
        container pll-dump {
          description
            "Display the timing card PLL dump information";
          uses TMG-PLL-DUMP;
        }
        container input-clock {
          description
            "Display the timing card input clock status
             information";
          uses TMG-CLKIN-INFO;
        }
        container tod {
          description
            "Display the timing card ToD information";
          uses TMG-TOD-INFO;
        }
        container pll {
          description
            "Display the timing card PLL status information";
          uses TMG-PLL-INFO;
        }
        leaf node-name {
          type xr:Node-id;
          description
            "Node Name";
        }
      }
    }
  }
}
