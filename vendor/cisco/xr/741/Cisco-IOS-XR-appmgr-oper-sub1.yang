submodule Cisco-IOS-XR-appmgr-oper-sub1 {
  belongs-to Cisco-IOS-XR-appmgr-oper {
    prefix Cisco-IOS-XR-appmgr-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR appmgr package operational data.
     
     Copyright (c) 2013-2021 by Cisco Systems, Inc.
     All rights reserved.";

  revision 2021-03-01 {
    description
      "Adding information about installed packages";
    semver:module-version "1.0.0";
  }
  revision 2021-02-15 {
    description
      "Support for process scripts.";
  }
  revision 2019-04-05 {
    description
      "Establish semantic version baseline.";
  }
  revision 2015-11-09 {
    description
      "IOS XR 6.0 revision.";
  }

  typedef Appmgr-app-state {
    type enumeration {
      enum "deactivated" {
        value 1;
        description
          "Deactivated";
      }
      enum "activated" {
        value 2;
        description
          "Activated";
      }
      enum "error" {
        value 4;
        description
          "Error";
      }
    }
    description
      "Appmgr application state";
  }

  typedef Appmgr-app {
    type enumeration {
      enum "docker" {
        value 1;
        description
          "Docker";
      }
      enum "rpm" {
        value 2;
        description
          "RPM";
      }
      enum "native" {
        value 3;
        description
          "Native";
      }
    }
    description
      "Appmgr application type";
  }

  typedef Package {
    type string;
    description
      "Package";
  }

  grouping VRF-RELAY-INFO {
    description
      "VRF Forwarding Relay information.";
    leaf name {
      type string;
      description
        "Container Name";
    }
    leaf status {
      type string;
      description
        "Vrf Forwarding Relay status.";
    }
    leaf error-info {
      type string;
      description
        "Vrf Forwarding Relay error information.";
    }
    leaf src-vrf {
      type string;
      description
        "Source VRF.";
    }
    leaf src-port {
      type string;
      description
        "Source Port.";
    }
    leaf dest-vrf {
      type string;
      description
        "Destination VRF.";
    }
    leaf dest-port {
      type string;
      description
        "Destination Port.";
    }
    leaf ip-range {
      type string;
      description
        "IP address range";
    }
  }

  grouping DOCKER-INFO {
    description
      "Docker container info";
    leaf id {
      type string;
      description
        "Container ID";
    }
    leaf image {
      type string;
      description
        "Image ID";
    }
    leaf command {
      type string;
      description
        "Quoted command";
    }
    leaf created-at {
      type string;
      description
        "Time when the container was created";
    }
    leaf running-for {
      type string;
      description
        "Elapsed time since the container was started.";
    }
    leaf ports {
      type string;
      description
        "Exposed ports.";
    }
    leaf status {
      type string;
      description
        "Container status.";
    }
    leaf size {
      type string;
      description
        "Container disk size.";
    }
    leaf names {
      type string;
      description
        "Container names.";
    }
    leaf labels {
      type string;
      description
        "All labels assigned to the container.";
    }
    leaf mounts {
      type string;
      description
        "Names of the volumes mounted in this container.";
    }
    leaf networks {
      type string;
      description
        "Names of the networks attached to this container
         .";
    }
    leaf local-volumes {
      type string;
      description
        "Names of the local volumes mounted in this
         container";
    }
    list vrf-relay-info {
      description
        "VRF forwarding relay information";
      uses VRF-RELAY-INFO;
    }
  }

  grouping APPMGR-VAR-INFO {
    description
      "Appmgr App Variable Info";
    container docker-info {
      when "../type = 'docker'" {
        description
          "../Type = 'Docker'";
      }
      description
        "Details of docker applications";
      uses DOCKER-INFO;
    }
    leaf type {
      type Appmgr-app;
      description
        "Type";
    }
  }

  grouping APPMGR-APP-INFO {
    description
      "Information about an Application managed by the
       App Mgr";
    container var-info {
      description
        "App Variable Info";
      uses APPMGR-VAR-INFO;
    }
    leaf name {
      type string;
      description
        "Application name";
    }
    leaf type {
      type Appmgr-app;
      description
        "Application type";
    }
    leaf source {
      type string;
      description
        "Application source";
    }
    leaf config-state {
      type Appmgr-app-state;
      description
        "Application config state";
    }
    leaf error-info {
      type string;
      description
        "App Error Info";
    }
  }

  grouping BAG-DOCKER-STATS {
    description
      "Docker stats output";
    leaf container {
      type string;
      description
        "Container name or ID (user input)";
    }
    leaf name {
      type string;
      description
        "Container name";
    }
    leaf id {
      type string;
      description
        "Container ID";
    }
    leaf cpu-perc {
      type string;
      units "percentage";
      description
        "CPU percentage";
    }
    leaf mem-usage {
      type string;
      description
        "Memory usage";
    }
    leaf net-io {
      type string;
      description
        "Network IO";
    }
    leaf block-io {
      type string;
      description
        "Block IO";
    }
    leaf mem-perc {
      type string;
      units "percentage";
      description
        "Memory percentage";
    }
    leaf pids {
      type string;
      description
        "Number of PIDs";
    }
  }

  grouping APPMGR-VAR-STATS {
    description
      "Appmgr App Variable Stats";
    container docker-stats {
      when "../type = 'docker'" {
        description
          "../Type = 'Docker'";
      }
      description
        "Stats for docker applications";
      uses BAG-DOCKER-STATS;
    }
    leaf type {
      type Appmgr-app;
      description
        "Type";
    }
  }

  grouping APPMGR-APP-STATS {
    description
      "Stats for an Application managed by the App Mgr";
    container var-stats {
      description
        "App Variable Stats";
      uses APPMGR-VAR-STATS;
    }
  }

  grouping APPMGR-SOURCE {
    description
      "Information about an installed source.";
    leaf name-xr {
      type string;
      description
        "Source name";
    }
    leaf file {
      type string;
      description
        "Source file";
    }
    leaf package {
      type Package;
      description
        "Parent package";
    }
  }

  grouping APPMGR-PACKAGES {
    description
      "Installed packages";
    leaf-list package {
      type Package;
      description
        "Packages";
    }
  }
}
