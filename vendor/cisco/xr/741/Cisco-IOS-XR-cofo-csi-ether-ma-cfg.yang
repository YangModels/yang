module Cisco-IOS-XR-cofo-csi-ether-ma-cfg {
  namespace "http://cisco.com/ns/yang/Cisco-IOS-XR-cofo-csi-ether-ma-cfg";
  prefix cofo-csi-ether-ma-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cofo-csi-ether-ma package configuration.
     
     This YANG module augments the
       Cisco-IOS-XR-ifmgr-cfg
     module with configuration data.
     
     Copyright (c) 2013-2019 by Cisco Systems, Inc.
     All rights reserved.";

  revision 2019-06-16 {
    description
      "Enhancement to support configuration of CSI-Ether MTU";
    semver:module-version "1.0.0";
  }
  revision 2019-04-05 {
    description
      "Establish semantic version baseline.";
  }
  revision 2015-11-09 {
    description
      "IOS XR 6.0 revision.";
  }

  augment "/a1:interface-configurations/a1:interface-configuration" {
    description
      "This augment extends the configuration data of
       'Cisco-IOS-XR-ifmgr-cfg'";
    container csi-ether {
      description
        "Interface CSI ETHER configuration data";
      leaf mtu {
        type uint32 {
          range "64..9500";
        }
        description
          "MTU Setting of Interface";
      }
    }
  }
}
