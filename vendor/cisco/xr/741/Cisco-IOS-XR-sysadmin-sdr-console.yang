module Cisco-IOS-XR-sysadmin-sdr-console {
  namespace "http://www.cisco.com/ns/yang/Cisco-IOS-XR-sysadmin-sdr-console";
  prefix sdr_console;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright (c) 2015-2020 by Cisco Systems, Inc.
     All rights reserved.";

  revision 2020-04-29 {
    description
      "Fixed sdr config error for B0 and D0";
    semver:module-version "2.0.0";
  }
  revision 2019-04-15 {
    description
      "Establish semantic version baseline.";
    semver:module-version "1.0.0";
  }
  revision 2018-04-09 {
    description
      "Required changes for ConfD 6.4.5";
  }
  revision 2017-12-05 {
    description
      "Removed cli-incomplete-command statement";
  }
  revision 2017-07-22 {
    description
      "Updated location pattern to include Compute Cards";
  }
  revision 2017-04-12 {
    description
      "Changed the namespace and module name";
  }
  revision 2015-05-11 {
    description
      "Initial version.";
  }

  grouping console-attach-config-group {
    container attach-sdr {
      container runtime {
        list location {
          key "location-rp";
          leaf location-rp {
            type string {
              pattern "((0?[0-9]|1[1-5]|([bB]|[dD])\\d)/(([rR][pP]|[cC][bB])\\d{1,2}))(/[cC][pP][uU]0)?";
            }
          }
          list tty-name {
            key "ttyname";
            leaf ttyname {
              type string {
                length "1..30";
                pattern "console1|console2";
              }
            }
            leaf sdr-name {
              type string {
                length "1..30";
                pattern "[a-zA-Z0-9_.{}+-]+";
              }
            }
          }
        }
      }
      container boot {
        list location {
          key "location-rp";
          leaf location-rp {
            type string {
              pattern "((0?[0-9]|1[1-5]|([bB]|[dD])\\d)/(([rR][pP]|[cC][bB])\\d{1,2}))(/[cC][pP][uU]0)?";
            }
          }
          leaf sdr-name {
            type string {
              length "1..30";
              pattern "[a-zA-Z0-9_.{}+-]+";
            }
          }
        }
      }
    }
  }
}
