module Cisco-IOS-XR-cfgmgr-rollback-act {
  namespace "http://cisco.com/ns/yang/Cisco-IOS-XR-cfgmgr-rollback-act";
  prefix rollback-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2016-2019 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2016-04-17 {
    description
      "IOS XR 6.1.1 revision.";
  }

  grouping ROLLBACK-ATTRIBUTES {
    description
      "Rollback Attributes";
    leaf force {
      when "../best-effort = 'false'" {
        description
          "Only when best-effort is false.";
      }
      type boolean;
      default "false";
      description
        "Override commit blocks";
    }
    leaf best-effort {
      when "../force = 'false'" {
        description
          "Only when force is false.";
      }
      type boolean;
      default "false";
      description
        "Rollback via best-effort operation";
    }
    leaf label {
      type string;
      description
        "Assign a label to this rollback";
    }
    leaf comment {
      type string;
      description
        "Assign a comment to this rollback";
    }
  }

  rpc roll-back-configuration-last {
    description
      "Rollback last <n> commits made";
    input {
      leaf count {
        type int32 {
          range "1..100";
        }
        mandatory true;
        description
          "Number of commits to rollback";
      }
      uses ROLLBACK-ATTRIBUTES;
    }
  }
  rpc roll-back-configuration-to {
    description
      "Rollback up to (and including) a specific commit";
    input {
      leaf commit-id {
        type string;
        mandatory true;
        description
          "Commit ID";
      }
      uses ROLLBACK-ATTRIBUTES;
    }
  }
  rpc roll-back-configuration-to-exclude {
    description
      "Rollback up to (and excluding) a specific commit";
    input {
      leaf commit-id {
        type string;
        mandatory true;
        description
          "Commit ID";
      }
      uses ROLLBACK-ATTRIBUTES;
    }
  }
  rpc roll-back-configuration {
    description
      "Rollback a specific commit";
    input {
      leaf commit-id {
        type string;
        mandatory true;
        description
          "Commit ID";
      }
      uses ROLLBACK-ATTRIBUTES;
    }
  }
}
