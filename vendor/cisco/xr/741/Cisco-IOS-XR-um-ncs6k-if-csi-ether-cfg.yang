module Cisco-IOS-XR-um-ncs6k-if-csi-ether-cfg {
  namespace "http://cisco.com/ns/yang/Cisco-IOS-XR-um-ncs6k-if-csi-ether-cfg";
  prefix um-ncs6k-if-csi-ether-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs6k-if-csi-ether package configuration.
     
     This YANG module augments the
     modules with configuration data.
     
     Copyright (c) 2020-2021 by Cisco Systems, Inc.
     All rights reserved.";

  revision 2020-09-23 {
    description
      "Initial release";
    semver:module-version "1.0.0";
  }

  grouping IF-BODY {
    container csi-ether {
      when "../a1:interface-name[starts-with(text(),'CSI-Ether')]" {
        tailf:dependency "../a1:interface-name";
      }
      description
        "CSI-Ether interface subcommands";
      leaf mtu {
        type uint32 {
          range "64..9500" {
            description
              "MTU size in bytes";
          }
        }
        description
          "Set the CSI Ether MA MTU";
      }
    }
  }

  augment "/a1:interfaces/a1:interface" {
    uses IF-BODY;
  }
  augment "/a1:interfaces/a1:interface-preconfigure" {
    uses IF-BODY;
  }
}
