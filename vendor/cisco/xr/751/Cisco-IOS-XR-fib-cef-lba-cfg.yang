module Cisco-IOS-XR-fib-cef-lba-cfg {
  namespace "http://cisco.com/ns/yang/Cisco-IOS-XR-fib-cef-lba-cfg";
  prefix fib-cef-lba-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fib-cef-lba package configuration.
     
     This module contains definitions
     for the following management objects:
       fiblb: FIB load-balancing
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Cef-load-balance-layer {
    type enumeration {
      enum "l3" {
        value 0;
        description
          "Layer 3 load balancing";
      }
      enum "l4" {
        value 1;
        description
          "Layer 3 and layer 4 load balancing";
      }
    }
    description
      "Cef load balance layer";
  }

  container fiblb {
    description
      "FIB load-balancing";
    leaf fields {
      type Cef-load-balance-layer;
      description
        "Specify number of fields used for the load
         balancing";
    }
    leaf payload {
      type empty;
      description
        "If set, Payload Load-Balancing 'L2' is enabled";
    }
  }
}
