module Cisco-IOS-XR-um-subscriber-cfg {
  namespace "http://cisco.com/ns/yang/Cisco-IOS-XR-um-subscriber-cfg";
  prefix um-subscriber-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber package configuration.
     
     This YANG module augments the
     modules with configuration data.
     
     Copyright (c) 2020 by Cisco Systems, Inc.
     All rights reserved.";

  revision 2020-08-11 {
    description
      "Initial release";
    semver:module-version "1.0.0";
  }

  container subscriber {
    description
      "Subscriber Configuration";
    container database {
      description
        "subdb batching configuration";
      leaf batch-control {
        type uint32 {
          range "0..4" {
            description
              "higher level, better batching, more delay. <0 - disable>";
          }
        }
        description
          "batching performance control";
      }
      leaf backpressure-level {
        type uint32 {
          range "0..3" {
            description
              "0 - disable, 1 - gentle, 3 - aggressive";
          }
        }
        description
          "backpressure level";
      }
    }
  }
}
