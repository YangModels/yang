module Cisco-IOS-XR-cnbng-nal-oper {
  namespace "http://cisco.com/ns/yang/Cisco-IOS-XR-cnbng-nal-oper";
  prefix cnbng-nal-oper;

  import Cisco-IOS-XR-types {
    prefix xr;
  }
  import cisco-semver {
    prefix semver;
  }
  include Cisco-IOS-XR-cnbng-nal-oper-sub2 {
    revision-date 2021-09-27;
  }
  include Cisco-IOS-XR-cnbng-nal-oper-sub1 {
    revision-date 2021-09-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cnbng-nal package operational data.
     
     This module contains definitions
     for the following management objects:
       cnbng-nal: cnBNG NAL operational data
     
     Copyright (c) 2013-2021 by Cisco Systems, Inc.
     All rights reserved.";

  revision 2021-09-27 {
    description
      "Updated transport and association status enum in yang model.
       2021-07-22
         Updated nal_main_edm_process_info to include SPIO connection information.
       2021-07-06
         Added schema support for all address family in show dynamic route command.
       2021-07-02
         Added connection status information and interface counters.
       2021-06-30
         Added process readiness and transaction pending flags in nal_main_edm_process_readiness.
       2021-06-26
         Updated nal_main_edm_process_info bag to include features supported from platform.
       2021-06-20
         Added new path for getting subscriber summary based on VRF name.
       2021-06-14
         Added tunnel vrf for LAC/LNS subscriber bag
       2021-06-11
         Updated subscriber brief bag with subscriber interface handle.
       2021-05-31
         Added new NAL counter type client api
       2021-05-29
         Added new bag for getting subscriber count and global routes installed.
       2021-05-05
         Added tr459 mode enable flag in bag structure.
       2021-04-01
         added LNS subcriber info in bag
       2021-03-15
         added details for LAC subcriber in bag";
    semver:module-version "2.0.0";
  }
  revision 2021-02-17 {
    description
      "Added AFI only filters";
    semver:module-version "1.0.0";
  }
  revision 2021-02-10 {
    description
      "Removed redundant fail route index";
  }
  revision 2021-02-04 {
    description
      "Added multi framed route support, metric and tag";
  }
  revision 2021-01-23 {
    description
      "Added new NAL counter type thread_stats";
  }
  revision 2020-12-13 {
    description
      "NAL SVM service final timestamp.";
  }
  revision 2020-12-08 {
    description
      "modify Disconnect History Filter keys.";
  }
  revision 2020-11-27 {
    description
      "NAL counters.";
  }
  revision 2020-11-10 {
    description
      "Update bgen path for dynamic routes and removed schema for dynamic routes history.";
  }
  revision 2020-10-26 {
    description
      "Update bag type for AIPC server stats.";
  }
  revision 2020-10-15 {
    description
      "Added schema support for cnbng-nal filter oper commands.";
  }
  revision 2020-10-08 {
    description
      "Moved counter and AIPC stats to new bag files.";
  }
  revision 2020-10-02 {
    description
      "Modified alter gen script to modify leaf list to list.";
  }
  revision 2020-09-18 {
    description
      "Added schema support for cnbng-nal access-interface oper commands.";
  }
  revision 2020-09-15 {
    description
      "adding schema support for NAL chunk statistics oper bag.";
  }
  revision 2020-09-10 {
    description
      "Updated schema for filtering subscriber summary.";
  }
  revision 2020-09-03 {
    description
      "adding schema support for NAL Counters, Dynamic routes, summary and history bag.";
  }
  revision 2020-07-24 {
    description
      "adding schema support for disconect uniuqe and modifying unique summary.";
  }
  revision 2020-06-06 {
    description
      "adding schema support for NAL Process-Info Bag";
  }
  revision 2020-05-29 {
    description
      "adding schema support for Disconnect History Filter.";
  }
  revision 2020-05-15 {
    description
      "adding schema support for NAL CP Transport Connection Status Bag";
  }
  revision 2020-04-30 {
    description
      "adding schema support for NAL VRF Table records";
  }
  revision 2020-04-23 {
    description
      "added new elements in bag";
  }
  revision 2020-04-09 {
    description
      "modified class name for FADB records";
  }
  revision 2020-04-03 {
    description
      "adding schema support for subsriber summary and FADB records";
  }
  revision 2020-04-02 {
    description
      "adding schema support for service profiles and process readiness";
  }
  revision 2020-03-30 {
    description
      "adding schema support for v4 and v6 framed route";
  }
  revision 2019-04-05 {
    description
      "Establish semantic version baseline.";
  }
  revision 2015-11-09 {
    description
      "IOS XR 6.0 revision.";
  }

  grouping TYPE-SESSION-TABLE {
    description
      "Common node of ipoe, pppoe, lac, lns";
    list type-session-table {
      key "up-id";
      description
        "list of sessions based on session type ";
      leaf up-id {
        type uint32;
        description
          "user plane ID";
      }
      uses NAL-SUBSCRIBER-SESSION-DATA;
    }
  }

  grouping DYNAMIC-ROUTE-AFI-TABLE {
    description
      "Common node of ipv4-route, ipv6-route, all-route";
    list dynamic-route-afi-table {
      key "route";
      description
        "operational data for dynamic route-entries based
         on AFI type";
      leaf route {
        type xr:Cisco-ios-xr-string;
        description
          "Dynamic Route";
      }
      leaf vrf {
        type xr:Cisco-ios-xr-string;
        description
          "Dynamic Route vrf";
      }
      uses NAL-MAIN-EDM-OC-ENTRY;
    }
  }

  grouping DETAIL-INTERNAL-AFI-SESSION-TABLE {
    description
      "Common node of filter-ipv4, filter-ipv4-only,
       filter-ipv6, filter-ipv6-only, filter-dual,
       filter-lac";
    list detail-internal-afi-session-table {
      key "up-id";
      description
        "Filter subscribers based on AFI type";
      leaf up-id {
        type uint32;
        description
          "user plane ID";
      }
      uses NAL-SUBSCRIBER-SESSION-DATA-INTERNAL;
    }
  }

  grouping DETAIL-INTERNAL-SESSION-TABLE {
    description
      "Common node of filter-ipoe, filter-pppoe,
       filter-lac, filter-lns";
    list detail-internal-session-table {
      key "up-id";
      description
        "Disply session detail internal type";
      leaf up-id {
        type uint32;
        description
          "user plane ID";
      }
      uses NAL-SUBSCRIBER-SESSION-DATA-INTERNAL;
    }
  }

  grouping AFI-SESSION-TABLE {
    description
      "Common node of ipv4, ipv4-only, ipv6, ipv6-only,
       dual, lac";
    list afi-session-table {
      key "up-id";
      description
        "Filter sessions based on AFI type";
      leaf up-id {
        type uint32;
        description
          "user plane ID";
      }
      uses NAL-SUBSCRIBER-SESSION-DATA;
    }
  }

  container cnbng-nal {
    config false;
    description
      "cnBNG NAL operational data";
    container nodes {
      description
        "List of cnBNG NAL supported nodes";
      list node {
        key "node-name";
        description
          "cnBNG NAL operational data for a particular
           node";
        container disconnect-uniques {
          description
            "operational data for disconnect history unique
             table";
          list disconnect-unique {
            key "disconnect-error-code";
            description
              "operational data for disconnect history
               unique table";
            leaf disconnect-error-code {
              type uint32;
              description
                "disconnect history unique error code";
            }
            uses NAL-SUBSCRIBER-DISCONNECT-HISTORY-UNIQUE-DETAIL-DATA;
          }
        }
        container session-detail-filter-afi {
          description
            "Filter sessions based on AFI type";
          container dual {
            description
              "Dual type";
            uses AFI-SESSION-TABLE;
          }
          container ipv4-only {
            description
              "Only IPV4 type";
            uses AFI-SESSION-TABLE;
          }
          container lac {
            description
              "Lac Sessiions";
            uses AFI-SESSION-TABLE;
          }
          container ipv4 {
            description
              "IPV4 type (includes DUAL stack)";
            uses AFI-SESSION-TABLE;
          }
          container ipv6-only {
            description
              "Only IPV6 type";
            uses AFI-SESSION-TABLE;
          }
          container ipv6 {
            description
              "IPV6 type (includes DUAL stack)";
            uses AFI-SESSION-TABLE;
          }
        }
        container session-detail-macs {
          description
            "Filter subscribers based on mac-address";
          list session-detail-mac {
            key "mac-addr";
            description
              "Select mac-address";
            leaf mac-addr {
              type xr:Cisco-ios-xr-string;
              description
                "mac address";
            }
            list mac-session-detail-table {
              key "up-id";
              description
                "Filter subscribers based on mac-address";
              leaf up-id {
                type uint32;
                description
                  "user plane ID";
              }
              uses NAL-SUBSCRIBER-SESSION-DATA;
            }
          }
        }
        container feature-ids {
          description
            "operational data for NAL subscriber sessions";
          list feature-id {
            key "fadb-path";
            description
              "operational data for NAL subscriber sessions
               FADB";
            leaf fadb-path {
              type uint32;
              description
                "FADB";
            }
            uses NAL-OPER-FADB-RECORD-DATA;
          }
        }
        container session-detail-internal-filter-upids {
          description
            "operational data based on filter UPID";
          list session-detail-internal-filter-upid {
            key "up-id";
            description
              "Filter based on UPID";
            leaf up-id {
              type uint32;
              description
                "user plane ID";
            }
            uses NAL-SUBSCRIBER-SESSION-DATA-INTERNAL;
          }
        }
        container services {
          description
            "operational data for NAL subscriber services";
          list service {
            key "service";
            description
              "operational data for NAL subscriber services";
            leaf service {
              type xr:Cisco-ios-xr-string;
              description
                "service name";
            }
            uses NAL-SERVICE-PROFILE-DATA;
          }
        }
        container detail-internal-vrf-names {
          description
            "operational data for NAL subscriber sessions";
          list detail-internal-vrf-name {
            key "vrf-name-filter";
            description
              "Disply subscribers based on vrf ";
            leaf vrf-name-filter {
              type xr:Cisco-ios-xr-string;
              description
                "vrf name";
            }
            list vrf-session-detail-internal-table {
              key "up-id";
              description
                "Disply subscribers based on vrf ";
              leaf up-id {
                type uint32;
                description
                  "user plane ID";
              }
              uses NAL-SUBSCRIBER-SESSION-DATA-INTERNAL;
            }
          }
        }
        container disconnect-unique-summaries {
          description
            "operational data for disconnect history unique
             table";
          list disconnect-unique-summary {
            key "disconnect-error-code";
            description
              "operational data for disconnect history
               unique";
            leaf disconnect-error-code {
              type uint32;
              description
                "disconnect history unique";
            }
            uses NAL-SUBSCRIBER-DISCONNECT-HISTORY-UNIQUE-DATA;
          }
        }
        container summary-filters-vrfs {
          description
            "Operational data for subscriber summary based
             on VRF name";
          list summary-filters-vrf {
            key "vrf-name";
            description
              "Operational data for subscriber summary based
               on VRF";
            leaf vrf-name {
              type xr:Cisco-ios-xr-string;
              description
                "VRF Name";
            }
            uses NAL-SUBSCRIBER-SUMMARY;
          }
        }
        container main {
          description
            "cnBNG NAL main";
          container events {
            description
              "operational data for NAL main process boot up
               events";
            uses NAL-MAIN-EDM-EVENTS;
          }
        }
        container disconnectlasttypemacs {
          description
            "operational data disconnected session by Mac ";
          list disconnectlasttypemac {
            key "disc-mac";
            description
              "operational data for disconnect history
               filter as mac ";
            leaf disc-mac {
              type xr:Cisco-ios-xr-string;
              description
                "mac";
            }
            uses NAL-SUBSCRIBER-DISCONNECT-HISTORY-DATA;
          }
        }
        container session-briefs {
          description
            "Brief data for subscriber sessions";
          list session-brief {
            key "up-id";
            description
              " Brief operational data for NAL subscriber
               sessions";
            leaf up-id {
              type uint32;
              description
                "user plane ID";
            }
            uses NAL-SUBSCRIBER-SESSION-INFO-BRIEF;
          }
        }
        container disconnectlasttypesubinterfaces {
          description
            "operational data disconnected session by
             subinterface ";
          list disconnectlasttypesubinterface {
            key "interface-name";
            description
              "operational data for disconnect history
               filter as subinterface ";
            leaf interface-name {
              type xr:Cisco-ios-xr-string;
              description
                "subscriber interface";
            }
            uses NAL-SUBSCRIBER-DISCONNECT-HISTORY-DATA;
          }
        }
        container session-detail-internal-access-intfs {
          description
            "operational data for NAL subscriber sessions";
          list session-detail-internal-access-intf {
            key "parent-intf";
            description
              "Disply subscribers based on Access Interface ";
            leaf parent-intf {
              type uint32;
              description
                "vrf name";
            }
            list access-intf-session-detail-internal-table {
              key "up-id";
              description
                "Disply subscribers based on Access Interface";
              leaf up-id {
                type uint32;
                description
                  "user plane ID";
              }
              uses NAL-SUBSCRIBER-SESSION-DATA-INTERNAL;
            }
          }
        }
        container session-detail-filter-upids {
          description
            "operational data for NAL subscriber sessions";
          list session-detail-filter-upid {
            key "up-id";
            description
              "Subscriber details based on UPID";
            leaf up-id {
              type uint32;
              description
                "user plane ID";
            }
            uses NAL-SUBSCRIBER-SESSION-DATA;
          }
        }
        container nal-chunks-stats-tbl {
          description
            "operational data for NAL chunks statistics
             info";
          uses NAL-MAIN-EDM-CHUNK-STATS;
        }
        container session-detail-internal-filter-afi {
          description
            "operational data for NAL subscriber sessions";
          container filter-ipv4-only {
            description
              "Select ipv4 only address-family";
            uses DETAIL-INTERNAL-AFI-SESSION-TABLE;
          }
          container filter-lac {
            description
              "Select LAC only address-family";
            uses DETAIL-INTERNAL-AFI-SESSION-TABLE;
          }
          container filter-ipv4 {
            description
              "Select ipv4 address-family (includes DUAL
               stack)";
            uses DETAIL-INTERNAL-AFI-SESSION-TABLE;
          }
          container filter-ipv6-only {
            description
              "Select ipv6 only address-family";
            uses DETAIL-INTERNAL-AFI-SESSION-TABLE;
          }
          container filter-ipv6 {
            description
              "Select ipv6 address-family (includes DUAL
               stack)";
            uses DETAIL-INTERNAL-AFI-SESSION-TABLE;
          }
          container filter-dual {
            description
              "Display subscriber sessions on address family
               filter";
            uses DETAIL-INTERNAL-AFI-SESSION-TABLE;
          }
        }
        container session-detail-internal-macs {
          description
            "operational data for NAL subscriber sessions";
          list session-detail-internal-mac {
            key "mac-addr";
            description
              "Disply subscribers based on subscriber mac";
            leaf mac-addr {
              type xr:Cisco-ios-xr-string;
              description
                "mac address";
            }
            list mac-session-detail-internal-table {
              key "up-id";
              description
                "Disply subscribers based on subscriber mac";
              leaf up-id {
                type uint32;
                description
                  "user plane ID";
              }
              uses NAL-SUBSCRIBER-SESSION-DATA-INTERNAL;
            }
          }
        }
        container dynamic-routes-hist-classes {
          description
            "operational data for dynamic-route history";
          list dynamic-routes-hist-class {
            key "history-path";
            description
              "operational data for dynamic-route history";
            leaf history-path {
              type uint32;
              description
                "Dynamic Routes history";
            }
            uses NAL-MAIN-EDM-SPA-RT-PROV-HIST-DATA;
          }
        }
        container access-intf {
          description
            "cnBNG NAL access interface";
          container intf-alls {
            description
              "cnBNG NAL access interface type";
            list intf-all {
              key "intf-handle";
              description
                "cnBNG NAL access interface ";
              leaf intf-handle {
                type uint32;
                description
                  "Access interface";
              }
              uses NAL-MAIN-EDM-PARENT-INTF-DATA;
            }
          }
          container intf-type {
            description
              "cnBNG NAL access interface type";
            container pppoe-intf-handles {
              description
                "cnBNG NAL access interface ip-sub type";
              list pppoe-intf-handle {
                key "pppoe-intf-handle";
                description
                  "cnBNG NAL access interface  pppoe type";
                leaf pppoe-intf-handle {
                  type uint32;
                  description
                    "Access interface";
                }
                uses NAL-MAIN-EDM-PARENT-INTF-DATA;
              }
            }
            container ipsub-intf-handles {
              description
                "cnBNG NAL access interface ip-sub type";
              list ipsub-intf-handle {
                key "ipsub-intf-handle";
                description
                  "cnBNG NAL access interface ip-sub type";
                leaf ipsub-intf-handle {
                  type uint32;
                  description
                    "Access interface";
                }
                uses NAL-MAIN-EDM-PARENT-INTF-DATA;
              }
            }
            container lns-intf-handles {
              description
                "cnBNG NAL access interface lns type";
              list lns-intf-handle {
                key "lns-intf-handle";
                description
                  "cnBNG NAL access interface  lns type";
                leaf lns-intf-handle {
                  type uint32;
                  description
                    "Access interface";
                }
                uses NAL-MAIN-EDM-PARENT-INTF-DATA;
              }
            }
          }
        }
        container session-detail-sub-intfs {
          description
            "Operational data based on subscriber interface
             filter";
          list session-detail-sub-intf {
            key "sub-intf";
            description
              "Filter based on Subscriber Interface";
            leaf sub-intf {
              type uint32;
              description
                "vrf name";
            }
            list sub-intf-session-detail-table {
              key "up-id";
              description
                "Filter based on Subscriber Interface";
              leaf up-id {
                type uint32;
                description
                  "user plane ID";
              }
              uses NAL-SUBSCRIBER-SESSION-DATA;
            }
          }
        }
        container process-readiness {
          description
            "operational data for NAL main process
             readiness";
          uses NAL-MAIN-EDM-PROCESS-READINESS;
        }
        container cp-server-table {
          description
            "operational data for NAL control-plane
             transport server info";
          container cp-connection-sts-info {
            description
              "operational data for NAL control-plane
               transport server connection status info";
            uses NAL-MAIN-EDM-CP-CONN-STS-INFO;
          }
        }
        container summary-table {
          description
            "operational data for NAL subscriber summary";
          container summary-filters {
            description
              "operational data for NAL subscriber summary
               filters";
            uses NAL-SUBSCRIBER-SUMMARY;
          }
        }
        container dynamic-route-summary-tbl {
          description
            "operational data for NAL dynamic-routes
             summary info";
          uses NAL-MAIN-EDM-OC-SUMMARY;
        }
        container aipc-server-stats {
          description
            "operational data for NAL AIPC Server stats";
          list aipc-server-stat {
            key "aipc-path";
            description
              "operational data for aipc stats ";
            leaf aipc-path {
              type xr:Cisco-ios-xr-string;
              description
                "aipc";
            }
            uses NAL-AIPC-SERVER-STATS-DATA;
          }
        }
        container session-detail-access-intfs {
          description
            "operational data for NAL subscriber sessions";
          list session-detail-access-intf {
            key "parent-intf";
            description
              "Session detail based on filter Access
               Interface";
            leaf parent-intf {
              type uint32;
              description
                "vrf name";
            }
            list access-intf-session-detail-table {
              key "up-id";
              description
                "Brief data for subscriber sessions";
              leaf up-id {
                type uint32;
                description
                  "user plane ID";
              }
              uses NAL-SUBSCRIBER-SESSION-DATA;
            }
          }
        }
        container disconnectlasttype-upids {
          description
            "operational data for disconnected session by
             upid";
          list disconnectlasttype-upid {
            key "disc-upid";
            description
              "operational data for disconnect history
               filtered by upid ";
            leaf disc-upid {
              type uint32;
              description
                "user plane ID";
            }
            uses NAL-SUBSCRIBER-DISCONNECT-HISTORY-DATA;
          }
        }
        container dynamic-route-filter-afi {
          description
            "operational data for dynamic-route tables";
          container ipv6-route {
            description
              "IPV6 type";
            uses DYNAMIC-ROUTE-AFI-TABLE;
          }
          container ipv4-route {
            description
              "IPV4 type";
            uses DYNAMIC-ROUTE-AFI-TABLE;
          }
          container all-route {
            description
              "All type";
            uses DYNAMIC-ROUTE-AFI-TABLE;
          }
        }
        container nal-counters-tbl {
          description
            "operational data for NAL counters context-path";
          container nal-counters-info {
            description
              "operational data for NAL counters context
               dump";
            uses NAL-MAIN-EDM-NAL-COUNTERS;
          }
        }
        container session-detail-filter-session-type {
          description
            "Filter sessions based on session type";
          container pppoe {
            description
              "select pppoe session type";
            uses TYPE-SESSION-TABLE;
          }
          container lns {
            description
              "select lns session type";
            uses TYPE-SESSION-TABLE;
          }
          container lac {
            description
              "select lac session type";
            uses TYPE-SESSION-TABLE;
          }
          container ipoe {
            description
              "select ipoe session type";
            uses TYPE-SESSION-TABLE;
          }
        }
        container disconnectlasts {
          description
            "operational data for Disconnected subscriber
             sessions";
          list disconnectlast {
            key "disconnect-last-upid";
            description
              "operational data for disconnect history stats";
            leaf disconnect-last-upid {
              type xr:Cisco-ios-xr-string;
              description
                "disconnect history last";
            }
            uses NAL-SUBSCRIBER-DISCONNECT-HISTORY-DATA;
          }
        }
        container detail-vrf-names {
          description
            "operational data for NAL subscriber sessions";
          list detail-vrf-name {
            key "vrf-name-filter";
            description
              "Filter subscribers based on vrf";
            leaf vrf-name-filter {
              type xr:Cisco-ios-xr-string;
              description
                "vrf name";
            }
            list vrf-session-detail-table {
              key "up-id";
              description
                "Session detail based on filter vrf";
              leaf up-id {
                type uint32;
                description
                  "user plane ID";
              }
              uses NAL-SUBSCRIBER-SESSION-DATA;
            }
          }
        }
        container vrf-names {
          description
            "operational data for NAL VRF-Table context";
          list vrf-name {
            key "vrf-name";
            description
              "operational data for NAL VRF-Table context";
            leaf vrf-name {
              type xr:Cisco-ios-xr-string;
              description
                "VRF Name";
            }
            uses NAL-MAIN-EDM-VRFTBL-INFO;
          }
        }
        container disconnectlasttypecpids {
          description
            "operational data disconnected session by cpid";
          list disconnectlasttypecpid {
            key "disc-cpid";
            description
              "operational data for disconnect history
               filter as cpid ";
            leaf disc-cpid {
              type uint32;
              description
                "control plane ID";
            }
            uses NAL-SUBSCRIBER-DISCONNECT-HISTORY-DATA;
          }
        }
        container session-detail-internal-filter-session-type {
          description
            "operational data for NAL subscriber sessions";
          container filter-lns {
            description
              "Select LNS type";
            uses DETAIL-INTERNAL-SESSION-TABLE;
          }
          container filter-lac {
            description
              "Select LAC type";
            uses DETAIL-INTERNAL-SESSION-TABLE;
          }
          container filter-pppoe {
            description
              "Select PPPoE type";
            uses DETAIL-INTERNAL-SESSION-TABLE;
          }
          container filter-ipoe {
            description
              "Select IPoE type";
            uses DETAIL-INTERNAL-SESSION-TABLE;
          }
        }
        container process-info-class {
          description
            "Significant operational data for NAL main
             process";
          uses NAL-MAIN-EDM-PROCESS-INFO;
        }
        container session-detail-internal-sub-intfs {
          description
            "Disply subscribers based on subscriber
             Interface ";
          list session-detail-internal-sub-intf {
            key "sub-intf";
            description
              "Disply subscribers based on subscriber
               Interface ";
            leaf sub-intf {
              type uint32;
              description
                "vrf name";
            }
            list sub-intf-session-detail-internal-table {
              key "up-id";
              description
                "Disply subscribers based on subscriber
                 Interface ";
              leaf up-id {
                type uint32;
                description
                  "user plane ID";
              }
              uses NAL-SUBSCRIBER-SESSION-DATA-INTERNAL;
            }
          }
        }
        leaf node-name {
          type xr:Node-id;
          description
            "Node name";
        }
      }
    }
  }
}
