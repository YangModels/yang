module Cisco-IOS-XR-um-subscriber-arp-cfg {
  namespace "http://cisco.com/ns/yang/Cisco-IOS-XR-um-subscriber-arp-cfg";
  prefix um-subscriber-arp-cfg;

  import Cisco-IOS-XR-um-subscriber-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-arp package configuration.
     
     This YANG module augments the
     modules with configuration data.
     
     Copyright (c) 2020-2021 by Cisco Systems, Inc.
     All rights reserved.";

  revision 2021-04-23 {
    description
      "Initial release";
    semver:module-version "1.0.0";
  }

  augment "/a2:subscriber" {
    container arp {
      description
        "ARP Subscriber configuration option";
      container scale-mode-enable {
        presence "Indicates a scale-mode-enable node is configured.";
        description
          "Supressing ARP entry creation on subscribers interfaces";
      }
      container uncond-proxy-arp-enable {
        presence "Indicates a uncond-proxy-arp-enable node is configured.";
        description
          "Enable unconditional proxy ARP";
      }
    }
  }
}
