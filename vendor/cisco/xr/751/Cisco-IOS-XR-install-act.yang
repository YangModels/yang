module Cisco-IOS-XR-install-act {
  namespace "http://cisco.com/ns/yang/Cisco-IOS-XR-install-act";
  prefix install-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install actions.
     
     Copyright (c) 2018-2021 by Cisco Systems, Inc.
     All rights reserved.";

  revision 2021-08-31 {
    description
      "7.5.1 release features:
       Ability to indicate to try operations best-effort with the force option.";
    semver:module-version "2.0.0";
  }
  revision 2021-03-22 {
    description
      "7.4.1 release features:
        Ability to add a description to a commit.
       2019-12-10
          Addition of install-mode-type enum, deprecation of update-all leaf, and
        addition of tar to packages-source-type";
    semver:module-version "1.2.0";
  }
  revision 2019-11-05 {
    description
      "Addition of INST-SHARED-OP-ID-TYPE for the return type of action RPCs";
    semver:module-version "1.1.0";
  }
  revision 2019-10-03 {
    description
      "Addition of apply type enumeration and option for replace/source commands
       2019-10-01
        Made changes to be RFC6087 compliant";
    semver:module-version "1.1.0";
  }
  revision 2019-04-05 {
    description
      "Establish semantic version baseline.";
    semver:module-version "1.0.0";
  }
  revision 2018-10-05 {
    description
      "IOS XR 7.0.1 revision.";
  }

  typedef replace-source-type {
    type enumeration {
      enum "local" {
        description
          "Install from a local file path";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
    }
    description
      "replace source type";
  }

  typedef packages-source-type {
    type enumeration {
      enum "local" {
        description
          "Install from a local directory or repository containing RPMs and/or
           tar files";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
      enum "any-configured-repository" {
        description
          "Install from any configured repository";
      }
      enum "configured-repository" {
        description
          "Install from the given repository";
      }
      enum "tar" {
        description
          "Install from a local tar file";
      }
    }
    description
      "packages source type";
  }

  typedef config-type {
    type enumeration {
      enum "ignore" {
        description
          "Ignore the configuration in the given ISO";
      }
      enum "merge" {
        description
          "Merge the configuration in the given ISO with existing
           configuration";
      }
      enum "replace" {
        description
          "Replace the existing configuration with the configuration
           in the given ISO";
      }
    }
    description
      "config type";
  }

  typedef apply-type {
    type enumeration {
      enum "restart" {
        description
          "Apply atomic change by restarting processes - only valid
           for the augmented 'install-apply' operation";
      }
      enum "reload" {
        description
          "Apply atomic change by reloading";
      }
      enum "least-impactful" {
        description
          "Apply atomic change by least impactful method";
      }
    }
    description
      "apply type";
  }

  typedef install-mode-type {
    type enumeration {
      enum "specified-packages" {
        description
          "Add the specified packages";
      }
      enum "upgrade-all" {
        description
          "Upgrade all packages that have a higher version available";
      }
      enum "install-all" {
        description
          "Install the highest compatible version of all packages
           from a specified source";
      }
    }
  }

  grouping INST-SHARED-OP-ID-TYPE {
    leaf op-id {
      type string;
      description
        "operation id of the triggered action";
    }
    leaf Error {
      type string;
      description
        "error information";
    }
  }

  rpc install-replace {
    description
      "Replace the existing software with that from the given ISO";
    input {
      leaf source-type {
        type replace-source-type;
        default "local";
        description
          "Type of source used to obtain the ISO";
      }
      leaf source {
        type string;
        mandatory true;
        description
          "Path to the location of the ISO";
      }
      leaf file {
        type string;
        mandatory true;
        description
          "Name of the ISO to install";
      }
      leaf commit {
        type boolean;
        default "false";
        description
          "Commit at the end of the replace operation, if the
           software is successfully applied";
      }
      leaf description {
        type string;
        description
          "Description to be stored for the transaction ID";
      }
      leaf config {
        type config-type;
        description
          "Action to take on any configuration present in the ISO";
      }
      leaf activation-type {
        type apply-type;
        default "least-impactful";
        description
          "Activate the software using the specified apply type";
      }
      leaf force {
        type boolean;
        default "false";
        description
          "Ignore non-critical errors";
      }
    }
    output {
      uses INST-SHARED-OP-ID-TYPE;
    }
    csc:xr-task "pkg-mgmt";
  }
  rpc install {
    description
      "Install packages from a given source";
    input {
      container packages {
        description
          "Set of packages to install. Should be set only when 'install-mode'
           is 'specified-packages'";
        leaf-list packagename {
          type string;
          description
            "package name";
        }
      }
      leaf update-all {
        type boolean;
        default "false";
        status deprecated;
        description
          "True to update all packages using the given source, False
           to only install or update the specified packages";
      }
      leaf source-type {
        type packages-source-type;
        default "local";
        description
          "Type of source used to obtain the packages";
      }
      leaf source {
        type string;
        description
          "Path to the location of the packages.  If source-type is
           'any-configured-repository' this field is unused, and if
           source-type is 'configured-repository' this should be the
           name of the repository to use.";
      }
      leaf activation-type {
        type apply-type;
        default "least-impactful";
        description
          "Activate the software using the specified apply type";
      }
      leaf install-mode {
        type install-mode-type;
        default "specified-packages";
        description
          "Mode of install operation";
      }
      leaf force {
        type boolean;
        default "false";
        description
          "Ignore non-critical errors";
      }
    }
    output {
      uses INST-SHARED-OP-ID-TYPE;
    }
    csc:xr-task "pkg-mgmt";
  }
  rpc install-commit {
    description
      "Commit the current software, such that it will persist over reload.";
    input {
      leaf description {
        type string;
        description
          "Description to be stored for the transaction ID";
      }
      leaf force {
        type boolean;
        default "false";
        description
          "Ignore non-critical errors";
      }
    }
    output {
      uses INST-SHARED-OP-ID-TYPE;
    }
    csc:xr-task "pkg-mgmt";
  }
}
