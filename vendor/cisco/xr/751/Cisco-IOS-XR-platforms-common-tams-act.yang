module Cisco-IOS-XR-platforms-common-tams-act {
  namespace "http://cisco.com/ns/yang/Cisco-IOS-XR-platforms-common-tams-act";
  prefix platforms-common-tams-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2019-2021 by Cisco Systems, Inc.
     All rights reserved.";

  revision 2010-10-01 {
    description
      "Intial revesion";
    semver:module-version "1.0.0";
  }

  rpc tam-app-data-clean-backup-start {
    description
      "To start clean appdb then backup";
    input {
      leaf location {
        type string;
        description
          "XR node identifier e.g. 0/RP0/CPU0, 0/0/CPU0";
      }
    }
  }
  rpc tam-app-data-restore-start {
    description
      "To start the appdb restore";
    input {
      leaf location {
        type string;
        description
          "XR node identifier e.g. 0/RP0/CPU0, 0/0/CPU0";
      }
    }
  }
}
