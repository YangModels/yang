module Cisco-IOS-XR-8000-qos-oper {
  namespace "http://cisco.com/ns/yang/Cisco-IOS-XR-8000-qos-oper";
  prefix xr-8000-qos-oper;

  import Cisco-IOS-XR-types {
    prefix xr;
  }
  import cisco-semver {
    prefix semver;
  }
  include Cisco-IOS-XR-8000-qos-oper-sub2 {
    revision-date 2021-06-28;
  }
  include Cisco-IOS-XR-8000-qos-oper-sub1 {
    revision-date 2021-06-28;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-qos package operational data.
     
     This module contains definitions
     for the following management objects:
       platform-qos: DPA QoS EA operational data
     
     Copyright (c) 2013-2021 by Cisco Systems, Inc.
     All rights reserved.";

  revision 2021-06-28 {
    description
      "Configured Max probability for RED ECN";
  }
  revision 2021-03-11 {
    description
      "Fix parent policy’s class default display";
  }
  revision 2020-09-14 {
    description
      "Converted Policer HW value to 64 bit.";
  }
  revision 2019-04-05 {
    description
      "Establish semantic version baseline.";
  }
  revision 2015-11-09 {
    description
      "IOS XR 6.0 revision.";
  }

  grouping POLICY-DETAILS {
    description
      "Common node of interface, bundle-interface,
       member-interface";
    container policy-details {
      description
        "QoS Policy Details";
      uses DPA-QOSEA-SHOW-IF-QOS-INFO-ST;
    }
  }

  grouping CLASS-TABLE {
    description
      "Common node of interface, bundle-interface,
       member-interface";
    container classes {
      description
        "QoS list of class names";
      list class {
        key "level-one-class-name";
        description
          "QoS policy class";
        leaf level-one-class-name {
          type string;
          description
            "QoS policy class name at level 1";
        }
        leaf level-two-class-name {
          type string;
          description
            "QoS policy child class name at level 2";
        }
        uses DPA-QOSEA-SHOW-CLASS-ST;
      }
    }
  }

  container platform-qos {
    config false;
    description
      "DPA QoS EA operational data";
    container nodes {
      description
        "List of nodes with platform specific QoS
         configuration";
      list node {
        key "node-name";
        description
          "Node with platform specific QoS configuration";
        container interfaces {
          description
            "QoS list of interfaces";
          list interface {
            description
              "QoS interface names";
            leaf interface-name {
              type xr:Interface-name;
              description
                "The name of the interface";
            }
            leaf qos-direction {
              type string;
              description
                "The interface direction on which QoS is
                 applied to.";
            }
            leaf policy-name {
              type string;
              description
                "The QoS policy name.";
            }
            uses POLICY-DETAILS;
            uses CLASS-TABLE;
          }
        }
        container bundle-interfaces {
          description
            "QoS list of bundle interfaces";
          list bundle-interface {
            description
              "QoS interface names";
            container member-interfaces {
              description
                "QoS list of member interfaces";
              list member-interface {
                key "interface-name";
                description
                  "QoS interface names";
                leaf interface-name {
                  type xr:Interface-name;
                  description
                    "Member interface";
                }
                uses POLICY-DETAILS;
                uses CLASS-TABLE;
              }
            }
            leaf interface-name {
              type xr:Interface-name;
              description
                "Bundle interface name";
            }
            leaf npu-id {
              type uint32;
              description
                "NPU ID";
            }
            leaf qos-direction {
              type string;
              description
                "The interface direction on which QoS is
                 applied to.";
            }
            leaf policy-name {
              type string;
              description
                "The QoS policy name.";
            }
            uses POLICY-DETAILS;
            uses CLASS-TABLE;
          }
        }
        container remote-interfaces {
          description
            "QoS list of remote interfaces";
          list remote-interface {
            key "interface-name";
            description
              "QoS remote interface names";
            leaf interface-name {
              type xr:Interface-name;
              description
                "The name of the remote interface";
            }
            uses DPA-QOSEA-SHOW-REMOTE-IF-INFO-ST;
          }
        }
        leaf node-name {
          type xr:Node-id;
          description
            "Node name";
        }
      }
    }
  }
}
