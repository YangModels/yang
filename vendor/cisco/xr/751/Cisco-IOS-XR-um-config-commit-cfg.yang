module Cisco-IOS-XR-um-config-commit-cfg {
  namespace "http://cisco.com/ns/yang/Cisco-IOS-XR-um-config-commit-cfg";
  prefix um-config-commit-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-commit package configuration.
     
     This YANG module augments the
     modules with configuration data.
     
     Copyright (c) 2021 by Cisco Systems, Inc.
     All rights reserved.";

  revision 2021-04-14 {
    description
      "Initial release";
    semver:module-version "1.0.0";
  }

  feature cflash_fs_supp_check {
    description
      "cflash fs supp check";
  }

  feature usb_fs_supp_check {
    description
      "usb fs supp check";
  }

  feature disk2_fs_supp_check {
    description
      "disk2 fs supp check";
  }

  feature harddisk_fs_supp_check {
    description
      "harddisk fs supp check";
  }

  feature lcdisk_fs_supp_check {
    description
      "lcdisk fs supp check";
  }

  feature classic-admin-config {
    description
      "Classic admin configuration supported";
  }

  container admin {
    if-feature "classic-admin-config";
    description
      "Admin configuration";
    container configuration {
      description
        "Set autosave on commit ";
      container commit {
        description
          "auto-save the running configuration";
        container auto-save {
          description
            "auto-save the running configuration";
          container filename {
            must
              "compactflash or compactflasha or usb or disk0
               or disk0a or disk1 or disk1a or disk2
               or harddisk or harddiska or harddiskb or nvram
               or lcdisk0 or lcdisk0a or tftp or ftp or rcp
               or save-to-file";
            presence "Indicates a filename node is configured.";
            description
              "filename to auto-save";
            container bootflash {
              must
                "not(../compactflash or ../compactflasha
                 or ../usb or ../disk0
                 or ../disk0a or ../disk1
                 or ../disk1a or ../disk2
                 or ../harddisk or ../harddiska
                 or ../harddiskb or ../nvram
                 or ../lcdisk0 or ../lcdisk0a
                 or ../tftp or ../ftp
                 or ../rcp)";
              presence "Indicates a bootflash node is configured.";
              description
                "Save to bootflash: file system";
            }
            container compactflash {
              if-feature "cflash_fs_supp_check";
              must
                "not(../bootflash or ../compactflasha
                 or ../usb or ../disk0
                 or ../disk0a or ../disk1
                 or ../disk1a or ../disk2
                 or ../harddisk or ../harddiska
                 or ../harddiskb or ../nvram
                 or ../lcdisk0 or ../lcdisk0a
                 or ../tftp or ../ftp
                 or ../rcp)";
              presence "Indicates a compactflash node is configured.";
              description
                "Save to compactflash: file system";
            }
            container compactflasha {
              if-feature "cflash_fs_supp_check";
              must
                "not(../bootflash or ../compactflash
                 or ../usb or ../disk0
                 or ../disk0a or ../disk1
                 or ../disk1a or ../disk2
                 or ../harddisk or ../harddiska
                 or ../harddiskb or ../nvram
                 or ../lcdisk0 or ../lcdisk0a
                 or ../tftp or ../ftp
                 or ../rcp)";
              presence "Indicates a compactflasha node is configured.";
              description
                "Save to compactflasha: file system";
            }
            container usb {
              if-feature "usb_fs_supp_check";
              must
                "not(../bootflash or ../compactflash
                 or ../compactflasha or ../disk0
                 or ../disk0a or ../disk1
                 or ../disk1a or ../disk2
                 or ../harddisk or ../harddiska
                 or ../harddiskb or ../nvram
                 or ../lcdisk0 or ../lcdisk0a
                 or ../tftp or ../ftp
                 or ../rcp)";
              presence "Indicates a usb node is configured.";
              description
                "Save to usb: file system";
            }
            container disk0 {
              must
                "not(../bootflash or ../compactflash
                 or ../compactflasha or ../usb
                 or ../disk0a or ../disk1
                 or ../disk1a or ../disk2
                 or ../harddisk or ../harddiska
                 or ../harddiskb or ../nvram
                 or ../lcdisk0 or ../lcdisk0a
                 or ../tftp or ../ftp
                 or ../rcp)";
              presence "Indicates a disk0 node is configured.";
              description
                "Save to disk0: file system";
            }
            container disk0a {
              must
                "not(../bootflash or ../compactflash
                 or ../compactflasha or ../usb
                 or ../disk0 or ../disk1
                 or ../disk1a or ../disk2
                 or ../harddisk or ../harddiska
                 or ../harddiskb or ../nvram
                 or ../lcdisk0 or ../lcdisk0a
                 or ../tftp or ../ftp
                 or ../rcp)";
              presence "Indicates a disk0a node is configured.";
              description
                "Save to disk0a: file system";
            }
            container disk1 {
              must
                "not(../bootflash or ../compactflash
                 or ../compactflasha or ../usb
                 or ../disk0 or ../disk0a
                 or ../disk1a or ../disk2
                 or ../harddisk or ../harddiska
                 or ../harddiskb or ../nvram
                 or ../lcdisk0 or ../lcdisk0a
                 or ../tftp or ../ftp
                 or ../rcp)";
              presence "Indicates a disk1 node is configured.";
              description
                "Save to disk1: file system";
            }
            container disk1a {
              must
                "not(../bootflash or ../compactflash
                 or ../compactflasha or ../usb
                 or ../disk0 or ../disk0a
                 or ../disk1 or ../disk2
                 or ../harddisk or ../harddiska
                 or ../harddiskb or ../nvram
                 or ../lcdisk0 or ../lcdisk0a
                 or ../tftp or ../ftp
                 or ../rcp)";
              presence "Indicates a disk1a node is configured.";
              description
                "Save to disk1a: file system";
            }
            container disk2 {
              if-feature "disk2_fs_supp_check";
              must
                "not(../bootflash or ../compactflash
                 or ../compactflasha or ../usb
                 or ../disk0 or ../disk0a
                 or ../disk1 or ../disk1a
                 or ../harddisk or ../harddiska
                 or ../harddiskb or ../nvram
                 or ../lcdisk0 or ../lcdisk0a
                 or ../tftp or ../ftp
                 or ../rcp)";
              presence "Indicates a disk2 node is configured.";
              description
                "Save to disk2: file system";
            }
            container harddisk {
              if-feature "harddisk_fs_supp_check";
              must
                "not(../bootflash or ../compactflash
                 or ../compactflasha or ../usb
                 or ../disk0 or ../disk0a
                 or ../disk1 or ../disk1a
                 or ../disk2 or ../harddiska
                 or ../harddiskb or ../nvram
                 or ../lcdisk0 or ../lcdisk0a
                 or ../tftp or ../ftp
                 or ../rcp)";
              presence "Indicates a harddisk node is configured.";
              description
                "Save to harddisk: file system";
            }
            container harddiska {
              if-feature "harddisk_fs_supp_check";
              must
                "not(../bootflash or ../compactflash
                 or ../compactflasha or ../usb
                 or ../disk0 or ../disk0a
                 or ../disk1 or ../disk1a
                 or ../disk2 or ../harddisk
                 or ../harddiskb or ../nvram
                 or ../lcdisk0 or ../lcdisk0a
                 or ../tftp or ../ftp
                 or ../rcp)";
              presence "Indicates a harddiska node is configured.";
              description
                "Save to harddiska: file system";
            }
            container harddiskb {
              if-feature "harddisk_fs_supp_check";
              must
                "not(../bootflash or ../compactflash
                 or ../compactflasha or ../usb
                 or ../disk0 or ../disk0a
                 or ../disk1 or ../disk1a
                 or ../disk2 or ../harddisk
                 or ../harddiska or ../nvram
                 or ../lcdisk0 or ../lcdisk0a
                 or ../tftp or ../ftp
                 or ../rcp)";
              presence "Indicates a harddiskb node is configured.";
              description
                "Save to harddiskb: file system";
            }
            container nvram {
              must
                "not(../bootflash or ../compactflash
                 or ../compactflasha or ../usb
                 or ../disk0 or ../disk0a
                 or ../disk1 or ../disk1a
                 or ../disk2 or ../harddisk
                 or ../harddiska or ../harddiskb
                 or ../lcdisk0 or ../lcdisk0a
                 or ../tftp or ../ftp
                 or ../rcp)";
              presence "Indicates a nvram node is configured.";
              description
                "Save to nvram: file system";
            }
            container lcdisk0 {
              if-feature "lcdisk_fs_supp_check";
              must
                "not(../bootflash or ../compactflash
                 or ../compactflasha or ../usb
                 or ../disk0 or ../disk0a
                 or ../disk1 or ../disk1a
                 or ../disk2 or ../harddisk
                 or ../harddiska or ../harddiskb
                 or ../nvram or ../lcdisk0a
                 or ../tftp or ../ftp
                 or ../rcp)";
              presence "Indicates a lcdisk0 node is configured.";
              description
                "Save to lcdisk0: file system";
            }
            container lcdisk0a {
              if-feature "lcdisk_fs_supp_check";
              must
                "not(../bootflash or ../compactflash
                 or ../compactflasha or ../usb
                 or ../disk0 or ../disk0a
                 or ../disk1 or ../disk1a
                 or ../disk2 or ../harddisk
                 or ../harddiska or ../harddiskb
                 or ../nvram or ../lcdisk0
                 or ../tftp or ../ftp
                 or ../rcp)";
              presence "Indicates a lcdisk0a node is configured.";
              description
                "Save to lcdisk0a: file system";
            }
            container tftp {
              must
                "not(../bootflash or ../compactflash
                 or ../compactflasha or ../usb
                 or ../disk0 or ../disk0a
                 or ../disk1 or ../disk1a
                 or ../disk2 or ../harddisk
                 or ../harddiska or ../harddiskb
                 or ../nvram or ../lcdisk0
                 or ../lcdisk0a or ../ftp
                 or ../rcp)";
              presence "Indicates a tftp node is configured.";
              description
                "Save to tftp: file system";
            }
            container ftp {
              must
                "not(../bootflash or ../compactflash
                 or ../compactflasha or ../usb
                 or ../disk0 or ../disk0a
                 or ../disk1 or ../disk1a
                 or ../disk2 or ../harddisk
                 or ../harddiska or ../harddiskb
                 or ../nvram or ../lcdisk0
                 or ../lcdisk0a or ../tftp
                 or ../rcp)";
              presence "Indicates a ftp node is configured.";
              description
                "Save to ftp: file system";
            }
            container rcp {
              must
                "not(../bootflash or ../compactflash
                 or ../compactflasha or ../usb
                 or ../disk0 or ../disk0a
                 or ../disk1 or ../disk1a
                 or ../disk2 or ../harddisk
                 or ../harddiska or ../harddiskb
                 or ../nvram or ../lcdisk0
                 or ../lcdisk0a or ../tftp
                 or ../ftp)";
              presence "Indicates a rcp node is configured.";
              description
                "Save to rcp: file system";
            }
            leaf save-to-file {
              type string {
                length "1..800" {
                  description
                    "Save to file";
                }
              }
              description
                "Save to file";
            }
          }
        }
      }
    }
  }
  container configuration {
    description
      "Configuration related settings ";
    container commit {
      description
        "auto-save the running configuration";
      container auto-save {
        description
          "auto-save the running configuration";
        container filename {
          must
            "compactflash or compactflasha or usb or disk0
             or disk0a or disk1 or disk1a or disk2
             or harddisk or harddiska or harddiskb or nvram
             or lcdisk0 or lcdisk0a or tftp or ftp or rcp
             or save-to-file";
          presence "Indicates a filename node is configured.";
          description
            "filename to auto-save";
          container bootflash {
            must
              "not(../compactflash or ../compactflasha
               or ../usb or ../disk0
               or ../disk0a or ../disk1
               or ../disk1a or ../disk2
               or ../harddisk or ../harddiska
               or ../harddiskb or ../nvram
               or ../lcdisk0 or ../lcdisk0a
               or ../tftp or ../ftp
               or ../rcp)";
            presence "Indicates a bootflash node is configured.";
            description
              "Save to bootflash: file system";
          }
          container compactflash {
            if-feature "cflash_fs_supp_check";
            must
              "not(../bootflash or ../compactflasha
               or ../usb or ../disk0
               or ../disk0a or ../disk1
               or ../disk1a or ../disk2
               or ../harddisk or ../harddiska
               or ../harddiskb or ../nvram
               or ../lcdisk0 or ../lcdisk0a
               or ../tftp or ../ftp
               or ../rcp)";
            presence "Indicates a compactflash node is configured.";
            description
              "Save to compactflash: file system";
          }
          container compactflasha {
            if-feature "cflash_fs_supp_check";
            must
              "not(../bootflash or ../compactflash
               or ../usb or ../disk0
               or ../disk0a or ../disk1
               or ../disk1a or ../disk2
               or ../harddisk or ../harddiska
               or ../harddiskb or ../nvram
               or ../lcdisk0 or ../lcdisk0a
               or ../tftp or ../ftp
               or ../rcp)";
            presence "Indicates a compactflasha node is configured.";
            description
              "Save to compactflasha: file system";
          }
          container usb {
            if-feature "usb_fs_supp_check";
            must
              "not(../bootflash or ../compactflash
               or ../compactflasha or ../disk0
               or ../disk0a or ../disk1
               or ../disk1a or ../disk2
               or ../harddisk or ../harddiska
               or ../harddiskb or ../nvram
               or ../lcdisk0 or ../lcdisk0a
               or ../tftp or ../ftp
               or ../rcp)";
            presence "Indicates a usb node is configured.";
            description
              "Save to usb: file system";
          }
          container disk0 {
            must
              "not(../bootflash or ../compactflash
               or ../compactflasha or ../usb
               or ../disk0a or ../disk1
               or ../disk1a or ../disk2
               or ../harddisk or ../harddiska
               or ../harddiskb or ../nvram
               or ../lcdisk0 or ../lcdisk0a
               or ../tftp or ../ftp
               or ../rcp)";
            presence "Indicates a disk0 node is configured.";
            description
              "Save to disk0: file system";
          }
          container disk0a {
            must
              "not(../bootflash or ../compactflash
               or ../compactflasha or ../usb
               or ../disk0 or ../disk1
               or ../disk1a or ../disk2
               or ../harddisk or ../harddiska
               or ../harddiskb or ../nvram
               or ../lcdisk0 or ../lcdisk0a
               or ../tftp or ../ftp
               or ../rcp)";
            presence "Indicates a disk0a node is configured.";
            description
              "Save to disk0a: file system";
          }
          container disk1 {
            must
              "not(../bootflash or ../compactflash
               or ../compactflasha or ../usb
               or ../disk0 or ../disk0a
               or ../disk1a or ../disk2
               or ../harddisk or ../harddiska
               or ../harddiskb or ../nvram
               or ../lcdisk0 or ../lcdisk0a
               or ../tftp or ../ftp
               or ../rcp)";
            presence "Indicates a disk1 node is configured.";
            description
              "Save to disk1: file system";
          }
          container disk1a {
            must
              "not(../bootflash or ../compactflash
               or ../compactflasha or ../usb
               or ../disk0 or ../disk0a
               or ../disk1 or ../disk2
               or ../harddisk or ../harddiska
               or ../harddiskb or ../nvram
               or ../lcdisk0 or ../lcdisk0a
               or ../tftp or ../ftp
               or ../rcp)";
            presence "Indicates a disk1a node is configured.";
            description
              "Save to disk1a: file system";
          }
          container disk2 {
            if-feature "disk2_fs_supp_check";
            must
              "not(../bootflash or ../compactflash
               or ../compactflasha or ../usb
               or ../disk0 or ../disk0a
               or ../disk1 or ../disk1a
               or ../harddisk or ../harddiska
               or ../harddiskb or ../nvram
               or ../lcdisk0 or ../lcdisk0a
               or ../tftp or ../ftp
               or ../rcp)";
            presence "Indicates a disk2 node is configured.";
            description
              "Save to disk2: file system";
          }
          container harddisk {
            if-feature "harddisk_fs_supp_check";
            must
              "not(../bootflash or ../compactflash
               or ../compactflasha or ../usb
               or ../disk0 or ../disk0a
               or ../disk1 or ../disk1a
               or ../disk2 or ../harddiska
               or ../harddiskb or ../nvram
               or ../lcdisk0 or ../lcdisk0a
               or ../tftp or ../ftp
               or ../rcp)";
            presence "Indicates a harddisk node is configured.";
            description
              "Save to harddisk: file system";
          }
          container harddiska {
            if-feature "harddisk_fs_supp_check";
            must
              "not(../bootflash or ../compactflash
               or ../compactflasha or ../usb
               or ../disk0 or ../disk0a
               or ../disk1 or ../disk1a
               or ../disk2 or ../harddisk
               or ../harddiskb or ../nvram
               or ../lcdisk0 or ../lcdisk0a
               or ../tftp or ../ftp
               or ../rcp)";
            presence "Indicates a harddiska node is configured.";
            description
              "Save to harddiska: file system";
          }
          container harddiskb {
            if-feature "harddisk_fs_supp_check";
            must
              "not(../bootflash or ../compactflash
               or ../compactflasha or ../usb
               or ../disk0 or ../disk0a
               or ../disk1 or ../disk1a
               or ../disk2 or ../harddisk
               or ../harddiska or ../nvram
               or ../lcdisk0 or ../lcdisk0a
               or ../tftp or ../ftp
               or ../rcp)";
            presence "Indicates a harddiskb node is configured.";
            description
              "Save to harddiskb: file system";
          }
          container nvram {
            must
              "not(../bootflash or ../compactflash
               or ../compactflasha or ../usb
               or ../disk0 or ../disk0a
               or ../disk1 or ../disk1a
               or ../disk2 or ../harddisk
               or ../harddiska or ../harddiskb
               or ../lcdisk0 or ../lcdisk0a
               or ../tftp or ../ftp
               or ../rcp)";
            presence "Indicates a nvram node is configured.";
            description
              "Save to nvram: file system";
          }
          container lcdisk0 {
            if-feature "lcdisk_fs_supp_check";
            must
              "not(../bootflash or ../compactflash
               or ../compactflasha or ../usb
               or ../disk0 or ../disk0a
               or ../disk1 or ../disk1a
               or ../disk2 or ../harddisk
               or ../harddiska or ../harddiskb
               or ../nvram or ../lcdisk0a
               or ../tftp or ../ftp
               or ../rcp)";
            presence "Indicates a lcdisk0 node is configured.";
            description
              "Save to lcdisk0: file system";
          }
          container lcdisk0a {
            if-feature "lcdisk_fs_supp_check";
            must
              "not(../bootflash or ../compactflash
               or ../compactflasha or ../usb
               or ../disk0 or ../disk0a
               or ../disk1 or ../disk1a
               or ../disk2 or ../harddisk
               or ../harddiska or ../harddiskb
               or ../nvram or ../lcdisk0
               or ../tftp or ../ftp
               or ../rcp)";
            presence "Indicates a lcdisk0a node is configured.";
            description
              "Save to lcdisk0a: file system";
          }
          container tftp {
            must
              "not(../bootflash or ../compactflash
               or ../compactflasha or ../usb
               or ../disk0 or ../disk0a
               or ../disk1 or ../disk1a
               or ../disk2 or ../harddisk
               or ../harddiska or ../harddiskb
               or ../nvram or ../lcdisk0
               or ../lcdisk0a or ../ftp
               or ../rcp)";
            presence "Indicates a tftp node is configured.";
            description
              "Save to tftp: file system";
          }
          container ftp {
            must
              "not(../bootflash or ../compactflash
               or ../compactflasha or ../usb
               or ../disk0 or ../disk0a
               or ../disk1 or ../disk1a
               or ../disk2 or ../harddisk
               or ../harddiska or ../harddiskb
               or ../nvram or ../lcdisk0
               or ../lcdisk0a or ../tftp
               or ../rcp)";
            presence "Indicates a ftp node is configured.";
            description
              "Save to ftp: file system";
          }
          container rcp {
            must
              "not(../bootflash or ../compactflash
               or ../compactflasha or ../usb
               or ../disk0 or ../disk0a
               or ../disk1 or ../disk1a
               or ../disk2 or ../harddisk
               or ../harddiska or ../harddiskb
               or ../nvram or ../lcdisk0
               or ../lcdisk0a or ../tftp
               or ../ftp)";
            presence "Indicates a rcp node is configured.";
            description
              "Save to rcp: file system";
          }
          leaf save-to-file {
            type string {
              length "1..800" {
                description
                  "Save to file";
              }
            }
            description
              "Save to file";
          }
        }
      }
    }
  }
}
