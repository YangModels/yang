module Cisco-IOS-XR-um-config-display-cfg {
  namespace "http://cisco.com/ns/yang/Cisco-IOS-XR-um-config-display-cfg";
  prefix um-config-display-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-display package configuration.
     
     This YANG module augments the
     modules with configuration data.
     
     Copyright (c) 2021 by Cisco Systems, Inc.
     All rights reserved.";

  revision 2021-04-14 {
    description
      "Initial release";
    semver:module-version "1.0.0";
  }

  container ipv4 {
    description
      "Global IPv4 configuration commands";
    container netmask-format {
      description
        "Display mode of ipv4 address mask";
      container bit-count {
        presence "Indicates a bit-count node is configured.";
        description
          "Display ipv4 addess mask in prefix length format";
      }
    }
  }
  container configuration {
    description
      "Configuration related settings";
    container display {
      description
        "Display mode";
      container interface {
        description
          "hardware interfaces";
        container slot-order {
          presence "Indicates a slot-order node is configured.";
          description
            "Display interfaces in the slot-order in show run output";
        }
      }
    }
  }
}
