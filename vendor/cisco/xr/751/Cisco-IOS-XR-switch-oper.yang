module Cisco-IOS-XR-switch-oper {
  namespace "http://cisco.com/ns/yang/Cisco-IOS-XR-switch-oper";
  prefix switch-oper;

  import Cisco-IOS-XR-types {
    prefix xr;
  }
  import cisco-semver {
    prefix semver;
  }
  include Cisco-IOS-XR-switch-oper-sub1 {
    revision-date 2020-08-13;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR switch package operational data.
     
     This module contains definitions
     for the following management objects:
       show-switch: Control plane Ethernet switch data
     
     Copyright (c) 2013-2020 by Cisco Systems, Inc.
     All rights reserved.";

  revision 2020-08-13 {
    description
      "Added an entry for show controller switch data-integrity errror";
    semver:module-version "1.0.0";
  }
  revision 2020-07-16 {
    description
      "Added an entry for show controller switch debug counters";
  }
  revision 2020-06-30 {
    description
      "Added an entry for show controller switch events";
  }
  revision 2020-05-22 {
    description
      "Added an entry for show controller switch health state";
  }
  revision 2020-03-16 {
    description
      "Added an entry for show controller switch txq";
  }
  revision 2019-10-30 {
    description
      "Change class name VLANInfoLnstance to VLANInfoInstance";
  }
  revision 2019-04-05 {
    description
      "Establish semantic version baseline.";
  }
  revision 2019-03-08 {
    description
      "and entry for show controller switch bridge";
  }
  revision 2019-03-01 {
    description
      "Rename esdma-oper to switch-oper, esdma-emon-oper to emon-oper";
  }
  revision 2019-02-07 {
    description
      "Rework clear and set operations.";
  }
  revision 2019-01-30 {
    description
      "Schema rework to match the CLI.";
  }
  revision 2015-11-09 {
    description
      "IOS XR 6.0 revision.";
  }

  container show-switch {
    config false;
    description
      "Control plane Ethernet switch data";
    container reachable {
      description
        "Lists all control plane Ethernet switches";
      uses ESDMA-SHOW-ETHSW-REACHABLE-INFO;
    }
    container data-integrity {
      description
        "Display switch data-integrity database";
      container data-integrity-error {
        description
          "Display switch data-integrity error database";
        container data-integrity-error-info {
          description
            "Display switch data-integrity error
             information database";
          container data-integrity-error-info-log-table-numbers {
            description
              "Filter data integrity based on logical table";
            list data-integrity-error-info-log-table-number {
              key "log-table";
              description
                "Logical table number";
              container data-integrity-error-info-log-table-location-instances {
                description
                  "switch location";
                list data-integrity-error-info-log-table-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              leaf log-table {
                type uint32;
                description
                  "Logical Table";
              }
            }
          }
          container data-integrity-error-info-mem-type-numbers {
            description
              "Filter data integrity based on memory type";
            list data-integrity-error-info-mem-type-number {
              key "mem-type";
              description
                "Memory type number";
              container data-integrity-error-info-mem-type-location-instances {
                description
                  "switch location";
                list data-integrity-error-info-mem-type-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              container data-integrity-error-info-mem-type-hw-table-numbers {
                description
                  "Filter data integrity based on hardware
                   table";
                list data-integrity-error-info-mem-type-hw-table-number {
                  key "hw-table";
                  description
                    "Hardware table number";
                  container data-integrity-error-info-mem-type-hw-table-log-table-numbers {
                    description
                      "Filter data integrity based on logical
                       table";
                    list data-integrity-error-info-mem-type-hw-table-log-table-number {
                      key "log-table";
                      description
                        "Logical table number";
                      container data-integrity-error-info-mem-type-hw-table-log-table-location-instances {
                        description
                          "switch location";
                        list data-integrity-error-info-mem-type-hw-table-log-table-location-instance {
                          key "node-id";
                          description
                            "Location information for switch data
                             integrity information";
                          leaf node-id {
                            type xr:Node-id;
                            description
                              "NodeID of the Location";
                          }
                          uses ESDMA-SHOW-ETHSW-DATA-INTEGRITY-ERROR-INFO;
                        }
                      }
                      leaf log-table {
                        type uint32;
                        description
                          "Logical Table";
                      }
                    }
                  }
                  container data-integrity-error-info-mem-type-hw-table-location-instances {
                    description
                      "switch location";
                    list data-integrity-error-info-mem-type-hw-table-location-instance {
                      key "node-id";
                      description
                        "Location information for switch data
                         integrity information";
                      leaf node-id {
                        type xr:Node-id;
                        description
                          "NodeID of the Location";
                      }
                      uses ESDMA-SHOW-ETHSW-DATA-INTEGRITY-ERROR-INFO;
                    }
                  }
                  leaf hw-table {
                    type uint32;
                    description
                      "Hardware Table";
                  }
                }
              }
              leaf mem-type {
                type uint32;
                description
                  "Memory Type";
              }
            }
          }
          container data-integrity-error-info-hw-table-numbers {
            description
              "Filter data integrity based on hardware table";
            list data-integrity-error-info-hw-table-number {
              key "hw-table";
              description
                "Hardware table number";
              container data-integrity-error-info-hw-table-location-instances {
                description
                  "switch location";
                list data-integrity-error-info-hw-table-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              container data-integrity-error-info-hw-table-log-table-numbers {
                description
                  "Filter data integrity based on logical
                   table";
                list data-integrity-error-info-hw-table-log-table-number {
                  key "log-table";
                  description
                    "Logical table number";
                  container data-integrity-error-info-hw-table-log-table-location-instances {
                    description
                      "switch location";
                    list data-integrity-error-info-hw-table-log-table-location-instance {
                      key "node-id";
                      description
                        "Location information for switch data
                         integrity information";
                      leaf node-id {
                        type xr:Node-id;
                        description
                          "NodeID of the Location";
                      }
                      uses ESDMA-SHOW-ETHSW-DATA-INTEGRITY-ERROR-INFO;
                    }
                  }
                  leaf log-table {
                    type uint32;
                    description
                      "Logical Table";
                  }
                }
              }
              leaf hw-table {
                type uint32;
                description
                  "Hardware Table";
              }
            }
          }
          container data-integrity-error-info-location-instances {
            description
              "switch location";
            list data-integrity-error-info-location-instance {
              key "node-id";
              description
                "Location information for switch data
                 integrity information";
              leaf node-id {
                type xr:Node-id;
                description
                  "NodeID of the Location";
              }
              uses ESDMA-SHOW-ETHSW-DATA-INTEGRITY-ERROR-INFO;
            }
          }
        }
        container data-integrity-error-history {
          description
            "Display switch data-integrity error history
             database";
          container data-integrity-error-history-log-table-numbers {
            description
              "Filter data integrity based on logical table";
            list data-integrity-error-history-log-table-number {
              key "log-table";
              description
                "Logical table number";
              container data-integrity-error-history-log-table-location-instances {
                description
                  "switch location";
                list data-integrity-error-history-log-table-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              leaf log-table {
                type uint32;
                description
                  "Logical Table";
              }
            }
          }
          container data-integrity-error-history-mem-type-numbers {
            description
              "Filter data integrity based on memory type";
            list data-integrity-error-history-mem-type-number {
              key "mem-type";
              description
                "Memory type number";
              container data-integrity-error-history-mem-type-location-instances {
                description
                  "switch location";
                list data-integrity-error-history-mem-type-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              container data-integrity-error-history-mem-type-hw-table-numbers {
                description
                  "Filter data integrity based on hardware
                   table";
                list data-integrity-error-history-mem-type-hw-table-number {
                  key "hw-table";
                  description
                    "Hardware table number";
                  container data-integrity-error-history-mem-type-hw-table-log-table-numbers {
                    description
                      "Filter data integrity based on logical
                       table";
                    list data-integrity-error-history-mem-type-hw-table-log-table-number {
                      key "log-table";
                      description
                        "Logical table number";
                      container data-integrity-error-history-mem-type-hw-table-log-table-location-instances {
                        description
                          "switch location";
                        list data-integrity-error-history-mem-type-hw-table-log-table-location-instance {
                          key "node-id";
                          description
                            "Location information for switch data
                             integrity information";
                          leaf node-id {
                            type xr:Node-id;
                            description
                              "NodeID of the Location";
                          }
                          uses ESDMA-SHOW-ETHSW-DATA-INTEGRITY-ERROR-INFO;
                        }
                      }
                      leaf log-table {
                        type uint32;
                        description
                          "Logical Table";
                      }
                    }
                  }
                  container data-integrity-error-history-mem-type-hw-table-location-instances {
                    description
                      "switch location";
                    list data-integrity-error-history-mem-type-hw-table-location-instance {
                      key "node-id";
                      description
                        "Location information for switch data
                         integrity information";
                      leaf node-id {
                        type xr:Node-id;
                        description
                          "NodeID of the Location";
                      }
                      uses ESDMA-SHOW-ETHSW-DATA-INTEGRITY-ERROR-INFO;
                    }
                  }
                  leaf hw-table {
                    type uint32;
                    description
                      "Hardware Table";
                  }
                }
              }
              leaf mem-type {
                type uint32;
                description
                  "Memory Type";
              }
            }
          }
          container data-integrity-error-history-hw-table-numbers {
            description
              "Filter data integrity based on hardware table";
            list data-integrity-error-history-hw-table-number {
              key "hw-table";
              description
                "Hardware table number";
              container data-integrity-error-history-hw-table-location-instances {
                description
                  "switch location";
                list data-integrity-error-history-hw-table-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              container data-integrity-error-history-hw-table-log-table-numbers {
                description
                  "Filter data integrity based on logical
                   table";
                list data-integrity-error-history-hw-table-log-table-number {
                  key "log-table";
                  description
                    "Logical table number";
                  container data-integrity-error-history-hw-table-log-table-location-instances {
                    description
                      "switch location";
                    list data-integrity-error-history-hw-table-log-table-location-instance {
                      key "node-id";
                      description
                        "Location information for switch data
                         integrity information";
                      leaf node-id {
                        type xr:Node-id;
                        description
                          "NodeID of the Location";
                      }
                      uses ESDMA-SHOW-ETHSW-DATA-INTEGRITY-ERROR-INFO;
                    }
                  }
                  leaf log-table {
                    type uint32;
                    description
                      "Logical Table";
                  }
                }
              }
              leaf hw-table {
                type uint32;
                description
                  "Hardware Table";
              }
            }
          }
          container data-integrity-error-history-location-instances {
            description
              "switch location";
            list data-integrity-error-history-location-instance {
              key "node-id";
              description
                "Location information for switch data
                 integrity information";
              leaf node-id {
                type xr:Node-id;
                description
                  "NodeID of the Location";
              }
              uses ESDMA-SHOW-ETHSW-DATA-INTEGRITY-ERROR-INFO;
            }
          }
        }
        container data-integrity-error-summary {
          description
            "Display switch data-integrity error summary
             database";
          container data-integrity-error-summary-mem-type-numbers {
            description
              "Filter data integrity based on memory type";
            list data-integrity-error-summary-mem-type-number {
              key "mem-type";
              description
                "Memory type number";
              container data-integrity-error-summary-mem-type-location-instances {
                description
                  "switch location";
                list data-integrity-error-summary-mem-type-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              container data-integrity-error-summary-mem-type-hw-table-numbers {
                description
                  "Filter data integrity based on hardware
                   table";
                list data-integrity-error-summary-mem-type-hw-table-number {
                  key "hw-table";
                  description
                    "Hardware table number";
                  container data-integrity-error-summary-mem-type-hw-table-location-instances {
                    description
                      "switch location";
                    list data-integrity-error-summary-mem-type-hw-table-location-instance {
                      key "node-id";
                      description
                        "Location information for switch data
                         integrity information";
                      leaf node-id {
                        type xr:Node-id;
                        description
                          "NodeID of the Location";
                      }
                      uses ESDMA-SHOW-ETHSW-DATA-INTEGRITY-ERROR-INFO;
                    }
                  }
                  container data-integrity-error-summary-mem-type-hw-table-log-table-numbers {
                    description
                      "Filter data integrity based on logical
                       table";
                    list data-integrity-error-summary-mem-type-hw-table-log-table-number {
                      key "log-table";
                      description
                        "Logical table number";
                      container data-integrity-error-summary-mem-type-hw-table-log-table-location-instances {
                        description
                          "switch location";
                        list data-integrity-error-summary-mem-type-hw-table-log-table-location-instance {
                          key "node-id";
                          description
                            "Location information for switch data
                             integrity information";
                          leaf node-id {
                            type xr:Node-id;
                            description
                              "NodeID of the Location";
                          }
                          uses ESDMA-SHOW-ETHSW-DATA-INTEGRITY-ERROR-INFO;
                        }
                      }
                      leaf log-table {
                        type uint32;
                        description
                          "Logical Table";
                      }
                    }
                  }
                  leaf hw-table {
                    type uint32;
                    description
                      "Hardware Table";
                  }
                }
              }
              leaf mem-type {
                type uint32;
                description
                  "Memory Type";
              }
            }
          }
          container data-integrity-error-summary-location-instances {
            description
              "switch location";
            list data-integrity-error-summary-location-instance {
              key "node-id";
              description
                "Location information for switch data
                 integrity information";
              leaf node-id {
                type xr:Node-id;
                description
                  "NodeID of the Location";
              }
              uses ESDMA-SHOW-ETHSW-DATA-INTEGRITY-ERROR-INFO;
            }
          }
          container data-integrity-error-summary-hw-table-numbers {
            description
              "Filter data integrity based on hardware table";
            list data-integrity-error-summary-hw-table-number {
              key "hw-table";
              description
                "Hardware table number";
              container data-integrity-error-summary-hw-table-location-instances {
                description
                  "switch location";
                list data-integrity-error-summary-hw-table-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              container data-integrity-error-summary-hw-table-log-table-numbers {
                description
                  "Filter data integrity based on logical
                   table";
                list data-integrity-error-summary-hw-table-log-table-number {
                  key "log-table";
                  description
                    "Logical table number";
                  container data-integrity-error-summary-hw-table-log-table-location-instances {
                    description
                      "switch location";
                    list data-integrity-error-summary-hw-table-log-table-location-instance {
                      key "node-id";
                      description
                        "Location information for switch data
                         integrity information";
                      leaf node-id {
                        type xr:Node-id;
                        description
                          "NodeID of the Location";
                      }
                      uses ESDMA-SHOW-ETHSW-DATA-INTEGRITY-ERROR-INFO;
                    }
                  }
                  leaf log-table {
                    type uint32;
                    description
                      "Logical Table";
                  }
                }
              }
              leaf hw-table {
                type uint32;
                description
                  "Hardware Table";
              }
            }
          }
          container data-integrity-error-summary-log-table-numbers {
            description
              "Filter data integrity based on logical table";
            list data-integrity-error-summary-log-table-number {
              key "log-table";
              description
                "Logical table number";
              container data-integrity-error-summary-log-table-location-instances {
                description
                  "switch location";
                list data-integrity-error-summary-log-table-location-instance {
                  key "node-id";
                  description
                    "Location information for switch data
                     integrity information";
                  leaf node-id {
                    type xr:Node-id;
                    description
                      "NodeID of the Location";
                  }
                  uses ESDMA-SHOW-ETHSW-DATA-INTEGRITY-ERROR-INFO;
                }
              }
              leaf log-table {
                type uint32;
                description
                  "Logical Table";
              }
            }
          }
        }
      }
    }
    container mac {
      description
        "Display mac information";
      container mac-instances {
        description
          "switch location";
        list mac-instance {
          key "node-id";
          description
            "Location information for switch MAC
             information";
          container mac-port-numbers {
            description
              "MAC filter type: Port";
            list mac-port-number {
              key "port";
              description
                "Port number filter for switch MAC
                 information";
              leaf port {
                type uint32;
                description
                  "Port number";
              }
              uses ESDMA-SHOW-ETHSW-REGISTER-INFO;
            }
          }
          leaf node-id {
            type xr:Node-id;
            description
              "NodeID of the Location";
          }
        }
      }
    }
    container fdb {
      description
        "Display switch forwarding database";
      container fdb-mac-addresses {
        description
          "FDB filter type: Mac";
        list fdb-mac-address {
          key "mac";
          description
            "Mac Address";
          container fdb-mac-instances {
            description
              "switch location";
            list fdb-mac-instance {
              key "node-id";
              description
                "Location information for switch FDB MAC
                 information";
              leaf node-id {
                type xr:Node-id;
                description
                  "NodeID of the Location";
              }
              uses ESDMA-SHOW-ETHSW-FDB-INFO;
            }
          }
          leaf mac {
            type xr:Cisco-ios-xr-string;
            description
              "Mac address";
          }
        }
      }
      container fdb-statistics {
        description
          "FDB request type: Statistics";
        container fdb-statistics-instances {
          description
            "switch location";
          list fdb-statistics-instance {
            key "node-id";
            description
              "Location information for switch FDB
               statistics information";
            leaf node-id {
              type xr:Node-id;
              description
                "NodeID of the Location";
            }
            uses ESDMA-SHOW-ETHSW-FDB-INFO;
          }
        }
      }
      container fdb-instances {
        description
          "switch location";
        list fdb-instance {
          key "node-id";
          description
            "Location information for switch FDB
             information";
          leaf node-id {
            type xr:Node-id;
            description
              "NodeID of the Location";
          }
          uses ESDMA-SHOW-ETHSW-FDB-INFO;
        }
      }
      container fdb-port-numbers {
        description
          "FDB filter type: Port";
        list fdb-port-number {
          key "port";
          description
            "Port number";
          container fdb-port-instances {
            description
              "switch location";
            list fdb-port-instance {
              key "node-id";
              description
                "Location information for switch FDB port
                 information";
              leaf node-id {
                type xr:Node-id;
                description
                  "NodeID of the Location";
              }
              uses ESDMA-SHOW-ETHSW-FDB-INFO;
            }
          }
          leaf port {
            type uint32;
            description
              "Port number";
          }
        }
      }
      container fdb-vlan-ids {
        description
          "FDB filter type: VLAN";
        list fdb-vlan-id {
          key "vlan";
          description
            "VLAN ID";
          container fdb-vlan-instances {
            description
              "switch location";
            list fdb-vlan-instance {
              key "node-id";
              description
                "Location information for switch FDB VLAN
                 information";
              leaf node-id {
                type xr:Node-id;
                description
                  "NodeID of the Location";
              }
              uses ESDMA-SHOW-ETHSW-FDB-INFO;
            }
          }
          leaf vlan {
            type uint32;
            description
              "VLAN Id";
          }
        }
      }
    }
    container bridge {
      description
        "Display switch bridge information";
      container bridge-statistics {
        description
          "Bridge request type, currently one option,
           statistics";
        container bridge-statistics-instances {
          description
            "switch location";
          list bridge-statistics-instance {
            key "node-id";
            description
              "Location information for switch bridge
               information";
            leaf node-id {
              type xr:Node-id;
              description
                "NodeID of the Location";
            }
            uses ESDMA-SHOW-ETHSW-BRIDGE-INFO;
          }
        }
      }
      container bridge-instances {
        description
          "switch location";
        list bridge-instance {
          key "node-id";
          description
            "Location information for switch bridge
             information";
          leaf node-id {
            type xr:Node-id;
            description
              "NodeID of the Location";
          }
          uses ESDMA-SHOW-ETHSW-BRIDGE-INFO;
        }
      }
    }
    container debug {
      description
        "Display switch debug info";
      container debug-counters {
        description
          "Display switch debug counters";
        container debug-counters-instances {
          description
            "Switch location";
          list debug-counters-instance {
            key "node-id";
            description
              "Location information for switch debug
               counters information";
            leaf node-id {
              type xr:Node-id;
              description
                "NodeID of the Location";
            }
            uses ESDMA-SHOW-ETHSW-DEBUG-COUNTERS-INFO;
          }
        }
      }
    }
    container health {
      description
        "Display switch health info";
      container health-state {
        description
          "Display switch health state";
        container health-state-instances {
          description
            "Switch location";
          list health-state-instance {
            key "node-id";
            description
              "Location information for switch health
               information";
            container health-state-port-numbers {
              description
                "Filter health state based on Port";
              list health-state-port-number {
                key "port-num";
                description
                  "Port Number";
                leaf port-num {
                  type uint32;
                  description
                    "Port Num";
                }
                uses ESDMA-SHOW-ETHSW-HEALTH-STATE-INFO;
              }
            }
            leaf node-id {
              type xr:Node-id;
              description
                "NodeID of the Location";
            }
          }
        }
      }
    }
    container trunk {
      description
        "Display the switch trunk group information";
      container trunk-instances {
        description
          "switch location";
        list trunk-instance {
          key "node-id";
          description
            "Location information for switch trunk group
             information";
          container trunk-port-numbers {
            description
              "Filter Trunk based on Port";
            list trunk-port-number {
              key "port";
              description
                "Port number filter for switch trunk group
                 information";
              leaf port {
                type uint32;
                description
                  "Port number";
              }
              uses ESDMA-SHOW-ETHSW-TRUNK-INFO;
            }
          }
          leaf node-id {
            type xr:Node-id;
            description
              "NodeID of the Location";
          }
        }
      }
    }
    container summary {
      description
        "Show summary switch status";
      container summary-instances {
        description
          "switch location";
        list summary-instance {
          key "node-id";
          description
            "Location information for switch summary status";
          container summary-port-numbers {
            description
              "Filter summary based on Port";
            list summary-port-number {
              key "port";
              description
                "Port information";
              leaf port {
                type uint32;
                description
                  "Port number";
              }
              uses ESDMA-SHOW-ETHSW-SUMMARY-INFO;
            }
          }
          leaf node-id {
            type xr:Node-id;
            description
              "NodeID of the Location";
          }
        }
      }
    }
    container all {
      description
        "Display all switch data";
      container all-instances {
        description
          "switch location";
        list all-instance {
          key "node-id";
          description
            "Location information for switch data";
          leaf node-id {
            type xr:Node-id;
            description
              "NodeID of the Location";
          }
          uses ESDMA-SHOW-ETHSW-ALL-INFO;
        }
      }
    }
    container txq {
      description
        "Display switch Txq info";
      container txq-statistics {
        description
          "Display txq statistics";
        container txq-statistics-instances {
          description
            "Switch location";
          list txq-statistics-instance {
            key "node-id";
            description
              "Location information for switch txq
               information";
            container txq-statistics-port-numbers {
              description
                "Filter txq Statistics based on Port";
              list txq-statistics-port-number {
                key "port-num";
                description
                  "Port Number";
                leaf port-num {
                  type uint32;
                  description
                    "Port Num";
                }
                uses ESDMA-SHOW-ETHSW-TXQ-INFO;
              }
            }
            leaf node-id {
              type xr:Node-id;
              description
                "NodeID of the Location";
            }
          }
        }
        container txq-statistics-detail {
          description
            "Detailed switch txq statistics";
          container txq-statistics-detail-instances {
            description
              "Switch location";
            list txq-statistics-detail-instance {
              key "node-id";
              description
                "Location information for switch txq
                 information";
              container txq-statistics-detail-port-numbers {
                description
                  "Filter txq Statistics based on Port";
                list txq-statistics-detail-port-number {
                  key "port-num";
                  description
                    "Port Number";
                  leaf port-num {
                    type uint32;
                    description
                      "Port Num";
                  }
                  uses ESDMA-SHOW-ETHSW-TXQ-INFO;
                }
              }
              leaf node-id {
                type xr:Node-id;
                description
                  "NodeID of the Location";
              }
            }
          }
        }
      }
      container txq-config {
        description
          "Display switch Txq config";
        container txq-config-instances {
          description
            "Switch location";
          list txq-config-instance {
            key "node-id";
            description
              "Location information for switch txq
               information";
            container txq-config-port-numbers {
              description
                "Filter txq config based on Port";
              list txq-config-port-number {
                key "port-num";
                description
                  "Port Number";
                leaf port-num {
                  type uint32;
                  description
                    "Port Num";
                }
                uses ESDMA-SHOW-ETHSW-TXQ-INFO;
              }
            }
            leaf node-id {
              type xr:Node-id;
              description
                "NodeID of the Location";
            }
          }
        }
      }
    }
    container events {
      description
        "Display all events data";
      container events-instances {
        description
          "switch location";
        list events-instance {
          key "node-id";
          description
            "Location information for switch data";
          leaf node-id {
            type xr:Node-id;
            description
              "NodeID of the Location";
          }
          uses ESDMA-SHOW-ETHSW-EVENTS-INFO;
        }
      }
    }
    container vlan {
      description
        "Control Plane Ethernet VLAN Information";
      container vlan-info {
        description
          "VLAN use information";
        container vlan-info-instances {
          description
            "switch location";
          list vlan-info-instance {
            key "node-id";
            description
              "Location information for switch VLAN
               information";
            leaf node-id {
              type xr:Node-id;
              description
                "NodeID of the Location";
            }
            uses ESDMA-SHOW-ETHSW-VLANINFO-INFO;
          }
        }
      }
      container vlan-membership {
        description
          "List switch port membership of VLANs";
        container vlan-membership-instances {
          description
            "switch location";
          list vlan-membership-instance {
            key "node-id";
            description
              "Location information for switch VLAN
               membership";
            container vlan-membership-vlan-ids {
              description
                "Filter VLAN membership based on VLAN";
              list vlan-membership-vlan-id {
                key "vlan";
                description
                  "VLAN ID filter for VLAN membership
                   information";
                leaf vlan {
                  type uint32;
                  description
                    "VLAN ID";
                }
                uses ESDMA-SHOW-ETHSW-VLANMEMBERSHIP-INFO;
              }
            }
            leaf node-id {
              type xr:Node-id;
              description
                "NodeID of the Location";
            }
          }
        }
      }
    }
    container statistics {
      description
        "Show switch statistics";
      container statistics-detail {
        description
          "Detailed switch port statistics";
        container statistics-detail-instances {
          description
            "switch location";
          list statistics-detail-instance {
            key "node-id";
            description
              "Location for detailed switch port statistics";
            container statistics-detail-port-numbers {
              description
                "Filter statistics detail based on Port";
              list statistics-detail-port-number {
                key "port";
                description
                  "Port number filter for detailed switch port
                   statistics";
                leaf port {
                  type uint32;
                  description
                    "Port number";
                }
                uses ESDMA-SHOW-ETHSW-STATISTICS-INFO;
              }
            }
            leaf node-id {
              type xr:Node-id;
              description
                "NodeID of the Location";
            }
          }
        }
      }
      container statistics-instances {
        description
          "switch location";
        list statistics-instance {
          key "node-id";
          description
            "Location information for switch statistics";
          container statistics-port-numbers {
            description
              "Filter statistics based on Port";
            list statistics-port-number {
              key "port";
              description
                "Port number filter for switch port
                 statistics";
              leaf port {
                type uint32;
                description
                  "Port number";
              }
              uses ESDMA-SHOW-ETHSW-STATISTICS-INFO;
            }
          }
          leaf node-id {
            type xr:Node-id;
            description
              "NodeID of the Location";
          }
        }
      }
    }
    container policing {
      description
        "Display switch policing database";
      container policing-statistics {
        description
          "Display policing Statistics";
        container policing-statistics-port-numbers {
          description
            "Filter policing Statistics based on Port";
          list policing-statistics-port-number {
            key "port-num";
            description
              "Port Number";
            container policing-statistics-port-instances {
              description
                "switch location";
              list policing-statistics-port-instance {
                key "node-id";
                description
                  "Location information for switch policing
                   information";
                leaf node-id {
                  type xr:Node-id;
                  description
                    "NodeID of the Location";
                }
                uses ESDMA-SHOW-ETHSW-POLICING-INFO;
              }
            }
            container policing-statistics-port-vlan-ids {
              description
                "Filter policing Statistics based on source
                 vlan";
              list policing-statistics-port-vlan-id {
                key "vlan-id";
                description
                  "VLAN ID";
                container policing-statistics-port-vlan-instances {
                  description
                    "switch location";
                  list policing-statistics-port-vlan-instance {
                    key "node-id";
                    description
                      "Location information for switch policing
                       information";
                    leaf node-id {
                      type xr:Node-id;
                      description
                        "NodeID of the Location";
                    }
                    uses ESDMA-SHOW-ETHSW-POLICING-INFO;
                  }
                }
                leaf vlan-id {
                  type uint32;
                  description
                    "VLAN Id";
                }
              }
            }
            leaf port-num {
              type uint32;
              description
                "Port Num";
            }
          }
        }
        container policing-statistics-vlan-ids {
          description
            "Filter policing Statistics based on source
             vlan";
          list policing-statistics-vlan-id {
            key "vlan-id";
            description
              "VLAN ID";
            container policing-statistics-vlan-instances {
              description
                "switch location";
              list policing-statistics-vlan-instance {
                key "node-id";
                description
                  "Location information for switch policing
                   information";
                leaf node-id {
                  type xr:Node-id;
                  description
                    "NodeID of the Location";
                }
                uses ESDMA-SHOW-ETHSW-POLICING-INFO;
              }
            }
            leaf vlan-id {
              type uint32;
              description
                "VLAN Id";
            }
          }
        }
        container policing-statistics-instances {
          description
            "switch location";
          list policing-statistics-instance {
            key "node-id";
            description
              "Location information for switch policing
               information";
            leaf node-id {
              type xr:Node-id;
              description
                "NodeID of the Location";
            }
            uses ESDMA-SHOW-ETHSW-POLICING-INFO;
          }
        }
      }
      container policing-config {
        description
          "Display policing config";
        container policing-config-port-numbers {
          description
            "Filter policing config based on Port";
          list policing-config-port-number {
            key "port-num";
            description
              "Port Number";
            container policing-config-port-instances {
              description
                "switch location";
              list policing-config-port-instance {
                key "node-id";
                description
                  "Location information for switch policing
                   information";
                leaf node-id {
                  type xr:Node-id;
                  description
                    "NodeID of the Location";
                }
                uses ESDMA-SHOW-ETHSW-POLICING-INFO;
              }
            }
            container policing-config-port-vlan-ids {
              description
                "Filter policing config based on source vlan";
              list policing-config-port-vlan-id {
                key "vlan-id";
                description
                  "VLAN ID";
                container policing-config-port-vlan-instances {
                  description
                    "switch location";
                  list policing-config-port-vlan-instance {
                    key "node-id";
                    description
                      "Location information for switch policing
                       information";
                    leaf node-id {
                      type xr:Node-id;
                      description
                        "NodeID of the Location";
                    }
                    uses ESDMA-SHOW-ETHSW-POLICING-INFO;
                  }
                }
                leaf vlan-id {
                  type uint32;
                  description
                    "VLAN Id";
                }
              }
            }
            leaf port-num {
              type uint32;
              description
                "Port Num";
            }
          }
        }
        container policing-config-vlan-ids {
          description
            "Filter policing config based on source vlan";
          list policing-config-vlan-id {
            key "vlan-id";
            description
              "VLAN ID";
            container policing-config-vlan-instances {
              description
                "switch location";
              list policing-config-vlan-instance {
                key "node-id";
                description
                  "Location information for switch policing
                   information";
                leaf node-id {
                  type xr:Node-id;
                  description
                    "NodeID of the Location";
                }
                uses ESDMA-SHOW-ETHSW-POLICING-INFO;
              }
            }
            leaf vlan-id {
              type uint32;
              description
                "VLAN Id";
            }
          }
        }
        container policing-config-instances {
          description
            "switch location";
          list policing-config-instance {
            key "node-id";
            description
              "Location information for switch policing
               information";
            leaf node-id {
              type xr:Node-id;
              description
                "NodeID of the Location";
            }
            uses ESDMA-SHOW-ETHSW-POLICING-INFO;
          }
        }
      }
    }
    container serdes {
      description
        "Display serdes information";
      container serdes-instances {
        description
          "switch location";
        list serdes-instance {
          key "node-id";
          description
            "Location information for switch SERDES
             information";
          container serdes-port-numbers {
            description
              "SERDES filter type: Port";
            list serdes-port-number {
              key "port";
              description
                "Port number filter for switch Serdes
                 information";
              leaf port {
                type uint32;
                description
                  "Port number";
              }
              uses ESDMA-SHOW-ETHSW-REGISTER-INFO;
            }
          }
          leaf node-id {
            type xr:Node-id;
            description
              "NodeID of the Location";
          }
        }
      }
    }
  }
}
