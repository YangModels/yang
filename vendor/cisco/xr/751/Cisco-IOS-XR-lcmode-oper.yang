module Cisco-IOS-XR-lcmode-oper {
  namespace "http://cisco.com/ns/yang/Cisco-IOS-XR-lcmode-oper";
  prefix lcmode-oper;

  import cisco-semver {
    prefix semver;
  }
  include Cisco-IOS-XR-lcmode-oper-sub1 {
    revision-date 2021-06-28;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lcmode package operational data.
     
     This module contains definitions
     for the following management objects:
       show-lcmodule: Show lc-module
     
     Copyright (c) 2013-2021 by Cisco Systems, Inc.
     All rights reserved.";

  revision 2021-06-28 {
    description
      "LCMODE for OTUCn-REGEN added
       2020-12-24
         LCMODE for FC-MXP added";
    semver:module-version "1.1.0";
  }
  revision 2019-04-05 {
    description
      "Establish semantic version baseline.";
    semver:module-version "1.0.0";
  }
  revision 2015-11-09 {
    description
      "IOS XR 6.0 revision.";
  }

  container show-lcmodule {
    config false;
    description
      "Show lc-module";
    container lcmode-gl {
      description
        "gl";
      container lcmode-slots {
        description
          "lcmode";
        list lcmode-slot {
          key "slot-id";
          description
            "Per slot lcmode data";
          leaf slot-id {
            type uint32;
            description
              "Slot Id";
          }
          uses LCMODE-INFO;
        }
      }
    }
  }
}
