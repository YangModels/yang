module Cisco-IOS-XR-um-snmp-server-cfg {
  namespace "http://cisco.com/ns/yang/Cisco-IOS-XR-um-snmp-server-cfg";
  prefix um-snmp-server-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR snmp-server package configuration.
     
     This YANG module augments the
     modules with configuration data.
     
     Copyright (c) 2019-2021 by Cisco Systems, Inc.
     All rights reserved.";

  revision 2020-04-14 {
    description
      "Added snmp agent configuration nodes.";
    semver:module-version "1.1.0";
  }
  revision 2019-06-10 {
    description
      "Establish semantic version baseline.";
    semver:module-version "1.0.1";
  }
  revision 2019-04-12 {
    description
      "Initial version";
  }

  feature is_dying_gasp_supported {
    description
      "is dying gasp supported";
  }

  container snmp-server-mibs {
    description
      "MIB for configurations";
  }
  container snmp-server {
    description
      "SNMP configuration subcommands";
    container community {
      description
        "Enable SNMP;  set community string and access privileges";
      container unencrypted {
        description
          "The UNENCRYPTED (cleartext) community string";
        list unencrypted-string {
          key "community-string";
          description
            "The UNENCRYPTED (cleartext) community string";
          leaf community-string {
            type string {
              length "1..32" {
                description
                  "The UNENCRYPTED community string";
              }
            }
            description
              "The UNENCRYPTED (cleartext) community string";
          }
          leaf view {
            type xr:Cisco-ios-xr-string {
              length "1..1024" {
                description
                  "MIB view to which the community has access";
              }
            }
            description
              "Restrict this community to a named view";
          }
          container ro {
            must "not(../rw)";
            presence "Indicates a ro node is configured.";
            description
              "Read-only community";
          }
          container rw {
            must "not(../ro)";
            presence "Indicates a rw node is configured.";
            description
              "Read-write community";
          }
          container sdrowner {
            must "not(../systemowner)";
            presence "Indicates a sdrowner node is configured.";
            description
              "SDR Owner permissions for MIB Objects";
          }
          container systemowner {
            must "not(../sdrowner)";
            presence "Indicates a systemowner node is configured.";
            description
              "System Owner permissions for MIB objects";
          }
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
        }
      }
      container encrypted {
        presence "Indicates a encrypted node is configured.";
        description
          "Specifies an ENCRYPTED community string";
        container encryption-defaults {
          description
            "Specifies an ENCRYPTED community string in default method";
          list encryption-default {
            key "community-string";
            description
              "Specifies an ENCRYPTED community string in default method";
            leaf community-string {
              type string {
                length "1..1024" {
                  description
                    "The ENCRYPTED community string in default method";
                }
              }
              description
                "Specifies an ENCRYPTED community string in default method";
            }
            leaf view {
              type xr:Cisco-ios-xr-string {
                length "1..1024" {
                  description
                    "MIB view to which the community has access";
                }
              }
              description
                "Restrict this community to a named view";
            }
            container ro {
              must "not(../rw)";
              presence "Indicates a ro node is configured.";
              description
                "Read-only community";
            }
            container rw {
              must "not(../ro)";
              presence "Indicates a rw node is configured.";
              description
                "Read-write community";
            }
            container sdrowner {
              must "not(../systemowner)";
              presence "Indicates a sdrowner node is configured.";
              description
                "SDR Owner permissions for MIB Objects";
            }
            container systemowner {
              must "not(../sdrowner)";
              presence "Indicates a systemowner node is configured.";
              description
                "System Owner permissions for MIB objects";
            }
            leaf ipv4 {
              type xr:Cisco-ios-xr-string {
                length "1..32" {
                  description
                    "V4 Access-list name";
                }
              }
              description
                "Type of Access-list";
            }
            leaf ipv6 {
              type xr:Cisco-ios-xr-string {
                length "1..32" {
                  description
                    "V6 Access-list name";
                }
              }
              description
                "Type of Access-list";
            }
          }
        }
        container encryption-aeses {
          description
            "Specifies an ENCRYPTED community string in aes-128 method";
          list encryption-aes {
            key "community-string";
            description
              "Specifies an ENCRYPTED community string in aes-128 method";
            leaf community-string {
              type string {
                length "1..1024" {
                  description
                    "The ENCRYPTED community string in aes-128 method";
                }
                pattern "[0-9a-zA-Z]+";
              }
              description
                "Specifies an ENCRYPTED community string in aes-128 method";
            }
            leaf view {
              type xr:Cisco-ios-xr-string {
                length "1..1024" {
                  description
                    "MIB view to which the community has access";
                }
              }
              description
                "Restrict this community to a named view";
            }
            container ro {
              must "not(../rw)";
              presence "Indicates a ro node is configured.";
              description
                "Read-only community";
            }
            container rw {
              must "not(../ro)";
              presence "Indicates a rw node is configured.";
              description
                "Read-write community";
            }
            container sdrowner {
              must "not(../systemowner)";
              presence "Indicates a sdrowner node is configured.";
              description
                "SDR Owner permissions for MIB Objects";
            }
            container systemowner {
              must "not(../sdrowner)";
              presence "Indicates a systemowner node is configured.";
              description
                "System Owner permissions for MIB objects";
            }
            leaf ipv4 {
              type xr:Cisco-ios-xr-string {
                length "1..32" {
                  description
                    "V4 Access-list name";
                }
              }
              description
                "Type of Access-list";
            }
            leaf ipv6 {
              type xr:Cisco-ios-xr-string {
                length "1..32" {
                  description
                    "V6 Access-list name";
                }
              }
              description
                "Type of Access-list";
            }
          }
        }
      }
    }
    container community-map {
      description
        "Community Mapping as per RFC-2576";
      container unencrypted {
        description
          "The UNENCRYPTED (cleartext) community string";
        list unencrypted-string {
          must "context or security-name or target-list";
          key "community-string";
          description
            "The UNENCRYPTED (cleartext) community string";
          leaf community-string {
            type string {
              length "1..32" {
                description
                  "The UNENCRYPTED community string";
              }
            }
            description
              "The UNENCRYPTED (cleartext) community string";
          }
          leaf context {
            type xr:Cisco-ios-xr-string {
              length "1..32" {
                description
                  "SNMP Context Name ";
              }
            }
            description
              "Context Name for the community mapping ";
          }
          leaf security-name {
            type xr:Cisco-ios-xr-string {
              length "1..1024" {
                description
                  "SNMP Security Name ";
              }
            }
            description
              "Security Name for the community mapping ";
          }
          leaf target-list {
            type xr:Cisco-ios-xr-string {
              length "1..1024" {
                description
                  "target list name ";
              }
            }
            description
              "list of targets valid with this community ";
          }
        }
      }
      container encrypted {
        presence "Indicates a encrypted node is configured.";
        description
          "Specifies an ENCRYPTED community string";
        container encryption-defaults {
          description
            "Specifies an ENCRYPTED community string in default method";
          list encryption-default {
            must "context or security-name or target-list";
            key "community-string";
            description
              "Specifies an ENCRYPTED community string in default method";
            leaf community-string {
              type string {
                length "1..1024" {
                  description
                    "The ENCRYPTED community string in default method";
                }
              }
              description
                "Specifies an ENCRYPTED community string in default method";
            }
            leaf context {
              type string {
                length "1..32" {
                  description
                    "SNMP Context Name ";
                }
              }
              description
                "Context Name for the community mapping ";
            }
            leaf security-name {
              type xr:Cisco-ios-xr-string {
                length "1..1024" {
                  description
                    "SNMP Security Name ";
                }
              }
              description
                "Security Name for the community mapping ";
            }
            leaf target-list {
              type xr:Cisco-ios-xr-string {
                length "1..1024" {
                  description
                    "target list name ";
                }
              }
              description
                "list of targets valid with this community ";
            }
          }
        }
        container encryption-aeses {
          description
            "Specifies an ENCRYPTED community string in aes-128 method";
          list encryption-aes {
            must "context or security-name or target-list";
            key "community-string";
            description
              "Specifies an ENCRYPTED community string in aes-128 method";
            leaf community-string {
              type string {
                length "1..1024" {
                  description
                    "The ENCRYPTED community string in aes-128 method";
                }
              }
              description
                "Specifies an ENCRYPTED community string in aes-128 method";
            }
            leaf context {
              type xr:Cisco-ios-xr-string {
                length "1..32" {
                  description
                    "SNMP Context Name ";
                }
              }
              description
                "Context Name for the community mapping ";
            }
            leaf security-name {
              type xr:Cisco-ios-xr-string {
                length "1..1024" {
                  description
                    "SNMP Security Name ";
                }
              }
              description
                "Security Name for the community mapping ";
            }
            leaf target-list {
              type xr:Cisco-ios-xr-string {
                length "1..1024" {
                  description
                    "target list name ";
                }
              }
              description
                "list of targets valid with this community ";
            }
          }
        }
      }
    }
    container traps {
      description
        "Enable SNMP traps";
      container snmp {
        description
          "Enable SNMPv2-MIB traps";
        container authentication {
          presence "Indicates an authentication node is configured.";
          description
            "Enable SNMPv2-MIB authenticationFailure trap";
        }
        container coldstart {
          presence "Indicates a coldstart node is configured.";
          description
            "Enable SNMPv2-MIB coldStart trap";
        }
        container linkdown {
          presence "Indicates a linkdown node is configured.";
          description
            "Enable SNMPv2-MIB linDownp traps";
        }
        container linkup {
          presence "Indicates a authentication node is configured.";
          description
            "Enable SNMPv2-MIB linkUp traps";
        }
        container warmstart {
          presence "Indicates a authentication node is configured.";
          description
            "Enable SNMPv2-MIB warmStart trap";
        }
        container all {
          presence "Indicates an all node is configured.";
          description
            "Enable all traps";
        }
      }
    }
    container hosts {
      description
        "Specify hosts to receive SNMP notifications";
      list host {
        key "address";
        description
          "Specify hosts to receive SNMP notifications";
        leaf address {
          type inet:ip-address-no-zone;
          description
            "Specify hosts to receive SNMP notifications";
        }
        container traps {
          description
            "Send Trap messages to this host";
          container encrypted {
            description
              "Specifies an ENCRYPTED community string";
            container encryption-defaults {
              description
                "Specifies an ENCRYPTED community string in default method";
              list encryption-default {
                key "community-string";
                description
                  "Specifies an ENCRYPTED community string in default method";
                leaf community-string {
                  type xr:Cisco-ios-xr-string {
                    length "1..1024" {
                      description
                        "The ENCRYPTED community string in default method";
                    }
                  }
                  description
                    "Specifies an ENCRYPTED community string in default method";
                }
                container version {
                  description
                    "SNMP version to use for notification messages";
                  container v2c {
                    must "not(../v3)";
                    presence "Indicates a v2c node is configured.";
                    description
                      "Use 2c for SNMPv2c";
                  }
                  container v3 {
                    must "not(../v2c)";
                    presence "Indicates a v3 node is configured.";
                    description
                      "Use 3 for SNMPv3";
                    leaf security-level {
                      type enumeration {
                        enum "auth" {
                          value 1;
                          description
                            "Using authNoPriv Security Level";
                        }
                        enum "noauth" {
                          value 0;
                          description
                            "Using noAuthNoPriv Security Level";
                        }
                        enum "priv" {
                          value 2;
                          description
                            "Using authPriv Security Level";
                        }
                      }
                      mandatory true;
                    }
                  }
                }
                leaf udp-port {
                  type uint32 {
                    range "1..65535" {
                      description
                        "udp port number";
                    }
                  }
                  description
                    "udp port to which notifications should be sent";
                }
                container dying-gasp {
                  if-feature "is_dying_gasp_supported";
                  presence "Indicates a dying-gasp node is configured.";
                  description
                    "This host will receive dying gasp trap";
                }
              }
            }
            container encryption-aeses {
              description
                "Specifies an ENCRYPTED community string in aes-128 method";
              list encryption-aes {
                key "community-string";
                description
                  "Specifies an ENCRYPTED community string in aes-128 method";
                leaf community-string {
                  type xr:Cisco-ios-xr-string {
                    length "1..1024" {
                      description
                        "The ENCRYPTED community string in aes-128 method";
                    }
                    pattern "[0-9a-zA-Z]+";
                  }
                  description
                    "Specifies an ENCRYPTED community string in aes-128 method";
                }
                container version {
                  description
                    "SNMP version to use for notification messages";
                  container v2c {
                    must "not(../v3)";
                    presence "Indicates a v2c node is configured.";
                    description
                      "Use 2c for SNMPv2c";
                  }
                  container v3 {
                    must "not(../v2c)";
                    presence "Indicates a v3 node is configured.";
                    description
                      "Use 3 for SNMPv3";
                    leaf security-level {
                      type enumeration {
                        enum "auth" {
                          value 1;
                          description
                            "Using authNoPriv Security Level";
                        }
                        enum "noauth" {
                          value 0;
                          description
                            "Using noAuthNoPriv Security Level";
                        }
                        enum "priv" {
                          value 2;
                          description
                            "Using authPriv Security Level";
                        }
                      }
                      mandatory true;
                    }
                  }
                }
                leaf udp-port {
                  type uint32 {
                    range "1..65535" {
                      description
                        "udp port number";
                    }
                  }
                  description
                    "udp port to which notifications should be sent";
                }
                container dying-gasp {
                  if-feature "is_dying_gasp_supported";
                  presence "Indicates a dying-gasp node is configured.";
                  description
                    "This host will receive dying gasp trap";
                }
              }
            }
          }
          container unencrypted {
            description
              "The UNENCRYPTED (cleartext) community string";
            list unencrypted-string {
              key "community-string";
              description
                "The UNENCRYPTED (cleartext) community string";
              leaf community-string {
                type string {
                  length "1..32" {
                    description
                      "The UNENCRYPTED (cleartext) community string";
                  }
                }
                description
                  "The UNENCRYPTED (cleartext) community string";
              }
              container version {
                description
                  "SNMP version to use for notification messages";
                container v2c {
                  must "not(../v3)";
                  presence "Indicates a v2c node is configured.";
                  description
                    "Use 2c for SNMPv2c";
                }
                container v3 {
                  must "not(../v2c)";
                  presence "Indicates a v3 node is configured.";
                  description
                    "Use 3 for SNMPv3";
                  leaf security-level {
                    type enumeration {
                      enum "auth" {
                        value 1;
                        description
                          "Using authNoPriv Security Level";
                      }
                      enum "noauth" {
                        value 0;
                        description
                          "Using noAuthNoPriv Security Level";
                      }
                      enum "priv" {
                        value 2;
                        description
                          "Using authPriv Security Level";
                      }
                    }
                    mandatory true;
                  }
                }
              }
              leaf udp-port {
                type uint32 {
                  range "1..65535" {
                    description
                      "udp port number";
                  }
                }
                description
                  "udp port to which notifications should be sent";
              }
              container dying-gasp {
                if-feature "is_dying_gasp_supported";
                presence "Indicates a dying-gasp node is configured.";
                description
                  "This host will receive dying gasp trap";
              }
            }
          }
        }
        container informs {
          description
            "Send Inform messages to this host";
          container encrypted {
            description
              "Specifies an ENCRYPTED community string";
            container encryption-defaults {
              description
                "Specifies an ENCRYPTED community string in default method";
              list encryption-default {
                must "version/v2c or version/v3";
                key "community-string";
                description
                  "Specifies an ENCRYPTED community string in default method";
                leaf community-string {
                  type string {
                    length "1..1024" {
                      description
                        "The ENCRYPTED community string in default method";
                    }
                  }
                  description
                    "Specifies an ENCRYPTED community string in default method";
                }
                container version {
                  description
                    "SNMP version to use for notification messages";
                  container v2c {
                    must "not(../v3)";
                    presence "Indicates a v2c node is configured.";
                    description
                      "Use 2c for SNMPv2c";
                  }
                  container v3 {
                    must "not(../v2c)";
                    presence "Indicates a v3 node is configured.";
                    description
                      "Use 3 for SNMPv3";
                    leaf security-level {
                      type enumeration {
                        enum "auth" {
                          value 1;
                          description
                            "Using authNoPriv Security Level";
                        }
                        enum "noauth" {
                          value 0;
                          description
                            "Using noAuthNoPriv Security Level";
                        }
                        enum "priv" {
                          value 2;
                          description
                            "Using authPriv Security Level";
                        }
                      }
                      mandatory true;
                    }
                  }
                }
                leaf udp-port {
                  type uint32 {
                    range "1..65535" {
                      description
                        "udp port number";
                    }
                  }
                  description
                    "udp port to which notifications should be sent";
                }
                container dying-gasp {
                  if-feature "is_dying_gasp_supported";
                  presence "Indicates a dying-gasp node is configured.";
                  description
                    "This host will receive dying gasp trap";
                }
              }
            }
            container encryption-aeses {
              description
                "Specifies an ENCRYPTED community string in aes-128 method";
              list encryption-aes {
                must "version/v2c or version/v3";
                key "community-string";
                description
                  "Specifies an ENCRYPTED community string in aes-128 method";
                leaf community-string {
                  type string {
                    length "1..1024" {
                      description
                        "The ENCRYPTED community string in aes-128 method";
                    }
                  }
                  description
                    "Specifies an ENCRYPTED community string in aes-128 method";
                }
                container version {
                  description
                    "SNMP version to use for notification messages";
                  container v2c {
                    must "not(../v3)";
                    presence "Indicates a v2c node is configured.";
                    description
                      "Use 2c for SNMPv2c";
                  }
                  container v3 {
                    must "not(../v2c)";
                    presence "Indicates a v3 node is configured.";
                    description
                      "Use 3 for SNMPv3";
                    leaf security-level {
                      type enumeration {
                        enum "auth" {
                          value 1;
                          description
                            "Using authNoPriv Security Level";
                        }
                        enum "noauth" {
                          value 0;
                          description
                            "Using noAuthNoPriv Security Level";
                        }
                        enum "priv" {
                          value 2;
                          description
                            "Using authPriv Security Level";
                        }
                      }
                      mandatory true;
                    }
                  }
                }
                leaf udp-port {
                  type uint32 {
                    range "1..65535" {
                      description
                        "udp port number";
                    }
                  }
                  description
                    "udp port to which notifications should be sent";
                }
                container dying-gasp {
                  if-feature "is_dying_gasp_supported";
                  presence "Indicates a dying-gasp node is configured.";
                  description
                    "This host will receive dying gasp trap";
                }
              }
            }
          }
          container unencrypted {
            description
              "The UNENCRYPTED (cleartext) community string";
            list unencrypted-string {
              must "version/v2c or version/v3";
              key "community-string";
              description
                "The UNENCRYPTED (cleartext) community string";
              leaf community-string {
                type string {
                  length "1..32" {
                    description
                      "The UNENCRYPTED (cleartext) community string";
                  }
                }
                description
                  "The UNENCRYPTED (cleartext) community string";
              }
              container version {
                description
                  "SNMP version to use for notification messages";
                container v2c {
                  must "not(../v3)";
                  presence "Indicates a v2c node is configured.";
                  description
                    "Use 2c for SNMPv2c";
                }
                container v3 {
                  must "not(../v2c)";
                  presence "Indicates a v3 node is configured.";
                  description
                    "Use 3 for SNMPv3";
                  leaf security-level {
                    type enumeration {
                      enum "auth" {
                        value 1;
                        description
                          "Using authNoPriv Security Level";
                      }
                      enum "noauth" {
                        value 0;
                        description
                          "Using noAuthNoPriv Security Level";
                      }
                      enum "priv" {
                        value 2;
                        description
                          "Using authPriv Security Level";
                      }
                    }
                    mandatory true;
                  }
                }
              }
              leaf udp-port {
                type uint32 {
                  range "1..65535" {
                    description
                      "udp port number";
                  }
                }
                description
                  "udp port to which notifications should be sent";
              }
              container dying-gasp {
                if-feature "is_dying_gasp_supported";
                presence "Indicates a dying-gasp node is configured.";
                description
                  "This host will receive dying gasp trap";
              }
            }
          }
        }
      }
    }
    leaf location {
      type string {
        length "1..255" {
          description
            "The physical location of this node";
        }
      }
      description
        "Text for mib Object sysLocation";
    }
    leaf contact {
      type string {
        length "1..255" {
          description
            "identification of the contact person for this managed node";
        }
      }
      description
        "Text for mib Object sysContact";
    }
    container views {
      description
        "Define an SNMPv2 MIB view";
      list view {
        must "mib-view-families/mib-view-family";
        key "view-name";
        description
          "Name of the view";
        leaf view-name {
          type xr:Cisco-ios-xr-string {
            length "1..32" {
              description
                "Name of the view";
            }
          }
          description
            "Name of the view";
        }
        container mib-view-families {
          description
            "MIB view family";
          list mib-view-family {
            must "included or excluded";
            key "mib-view-family-name";
            leaf mib-view-family-name {
              type string {
                length "1..1024" {
                  description
                    "MIB view family name";
                }
              }
              description
                "MIB view family name";
            }
            container included {
              must "not(../excluded)";
              presence "Indicates a included node is configured.";
              description
                "MIB family is included in the view";
            }
            container excluded {
              must "not(../included)";
              presence "Indicates a excluded node is configured.";
              description
                "MIB family is excluded from the view";
            }
          }
        }
      }
    }
    leaf chassis-id {
      type string {
        length "1..255" {
          description
            "Unique ID string";
        }
      }
      description
        "String to uniquely identify this chassis";
    }
    leaf packetsize {
      type uint32 {
        range "484..65500" {
          description
            "Packet size";
        }
      }
      description
        "Largest SNMP packet size";
    }
    container trap-source {
      description
        "Assign an interface for the source address of all traps";
      leaf both {
        type xr:Interface-name;
        description
          "Assign an interface for the source address of all traps";
      }
      leaf ipv4 {
        type xr:Interface-name;
        description
          "IPv4 address of the interface";
      }
      leaf ipv6 {
        type xr:Interface-name;
        description
          "IPv6 address of the interface";
      }
      leaf port {
        type uint32 {
          range "1024..65535" {
            description
              "UDP port number";
          }
        }
        description
          "Change the source port of all traps (default 161).";
      }
    }
    container trap {
      description
        "MIB trap configurations";
      leaf throttle-time {
        type uint32 {
          range "10..500" {
            description
              "Time in msec (default 250 msecs)";
          }
        }
        description
          "Set throttle time for handling more traps";
      }
      container authentication {
        description
          "Configure authentication trap";
        container vrf {
          description
            "VRF configuration";
          container disable {
            presence "Indicates a disable node is configured.";
            description
              "Disable authentication traps for packets on a vrf";
          }
        }
      }
      leaf delay-timer {
        type uint32 {
          range "30..240" {
            description
              "Time in minutes";
          }
        }
        description
          "Set time to delay traps on init";
      }
    }
    leaf trap-timeout {
      type uint32 {
        range "1..1000" {
          description
            "Timeout (default 30 seconds)";
        }
      }
      description
        "Set timeout for TRAP message retransmissions";
    }
    leaf queue-length {
      type uint32 {
        range "1..5000" {
          description
            "Queue length (default 100)";
        }
      }
      description
        "Message queue length for each TRAP host";
    }
    leaf throttle-time {
      type uint32 {
        range "50..1000" {
          description
            "Throttle Time for incoming queue (default 0 msec)";
        }
      }
      description
        "Set throttle time for handling incoming messages";
    }
    leaf overload-control {
      type uint32 {
        range "0..300" {
          description
            "Overload drop time (in seconds) for incoming queue (default 1 sec)";
        }
      }
      must "../overload-throttle-rate";
      description
        "Set overload-control params for handling incoming messages in critical processing mode";
    }
    leaf overload-throttle-rate {
      type uint32 {
        range "0..1000" {
          description
            "Overload throttle rate for incoming queue (default 500 msec)";
        }
      }
      must "../overload-control";
      description
        "Overload throttle rate for incoming queue (default 500 msec)";
    }
    container ipv4 {
      description
        "Mark the dscp/precedence bit for ipv4 packets";
      leaf dscp {
        type union {
          type uint32 {
            range "0..63" {
              description
                "Differentiated services codepoint value";
            }
          }
          type enumeration {
            enum "default" {
              value 0;
              description
                "Match packets with default dscp (000000)";
            }
            enum "cs1" {
              value 8;
              description
                "Match packets with CS1(precedence 1) dscp (001000)";
            }
            enum "af11" {
              value 10;
              description
                "Match packets with AF11 dscp (001010)";
            }
            enum "af12" {
              value 12;
              description
                "Match packets with AF12 dscp (001100)";
            }
            enum "af13" {
              value 14;
              description
                "Match packets with AF13 dscp (001110)";
            }
            enum "cs2" {
              value 16;
              description
                "Match packets with CS2(precedence 2) dscp (010000)";
            }
            enum "af21" {
              value 18;
              description
                "Match packets with AF21 dscp (010010)";
            }
            enum "af22" {
              value 20;
              description
                "Match packets with AF22 dscp (010100)";
            }
            enum "af23" {
              value 22;
              description
                "Match packets with AF23 dscp (010110)";
            }
            enum "cs3" {
              value 24;
              description
                "Match packets with CS3(precedence 3) dscp (011000)";
            }
            enum "af31" {
              value 26;
              description
                "Match packets with AF31 dscp (011010)";
            }
            enum "af32" {
              value 28;
              description
                "Match packets with AF32 dscp (011100)";
            }
            enum "af33" {
              value 30;
              description
                "Match packets with AF33 dscp (011110)";
            }
            enum "cs4" {
              value 32;
              description
                "Match packets with CS4(precedence 4) dscp (100000)";
            }
            enum "af41" {
              value 34;
              description
                "Match packets with AF41 dscp (100010)";
            }
            enum "af42" {
              value 36;
              description
                "Match packets with AF42 dscp (100100)";
            }
            enum "af43" {
              value 38;
              description
                "Match packets with AF43 dscp (100110)";
            }
            enum "cs5" {
              value 40;
              description
                "Match packets with CS5(precedence 5) dscp (101000)";
            }
            enum "ef" {
              value 46;
              description
                "Match packets with EF dscp (101110)";
            }
            enum "cs6" {
              value 48;
              description
                "Match packets with CS6(precedence 6) dscp (110000)";
            }
            enum "cs7" {
              value 56;
              description
                "Match packets with CS7(precedence 7) dscp (111000)";
            }
          }
        }
        must "not(../precedence)";
        description
          "Set IP DSCP (DiffServ CodePoint)";
      }
      leaf precedence {
        type union {
          type uint32 {
            range "0..7" {
              description
                "Precedence value";
            }
          }
          type enumeration {
            enum "routine" {
              value 0;
              description
                "Match packets with routine precedence (0)";
            }
            enum "priority" {
              value 1;
              description
                "Match packets with priority precedence (1)";
            }
            enum "immediate" {
              value 2;
              description
                "Match packets with immediate precedence (2)";
            }
            enum "flash" {
              value 3;
              description
                "Match packets with flash precedence (3)";
            }
            enum "flash-override" {
              value 4;
              description
                "Match packets with flash override precedence (4)";
            }
            enum "critical" {
              value 5;
              description
                "Match packets with critical precedence (5)";
            }
            enum "internet" {
              value 6;
              description
                "Match packets with internetwork control precedence (6)";
            }
            enum "network" {
              value 7;
              description
                "Match packets with network control precedence (7)";
            }
          }
        }
        must "not(../dscp)";
        description
          "Set precedence";
      }
    }
    container ipv6 {
      description
        "Mark the dscp/precedence bit for ipv6 packets";
      leaf dscp {
        type union {
          type uint32 {
            range "0..63" {
              description
                "Differentiated services codepoint value";
            }
          }
          type enumeration {
            enum "default" {
              value 0;
              description
                "Match packets with default dscp (000000)";
            }
            enum "cs1" {
              value 8;
              description
                "Match packets with CS1(precedence 1) dscp (001000)";
            }
            enum "af11" {
              value 10;
              description
                "Match packets with AF11 dscp (001010)";
            }
            enum "af12" {
              value 12;
              description
                "Match packets with AF12 dscp (001100)";
            }
            enum "af13" {
              value 14;
              description
                "Match packets with AF13 dscp (001110)";
            }
            enum "cs2" {
              value 16;
              description
                "Match packets with CS2(precedence 2) dscp (010000)";
            }
            enum "af21" {
              value 18;
              description
                "Match packets with AF21 dscp (010010)";
            }
            enum "af22" {
              value 20;
              description
                "Match packets with AF22 dscp (010100)";
            }
            enum "af23" {
              value 22;
              description
                "Match packets with AF23 dscp (010110)";
            }
            enum "cs3" {
              value 24;
              description
                "Match packets with CS3(precedence 3) dscp (011000)";
            }
            enum "af31" {
              value 26;
              description
                "Match packets with AF31 dscp (011010)";
            }
            enum "af32" {
              value 28;
              description
                "Match packets with AF32 dscp (011100)";
            }
            enum "af33" {
              value 30;
              description
                "Match packets with AF33 dscp (011110)";
            }
            enum "cs4" {
              value 32;
              description
                "Match packets with CS4(precedence 4) dscp (100000)";
            }
            enum "af41" {
              value 34;
              description
                "Match packets with AF41 dscp (100010)";
            }
            enum "af42" {
              value 36;
              description
                "Match packets with AF42 dscp (100100)";
            }
            enum "af43" {
              value 38;
              description
                "Match packets with AF43 dscp (100110)";
            }
            enum "cs5" {
              value 40;
              description
                "Match packets with CS5(precedence 5) dscp (101000)";
            }
            enum "ef" {
              value 46;
              description
                "Match packets with EF dscp (101110)";
            }
            enum "cs6" {
              value 48;
              description
                "Match packets with CS6(precedence 6) dscp (110000)";
            }
            enum "cs7" {
              value 56;
              description
                "Match packets with CS7(precedence 7) dscp (111000)";
            }
          }
        }
        must "not(../precedence)";
        description
          "Set IP DSCP (DiffServ CodePoint)";
      }
      leaf precedence {
        type union {
          type uint32 {
            range "0..7" {
              description
                "Precedence value";
            }
          }
          type enumeration {
            enum "routine" {
              value 0;
              description
                "Match packets with routine precedence (0)";
            }
            enum "priority" {
              value 1;
              description
                "Match packets with priority precedence (1)";
            }
            enum "immediate" {
              value 2;
              description
                "Match packets with immediate precedence (2)";
            }
            enum "flash" {
              value 3;
              description
                "Match packets with flash precedence (3)";
            }
            enum "flash-override" {
              value 4;
              description
                "Match packets with flash override precedence (4)";
            }
            enum "critical" {
              value 5;
              description
                "Match packets with critical precedence (5)";
            }
            enum "internet" {
              value 6;
              description
                "Match packets with internetwork control precedence (6)";
            }
            enum "network" {
              value 7;
              description
                "Match packets with network control precedence (7)";
            }
          }
        }
        must "not(../dscp)";
        description
          "Set precedence";
      }
    }
    container drop {
      description
        "Drop packets";
      container unknown-user {
        presence "Indicates a unknown-user node is configured.";
        description
          "Silently drop unknown v3 user packets";
      }
      container report {
        description
          "Config to drop snmpv3 error reports";
        container acl {
          description
            "Config to drop snmpv3 error reports matching ACL";
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
        }
      }
    }
    container groups {
      description
        "Define a User Security Model group";
      list group {
        key "group-name";
        description
          "Name of the group";
        leaf group-name {
          type xr:Cisco-ios-xr-string {
            length "1..128" {
              description
                "Name of the group";
            }
          }
          description
            "Name of the group";
        }
        container v1 {
          must "not(../v2c or ../v3)";
          presence "Indicates a v1 node is configured.";
          description
            "group using the v1 security model";
          leaf read {
            type xr:Cisco-ios-xr-string {
              length "1..1024" {
                description
                  "read view name";
              }
            }
            description
              "specify a read view for this group";
          }
          leaf write {
            type xr:Cisco-ios-xr-string {
              length "1..1024" {
                description
                  "write view name";
              }
            }
            description
              "specify a write view for this group";
          }
          leaf context {
            type xr:Cisco-ios-xr-string {
              length "1..32" {
                description
                  "Context name";
              }
            }
            description
              "Attach a SNMP context";
          }
          leaf notify {
            type xr:Cisco-ios-xr-string {
              length "1..1024" {
                description
                  "notify view name";
              }
            }
            description
              "specify a notify view for the group";
          }
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
        }
        container v2c {
          must "not(../v1 or ../v3)";
          presence "Indicates a v2c node is configured.";
          description
            "group using the v2c security model";
          leaf read {
            type xr:Cisco-ios-xr-string {
              length "1..1024" {
                description
                  "read view name";
              }
            }
            description
              "specify a read view for this group";
          }
          leaf write {
            type xr:Cisco-ios-xr-string {
              length "1..1024" {
                description
                  "write view name";
              }
            }
            description
              "specify a write view for this group";
          }
          leaf context {
            type xr:Cisco-ios-xr-string {
              length "1..32" {
                description
                  "Context name";
              }
            }
            description
              "Attach a SNMP context";
          }
          leaf notify {
            type xr:Cisco-ios-xr-string {
              length "1..1024" {
                description
                  "notify view name";
              }
            }
            description
              "specify a notify view for the group";
          }
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
        }
        container v3 {
          must "not(../v1 or ../v2c) and (priv or auth or noauth)";
          presence "Indicates a v3 node is configured.";
          description
            "group using the User Security Model (SNMPv3)";
          leaf read {
            type xr:Cisco-ios-xr-string {
              length "1..1024" {
                description
                  "read view name";
              }
            }
            description
              "specify a read view for this group";
          }
          leaf write {
            type xr:Cisco-ios-xr-string {
              length "1..1024" {
                description
                  "write view name";
              }
            }
            description
              "specify a write view for this group";
          }
          leaf context {
            type xr:Cisco-ios-xr-string {
              length "1..32" {
                description
                  "Context name";
              }
            }
            description
              "Attach a SNMP context";
          }
          leaf notify {
            type xr:Cisco-ios-xr-string {
              length "1..1024" {
                description
                  "notify view name";
              }
            }
            description
              "specify a notify view for the group";
          }
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
          container priv {
            must "not(../auth or ../noauth)";
            presence "Indicates a priv node is configured.";
            description
              "group using authPriv Security Level";
          }
          container auth {
            must "not(../priv or ../noauth)";
            presence "Indicates an auth node is configured.";
            description
              "group using the authNoPriv Security Level";
          }
          container noauth {
            must "not(../auth or ../priv)";
            presence "Indicates an noauth node is configured.";
            description
              "group using the noAuthNoPriv Security Level";
          }
        }
      }
    }
    container engine-id {
      description
        "Configure a local or remote SNMPv3 engineID";
      leaf local {
        type xr:Cisco-ios-xr-string {
          length "1..800" {
            description
              "engine ID octet string";
          }
        }
        description
          "engineID of the local agent";
      }
      container remotes {
        description
          "engineID of the remote agent";
        list remote {
          key "address";
          description
            "engineID of the remote agent";
          leaf address {
            type inet:ip-address-no-zone;
            description
              "engineID of the remote agent";
          }
          leaf engine-id {
            type xr:Cisco-ios-xr-string {
              length "1..800" {
                description
                  "engine ID octet string";
              }
            }
            mandatory true;
            description
              "engine ID octet string";
          }
          leaf udp-port {
            type uint32 {
              range "1..65535" {
                description
                  "UDP port number";
              }
            }
            mandatory true;
            description
              "The remote notification host's UDP port number";
          }
        }
      }
    }
    container users {
      description
        "Define a user who can access the SNMP engine";
      list user {
        key "user-name";
        description
          "Name of the user";
        leaf user-name {
          type string {
            length "1..32" {
              description
                "Name of the user";
            }
          }
          description
            "Name of the user";
        }
        leaf group-name {
          type xr:Cisco-ios-xr-string {
            length "1..32" {
              description
                "Group to which the user belongs";
            }
          }
          mandatory true;
          description
            "Group to which the user belongs";
        }
        leaf remote {
          type inet:ip-address-no-zone;
          description
            "Specify a remote SNMP entity to which the user belongs";
        }
        leaf udp-port {
          type uint32 {
            range "1..65535" {
              description
                "The remote SNMP entity's UDP port number";
            }
          }
          must "../remote";
          description
            "The remote SNMP entity's UDP port number";
        }
        container v1 {
          must "not(../v2c or ../v3)";
          presence "Indicates a v1 node is configured.";
          description
            "user using the v1 security model";
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
          container sdrowner {
            must "not(../systemowner)";
            presence "Indicates a sdrowner node is configured.";
            description
              "SDR Owner permissions for MIB Objects";
          }
          container systemowner {
            must "not(../sdrowner)";
            presence "Indicates a systemowner node is configured.";
            description
              "System Owner permissions for MIB objects";
          }
        }
        container v2c {
          must "not(../v1 or ../v3)";
          presence "Indicates a v2c node is configured.";
          description
            "user using the v2c security model";
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
          container sdrowner {
            must "not(../systemowner)";
            presence "Indicates a sdrowner node is configured.";
            description
              "SDR Owner permissions for MIB Objects";
          }
          container systemowner {
            must "not(../sdrowner)";
            presence "Indicates a systemowner node is configured.";
            description
              "System Owner permissions for MIB objects";
          }
        }
        container v3 {
          presence "Indicates a v3 node is configured.";
          description
            "user using the v3 security model";
          container auth {
            must
              "(md5/encryption-default or
                md5/encryption-aes or
                sha/encryption-default or
                sha/encryption-aes)";
            presence "Indicates a auth node is configured.";
            description
              "authentication parameters for the user";
            container md5 {
              description
                "Use HMAC MD5 algorithm for authentication";
              leaf encryption-default {
                type xr:Proprietary-password;
                must
                  "not(../encryption-aes or
                   ../../sha/encryption-default or
                   ../../sha/encryption-aes)";
                description
                  "Specifies an default ENCRYPTED authentication password";
              }
              leaf encryption-aes {
                type string {
                  length "1..1024" {
                    description
                      "The aes-128 ENCRYPTED authentication password";
                  }
                  pattern "[0-9a-zA-Z]+";
                }
                must
                  "not(../encryption-default or
                   ../../sha/encryption-default or
                   ../../sha/encryption-aes)";
                description
                  "Specifies an aes-128 ENCRYPTED authentication password";
              }
            }
            container sha {
              description
                "Use HMAC SHA algorithm for authentication";
              leaf encryption-default {
                type xr:Proprietary-password;
                must
                  "not(../encryption-aes or
                   ../../md5/encryption-default or
                   ../../md5/encryption-aes)";
                description
                  "Specifies an default ENCRYPTED authentication password";
              }
              leaf encryption-aes {
                type string {
                  length "1..1024" {
                    description
                      "The aes-128 ENCRYPTED authentication password";
                  }
                  pattern "[0-9a-zA-Z]+";
                }
                must
                  "not(../encryption-default or
                   ../../md5/encryption-default or
                   ../../md5/encryption-aes)";
                description
                  "Specifies an aes-128 ENCRYPTED authentication password";
              }
            }
          }
          container priv {
            must
              "../auth and (three-des/encryption-default or
               three-des/encryption-aes or
               des56/encryption-default or
               des56/encryption-aes or
               aes/aes-128/encryption-default or
               aes/aes-128/encryption-aes or
               aes/aes-192/encryption-default or
               aes/aes-192/encryption-aes or
               aes/aes-256/encryption-default or
               aes/aes-256/encryption-aes)";
            presence "Indicates a priv node is configured.";
            description
              "encryption parameters for the user";
            container three-des {
              description
                " Use 168 bit 3DES algorithm for encryption";
              leaf encryption-default {
                type xr:Proprietary-password;
                must
                  "not(../encryption-aes or
                   ../../des56/encryption-default or
                   ../../des56/encryption-aes or
                   ../../aes/aes-128/encryption-default or
                   ../../aes/aes-128/encryption-aes or
                   ../../aes/aes-192/encryption-default or
                   ../../aes/aes-192/encryption-aes or
                   ../../aes/aes-256/encryption-default or
                   ../../aes/aes-256/encryption-aes)";
                description
                  "Specifies an default ENCRYPTED authentication password";
              }
              leaf encryption-aes {
                type string {
                  length "1..1024" {
                    description
                      "The aes-128 ENCRYPTED authentication password";
                  }
                  pattern "[0-9a-zA-Z]+";
                }
                must
                  "not(../encryption-default or
                   ../../des56/encryption-default or
                   ../../des56/encryption-aes or
                   ../../aes/aes-128/encryption-default or
                   ../../aes/aes-128/encryption-aes or
                   ../../aes/aes-192/encryption-default or
                   ../../aes/aes-192/encryption-aes or
                   ../../aes/aes-256/encryption-default or
                   ../../aes/aes-256/encryption-aes)";
                description
                  "Specifies an aes-128 ENCRYPTED authentication password";
              }
            }
            container des56 {
              description
                " Use 56 bit DES algorithm for encryption";
              leaf encryption-default {
                type xr:Proprietary-password;
                must
                  "not(../encryption-aes or
                   ../../three-des/encryption-default or
                   ../../three-des/encryption-aes or
                   ../../aes/aes-128/encryption-default or
                   ../../aes/aes-128/encryption-aes or
                   ../../aes/aes-192/encryption-default or
                   ../../aes/aes-192/encryption-aes or
                   ../../aes/aes-256/encryption-default or
                   ../../aes/aes-256/encryption-aes)";
                description
                  "Specifies an default ENCRYPTED authentication password";
              }
              leaf encryption-aes {
                type string {
                  length "1..1024" {
                    description
                      "The aes-128 ENCRYPTED authentication password";
                  }
                  pattern "[0-9a-zA-Z]+";
                }
                must
                  "not(../encryption-default or
                   ../../three-des/encryption-default or
                   ../../three-des/encryption-aes or
                   ../../aes/aes-128/encryption-default or
                   ../../aes/aes-128/encryption-aes or
                   ../../aes/aes-192/encryption-default or
                   ../../aes/aes-192/encryption-aes or
                   ../../aes/aes-256/encryption-default or
                   ../../aes/aes-256/encryption-aes)";
                description
                  "Specifies an aes-128 ENCRYPTED authentication password";
              }
            }
            container aes {
              description
                " Use 128 bit AES algorithm for encryption";
              container aes-128 {
                description
                  " Use AES 128 bit encryption";
                leaf encryption-default {
                  type xr:Proprietary-password;
                  must
                    "not(../../../des56/encryption-default or
                     ../../../des56/encryption-aes or
                     ../../../three-des/encryption-default or
                     ../../../three-des/encryption-aes or
                     ../../aes-192/encryption-default or
                     ../../aes-192/encryption-aes or
                     ../../aes-256/encryption-default or
                     ../../aes-256/encryption-aes or
                     ../encryption-aes)";
                  description
                    "Specifies an default ENCRYPTED authentication password";
                }
                leaf encryption-aes {
                  type string {
                    length "1..1024" {
                      description
                        "The aes-128 ENCRYPTED authentication password";
                    }
                    pattern "[0-9a-zA-Z]+";
                  }
                  must
                    "not(../../../des56/encryption-default or
                     ../../../des56/encryption-aes or
                     ../../../three-des/encryption-default or
                     ../../../three-des/encryption-aes or
                     ../../aes-192/encryption-default or
                     ../../aes-192/encryption-aes or
                     ../../aes-256/encryption-default or
                     ../../aes-256/encryption-aes or
                     ../encryption-default)";
                  description
                    "Specifies an aes-128 ENCRYPTED authentication password";
                }
              }
              container aes-192 {
                description
                  " Use AES 256 bit encryption";
                leaf encryption-default {
                  type xr:Proprietary-password;
                  must
                    "not(../../../des56/encryption-default or
                     ../../../des56/encryption-aes or
                     ../../../three-des/encryption-default or
                     ../../../three-des/encryption-aes or
                     ../../aes-128/encryption-default or
                     ../../aes-128/encryption-aes or
                     ../../aes-256/encryption-default or
                     ../../aes-256/encryption-aes or
                     ../encryption-aes)";
                  description
                    "Specifies an default ENCRYPTED authentication password";
                }
                leaf encryption-aes {
                  type string {
                    length "1..1024" {
                      description
                        "The aes-128 ENCRYPTED authentication password";
                    }
                    pattern "[0-9a-zA-Z]+";
                  }
                  must
                    "not(../../../des56/encryption-default or
                     ../../../des56/encryption-aes or
                     ../../../three-des/encryption-default or
                     ../../../three-des/encryption-aes or
                     ../../aes-128/encryption-default or
                     ../../aes-128/encryption-aes or
                     ../../aes-256/encryption-default or
                     ../../aes-256/encryption-aes or
                     ../encryption-default)";
                  description
                    "Specifies an aes-128 ENCRYPTED authentication password";
                }
              }
              container aes-256 {
                description
                  " Use AES 256 bit encryption";
                leaf encryption-default {
                  type xr:Proprietary-password;
                  must
                    "not(../../../des56/encryption-default or
                     ../../../des56/encryption-aes or
                     ../../../three-des/encryption-default or
                     ../../../three-des/encryption-aes or
                     ../../aes-128/encryption-default or
                     ../../aes-128/encryption-aes or
                     ../../aes-192/encryption-default or
                     ../../aes-192/encryption-aes or
                     ../encryption-aes)";
                  description
                    "Specifies an default ENCRYPTED authentication password";
                }
                leaf encryption-aes {
                  type string {
                    length "1..1024" {
                      description
                        "The aes-128 ENCRYPTED authentication password";
                    }
                    pattern "[0-9a-zA-Z]+";
                  }
                  must
                    "not(../../../des56/encryption-default or
                     ../../../des56/encryption-aes or
                     ../../../three-des/encryption-default or
                     ../../../three-des/encryption-aes or
                     ../../aes-128/encryption-default or
                     ../../aes-128/encryption-aes or
                     ../../aes-192/encryption-default or
                     ../../aes-192/encryption-aes or
                     ../encryption-default)";
                  description
                    "Specifies an aes-128 ENCRYPTED authentication password";
                }
              }
            }
          }
          leaf ipv4 {
            type xr:Cisco-ios-xr-string {
              length "1..32" {
                description
                  "V4 Access-list name";
              }
            }
            description
              "Type of Access-list";
          }
          leaf ipv6 {
            type xr:Cisco-ios-xr-string {
              length "1..32" {
                description
                  "V6 Access-list name";
              }
            }
            description
              "Type of Access-list";
          }
          container sdrowner {
            must "not(../systemowner)";
            presence "Indicates a sdrowner node is configured.";
            description
              "SDR Owner permissions for MIB Objects";
          }
          container systemowner {
            must "not(../sdrowner)";
            presence "Indicates a systemowner node is configured.";
            description
              "System Owner permissions for MIB objects";
          }
        }
      }
    }
    container target {
      description
        "SNMP target subcommands";
      container lists {
        description
          "Specify list of targets";
        list list {
          key "list-name";
          description
            "Specify list of targets";
          leaf list-name {
            type xr:Cisco-ios-xr-string {
              length "1..800" {
                description
                  "Name of the target list";
              }
            }
            description
              "Specify list of targets";
          }
          list vrf {
            key "vrf-name";
            description
              "Specify VRF name";
            leaf vrf-name {
              type xr:Cisco-ios-xr-string {
                length "1..32" {
                  description
                    "VRF Name";
                }
              }
              description
                "Specify VRF name";
            }
          }
          container hosts {
            description
              "Specify host name";
            list host {
              key "address";
              description
                "Specify host name";
              leaf address {
                type inet:ip-address-no-zone;
                description
                  "Specify host name";
              }
            }
          }
        }
      }
    }
    container context {
      description
        "Configure SNMP context ";
      container contexts {
        description
          "Context Name";
        list context {
          key "context-name";
          description
            "Context Name";
          leaf context-name {
            type xr:Cisco-ios-xr-string {
              length "1..32" {
                description
                  "Context Name";
              }
            }
            description
              "Context Name";
          }
        }
      }
      container mappings {
        description
          "context mapping";
        list mapping {
          must "instance or topology or vrf";
          key "context-name";
          description
            "context mapping";
          leaf context-name {
            type xr:Cisco-ios-xr-string {
              length "1..32" {
                description
                  "Context Name";
              }
            }
            description
              "context mapping";
          }
          leaf feature {
            type enumeration {
              enum "vrf" {
                value 1;
                description
                  "Vrf feature";
              }
              enum "bridge" {
                value 4;
                description
                  "L2vpn bridge feature";
              }
              enum "ospf" {
                value 5;
                description
                  "Ospf feature";
              }
              enum "ospfv3" {
                value 6;
                description
                  "Ospfv3 feature";
              }
            }
            mandatory true;
            description
              "Configure feature ";
          }
          leaf instance {
            type xr:Cisco-ios-xr-string {
              length "1..32" {
                description
                  "Protocol Instance Name";
              }
            }
            description
              "Protocol instance associated with the context";
          }
          leaf vrf {
            type xr:Cisco-ios-xr-string {
              length "1..32" {
                description
                  "Vrf name";
              }
            }
            description
              "Vrf associated with the context";
          }
          leaf topology {
            type xr:Cisco-ios-xr-string {
              length "1..32" {
                description
                  "Topology Name";
              }
            }
            description
              "Topology name associated with the context";
          }
        }
      }
    }
    container vrfs {
      description
        "SNMP VRF configuration commands";
      list vrf {
        key "vrf-name";
        description
          "VRF name";
        leaf vrf-name {
          type xr:Cisco-ios-xr-string {
            length "1..32" {
              description
                "VRF name";
            }
          }
          description
            "VRF name";
        }
        container hosts {
          description
            "Specify hosts to receive SNMP notifications";
          list host {
            key "address";
            description
              "Specify hosts to receive SNMP notifications";
            leaf address {
              type inet:ip-address-no-zone;
              description
                "Specify hosts to receive SNMP notifications";
            }
            container traps {
              description
                "Send Trap messages to this host";
              container encrypted {
                description
                  "Specifies an ENCRYPTED community string";
                container encryption-defaults {
                  description
                    "Specifies an ENCRYPTED community string in default method";
                  list encryption-default {
                    key "community-string";
                    description
                      "Specifies an ENCRYPTED community string in default method";
                    leaf community-string {
                      type string {
                        length "1..1024" {
                          description
                            "The ENCRYPTED community string in default method";
                        }
                      }
                      description
                        "Specifies an ENCRYPTED community string in default method";
                    }
                    container version {
                      description
                        "SNMP version to use for notification messages";
                      container v2c {
                        must "not(../v3)";
                        presence "Indicates a v2c node is configured.";
                        description
                          "Use 2c for SNMPv2c";
                      }
                      container v3 {
                        must "not(../v2c)";
                        presence "Indicates a v3 node is configured.";
                        description
                          "Use 3 for SNMPv3";
                        leaf security-level {
                          type enumeration {
                            enum "auth" {
                              value 1;
                              description
                                "Using authNoPriv Security Level";
                            }
                            enum "noauth" {
                              value 0;
                              description
                                "Using noAuthNoPriv Security Level";
                            }
                            enum "priv" {
                              value 2;
                              description
                                "Using authPriv Security Level";
                            }
                          }
                          mandatory true;
                        }
                      }
                    }
                    leaf udp-port {
                      type union {
                        type enumeration {
                          enum "default" {
                            value 162;
                            description
                              "Default UDP port (162)";
                          }
                        }
                        type uint32 {
                          range "1..65535" {
                            description
                              "udp port number";
                          }
                        }
                      }
                      mandatory true;
                      description
                        "udp port to which notifications should be sent";
                    }
                    container dying-gasp {
                      if-feature "is_dying_gasp_supported";
                      presence "Indicates a dying-gasp node is configured.";
                      description
                        "This host will receive dying gasp trap";
                    }
                  }
                }
                container encryption-aeses {
                  description
                    "Specifies an ENCRYPTED community string in aes-128 method";
                  list encryption-aes {
                    key "community-string";
                    description
                      "Specifies an ENCRYPTED community string in aes-128 method";
                    leaf community-string {
                      type string {
                        length "1..1024" {
                          description
                            "The ENCRYPTED community string in aes-128 method";
                        }
                        pattern "[0-9a-zA-Z]+";
                      }
                      description
                        "Specifies an ENCRYPTED community string in aes-128 method";
                    }
                    container version {
                      description
                        "SNMP version to use for notification messages";
                      container v2c {
                        must "not(../v3)";
                        presence "Indicates a v2c node is configured.";
                        description
                          "Use 2c for SNMPv2c";
                      }
                      container v3 {
                        must "not(../v2c)";
                        presence "Indicates a v3 node is configured.";
                        description
                          "Use 3 for SNMPv3";
                        leaf security-level {
                          type enumeration {
                            enum "auth" {
                              value 1;
                              description
                                "Using authNoPriv Security Level";
                            }
                            enum "noauth" {
                              value 0;
                              description
                                "Using noAuthNoPriv Security Level";
                            }
                            enum "priv" {
                              value 2;
                              description
                                "Using authPriv Security Level";
                            }
                          }
                          mandatory true;
                        }
                      }
                    }
                    leaf udp-port {
                      type union {
                        type enumeration {
                          enum "default" {
                            value 162;
                            description
                              "Default UDP port (162)";
                          }
                        }
                        type uint32 {
                          range "1..65535" {
                            description
                              "udp port number";
                          }
                        }
                      }
                      mandatory true;
                      description
                        "udp port to which notifications should be sent";
                    }
                    container dying-gasp {
                      if-feature "is_dying_gasp_supported";
                      presence "Indicates a dying-gasp node is configured.";
                      description
                        "This host will receive dying gasp trap";
                    }
                  }
                }
              }
              container unencrypted {
                description
                  "The UNENCRYPTED (cleartext) community string";
                list unencrypted-string {
                  key "community-string";
                  description
                    "The UNENCRYPTED (cleartext) community string";
                  leaf community-string {
                    type string {
                      length "1..32" {
                        description
                          "The UNENCRYPTED (cleartext) community string";
                      }
                    }
                    description
                      "The UNENCRYPTED (cleartext) community string";
                  }
                  container version {
                    description
                      "SNMP version to use for notification messages";
                    container v2c {
                      must "not(../v3)";
                      presence "Indicates a v2c node is configured.";
                      description
                        "Use 2c for SNMPv2c";
                    }
                    container v3 {
                      must "not(../v2c)";
                      presence "Indicates a v3 node is configured.";
                      description
                        "Use 3 for SNMPv3";
                      leaf security-level {
                        type enumeration {
                          enum "auth" {
                            value 1;
                            description
                              "Using authNoPriv Security Level";
                          }
                          enum "noauth" {
                            value 0;
                            description
                              "Using noAuthNoPriv Security Level";
                          }
                          enum "priv" {
                            value 2;
                            description
                              "Using authPriv Security Level";
                          }
                        }
                        mandatory true;
                      }
                    }
                  }
                  leaf udp-port {
                    type union {
                      type enumeration {
                        enum "default" {
                          value 162;
                          description
                            "Default UDP port (162)";
                        }
                      }
                      type uint32 {
                        range "1..65535" {
                          description
                            "udp port number";
                        }
                      }
                    }
                    mandatory true;
                    description
                      "udp port to which notifications should be sent";
                  }
                  container dying-gasp {
                    if-feature "is_dying_gasp_supported";
                    presence "Indicates a dying-gasp node is configured.";
                    description
                      "This host will receive dying gasp trap";
                  }
                }
              }
            }
            container informs {
              description
                "Send Inform messages to this host";
              container encrypted {
                description
                  "Specifies an ENCRYPTED community string";
                container encryption-defaults {
                  description
                    "Specifies an ENCRYPTED community string in default method";
                  list encryption-default {
                    must "version/v2c or version/v3";
                    key "community-string";
                    description
                      "Specifies an ENCRYPTED community string in default method";
                    leaf community-string {
                      type string {
                        length "1..1024" {
                          description
                            "The ENCRYPTED community string in default method";
                        }
                      }
                      description
                        "Specifies an ENCRYPTED community string in default method";
                    }
                    container version {
                      description
                        "SNMP version to use for notification messages";
                      container v2c {
                        must "not(../v3)";
                        presence "Indicates a v2c node is configured.";
                        description
                          "Use 2c for SNMPv2c";
                      }
                      container v3 {
                        must "not(../v2c)";
                        presence "Indicates a v3 node is configured.";
                        description
                          "Use 3 for SNMPv3";
                        leaf security-level {
                          type enumeration {
                            enum "auth" {
                              value 1;
                              description
                                "Using authNoPriv Security Level";
                            }
                            enum "noauth" {
                              value 0;
                              description
                                "Using noAuthNoPriv Security Level";
                            }
                            enum "priv" {
                              value 2;
                              description
                                "Using authPriv Security Level";
                            }
                          }
                          mandatory true;
                        }
                      }
                    }
                    leaf udp-port {
                      type union {
                        type enumeration {
                          enum "default" {
                            value 162;
                            description
                              "Default UDP port (162)";
                          }
                        }
                        type uint32 {
                          range "1..65535" {
                            description
                              "udp port number";
                          }
                        }
                      }
                      mandatory true;
                      description
                        "udp port to which notifications should be sent";
                    }
                    container dying-gasp {
                      if-feature "is_dying_gasp_supported";
                      presence "Indicates a dying-gasp node is configured.";
                      description
                        "This host will receive dying gasp trap";
                    }
                  }
                }
                container encryption-aeses {
                  description
                    "Specifies an ENCRYPTED community string in aes-128 method";
                  list encryption-aes {
                    must "version/v2c or version/v3";
                    key "community-string";
                    description
                      "Specifies an ENCRYPTED community string in aes-128 method";
                    leaf community-string {
                      type string {
                        length "1..1024" {
                          description
                            "The ENCRYPTED community string in aes-128 method";
                        }
                        pattern "[0-9a-zA-Z]+";
                      }
                      description
                        "Specifies an ENCRYPTED community string in aes-128 method";
                    }
                    container version {
                      description
                        "SNMP version to use for notification messages";
                      container v2c {
                        must "not(../v3)";
                        presence "Indicates a v2c node is configured.";
                        description
                          "Use 2c for SNMPv2c";
                      }
                      container v3 {
                        must "not(../v2c)";
                        presence "Indicates a v3 node is configured.";
                        description
                          "Use 3 for SNMPv3";
                        leaf security-level {
                          type enumeration {
                            enum "auth" {
                              value 1;
                              description
                                "Using authNoPriv Security Level";
                            }
                            enum "noauth" {
                              value 0;
                              description
                                "Using noAuthNoPriv Security Level";
                            }
                            enum "priv" {
                              value 2;
                              description
                                "Using authPriv Security Level";
                            }
                          }
                          mandatory true;
                        }
                      }
                    }
                    leaf udp-port {
                      type union {
                        type enumeration {
                          enum "default" {
                            value 162;
                            description
                              "Default UDP port (162)";
                          }
                        }
                        type uint32 {
                          range "1..65535" {
                            description
                              "udp port number";
                          }
                        }
                      }
                      mandatory true;
                      description
                        "udp port to which notifications should be sent";
                    }
                    container dying-gasp {
                      if-feature "is_dying_gasp_supported";
                      presence "Indicates a dying-gasp node is configured.";
                      description
                        "This host will receive dying gasp trap";
                    }
                  }
                }
              }
              container unencrypted {
                description
                  "The UNENCRYPTED (cleartext) community string";
                list unencrypted-string {
                  must "version/v2c or version/v3";
                  key "community-string";
                  description
                    "The UNENCRYPTED (cleartext) community string";
                  leaf community-string {
                    type string {
                      length "1..32" {
                        description
                          "The UNENCRYPTED (cleartext) community string";
                      }
                    }
                    description
                      "The UNENCRYPTED (cleartext) community string";
                  }
                  container version {
                    description
                      "SNMP version to use for notification messages";
                    container v2c {
                      must "not(../v3)";
                      presence "Indicates a v2c node is configured.";
                      description
                        "Use 2c for SNMPv2c";
                    }
                    container v3 {
                      must "not(../v2c)";
                      presence "Indicates a v3 node is configured.";
                      description
                        "Use 3 for SNMPv3";
                      leaf security-level {
                        type enumeration {
                          enum "auth" {
                            value 1;
                            description
                              "Using authNoPriv Security Level";
                          }
                          enum "noauth" {
                            value 0;
                            description
                              "Using noAuthNoPriv Security Level";
                          }
                          enum "priv" {
                            value 2;
                            description
                              "Using authPriv Security Level";
                          }
                        }
                        mandatory true;
                      }
                    }
                  }
                  leaf udp-port {
                    type union {
                      type enumeration {
                        enum "default" {
                          value 162;
                          description
                            "Default UDP port (162)";
                        }
                      }
                      type uint32 {
                        range "1..65535" {
                          description
                            "udp port number";
                        }
                      }
                    }
                    mandatory true;
                    description
                      "udp port to which notifications should be sent";
                  }
                  container dying-gasp {
                    if-feature "is_dying_gasp_supported";
                    presence "Indicates a dying-gasp node is configured.";
                    description
                      "This host will receive dying gasp trap";
                  }
                }
              }
            }
          }
        }
        container contexts {
          description
            "SNMP Context Name";
          list context {
            key "context-name";
            description
              "SNMP Context Name";
            leaf context-name {
              type xr:Cisco-ios-xr-string {
                length "1..32" {
                  description
                    "Context Name";
                }
              }
              description
                "SNMP Context Name";
            }
          }
        }
      }
    }
    container oid-poll-stats {
      presence "Indicates a oid-poll-stats node is configured.";
      description
        "Enable OID poll stats oper CLI";
    }
    container timeouts {
      description
        "SNMP timeouts";
      leaf subagent {
        type uint32 {
          range "1..20" {
            description
              "timeout in secs (default 10)";
          }
        }
        description
          "Sub-Agent Request timeout";
      }
      leaf duplicate {
        type uint32 {
          range "0..20" {
            description
              "timeout in secs (default 1)";
          }
        }
        description
          "Duplicate request feature timeout";
      }
      leaf in-qdrop {
        type uint32 {
          range "0..20" {
            description
              "timeout in secs (default 10)";
          }
        }
        description
          "incoming queue drop feature";
      }
      leaf threshold {
        type uint32 {
          range "0..100000" {
            description
              "Max number of packets in Pre processing Q(default 50000)";
          }
        }
        description
          "threshold incoming queue drop feature";
      }
      container pdu {
        description
          "SNMP pdu statistics end to end";
        leaf stats {
          type uint32 {
            range "1..10" {
              description
                "timeout in secs (default 2)";
            }
          }
          description
            "SNMP pdu statistics timeout";
        }
      }
    }
    container correlator {
      description
        "Configure properties of the event correlator";
      container rules {
        description
          "Configure a specified correlation rule";
        list rule {
          key "rule-name";
          description
            "Configure a specified correlation rule";
          leaf rule-name {
            type string {
              length "1..32" {
                description
                  "Rule name";
              }
            }
            description
              "Configure a specified correlation rule";
          }
          leaf timeout {
            type uint32 {
              range "1..600000" {
                description
                  "Timeout (time the rule is to be active) in milliseconds";
              }
            }
            description
              "Specify timeout";
          }
          container rootcauses {
            description
              "Specify root cause trap";
            list rootcause {
              key "rootcause-name";
              description
                "Specify root cause trap";
              leaf rootcause-name {
                type string {
                  length "1..256" {
                    description
                      "OID of the root message";
                  }
                }
                description
                  "Specify root cause trap";
              }
              container varbinds {
                description
                  "Specify varbind (optional)";
                list varbind {
                  must "index/regex or value/regex";
                  key "varbind-name";
                  description
                    "Specify varbind (optional)";
                  leaf varbind-name {
                    type string {
                      length "1..256" {
                        description
                          "OID of the varbind";
                      }
                    }
                    description
                      "Specify varbind (optional)";
                  }
                  container index {
                    description
                      "Match the varbind index";
                    leaf regex {
                      type string {
                        length "1..512" {
                          description
                            "Regular expression to match for the varbind";
                        }
                      }
                      description
                        "Regular expression to match";
                    }
                  }
                  container value {
                    description
                      "Match the varbind value";
                    leaf regex {
                      type string {
                        length "1..512" {
                          description
                            "Regular expression to match for the varbind";
                        }
                      }
                      description
                        "Regular expression to match";
                    }
                  }
                }
              }
            }
          }
          container nonrootcause {
            description
              "nonrootcause trap";
            container traps {
              description
                "Specify non-root cause trap";
              list trap {
                key "trap-name";
                description
                  "Specify non-root cause trap";
                leaf trap-name {
                  type string {
                    length "1..256" {
                      description
                        "OID of the correlated message";
                    }
                  }
                  description
                    "Specify non-root cause trap";
                }
                container varbinds {
                  description
                    "Specify varbind (optional)";
                  list varbind {
                    must "index/regex or value/regex";
                    key "varbind-name";
                    description
                      "Specify varbind (optional)";
                    leaf varbind-name {
                      type string {
                        length "1..256" {
                          description
                            "OID of the varbind";
                        }
                      }
                      description
                        "Specify varbind (optional)";
                    }
                    container index {
                      description
                        "Match the varbind index";
                      leaf regex {
                        type string {
                          length "1..512" {
                            description
                              "Regular expression to match for the varbind";
                          }
                        }
                        description
                          "Regular expression to match";
                      }
                    }
                    container value {
                      description
                        "Match the varbind value";
                      leaf regex {
                        type string {
                          length "1..512" {
                            description
                              "Regular expression to match for the varbind";
                          }
                        }
                        description
                          "Regular expression to match";
                      }
                    }
                  }
                }
              }
            }
          }
        }
      }
      container rulesets {
        description
          "Configure a specified correlation ruleset";
        list ruleset {
          key "ruleset-name";
          description
            "Configure a specified correlation ruleset";
          leaf ruleset-name {
            type string {
              length "1..32" {
                description
                  "Ruleset name";
              }
            }
            description
              "Configure a specified correlation ruleset";
          }
          container rulenames {
            description
              "Specify rule name";
            list rulename {
              key "rule-name";
              description
                "Specify rule name";
              leaf rule-name {
                type string {
                  length "1..32" {
                    description
                      "Rule name";
                  }
                }
                description
                  "Specify rule name";
              }
            }
          }
        }
      }
      container apply {
        description
          "Apply rule or ruleset";
        container rules {
          description
            "Apply rule";
          list rule {
            key "rule-name";
            description
              "Apply rule";
            leaf rule-name {
              type string {
                length "1..32" {
                  description
                    "Rule name";
                }
              }
              description
                "Apply rule";
            }
            container all-hosts {
              presence "Indicates a all-hosts node is configured.";
              description
                "Apply the rule to all hosts";
            }
            container host {
              description
                "Apply rule to traps destined for specified host";
              container ipv4 {
                description
                  "Host IPv4 address";
                list address {
                  key "address port";
                  description
                    "Host IP address";
                  leaf address {
                    type inet:ipv4-address-no-zone;
                    description
                      "Host IP address";
                  }
                  leaf port {
                    type union {
                      type enumeration {
                        enum "default" {
                          value 162;
                          description
                            "Default UDP port (162)";
                        }
                      }
                      type uint32 {
                        range "1..65535" {
                          description
                            "Host UDP port";
                        }
                      }
                    }
                    description
                      "Host Port number";
                  }
                }
              }
            }
          }
        }
        container rulesets {
          description
            "Apply Ruleset";
          list ruleset {
            key "ruleset-name";
            description
              "Apply Ruleset";
            leaf ruleset-name {
              type string {
                length "1..32" {
                  description
                    "Ruleset name";
                }
              }
              description
                "Apply Ruleset";
            }
            container all-hosts {
              presence "Indicates a all-hosts node is configured.";
              description
                "Apply the rule to all hosts";
            }
            container host {
              description
                "Apply rule to traps destined for specified host";
              container ipv4 {
                description
                  "Host IPv4 address";
                list address {
                  key "address port";
                  description
                    "Host IP address";
                  leaf address {
                    type inet:ipv4-address-no-zone;
                    description
                      "Host IP address";
                  }
                  leaf port {
                    type union {
                      type enumeration {
                        enum "default" {
                          value 162;
                          description
                            "Default UDP port (162)";
                        }
                      }
                      type uint32 {
                        range "1..65535" {
                          description
                            "Host UDP port";
                        }
                      }
                    }
                    description
                      "Host Port number";
                  }
                }
              }
            }
          }
        }
      }
      leaf buffer-size {
        type uint32 {
          range "1024..52428800" {
            description
              "Size of the correlator buffer";
          }
        }
        description
          "Configure size of the correlator buffer";
      }
    }
    container logging {
      description
        "Configuration for logging operations";
      container threshold {
        description
          "Configure thresholds for SNMP data logging";
        leaf oid-processing {
          type uint32 {
            range "0..20000" {
              description
                "Threshold in ms (default 500). Set 0 to log every transaction";
            }
          }
          description
            "Configure threshold to start logging slow OID requests processing";
        }
        leaf pdu-processing {
          type uint32 {
            range "0..20000" {
              description
                "Threshold in ms (default 20000). Set 0 to log every transaction, set to 20000 to disable logging PDU processing time";
            }
          }
          description
            "Configure threshold to start logging slow PDU requests processing";
        }
      }
    }
    container inform {
      description
        "Configure SNMP Informs options";
      leaf retries {
        type uint32 {
          range "0..100" {
            description
              "Number of times to retry an Inform request, default #3";
          }
        }
        description
          "Set retry count for informs";
      }
      leaf timeout {
        type uint32 {
          range "1..42949671" {
            description
              "Timeout value, in seconds, default #15";
          }
        }
        description
          "Set timeout for informs";
      }
      leaf pending {
        type uint32 {
          range "1..4294967295" {
            description
              "Max nmber of informs to hold in queue, default #25";
          }
        }
        description
          "Set max number of informs to hold in queue";
      }
    }
    container mib {
      description
        "SNMP bulk stats configuration commands";
      container bulkstat {
        description
          "SNMP bulk stats configuration commands";
        leaf max-procmem-size {
          type uint32 {
            range "100..200000" {
              description
                "per process memory limit in kilo bytes (default 200000)";
            }
          }
          description
            "per process memory limit in kilo bytes";
        }
        container object-lists {
          description
            "Configure an Object List ";
          list object-list {
            key "object-list-name";
            description
              "Configure an Object List ";
            leaf object-list-name {
              type xr:Cisco-ios-xr-string {
                length "1..32" {
                  description
                    "Name of the object List";
                }
              }
              description
                "Configure an Object List ";
            }
            container adds {
              description
                "Object name or OID ";
              list add {
                key "object-name";
                description
                  "Object name or OID ";
                leaf object-name {
                  type string {
                    length "1..800" {
                      description
                        "Object name or OID ";
                    }
                  }
                  description
                    "Object name or OID ";
                }
              }
            }
          }
        }
        container schemas {
          description
            "Configure schema definition";
          list schema {
            key "schema-name";
            description
              "Configure schema definition";
            leaf schema-name {
              type xr:Cisco-ios-xr-string {
                length "1..32" {
                  description
                    "Name of the schema";
                }
              }
              description
                "Configure schema definition";
            }
            leaf object-list {
              type xr:Cisco-ios-xr-string {
                length "1..32" {
                  description
                    "Name of an object List";
                }
              }
              description
                "Name of an object List";
            }
            leaf poll-interval {
              type uint32 {
                range "1..20000" {
                  description
                    "Periodicity for polling of objects in this schema in Min (default 5)";
                }
              }
              description
                "Periodicity for polling of objects in this schema in Min";
            }
            container instance {
              description
                "Object instance information";
              container exact {
                must "not(../wild or ../range or ../repetition) and (interface or oid)";
                presence "Indicates an exact node is configured.";
                description
                  "Instance when appended with object gives complete oid";
                leaf interface {
                  type xr:Interface-name;
                  must "not(../oid)";
                  description
                    "Specify instance as interface";
                }
                container sub-if {
                  must "../interface";
                  presence "Indicates a sub-if node is configured.";
                  description
                    "Includes all the sub interfaces";
                }
                leaf oid {
                  type string {
                    length "1..1024" {
                      description
                        "Instance oid for objects in this schema";
                    }
                  }
                  must "not(../interface)";
                  description
                    "Specify instance as oid";
                }
              }
              container wild {
                must "not(../exact or ../range or ../repetition) and (interface or oid)";
                presence "Indicates an exact node is configured.";
                description
                  "Remaining indices after appending this instance to objects will be treated as being wild carded";
                leaf interface {
                  type xr:Interface-name;
                  must "not(../oid)";
                  description
                    "Specify instance as interface";
                }
                container sub-if {
                  presence "Indicates a sub-if node is configured.";
                  description
                    "Includes all the sub interfaces";
                }
                leaf oid {
                  type string {
                    length "1..1024" {
                      description
                        "Instance oid for objects in this schema";
                    }
                  }
                  must "not(../interface)";
                  description
                    "Specify instance as oid";
                }
              }
              container range {
                must "not(../exact or ../wild or ../repetition)";
                presence "Indicates a range node is configured.";
                description
                  "SNMP OID ranges are generated when objects get appended with these oids";
                leaf start {
                  type string {
                    length "1..1024" {
                      description
                        "Starting OID of instance range";
                    }
                  }
                  mandatory true;
                  description
                    "Keyword specify as start of OID range";
                }
                leaf end {
                  type string {
                    length "1..1024" {
                      description
                        "End OID of instance range";
                    }
                  }
                  mandatory true;
                  description
                    "Keyword specify as end of OID range";
                }
              }
              leaf repetition {
                type string {
                  length "1..1024" {
                    description
                      "Instance OID for repetition";
                  }
                }
                must "../max";
                description
                  "Collect a sequence of instances starting with a specified instance";
              }
              leaf max {
                type uint32 {
                  range "1..4294967295" {
                    description
                      "Repetition number";
                  }
                }
                must "../repetition";
                description
                  "Keyword specify maximum repetition count";
              }
            }
          }
        }
        container transfer-ids {
          description
            "Configure transfer parameters";
          list transfer-id {
            key "transfer-name";
            description
              "Configure transfer parameters";
            leaf transfer-name {
              type xr:Cisco-ios-xr-string {
                length "1..32" {
                  description
                    "Name of bulk transfer";
                }
              }
              description
                "Configure transfer parameters";
            }
            leaf buffer-size {
              type uint32 {
                range "1024..2147483647" {
                  description
                    "Bulkstat data file maximum size in bytes (default 2048)";
                }
              }
              description
                "Bulkstat data file maximum size";
            }
            container schemas {
              description
                "Schema that contains objects to be collected";
              list schema {
                key "schema-name";
                description
                  "Schema that contains objects to be collected";
                leaf schema-name {
                  type xr:Cisco-ios-xr-string {
                    length "1..32" {
                      description
                        "Schema that contains objects to be collected";
                    }
                  }
                  description
                    "Schema that contains objects to be collected";
                }
              }
            }
            container format {
              description
                "Format of the bulk data file";
              container schema-ascii {
                presence "Indicates a schema-ascii node is configured.";
                description
                  "Schema ASCII format (default)";
              }
            }
            leaf transfer-interval {
              type uint32 {
                range "0..4294967295" {
                  description
                    "Periodicity for transfer of bulk data in minutes (default 30)";
                }
              }
              description
                "Periodicity for the transfer of bulk data in Minutes";
            }
            leaf retry {
              type uint32 {
                range "1..100" {
                  description
                    "Number of transmission retries (default 0)";
                }
              }
              description
                "Number of Retries";
            }
            leaf retain {
              type uint32 {
                range "1..20000" {
                  description
                    "Bulk file retention time in minutes (default 0)";
                }
              }
              description
                "Retention period in Min";
            }
            container enable {
              presence "Indicates a enable node is configured.";
              description
                "Start Data Collection for this Configuration";
            }
            container url {
              description
                "Configure destination address as URL";
              leaf primary {
                type string {
                  length "1..800" {
                    description
                      "FTP or rcp or TFTP can be used for file transfer";
                  }
                }
                description
                  "URL of primary destination";
              }
              leaf secondary {
                type string {
                  length "1..800" {
                    description
                      "FTP or rcp or TFTP can be used for file transfer";
                  }
                }
                description
                  "URL of secondary destination";
              }
            }
          }
        }
      }
    }
  }
}
