module Cisco-IOS-XR-ptp-pd-oper {
  namespace "http://cisco.com/ns/yang/Cisco-IOS-XR-ptp-pd-oper";
  prefix ptp-pd-oper;

  import cisco-semver {
    prefix semver;
  }
  import Cisco-IOS-XR-ptp-oper {
    prefix a1;
  }
  include Cisco-IOS-XR-ptp-pd-oper-sub1 {
    revision-date 2021-08-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ptp-pd package operational data.
     
     This YANG module augments the
       Cisco-IOS-XR-ptp-oper
     module with state data.
     
     Copyright (c) 2013-2021 by Cisco Systems, Inc.
     All rights reserved.";

  revision 2021-08-04 {
    description
      "Schema added for PTP statistics.
       2021-01-25
         Schema added for timestamps logger.";
    semver:module-version "1.1.0";
  }
  revision 2019-04-05 {
    description
      "Establish semantic version baseline.";
    semver:module-version "1.0.1";
  }
  revision 2016-06-08 {
    description
      "Schema added.";
  }
  revision 2015-11-09 {
    description
      "IOS XR 6.0 revision.";
  }

  augment "/a1:ptp" {
    description
      "This augment extends the operational data of
       'Cisco-IOS-XR-ptp-oper'";
    container platform {
      description
        "PTP platform specific data";
      container servo {
        description
          "PTP servo related parameters";
        uses PTP-PD-SERVO-INFO;
      }
      container servo-statistics {
        description
          "PTP servo statistics";
        uses PTP-PD-SERVO-STAT-BUCKETS;
      }
      container timestamps-logger {
        description
          "PTP timestamps logger information";
        uses PTP-PD-TS-LOGGER-INFO;
      }
    }
  }
}
