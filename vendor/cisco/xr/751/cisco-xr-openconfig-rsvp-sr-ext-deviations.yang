//*************  DO-NOT EDIT  **************
//*********** Auto-generated file ********** 

 module cisco-xr-openconfig-rsvp-sr-ext-deviations {


  namespace "http://cisco.com/ns/yang/cisco-xr-openconfig-rsvp-sr-ext-deviations";
  prefix  "oc-sr-rsvp-extdevs";

  import openconfig-rsvp-sr-ext { prefix oc-sr-rsvp-ext; }
  import openconfig-network-instance { prefix oc-ni; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-rsvp-sr-ext.yang@2017-03-06 

     on Cisco IOS-XR devices.

     Copyright (c) 2017, 2019 by Cisco Systems, Inc.
     All rights reserved.";

  revision "2019-05-30" {
    description
      "Initial revision applicable to IOS-XR 6.4.1";
  }


  deviation /oc-ni:network-instances/oc-ni:network-instance/oc-ni:mpls/oc-ni:te-global-attributes/oc-sr-rsvp-ext:bandwidth-measurement/oc-sr-rsvp-ext:update-trigger/oc-sr-rsvp-ext:config/oc-sr-rsvp-ext:update-trigger {
    deviate not-supported;
  }

  deviation /oc-ni:network-instances/oc-ni:network-instance/oc-ni:mpls/oc-ni:te-global-attributes/oc-sr-rsvp-ext:bandwidth-measurement/oc-sr-rsvp-ext:update-trigger/oc-sr-rsvp-ext:config/oc-sr-rsvp-ext:sr-traffic-pct {
    deviate not-supported;
  }

  deviation /oc-ni:network-instances/oc-ni:network-instance/oc-ni:mpls/oc-ni:te-global-attributes/oc-sr-rsvp-ext:bandwidth-measurement/oc-sr-rsvp-ext:update-trigger/oc-sr-rsvp-ext:state/oc-sr-rsvp-ext:sr-traffic-pct {
    deviate not-supported;
  }


}
//total deviations:3
