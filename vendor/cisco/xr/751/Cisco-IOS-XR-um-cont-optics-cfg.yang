module Cisco-IOS-XR-um-cont-optics-cfg {
  namespace "http://cisco.com/ns/yang/Cisco-IOS-XR-um-cont-optics-cfg";
  prefix um-cont-optics-cfg;

  import Cisco-IOS-XR-types {
    prefix xr;
  }
  import Cisco-IOS-XR-um-interface-cfg {
    prefix a1;
  }
  import Cisco-IOS-XR-um-snmp-server-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-optics package configuration.
     
     This YANG module augments the
     modules with configuration data.
     
     Copyright (c) 2021 by Cisco Systems, Inc.
     All rights reserved.";

  revision 2021-08-24 {
    description
      "Updated model as per 24I DT image CLI command";
    semver:module-version "2.0.0";
  }
  revision 2021-05-10 {
    description
      "Initial release";
    semver:module-version "1.0.0";
  }

  feature optics {
    description
      "optics";
  }

  feature optics_config_supp_check {
    description
      "optics config supp check";
  }

  grouping CONT-BODY {
    container dwdm-carrier {
      description
        "Configure the DWDM Carrier Channel";
      container grid-50ghz {
        description
          "Configure Wavelength in 50GHz grid";
        leaf itu-ch {
          type uint32 {
            range "1..100" {
              description
                "Select an ITU channel number; C Band: 1-100";
            }
          }
          must "not(../../grid-100mhz/frequency)";
          must "not(../frequency or ../wavelength)";
          description
            "Configure the ITU 50GHz Grid ITU Channel";
        }
        leaf frequency {
          type uint32 {
            range "19115..19610" {
              description
                "Enter 5-digit Frequency data; e.g. 19580 for 195.8 THz";
            }
          }
          must "not(../../grid-100mhz/frequency)";
          must "not(../itu-ch or ../wavelength)";
          description
            "Configure Frequency and Map to ITU Channel";
        }
        leaf wavelength {
          type uint32 {
            range "1528773..1568362" {
              description
                "Enter 7-digit Wavelength data; e.g. 1532290 for 1532.29 nm";
            }
          }
          must "not(../../grid-100mhz/frequency)";
          must "not(../itu-ch or ../frequency)";
          description
            "Configure Wavelength and Map to ITU Channel";
        }
      }
      container grid-100mhz {
        description
          "Configure Wavelength in 100MHz Grid";
        leaf frequency {
          type uint32 {
            range "1861000..1961000" {
              description
                "Select a Frequency in 100MHz, C Band: 1911500-1961000, L Band: 1861000-1908500";
            }
          }
          must
            "not(../../grid-50ghz/itu-ch or
                 ../../grid-50ghz/frequency or
                 ../../grid-50ghz/wavelength)";
          description
            "Configure Frequency in 100MHz";
        }
      }
    }
    leaf transmit-power {
      type int32 {
        range "-190..50" {
          description
            "Select power level (in units of 0.1dBm)";
        }
      }
      description
        "Configure transponder transmit power ";
    }
    leaf cd-min {
      type int32 {
        range "-350000..350000" {
          description
            "Select  chromatic dispersion min";
        }
      }
      description
        "Chromatic Dispersion min";
    }
    leaf cd-max {
      type int32 {
        range "-350000..350000" {
          description
            "Select  chromatic dispersion max";
        }
      }
      description
        "Chromatic Dispersion max";
    }
    leaf cd-high-threshold {
      type int32 {
        range "-350000..350000" {
          description
            "Select CD value";
        }
      }
      description
        "Configure maximum acceptable CD value";
    }
    leaf cd-low-threshold {
      type int32 {
        range "-350000..350000" {
          description
            "Select CD value";
        }
      }
      description
        "Configure minimum acceptable CD value";
    }
    leaf osnr-low-threshold {
      type uint32 {
        range "0..4000" {
          description
            "Select osnr value (in units of 0.01db)";
        }
      }
      description
        "Configure minimum acceptable OSNR value in 0.01db";
    }
    leaf dgd-high-threshold {
      type uint32 {
        range "0..18000" {
          description
            "Select Differential Group Delay value (in units of 0.01ps)";
        }
      }
      description
        "Configure maximum acceptable Differential Group Delay in 0.01ps";
    }
    container transmit-shutdown {
      presence "Indicates a transmit-shutdown node is configured.";
      description
        "Shutdown the transmit laser";
    }
    leaf rx-low-threshold {
      type int32 {
        range "-400..300" {
          description
            "Select power level (in units of 0.1dBm)";
        }
      }
      description
        "Configure transponder receive power low threshold";
    }
    leaf rx-high-threshold {
      type int32 {
        range "-400..300" {
          description
            "Select power level (in units of 0.1dBm)";
        }
      }
      description
        "Configure transponder receive power high threshold";
    }
    leaf tx-low-threshold {
      type int32 {
        range "-400..300" {
          description
            "Select power level (in units of 0.1dBm)";
        }
      }
      description
        "Configure transponder low transmit power threshold";
    }
    leaf tx-high-threshold {
      type int32 {
        range "-400..300" {
          description
            "Select power level (in units of 0.1dBm)";
        }
      }
      description
        "Configure transponder high transmit power threshold";
    }
    leaf lbc-high-threshold {
      if-feature "optics_config_supp_check";
      type uint32 {
        range "0..100" {
          description
            "Select power level (in units of percentage)";
        }
      }
      description
        "Configure high laser bias current threshold";
    }
    leaf soak-time {
      type uint32 {
        range "10..28800" {
          description
            "Select power level (in units of seconds)";
        }
      }
      description
        "Configure soak time for automatic in-service";
    }
    leaf loopback {
      type enumeration {
        enum "internal" {
          value 1;
          description
            "Select internal loopback mode";
        }
        enum "line" {
          value 2;
          description
            "Select line loopback mode";
        }
      }
      description
        "Configure loopback mode ";
    }
    leaf modulation {
      type enumeration {
        enum "Bpsk" {
          value 1;
          description
            "Select BPSK modulation type";
        }
        enum "Qpsk" {
          value 2;
          description
            "Select QPSK modulation type";
        }
        enum "8Qam" {
          value 3;
          description
            "Select 8QAM modulation type";
        }
        enum "16Qam" {
          value 4;
          description
            "Select 16QAM modulation type";
        }
        enum "32Qam" {
          value 5;
          description
            "Select 32QAM modulation type";
        }
        enum "64Qam" {
          value 6;
          description
            "Select 64QAM modulation type";
        }
        enum "Bpsk-Qpsk" {
          value 7;
          description
            "Select BPSK_QPSK modulation type";
        }
        enum "Qpsk-8Qam" {
          value 8;
          description
            "Select QPSK_8QAM modulation type";
        }
        enum "8Qam-16Qam" {
          value 9;
          description
            "Select 8QAM_16QAM modulation type";
        }
        enum "16Qam-32Qam" {
          value 10;
          description
            "Select 16QAM_32QAM modulation type";
        }
        enum "32Qam-64Qam" {
          value 11;
          description
            "Select 32QAM_64QAM modulation type";
        }
      }
      description
        "Configure modulation types";
    }
    leaf bits-per-symbol {
      type xr:Cisco-ios-xr-string {
        length "1..9" {
          description
            "Enter Bits per Symbol; e.g 13456789";
        }
      }
      description
        "Select bits-per-symbol for this controller";
    }
    leaf baud-rate {
      type xr:Cisco-ios-xr-string {
        length "1..10" {
          description
            "Enter Baud Rate in GBd; e.g 32.4567892";
        }
      }
      description
        "Set baud-rate for this controller in GBd";
    }
    container perf-mon {
      if-feature "optics_config_supp_check";
      description
        "To enable Performance Monitoring";
      container disable {
        must "not(../enable)";
        presence "Indicates a disable node is configured.";
        description
          "Disable performance monitoring";
      }
      container enable {
        must "not(../disable)";
        presence "Indicates a enable node is configured.";
        description
          "Enable performance monitoring";
      }
    }
    leaf fec {
      type enumeration {
        enum "EnhancedHG15" {
          value 1;
          description
            "Forward Error Correction Enhanced_HG15";
        }
        enum "EnhancedHG25" {
          value 2;
          description
            "Forward Error Correction Enhanced_HG25";
        }
        enum "EnhancedHG15DE" {
          value 4;
          description
            "Forward Error Correction Enhanced_HG15_DE";
        }
        enum "EnhancedHG25DE" {
          value 8;
          description
            "Forward Error Correction Enhanced_HG25_DE";
        }
        enum "None" {
          value 32;
          description
            "Forward Error Correction None";
        }
        enum "EnhancedI7" {
          value 128;
          description
            "Forward Error Correction Enhanced_I_7";
        }
        enum "EnhancedI4" {
          value 256;
          description
            "Forward Error Correction Enhanced_I_4";
        }
        enum "EnhancedSwizzle" {
          value 512;
          description
            "Forward Error Correction Enhanced_Swizzle";
        }
        enum "EnhancedHG20" {
          value 1024;
          description
            "Forward Error Correction Enhanced_HG20";
        }
        enum "EnhancedHG7" {
          value 2048;
          description
            "Forward Error Correction Enhanced_HG7";
        }
        enum "EnhancedSD20" {
          value 4096;
          description
            "Forward Error Correction Soft-Decision 20";
        }
        enum "EnhancedSD7" {
          value 8192;
          description
            "Forward Error Correction Soft-Decision 7";
        }
        enum "EnhancedSD15" {
          value 16384;
          description
            "Forward Error Correction Soft-Decision 15";
        }
        enum "EnhancedSD27" {
          value 32768;
          description
            "Forward Error Correction Soft-Decision 27";
        }
        enum "EnhancedSD15DE" {
          value 65536;
          description
            "Forward Error Correction Soft-Decision 15 with DE";
        }
        enum "EnhancedStaircaseDE" {
          value 131072;
          description
            "Forward Error Correction Enhanced Staircase FEC with DE";
        }
        enum "OFEC" {
          value 262144;
          description
            "Forward Error Correction O_FEC";
        }
        enum "CFEC" {
          value 524288;
          description
            "Forward Error Correction C_FEC";
        }
        enum "Standard" {
          value 1048576;
          description
            "Forward Error Correction Standard";
        }
      }
      description
        "Configure Forward Error Correction mode";
    }
    leaf ext-description {
      type string {
        length "1..800" {
          description
            "Ext-Description for this controller";
        }
      }
      description
        "Set ext-description for this controller";
    }
    container logging {
      description
        "Per-interface logging configuration";
      container events {
        description
          "Per-interface logging events";
        container link-status {
          presence "Indicates a link-status node is configured.";
          description
            "Enable interface and line-protocol state change alarms";
        }
      }
    }
    leaf filter-roll-off-factor {
      type xr:Cisco-ios-xr-string {
        length "5" {
          description
            "RRC Filter Roll-Off factor in increments of 0.001";
        }
      }
      description
        "RRC Filter Roll-Off factor.";
    }
    leaf enh-colorless-mode {
      type uint32 {
        range "1..3" {
          description
            "Select enhanced colorless mode";
        }
      }
      description
        "Enhanced Colorless Mode.";
    }
    leaf enh-sop-tol-mode {
      type uint32 {
        range "1..3" {
          description
            "Select enhanced SOP tolerance mode";
        }
      }
      description
        "Enhanced SOP Tolerance Mode.";
    }
    leaf nleq-comp-mode {
      type uint32 {
        range "1..4" {
          description
            "Select non linear effect compenstation mode";
        }
      }
      description
        "Non Linear Effect Compenstation.";
    }
    leaf cross-pol-gain-mode {
      type uint32 {
        range "1..15" {
          description
            "Select carrier phase recovery cross polarization gain mode";
        }
      }
      description
        "Carrier Phase Recovery Cross Polarization Gain Mode.";
    }
    leaf cross-pol-weight-mode {
      type uint32 {
        range "1..7" {
          description
            "Select carrier phase recovery cross polarization weight mode";
        }
      }
      description
        "Carrier Phase Recovery Cross Polarization Weight Mode.";
    }
    leaf cpr-win-mode {
      type uint32 {
        range "1..4" {
          description
            "Select carrier phase recovery window mode";
        }
      }
      description
        "Carrier Phase Recovery Window Mode.";
    }
    leaf cpr-ext-win-mode {
      type uint32 {
        range "1..9" {
          description
            "Select carrier phase recovery extended window mode";
        }
      }
      description
        "Carrier Phase Recovery Extended Window Mode.";
    }
    container submarine-params {
      description
        "Proprietary Submarine Parameters";
      list submarine-param {
        key "parameter-type";
        description
          "Proprietary Submarine Parameters";
        leaf parameter-type {
          type uint32 {
            range "1..10" {
              description
                "Proprietary Submarine Parameter Type";
            }
          }
          description
            "Proprietary Submarine Parameters";
        }
        leaf parameter-value {
          type uint32 {
            range "1..1000" {
              description
                "Proprietary Submarine Parameter Value";
            }
          }
          mandatory true;
          description
            "Proprietary Submarine Parameters";
        }
      }
    }
    container rx-voa {
      description
        "rx-voa configuration.";
      leaf target-power {
        type int32 {
          range "-190..30" {
            description
              "Receive Target Power in 0.1 dbm.";
          }
        }
        description
          "Receive Target Power";
      }
      leaf fixed-ratio {
        type int32 {
          range "100..1700" {
            description
              "Receive Ratio of Optical Attenuation in 0.01 db";
          }
        }
        description
          "Receive Ratio of Optical Attenuation.";
      }
    }
    container transceiver {
      description
        "Configure the transceiver module";
      container disable {
        if-feature "optics_config_supp_check";
        presence "Indicates a disable node is configured.";
        description
          "disable the transceiver module";
      }
    }
    leaf ampli-gain {
      type int32 {
        range "0..500" {
          description
            "Select power level (in units of 0.1dBm)";
        }
      }
      description
        "Configure AMPLI GAIN";
    }
    leaf ampli-gain-range {
      type enumeration {
        enum "normal" {
          value 1;
          description
            "Select Ampli Gain Range as Normal";
        }
        enum "extended" {
          value 2;
          description
            "Select Ampli Gain Range as Extended";
        }
      }
      description
        "Ampli Gain Range";
    }
    container osri {
      description
        "Configure Optical safety remote interlock (OSRI)";
      container on {
        must "not(../off)";
        presence "Indicates a on node is configured.";
        description
          "Enable OSRI ";
      }
      container off {
        must "not(../on)";
        presence "Indicates a off node is configured.";
        description
          "Disable OSRI ";
      }
    }
    leaf safety-control-mode {
      type enumeration {
        enum "auto" {
          value 1;
          description
            "Select Safety Control Mode: Automatic";
        }
        enum "disabled" {
          value 2;
          description
            "Disable Safety Control Mode";
        }
      }
      description
        "Configure safety Control Mode ";
    }
    leaf ampli-channel-power {
      type int32 {
        range "-400..300" {
          description
            "Select power level (in units of 0.1dBm)";
        }
      }
      description
        "Configure amplifier per channel power set point";
    }
    leaf channel-power-max-delta {
      type int32 {
        range "0..200" {
          description
            "Select power level (in units of 0.1dBm)";
        }
      }
      description
        "Configure max delta among all measured channel powers ";
    }
    leaf ampli-gain-thr-deg-low {
      type int32 {
        range "0..500" {
          description
            "Select power level (in units of 0.1dBm)";
        }
      }
      description
        "Configure low amplifier gain degrade theshold for gain alarm";
    }
    leaf ampli-gain-thr-deg-high {
      type int32 {
        range "0..500" {
          description
            "Select power level (in units of 0.1dBm)";
        }
      }
      description
        "Configure high amplifier gain degrade theshold for gain alarm";
    }
    leaf ampli-control-mode {
      type enumeration {
        enum "automatic" {
          value 1;
          description
            "Select Amplifier Working Mode: Automatic";
        }
        enum "manual" {
          value 2;
          description
            "Select Amplifier Working Mode: Manual";
        }
      }
      description
        "Configure amplifier working mode ";
    }
    leaf ampli-tilt {
      type int32 {
        range "-50..50" {
          description
            "Select level (in units of 0.1dB)";
        }
      }
      description
        "Configure amplifier tilt";
    }
    leaf rx-voa-attenuation {
      type int32 {
        range "0..200" {
          description
            "Select attenuation level (in units of 0.1dBm)";
        }
      }
      description
        "Configure RX Voa Attenuation Setpoint";
    }
    leaf tx-voa-attenuation {
      type int32 {
        range "0..200" {
          description
            "Select attenuation level (in units of 0.1dB)";
        }
      }
      description
        "Configure TX voa Attenuation Setpoint";
    }
    leaf tx-enable {
      type uint32 {
        range "0..1" {
          description
            "0:Disable TX, 1:Enable TX";
        }
      }
      description
        "Configure TX param";
    }
    leaf rx-enable {
      type uint32 {
        range "0..1" {
          description
            "0:Disable RX, 1:Enable RX";
        }
      }
      description
        "Configure RX param";
    }
    leaf rx-low-threshold-delta {
      type int32 {
        range "0..300" {
          description
            "Set revertive threshold delta value (in units of 0.1dBm)";
        }
      }
      description
        "Configure revertive hysteresis value for the low fail threshold ";
    }
    leaf ampli-channel-psd {
      type int32 {
        range "0..800000" {
          description
            "Select psd level (in units of 0.001 nW/MHz)";
        }
      }
      description
        "Configure amplifier per channel psd set point";
    }
    leaf rx-low-threshold-psd {
      type int32 {
        range "0..800000" {
          description
            "Select psd level (in units of 0.001 nW/MHz)";
        }
      }
      description
        "Configure transponder low receive psd threshold";
    }
    leaf add-drop-channel {
      type xr:Interface-name {
        pattern "OTS-OCH.*";
      }
      description
        "configures optical cross connect";
    }
    leaf ingress-ampli-gain {
      type int32 {
        range "80..330" {
          description
            "Select power level (in units of 0.1dB)";
        }
      }
      description
        "Configure INGRESS AMPLI GAIN";
    }
    leaf ingress-ampli-gain-range {
      type enumeration {
        enum "normal" {
          value 1;
          description
            "Select Ampli Gain Range as Normal";
        }
        enum "extended" {
          value 2;
          description
            "Select Ampli Gain Range as Extended";
        }
      }
      description
        "Ingress Ampli Gain Range";
    }
    leaf ingress-ampli-gain-thr-deg-low {
      type int32 {
        range "0..500" {
          description
            "Select power level (in units of 0.1dB)";
        }
      }
      description
        "Configure low amplifier gain degrade theshold for gain alarm";
    }
    leaf ingress-ampli-gain-thr-deg-high {
      type int32 {
        range "0..500" {
          description
            "Select power level (in units of 0.1dB)";
        }
      }
      description
        "Configure high amplifier gain degrade theshold for gain alarm";
    }
    leaf ingress-ampli-tilt {
      type int32 {
        range "-50..50" {
          description
            "Select level (in units of 0.1dB)";
        }
      }
      description
        "Configure amplifier tilt";
    }
    leaf egress-ampli-gain {
      type int32 {
        range "80..330" {
          description
            "Select power level (in units of 0.1dB)";
        }
      }
      description
        "Configure EGRESS AMPLI GAIN";
    }
    leaf egress-ampli-gain-range {
      type enumeration {
        enum "normal" {
          value 1;
          description
            "Select Ampli Gain Range as Normal";
        }
        enum "extended" {
          value 2;
          description
            "Select Ampli Gain Range as Extended";
        }
      }
      description
        "egress Ampli Gain Range";
    }
    leaf egress-ampli-gain-thr-deg-low {
      type int32 {
        range "0..500" {
          description
            "Select power level (in units of 0.1dB)";
        }
      }
      description
        "Configure low amplifier gain degrade theshold for gain alarm";
    }
    leaf egress-ampli-gain-thr-deg-high {
      type int32 {
        range "0..500" {
          description
            "Select power level (in units of 0.1dB)";
        }
      }
      description
        "Configure high amplifier gain degrade theshold for gain alarm";
    }
    leaf egress-ampli-tilt {
      type int32 {
        range "-50..50" {
          description
            "Select level (in units of 0.1dB)";
        }
      }
      description
        "Configure amplifier tilt";
    }
    container raman-tx-powers {
      description
        "configure Raman Transmit Power Param";
      list raman-tx-power {
        key "raman-tx-power-id";
        description
          "configure Raman Transmit Power Param";
        leaf raman-tx-power-id {
          type uint32 {
            range "1..5" {
              description
                "RAMAN Transmit Pump Instance";
            }
          }
          description
            "configure Raman Transmit Power Param";
        }
        leaf value {
          type uint32 {
            range "35..360" {
              description
                "Select power level (in units of 0.01mW)";
            }
          }
          description
            "set value";
        }
      }
    }
    leaf ingress-ampli-safety-control-mode {
      type enumeration {
        enum "auto" {
          value 1;
          description
            "Select Safety Control Mode: Automatic";
        }
        enum "disabled" {
          value 2;
          description
            "Disable Safety Control Mode";
        }
      }
      description
        "Configure ingress ampli safety Control Mode ";
    }
    container ingress-ampli-osri {
      description
        "Configure Optical safety remote interlock (OSRI)";
      container on {
        must "not(../off)";
        presence "Indicates a on node is configured.";
        description
          "Enable OSRI ";
      }
      container off {
        must "not(../on)";
        presence "Indicates a off node is configured.";
        description
          "Disable OSRI ";
      }
    }
    container ingress-ampli-force-apr {
      description
        "Configure ingress Ampli Force Automatic Power Reduction";
      container on {
        must "not(../off)";
        presence "Indicates a on node is configured.";
        description
          "Enable Force APR ";
      }
      container off {
        must "not(../on)";
        presence "Indicates a off node is configured.";
        description
          "Disable Force APR ";
      }
    }
    leaf egress-ampli-safety-control-mode {
      type enumeration {
        enum "auto" {
          value 1;
          description
            "Select Safety Control Mode: Automatic";
        }
        enum "disabled" {
          value 2;
          description
            "Disable Safety Control Mode";
        }
      }
      description
        "Configure egress ampli safety Control Mode ";
    }
    container egress-ampli-osri {
      description
        "Configure egress Optical safety remote interlock (OSRI)";
      container on {
        must "not(../off)";
        presence "Indicates a on node is configured.";
        description
          "Enable OSRI ";
      }
      container off {
        must "not(../on)";
        presence "Indicates a off node is configured.";
        description
          "Disable OSRI ";
      }
    }
    container egress-ampli-force-apr {
      description
        "Configure egress ampli Force Automatic Power Reduction";
      container on {
        must "not(../off)";
        presence "Indicates a on node is configured.";
        description
          "Enable Force APR ";
      }
      container off {
        must "not(../on)";
        presence "Indicates a off node is configured.";
        description
          "Disable Force APR ";
      }
    }
    container egress-ampli-br {
      description
        "Configure egress ampli back reflection";
      container enable {
        must "not(../disable)";
        presence "Indicates a enable node is configured.";
        description
          "Enable Back Reflection ";
      }
      container disable {
        must "not(../enable)";
        presence "Indicates a disable node is configured.";
        description
          "Disable Back Reflection ";
      }
    }
    leaf egress-ampli-br-high-threshold {
      type int32 {
        range "-500..300" {
          description
            "Select value (in units of 0.1dBm)";
        }
      }
      description
        "Configure egress ampli back reflection high threshold";
    }
    leaf raman-safety-control-mode {
      type enumeration {
        enum "auto" {
          value 1;
          description
            "Select Safety Control Mode: Automatic";
        }
        enum "disabled" {
          value 2;
          description
            "Disable Safety Control Mode";
        }
      }
      description
        "Configure Raman safety Control Mode ";
    }
    container raman-osri {
      description
        "Configure raman Optical safety remote interlock (OSRI)";
      container on {
        must "not(../off)";
        presence "Indicates a on node is configured.";
        description
          "Enable OSRI ";
      }
      container off {
        must "not(../on)";
        presence "Indicates a off node is configured.";
        description
          "Disable OSRI ";
      }
    }
    container raman-force-apr {
      description
        "Configure raman Force Automatic Power Reduction";
      container on {
        must "not(../off)";
        presence "Indicates a on node is configured.";
        description
          "Enable Force APR ";
      }
      container off {
        must "not(../on)";
        presence "Indicates a off node is configured.";
        description
          "Disable Force APR ";
      }
    }
    container raman-br {
      description
        "Configure raman back reflection";
      container enable {
        must "not(../disable)";
        presence "Indicates a enable node is configured.";
        description
          "Enable Back Reflection ";
      }
      container disable {
        must "not(../enable)";
        presence "Indicates a disable node is configured.";
        description
          "Disable Back Reflection ";
      }
    }
    leaf raman-br-high-threshold {
      type int32 {
        range "-500..300" {
          description
            "Select value (in units of 0.1dBm)";
        }
      }
      description
        "Configure raman back reflection high threshold";
    }
    container ingress-channel-slices {
      description
        "Configure Ingress Channel Slice";
      list ingress-channel-slice {
        key "ingress-channel-slice-id";
        description
          "Configure Ingress Channel Slice";
        leaf ingress-channel-slice-id {
          type uint32 {
            range "1..1548" {
              description
                "Ingress Channel Slice";
            }
          }
          description
            "Configure Ingress Channel Slice";
        }
        leaf attn {
          type uint32 {
            range "0..250" {
              description
                "Select attenuation (in units of 0.1 dB)";
            }
          }
          description
            "set attenuation";
        }
      }
    }
    container egress-channel-slices {
      description
        "Configure egress Channel Slice";
      list egress-channel-slice {
        key "egress-channel-slice-id";
        description
          "Configure egress Channel Slice";
        leaf egress-channel-slice-id {
          type uint32 {
            range "1..1548" {
              description
                "egress Channel Slice";
            }
          }
          description
            "Configure egress Channel Slice";
        }
        leaf attn {
          type uint32 {
            range "0..250" {
              description
                "Select attenuation (in units of 0.1 dB)";
            }
          }
          description
            "set attenuation";
        }
      }
    }
    leaf channel-attn {
      type uint32 {
        range "0..250" {
          description
            "Select value (in units of 0.1dB)";
        }
      }
      description
        "Configure channel attenuation";
    }
    container fastpoll {
      description
        "To enable fastpoll";
      container disable {
        must "not(../enable)";
        presence "Indicates a disable node is configured.";
        description
          "Disable fastpoll";
      }
      container enable {
        must "not(../disable)";
        presence "Indicates a enable node is configured.";
        description
          "Enable fastpoll";
      }
    }
    container network {
      description
        "Configure OPTICS network information";
      container srlg {
        description
          "Submode to configure shared risks for the connection";
        container sets {
          description
            "Configure Network SRLG sets";
          list set {
            key "set-index";
            description
              "Configure Network SRLG sets";
            leaf set-index {
              type uint32 {
                range "1..17" {
                  description
                    "Set index";
                }
              }
              description
                "Configure Network SRLG sets";
            }
            leaf-list network-srlg-value {
              type uint32 {
                range "0..4294967294" {
                  description
                    "Network SRLG values";
                }
              }
              min-elements 1;
              max-elements "6";
              description
                "Network SRLG values";
            }
          }
        }
      }
    }
    container lane-id {
      description
        "Lane Number for optics port";
      list lane-number {
        key "number";
        description
          "Lane Number";
        leaf number {
          type uint32 {
            range "1..12" {
              description
                "Lane Number";
            }
          }
          description
            "Lane Number";
        }
        leaf lane-description {
          type string {
            length "1..800" {
              description
                "Description";
            }
          }
          mandatory true;
          description
            "Description of the channel";
        }
      }
    }
  }

  augment "/a1:interfaces/a1:controller" {
    uses CONT-BODY;
  }
  augment "/a1:interfaces/a1:controller-preconfigure" {
    uses CONT-BODY;
  }
  augment "/a2:snmp-server/a2:traps" {
    container optical {
      presence "Indicates a optical node is configured.";
      description
        "Enable SNMP Cisco optical traps";
    }
    container optical-ots {
      presence "Indicates a optical-ots node is configured.";
      description
        "Enable SNMP Cisco optical ots traps";
    }
  }
}
