module Cisco-IOS-XR-ppp-ma-oper {
  namespace "http://cisco.com/ns/yang/Cisco-IOS-XR-ppp-ma-oper";
  prefix ppp-ma-oper;

  import Cisco-IOS-XR-types {
    prefix xr;
  }
  import cisco-semver {
    prefix semver;
  }
  include Cisco-IOS-XR-ppp-ma-oper-sub4 {
    revision-date 2021-06-15;
  }
  include Cisco-IOS-XR-ppp-ma-oper-sub3 {
    revision-date 2021-06-15;
  }
  include Cisco-IOS-XR-ppp-ma-oper-sub2 {
    revision-date 2021-06-15;
  }
  include Cisco-IOS-XR-ppp-ma-oper-sub1 {
    revision-date 2021-06-15;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ppp-ma package operational data.
     
     This module contains definitions
     for the following management objects:
       ppp: PPP operational data
     
     Copyright (c) 2013-2021 by Cisco Systems, Inc.
     All rights reserved.";

  revision 2021-06-15 {
    description
      "Added new elements in ppp oper idump bag.";
    semver:module-version "1.0.1";
  }
  revision 2019-04-05 {
    description
      "Establish semantic version baseline.";
    semver:module-version "1.0.1";
  }
  revision 2015-11-09 {
    description
      "IOS XR 6.0 revision.";
  }

  container ppp {
    config false;
    description
      "PPP operational data";
    container nodes {
      description
        "Per node PPP operational data";
      list node {
        key "node-name";
        description
          "The PPP operational data for a particular node";
        container statistics {
          description
            "PPP statistics data for a particular node";
          uses PPP-OPER-STATS-GLOBAL;
        }
        container node-interfaces {
          description
            "Per interface PPP operational data";
          list node-interface {
            key "interface";
            description
              "LCP and summarized NCP data for an interface
               running PPP";
            leaf interface {
              type xr:Interface-name;
              description
                "Interface running PPP";
            }
            uses PPP-PROTOCOL-INFO;
          }
        }
        container sso-alerts {
          description
            "PPP SSO Alert data for a particular node";
          list sso-alert {
            key "interface";
            description
              "PPP SSO Alert data for a particular interface";
            leaf interface {
              type xr:Interface-name;
              description
                "Interface with SSO Alert";
            }
            uses PPP-OPER-SSO-ALERTS;
          }
        }
        container node-interface-statistics {
          description
            "Per interface PPP operational statistics";
          list node-interface-statistic {
            key "interface-name";
            description
              "LCP and NCP statistics for an interface
               running PPP";
            leaf interface-name {
              type xr:Interface-name;
              description
                "Interface running PPP";
            }
            uses PPP-OPER-STATS-INTERFACE;
          }
        }
        container sso-summary {
          description
            "Summarized PPP SSO data for a particular node";
          uses PPP-OPER-SSO-SUMMARY;
        }
        container sso-groups {
          description
            "PPP SSO Group data for a particular node";
          list sso-group {
            key "group-id";
            description
              "PPP SSO state data for a particular group";
            container sso-states {
              description
                "PPP SSO State data for a particular group";
              list sso-state {
                key "session-id";
                description
                  "PPP SSO State data for a particular
                   interface";
                leaf session-id {
                  type uint32 {
                    range "1..4294967295";
                  }
                  description
                    "Session ID for the interface with SSO
                     State";
                }
                uses PPP-OPER-SSO-STATE;
              }
            }
            leaf group-id {
              type uint32 {
                range "1..65535";
              }
              description
                "The identifier for the group";
            }
          }
        }
        container summary {
          description
            "Summarized PPP data for a particular node";
          uses PPP-OPER-SUMMARY;
        }
        leaf node-name {
          type xr:Node-id;
          description
            "The identifier for the node";
        }
      }
    }
  }
}
