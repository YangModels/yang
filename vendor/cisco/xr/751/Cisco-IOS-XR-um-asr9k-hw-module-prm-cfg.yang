module Cisco-IOS-XR-um-asr9k-hw-module-prm-cfg {
  namespace "http://cisco.com/ns/yang/Cisco-IOS-XR-um-asr9k-hw-module-prm-cfg";
  prefix um-asr9k-hw-module-prm-cfg;

  import Cisco-IOS-XR-types {
    prefix xr;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-hw-module-prm package configuration.
     
     This YANG module augments the
     modules with configuration data.
     
     Copyright (c) 2021 by Cisco Systems, Inc.
     All rights reserved.";

  revision 2021-06-11 {
    description
      "Initial release";
    semver:module-version "1.0.0";
  }

  grouping LOCATION-BODY {
    container loopback-shape {
      description
        "Configure loopback shaper";
      list np {
        key "np-id app-set";
        description
          "NP to configure";
        leaf np-id {
          type uint32 {
            range "0..7" {
              description
                "Number between 0-7";
            }
          }
          description
            "NP to configure";
        }
        leaf app-set {
          type uint32 {
            range "0..2" {
              description
                "App-set 0: Multicast, SPAN & Netflow. App-set 1: ABF, GRE & LI. App-set 2: IRB";
            }
          }
          description
            "Set of Loopback apps to configure";
        }
        leaf rate {
          type uint32 {
            range "160..10000000" {
              description
                "Number between 160-10000000";
            }
          }
          mandatory true;
          description
            "Shape rate";
        }
      }
    }
  }

  augment "/location:locations/location:location" {
    uses LOCATION-BODY;
  }
  container hw-module {
    description
      "Configure h/w module";
    container early-fast-discard {
      description
        "Configure Early Fast Discard";
      container locations {
        description
          "Configure line card location";
        list location {
          key "location-name";
          description
            "Configure line card location";
          leaf location-name {
            type xr:Node-id;
            description
              "Configure line card location";
          }
          leaf mode {
            type enumeration {
              enum "only-outer-encap" {
                value 0;
                description
                  "Only check out outer encap";
              }
              enum "include-inner-encap" {
                value 1;
                description
                  "Check outer and inner encap";
              }
            }
            description
              "Configure mode (default = only-outer-encap)";
          }
          container high-priority-list {
            description
              "Configure COS mapping to high priority";
            container vlan-cos {
              description
                "Select VLAN COS";
              container zero {
                presence "Indicates a zero node is configured.";
                description
                  "0";
              }
              container one {
                presence "Indicates a one node is configured.";
                description
                  "1";
              }
              container two {
                presence "Indicates a two node is configured.";
                description
                  "2";
              }
              container three {
                presence "Indicates a three node is configured.";
                description
                  "3";
              }
              container four {
                presence "Indicates a four node is configured.";
                description
                  "4";
              }
              container five {
                presence "Indicates a five node is configured.";
                description
                  "5";
              }
              container six {
                presence "Indicates a six node is configured.";
                description
                  "6";
              }
              container seven {
                presence "Indicates a seven node is configured.";
                description
                  "7";
              }
            }
          }
          leaf vlan-cos {
            type uint32 {
              range "0..7" {
                description
                  "Specify VLAN COS threshold";
              }
            }
            description
              "Select a VLAN COS threshold ";
          }
          leaf vlan-op {
            type enumeration {
              enum "lt" {
                value 2;
                description
                  "Less-than";
              }
              enum "ge" {
                value 3;
                description
                  "Greater-than-or-equal";
              }
            }
            must "../vlan-cos";
            description
              "Select VLAN operation (default = greater-than-or-equal)";
          }
          leaf ip-prec {
            type uint32 {
              range "0..7" {
                description
                  "Specify IP TOS Precedence threshold";
              }
            }
            description
              "Select an IP TOS Precedence threshold ";
          }
          leaf ip-op {
            type enumeration {
              enum "lt" {
                value 2;
                description
                  "Less-than";
              }
              enum "ge" {
                value 3;
                description
                  "Greater-than-or-equal";
              }
            }
            must "../ip-prec";
            description
              "Select IP operation (default = greater-than-or-equal)";
          }
          leaf mpls-exp {
            type uint32 {
              range "0..7" {
                description
                  "Specify MPLS EXP threshold";
              }
            }
            description
              "Select an MPLS EXP threshold ";
          }
          leaf mpls-op {
            type enumeration {
              enum "lt" {
                value 2;
                description
                  "Less-than";
              }
              enum "ge" {
                value 3;
                description
                  "Greater-than-or-equal";
              }
            }
            must "../mpls-exp";
            description
              "Select MPLS operation (default = greater-than-or-equal)";
          }
          container burst-absorption {
            presence "Indicates a burst-absorption node is configured.";
            description
              "Enable burst absorption mode.";
          }
        }
      }
      container all {
        description
          "All locations";
        leaf mode {
          type enumeration {
            enum "only-outer-encap" {
              value 0;
              description
                "Only check out outer encap";
            }
            enum "include-inner-encap" {
              value 1;
              description
                "Check outer and inner encap";
            }
          }
          description
            "Configure mode (default = only-outer-encap)";
        }
        container high-priority-list {
          description
            "Configure COS mapping to high priority";
          container vlan-cos {
            description
              "Select VLAN COS";
            container zero {
              presence "Indicates a zero node is configured.";
              description
                "0";
            }
            container one {
              presence "Indicates a one node is configured.";
              description
                "1";
            }
            container two {
              presence "Indicates a two node is configured.";
              description
                "2";
            }
            container three {
              presence "Indicates a three node is configured.";
              description
                "3";
            }
            container four {
              presence "Indicates a four node is configured.";
              description
                "4";
            }
            container five {
              presence "Indicates a five node is configured.";
              description
                "5";
            }
            container six {
              presence "Indicates a six node is configured.";
              description
                "6";
            }
            container seven {
              presence "Indicates a seven node is configured.";
              description
                "7";
            }
          }
        }
        leaf vlan-cos {
          type uint32 {
            range "0..7" {
              description
                "Specify VLAN COS threshold";
            }
          }
          description
            "Select a VLAN COS threshold";
        }
        leaf vlan-op {
          type enumeration {
            enum "lt" {
              value 2;
              description
                "Less-than";
            }
            enum "ge" {
              value 3;
              description
                "Greater-than-or-equal";
            }
          }
          must "../vlan-cos";
          description
            "Select VLAN operation (default = greater-than-or-equal)";
        }
        leaf ip-prec {
          type uint32 {
            range "0..7" {
              description
                "Specify IP TOS Precedence threshold";
            }
          }
          description
            "Select an IP TOS Precedence threshold ";
        }
        leaf ip-op {
          type enumeration {
            enum "lt" {
              value 2;
              description
                "Less-than";
            }
            enum "ge" {
              value 3;
              description
                "Greater-than-or-equal";
            }
          }
          must "../ip-prec";
          description
            "Select IP operation (default = greater-than-or-equal)";
        }
        leaf mpls-exp {
          type uint32 {
            range "0..7" {
              description
                "Specify MPLS EXP threshold";
            }
          }
          description
            "Select an MPLS EXP threshold";
        }
        leaf mpls-op {
          type enumeration {
            enum "lt" {
              value 2;
              description
                "Less-than";
            }
            enum "ge" {
              value 3;
              description
                "Greater-than-or-equal";
            }
          }
          must "../mpls-exp";
          description
            "Select MPLS operation (default = greater-than-or-equal)";
        }
        container burst-absorption {
          presence "Indicates a burst-absorption node is configured.";
          description
            "Enable burst absorption mode.";
        }
      }
    }
    container qos-mode {
      description
        "Configure qos mode in HW Module port(s)";
      container locations {
        description
          "Configure line card location";
        list location {
          key "location-name";
          description
            "Configure line card location";
          leaf location-name {
            type xr:Node-id;
            description
              "Configure line card location";
          }
          container qos-child-shaping-disabled {
            presence "Indicates a qos-child-shaping-disabled node is configured.";
            description
              "Configure QoS mode child level / flat policy shaping disabled on all the line card interfaces";
          }
          container lowburst-enabled {
            presence "Indicates a lowburst-enabled node is configured.";
            description
              "Configure lowburst mode";
          }
          container pwhe-aggregate-shaper {
            description
              "Configure pseudo wire headend interface qos parameters";
            container sub-interface {
              description
                "Configure pseudo wire headend sub interface qos mode";
              leaf ingress {
                type enumeration {
                  enum "non-queuing" {
                    value 1;
                    description
                      "coexistence non-queuing";
                  }
                  enum "queuing" {
                    value 2;
                    description
                      "coexistence queuing";
                  }
                }
                description
                  "ingress direction";
              }
              leaf egress {
                type enumeration {
                  enum "non-queuing" {
                    value 1;
                    description
                      "coexistence non-queuing";
                  }
                  enum "queuing" {
                    value 2;
                    description
                      "coexistence queuing";
                  }
                }
                description
                  "egress direction";
              }
            }
          }
          container port-limit-oversubscribe {
            presence "Indicates a port-limit-oversubscribe node is configured.";
            description
              "Double port buffer limits, oversubscribing buffer memory";
          }
          leaf fastq-threshold-increase {
            type uint32 {
              range "1..100" {
                description
                  "fastq-threshold-increase between 1 to 100 percent";
              }
            }
            description
              "increase fastq threshold value in percent ";
          }
          leaf low-bandwidth-mode {
            type uint32 {
              range "8..12" {
                description
                  "low bandwidth weight factor between 8 to 12";
              }
            }
            description
              "low bandwidth weights for low shaper rate less than 31 mbps";
          }
        }
      }
    }
    container tcp-mss-adjust {
      description
        "Configure TCP MSS Adjust for an NP";
      container locations {
        description
          "Configure line card location";
        list location {
          key "location-name";
          description
            "Configure line card location";
          leaf location-name {
            type xr:Node-id;
            description
              "Configure line card location";
          }
          container nps {
            description
              "NP to configure";
            list np {
              key "np-id";
              description
                "NP to configure";
              leaf np-id {
                type uint32 {
                  range "0..7" {
                    description
                      "Number between 0-7";
                  }
                }
                description
                  "NP to configure";
              }
              leaf value {
                type uint32 {
                  range "1280..1535" {
                    description
                      "TCP MSS Adjust value for all interfaces on this NP";
                  }
                }
                mandatory true;
                description
                  "TCP MSS adjust value";
              }
            }
          }
        }
      }
    }
    container profile {
      description
        "Configure memory resource profile";
      leaf scale {
        type enumeration {
          enum "l2" {
            value 1;
            description
              "L2 scale profile";
          }
          enum "default" {
            value 2;
            description
              "Default scale profile (L3)";
          }
          enum "l3xl" {
            value 3;
            description
              "L3 XL scale profile";
          }
          enum "evpn-convergence" {
            value 5;
            description
              "evpn convergence scale profile";
          }
          enum "bng-max" {
            value 11;
            description
              "BNG max scale profile";
          }
        }
        description
          "Configure scale profile";
      }
      container itcam {
        description
          "Configure internal tcam partition profile";
        container locations {
          description
            "All internal TCAM partition provisionable locations";
          list location {
            must "internal-itcam or lightspeed";
            key "location-name";
            description
              "All internal TCAM partition provisionable locations";
            leaf location-name {
              type xr:Node-id;
              description
                "All internal TCAM partition provisionable locations";
            }
            leaf internal-itcam {
              type enumeration {
                enum "to-default" {
                  value 0;
                  description
                    "Set default internal tcam partitions (L2 1k, V4 24k, V6 1.75k entries): Tomahawk";
                }
                enum "to-profile-se1" {
                  value 1;
                  description
                    "Set internal tcam partitions for service edge (L2 4k, V4 15k, V6 3.25k entries): Tomahawk";
                }
              }
              description
                "Configure internal tcam partition profile";
            }
            container lightspeed {
              presence "Indicates a lightspeed node is configured.";
              description
                "the 4th generation LC type";
              leaf v4-ing {
                type uint32 {
                  range "1..13" {
                    description
                      "Number of TCAM blocks, default 8";
                  }
                }
                mandatory true;
                description
                  "160-ingress region";
              }
              leaf v4-egr {
                type uint32 {
                  range "1..13" {
                    description
                      "Number of TCAM blocks, default 4";
                  }
                }
                mandatory true;
                description
                  "160-egress region";
              }
              leaf v6-ing {
                type uint32 {
                  range "1..13" {
                    description
                      "Number of TCAM blocks, default 3";
                  }
                }
                mandatory true;
                description
                  "640-ingress region";
              }
              leaf v6-egr {
                type uint32 {
                  range "1..13" {
                    description
                      "Number of TCAM blocks, default 1";
                  }
                }
                mandatory true;
                description
                  "640-egress region";
              }
            }
          }
        }
      }
    }
    container flow-qos {
      description
        "Configure flow-qos feature parameters";
      container locations {
        description
          "Configure line card location";
        list location {
          key "location-name";
          description
            "Configure line card location";
          leaf location-name {
            type xr:Node-id;
            description
              "Configure line card location";
          }
          leaf max-flow-count {
            type uint32 {
              range "1..368" {
                description
                  "Number in multiples of 1k (1024) from 1 to 368";
              }
            }
            mandatory true;
            description
              "required number of policers for flow-aware qos feature";
          }
        }
      }
    }
    container buffer-carve-mode {
      description
        "Configure buffer-carve-mode feature parameters";
      container locations {
        description
          "Configure line card location";
        list location {
          must "static";
          key "location-name";
          description
            "Configure line card location";
          leaf location-name {
            type xr:Node-id;
            description
              "Configure line card location";
          }
          container static {
            presence "Indicates a static node is configured.";
            description
              "required to set static buffer carve mode qos feature";
          }
        }
      }
    }
    container processor {
      description
        "Configure PA processor performance";
      container locations {
        description
          "Configure line card location";
        list location {
          key "location-name";
          description
            "Configure line card location";
          leaf location-name {
            type xr:Node-id;
            description
              "Configure line card location";
          }
          leaf mode {
            type enumeration {
              enum "mode-default" {
                value 0;
                description
                  "Configure processor array processor to default settings";
              }
              enum "mode-full" {
                value 1;
                description
                  "Configure processor array processor to full settings";
              }
            }
            mandatory true;
            description
              "processor mode setting";
          }
        }
      }
    }
    container mac-move {
      description
        "Configure mac-move behavior";
      leaf police-mode {
        type enumeration {
          enum "off" {
            value 0;
            description
              "Switch off mac-move policing";
          }
          enum "on" {
            value 1;
            description
              "Switch on mac-move policing";
          }
        }
        description
          "Control the mode for mac-move";
      }
    }
    container all {
      description
        "all line cards";
      container qos-mode {
        description
          "Configure qos mode in HW Module port(s)";
        container pwhe-aggregate-shaper {
          description
            "Configure pseudo wire headend interface qos parameters";
          container sub-interface {
            description
              "Configure pseudo wire headend sub interface qos mode";
            leaf ingress {
              type enumeration {
                enum "non-queuing" {
                  value 1;
                  description
                    "coexistence non-queuing";
                }
                enum "queuing" {
                  value 2;
                  description
                    "coexistence queuing";
                }
              }
              description
                "ingress direction";
            }
            leaf egress {
              type enumeration {
                enum "non-queuing" {
                  value 1;
                  description
                    "coexistence non-queuing";
                }
                enum "queuing" {
                  value 2;
                  description
                    "coexistence queuing";
                }
              }
              description
                "egress direction";
            }
          }
        }
        container wred-buffer-mode {
          presence "Indicates a wred-buffer-mode node is configured.";
          description
            "Configure L4 WRED accounting mode to buffer mode";
        }
        container per-priority-buffer-limit {
          presence "Indicates a per-priority-buffer-limit node is configured.";
          description
            "set different buffer limit for different priority";
        }
        container ingress-queue-enable {
          presence "Indicates a ingress-queue-enable node is configured.";
          description
            "enable ingress queueuing support for MOD-80 4*10G MPA or MOD-400 20*10G MPAMOD-200 8*10G MPA";
        }
        container aggregate-bundle-mode {
          presence "Indicates a aggregate-bundle-mode node is configured.";
          description
            "set aggregate bundle mode ";
        }
        container bundle-agg-policer {
          presence "Indicates a bundle-agg-policer node is configured.";
          description
            "set bundle aggregate policer mode ";
        }
      }
    }
    container reset {
      description
        "Configure reset behavior";
      container threshold {
        description
          "set the NP hard-reset threshold";
        container five {
          description
            "5 resets will take next action";
          container reload {
            presence "Indicates a reload node is configured.";
            description
              "reload linecard after retries";
          }
          container slice-down {
            presence "Indicates a slice-down node is configured.";
            description
              "bring down the slice after retries";
          }
        }
        container ten {
          description
            "10 resets will take next action";
          container reload {
            presence "Indicates a reload node is configured.";
            description
              "reload linecard after retries";
          }
          container slice-down {
            presence "Indicates a slice-down node is configured.";
            description
              "bring down the slice after retries";
          }
        }
        container infinite {
          description
            "10 resets will take next action";
          container logging {
            description
              "set logging enable/disable";
            container enable {
              presence "Indicates a enable node is configured.";
              description
                "continue restarting np on fault, and collect data log";
            }
            container disable {
              presence "Indicates a disable node is configured.";
              description
                "continue resetting np on fault, disable np datalog collection";
            }
          }
        }
      }
    }
  }
  container tcam {
    description
      "Configure tcam";
    container locations {
      description
        "Configure line card location";
      list location {
        key "location-name";
        description
          "Configure line card location";
        leaf location-name {
          type xr:Node-id;
          description
            "Configure line card location";
        }
        leaf partition {
          type enumeration {
            enum "profile0" {
              value 0;
              description
                "config profile 0";
            }
            enum "profile1" {
              value 1;
              description
                "config profile 1";
            }
            enum "profile2" {
              value 2;
              description
                "config profile 2";
            }
          }
          mandatory true;
          description
            "Configure tcam partition";
        }
      }
    }
    container all {
      presence "Indicates a all node is configured.";
      description
        "All locations";
    }
  }
}
