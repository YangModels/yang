module Cisco-IOS-XR-sysadmin-eobc-iosxrwbd {
  namespace "http://www.cisco.com/ns/yang/Cisco-IOS-XR-sysadmin-eobc-iosxrwbd";
  prefix eobc-iosxrwbd;

  import Cisco-IOS-XR-sysadmin-types {
    prefix calvados;
  }
  import tailf-xsd-types {
    prefix xs;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for accessing the EOBC port's info of each rack.
     
     Copyright (c) 2012-2020 by Cisco Systems, Inc.
     All rights reserved.";

  revision 2021-07-07 {
    description
      "This revision restructures the eobc sfp details
       output";
    semver:module-version "1.0.0";
  }
  revision 2021-05-06 {
    description
      "Initial revision";
  }

  grouping onie-port-group {
    description
      "ONIE ports connectivity information group";
    container onie {
      config false;
      description
        "ONIE ports information";
      uses onie-port-status-group;
    }
  }

  grouping onie-port-status-group {
    description
      "Port Status Group";
    list location {
      key "location";
      description
        "Select Location";
      leaf location {
        type string;
        description
          "Location";
      }
      container onie_output {
        description
          "ONIE ports status Output";
        leaf-list onie_show_output {
          type string;
          description
            "ONIE ports status Output Values";
        }
      }
    }
  }

  grouping eobc-port-group {
    description
      "eobc ports connectivity information group";
    container eobc {
      config false;
      description
        "EOBC ports information";
      uses eobc-port-status-group;
      uses eobc-sfp-details-group;
    }
  }

  grouping eobc-port-status-group {
    description
      "Port Status Group";
    list location {
      key "location";
      description
        "Select Location";
      leaf location {
        type string;
        description
          "Location";
      }
      container eobc_output {
        description
          "EOBC ports status Output";
        leaf-list eobc_show_output {
          type string;
          description
            "EOBC ports status Output Values";
        }
      }
    }
  }

  grouping eobc-sfp-details-group {
    description
      "SFP Details Group";
    container sfp {
      config false;
      description
        "EOBC sfp information";
      list location {
        key "location";
        description
          "Select Location";
        leaf location {
          type string;
          description
            "Location";
        }
        list eobc-ports {
          key "eobc-sfp-port-rsip";
          description
            "Select CE Port";
          leaf eobc-sfp-port-rsip {
            type string;
            description
              "CE port num in rsip";
          }
          leaf eobc-show-port {
            type boolean;
            default "false";
            description
              "Display check for eobc sfp information";
          }
          leaf eobc-error-msg {
            type string;
            description
              "Error message";
          }
          leaf eobc-optics-description {
            type string;
            description
              "Optics type";
          }
          leaf eobc-vendor-name {
            type string;
            description
              "Vendor name";
          }
          leaf eobc-vendor-rev-num {
            type string;
            description
              "Vendor id";
          }
          leaf eobc-pid {
            type string;
            description
              "PID";
          }
          leaf eobc-is-cisco-supported {
            type boolean;
            description
              "Supported optics";
          }
          leaf eobc-vendor-pn {
            type string;
            description
              "Vendor part number";
          }
          leaf eobc-vendor-sn {
            type string;
            description
              "Vendor serial number";
          }
          leaf eobc-temp-rd {
            type xs:double;
            description
              "Module temperature";
          }
          leaf eobc-volt-rd {
            type xs:double;
            description
              "Module voltage";
          }
          leaf eobc-wavelength {
            type xs:double;
            description
              "Laser wavelength";
          }
          leaf eobc-temp-hi-alarm-sts {
            type string;
            description
              "Temperature high alarm status";
          }
          leaf eobc-temp-lo-alarm-sts {
            type string;
            description
              "Temperature low alarm status";
          }
          leaf eobc-volt-hi-alarm-sts {
            type string;
            description
              "Voltage high alarm status";
          }
          leaf eobc-volt-lo-alarm-sts {
            type string;
            description
              "Voltage low alarm status";
          }
          leaf eobc-tx-err-count {
            type uint64;
            description
              "Tx Error Count";
          }
          leaf eobc-rx-err-count {
            type uint64;
            description
              "Rx Error Count";
          }
          leaf eobc-rx-crc-err-count {
            type uint64;
            description
              "Rx CRC Error Count";
          }
          leaf eobc-rx-power-dbm-0 {
            type xs:double;
            description
              "Rx power for lane 0";
          }
          leaf eobc-rx-power-dbm-1 {
            type xs:double;
            description
              "Rx power for lane 1";
          }
          leaf eobc-rx-power-dbm-2 {
            type xs:double;
            description
              "Rx power for lane 2";
          }
          leaf eobc-rx-power-dbm-3 {
            type xs:double;
            description
              "Rx power for lane 3";
          }
          leaf eobc-rx-los-0 {
            type string;
            description
              "Rx loss of signal alarm for lane 0";
          }
          leaf eobc-rx-los-1 {
            type string;
            description
              "Rx loss of signal alarm for lane 1";
          }
          leaf eobc-rx-los-2 {
            type string;
            description
              "Rx loss of signal alarm for lane 2";
          }
          leaf eobc-rx-los-3 {
            type string;
            description
              "Rx loss of signal alarm for lane 3";
          }
          leaf eobc-rx-cdr-lol-0 {
            type string;
            description
              "Rx CDR loss of lock alarm for lane 0";
          }
          leaf eobc-rx-cdr-lol-1 {
            type string;
            description
              "Rx CDR loss of lock alarm for lane 1";
          }
          leaf eobc-rx-cdr-lol-2 {
            type string;
            description
              "Rx CDR loss of lock alarm for lane 2";
          }
          leaf eobc-rx-cdr-lol-3 {
            type string;
            description
              "Rx CDR loss of lock alarm for lane 3";
          }
          leaf eobc-rx-hi-alarm-0 {
            type string;
            description
              "Rx high alarm for lane 0";
          }
          leaf eobc-rx-hi-alarm-1 {
            type string;
            description
              "Rx high alarm for lane 1";
          }
          leaf eobc-rx-hi-alarm-2 {
            type string;
            description
              "Rx high alarm for lane 2";
          }
          leaf eobc-rx-hi-alarm-3 {
            type string;
            description
              "Rx high alarm for lane 3";
          }
          leaf eobc-rx-lo-alarm-0 {
            type string;
            description
              "Rx low alarm for lane 0";
          }
          leaf eobc-rx-lo-alarm-1 {
            type string;
            description
              "Rx low alarm for lane 1";
          }
          leaf eobc-rx-lo-alarm-2 {
            type string;
            description
              "Rx low alarm for lane 2";
          }
          leaf eobc-rx-lo-alarm-3 {
            type string;
            description
              "Rx low alarm for lane 3";
          }
          leaf eobc-tx-power-dbm-0 {
            type xs:double;
            description
              "Tx power for lane 0";
          }
          leaf eobc-tx-power-dbm-1 {
            type xs:double;
            description
              "Tx power for lane 1";
          }
          leaf eobc-tx-power-dbm-2 {
            type xs:double;
            description
              "Tx power for lane 2";
          }
          leaf eobc-tx-power-dbm-3 {
            type xs:double;
            description
              "Tx power for lane 3";
          }
          leaf eobc-tx-bias-current-0 {
            type xs:double;
            description
              "Tx Bias Current for lane 0";
          }
          leaf eobc-tx-bias-current-1 {
            type xs:double;
            description
              "Tx Bias Current for lane 1";
          }
          leaf eobc-tx-bias-current-2 {
            type xs:double;
            description
              "Tx Bias Current for lane 2";
          }
          leaf eobc-tx-bias-current-3 {
            type xs:double;
            description
              "Tx Bias Current for lane 3";
          }
          leaf eobc-tx-laser-status-0 {
            type string;
            description
              "Tx laser status for lane 0";
          }
          leaf eobc-tx-laser-status-1 {
            type string;
            description
              "Tx laser status for lane 1";
          }
          leaf eobc-tx-laser-status-2 {
            type string;
            description
              "Tx laser status for lane 2";
          }
          leaf eobc-tx-laser-status-3 {
            type string;
            description
              "Tx laser status for lane 3";
          }
          leaf eobc-tx-los-status-0 {
            type string;
            description
              "Tx LOS status for lane 0";
          }
          leaf eobc-tx-los-status-1 {
            type string;
            description
              "Tx LOS status for lane 1";
          }
          leaf eobc-tx-los-status-2 {
            type string;
            description
              "Tx LOS status for lane 2";
          }
          leaf eobc-tx-los-status-3 {
            type string;
            description
              "Tx LOS status for lane 3";
          }
          leaf eobc-tx-fault-status-0 {
            type string;
            description
              "Tx fault status for lane 0";
          }
          leaf eobc-tx-fault-status-1 {
            type string;
            description
              "Tx fault status for lane 1";
          }
          leaf eobc-tx-fault-status-2 {
            type string;
            description
              "Tx fault status for lane 2";
          }
          leaf eobc-tx-fault-status-3 {
            type string;
            description
              "Tx fault status for lane 3";
          }
          leaf eobc-tx-cdr-lol-status-0 {
            type string;
            description
              "Tx CDR LOL status for lane 0";
          }
          leaf eobc-tx-cdr-lol-status-1 {
            type string;
            description
              "Tx CDR LOL status for lane 1";
          }
          leaf eobc-tx-cdr-lol-status-2 {
            type string;
            description
              "Tx CDR LOL status for lane 2";
          }
          leaf eobc-tx-cdr-lol-status-3 {
            type string;
            description
              "Tx CDR LOL status for lane 3";
          }
          leaf eobc-tx-power-high-alarm-status-0 {
            type string;
            description
              "Tx power high alarm status for lane 0";
          }
          leaf eobc-tx-power-high-alarm-status-1 {
            type string;
            description
              "Tx power high alarm status for lane 1";
          }
          leaf eobc-tx-power-high-alarm-status-2 {
            type string;
            description
              "Tx power high alarm status for lane 2";
          }
          leaf eobc-tx-power-high-alarm-status-3 {
            type string;
            description
              "Tx power high alarm status for lane 3";
          }
          leaf eobc-tx-power-low-alarm-status-0 {
            type string;
            description
              "Tx power low alarm status for lane 0";
          }
          leaf eobc-tx-power-low-alarm-status-1 {
            type string;
            description
              "Tx power low alarm status for lane 1";
          }
          leaf eobc-tx-power-low-alarm-status-2 {
            type string;
            description
              "Tx power low alarm status for lane 2";
          }
          leaf eobc-tx-power-low-alarm-status-3 {
            type string;
            description
              "Tx power low alarm status for lane 3";
          }
          leaf eobc-tx-laser-bias-high-alarm-status-0 {
            type string;
            description
              "Tx laser bias high alarm status for lane 0";
          }
          leaf eobc-tx-laser-bias-high-alarm-status-1 {
            type string;
            description
              "Tx laser bias high alarm status for lane 1";
          }
          leaf eobc-tx-laser-bias-high-alarm-status-2 {
            type string;
            description
              "Tx laser bias high alarm status for lane 2";
          }
          leaf eobc-tx-laser-bias-high-alarm-status-3 {
            type string;
            description
              "Tx laser bias high alarm status for lane 3";
          }
          leaf eobc-tx-laser-bias-low-alarm-status-0 {
            type string;
            description
              "Tx laser bias low alarm status for lane 0";
          }
          leaf eobc-tx-laser-bias-low-alarm-status-1 {
            type string;
            description
              "Tx laser bias low alarm status for lane 1";
          }
          leaf eobc-tx-laser-bias-low-alarm-status-2 {
            type string;
            description
              "Tx laser bias low alarm status for lane 2";
          }
          leaf eobc-tx-laser-bias-low-alarm-status-3 {
            type string;
            description
              "Tx laser bias low alarm status for lane 3";
          }
          leaf eobc-temp-high-alarm {
            type xs:double;
            description
              "Temperature alarm high threshold";
          }
          leaf eobc-temp-high-warn-alarm {
            type xs:double;
            description
              "Temperature alarm high threshold warning";
          }
          leaf eobc-temp-low-warn-alarm {
            type xs:double;
            description
              "Temperature alarm low threshold warning";
          }
          leaf eobc-temp-low-alarm {
            type xs:double;
            description
              "Temperature alarm low threshold";
          }
          leaf eobc-volt-high-alarm {
            type xs:double;
            description
              "Voltage alarm high threshold";
          }
          leaf eobc-volt-high-warn-alarm {
            type xs:double;
            description
              "Voltage alarm high threshold warning";
          }
          leaf eobc-volt-low-warn-alarm {
            type xs:double;
            description
              "Voltage alarm low threshold warning";
          }
          leaf eobc-volt-low-alarm {
            type xs:double;
            description
              "Voltage alarm low threshold";
          }
          leaf eobc-tx-cur-high-alarm {
            type xs:double;
            description
              "Tx current alarm high threshold";
          }
          leaf eobc-tx-cur-high-warn-alarm {
            type xs:double;
            description
              "Tx current warning high threshold";
          }
          leaf eobc-tx-cur-low-warn-alarm {
            type xs:double;
            description
              "Tx current warning low threshold";
          }
          leaf eobc-tx-cur-low-alarm {
            type xs:double;
            description
              "Tx current alarm low threshold";
          }
          leaf eobc-tx-pwr-high-alarm {
            type xs:double;
            description
              "Tx power alarm high threshold";
          }
          leaf eobc-tx-pwr-high-warn-alarm {
            type xs:double;
            description
              "Tx power warning high threshold";
          }
          leaf eobc-tx-pwr-low-warn-alarm {
            type xs:double;
            description
              "Tx power warning low threshold";
          }
          leaf eobc-tx-pwr-low-alarm {
            type xs:double;
            description
              "Tx power alarm low threshold";
          }
          leaf eobc-rx-pwr-high-alarm {
            type xs:double;
            description
              "Rx power alarm high threshold";
          }
          leaf eobc-rx-pwr-high-warn-alarm {
            type xs:double;
            description
              "Rx power warning high threshold";
          }
          leaf eobc-rx-pwr-low-warn-alarm {
            type xs:double;
            description
              "Rx power warning low threshold";
          }
          leaf eobc-rx-pwr-low-alarm {
            type xs:double;
            description
              "Rx power alarm low threshold";
          }
        }
      }
    }
  }
}
