module Cisco-IOS-XR-sysadmin-tacacs-test-tacacs {
  namespace "http://www.cisco.com/ns/yang/Cisco-IOS-XR-sysadmin-tacacs-test-tacacs";
  prefix test_tacacs;

  import Cisco-IOS-XR-sysadmin-tacacs-tacacs-server {
    prefix tacacs-server;
  }
  import cisco-semver {
    prefix semver;
  }

  organization
    "Cisco Systems Inc.";
  contact
    "aaa-ng-tacacs-dev@cisco.com";
  description
    "This clie part is for test commands for tacacs
     
     Copyright (c) 2012-2020 by Cisco Systems, Inc.
     All rights reserved.";

  revision 2021-02-26 {
    description
      "Updated presence string to command containers";
    semver:module-version "1.1.0";
  }
  revision 2019-04-15 {
    description
      "Establish semantic version baseline.";
    semver:module-version "1.0.0";
  }
  revision 2017-05-10 {
    description
      "Namespace changed from test_tacacs to Cisco-IOS-XR-sysadmin-tacacs-test-tacacs";
  }
  revision 2015-07-07 {
    description
      "Initial revision";
  }

  augment "/tacacs-server:tacacs-server" {
    container test-authentication {
      presence "Indicates test-authentication is configured";
      config false;
      leaf authentication {
        type string;
        mandatory false;
        description
          "Authentication";
      }
    }
    container test-authorization {
      presence "Indicates test-authorization is configured";
      config false;
      leaf authorization {
        type string;
        mandatory false;
        description
          "Authorization";
      }
    }
    container test-accounting {
      presence "Indicates test-accounting is configured";
      config false;
      leaf accounting {
        type string;
        mandatory false;
        description
          "Accounting";
      }
    }
  }
}
