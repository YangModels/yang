module Cisco-IOS-XR-uea-optics-driver-cfg {
  namespace "http://cisco.com/ns/yang/Cisco-IOS-XR-uea-optics-driver-cfg";
  prefix uea-optics-driver-cfg;

  import cisco-semver {
    prefix semver;
  }
  import Cisco-IOS-XR-ifmgr-cfg {
    prefix a1;
  }
  import Cisco-IOS-XR-controller-optics-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR uea-optics-driver package configuration.
     
     This YANG module augments the
       Cisco-IOS-XR-ifmgr-cfg,
       Cisco-IOS-XR-controller-optics-cfg
     modules with configuration data.
     
     Copyright (c) 2013-2019 by Cisco Systems, Inc.
     All rights reserved.";

  revision 2019-04-05 {
    description
      "Establish semantic version baseline.";
    semver:module-version "1.0.0";
  }
  revision 2016-03-21 {
    description
      "Schema added.";
  }
  revision 2015-11-09 {
    description
      "IOS XR 6.0 revision.";
  }

  typedef Breakout-type-list {
    type string {
      pattern "(4x10)|(4x25)";
    }
    description
      "4x10:4x10 optics breakout config, 4x25:4x25
       optics breakout config";
  }

  augment "/a1:interface-configurations/a1:interface-configuration/a2:optics" {
    description
      "This augment extends the configuration data of
       'Cisco-IOS-XR-controller-optics-cfg'";
    leaf breakout {
      type Breakout-type-list;
      description
        "breakout mode configuration";
    }
  }
}
