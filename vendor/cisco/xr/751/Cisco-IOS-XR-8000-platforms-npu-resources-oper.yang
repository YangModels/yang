module Cisco-IOS-XR-8000-platforms-npu-resources-oper {
  namespace "http://cisco.com/ns/yang/Cisco-IOS-XR-8000-platforms-npu-resources-oper";
  prefix xr-8000-platforms-npu-resources-oper;

  import cisco-semver {
    prefix semver;
  }
  import Cisco-IOS-XR-platforms-ofa-oper {
    prefix a1;
  }
  include Cisco-IOS-XR-8000-platforms-npu-resources-oper-sub1 {
    revision-date 2020-10-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-platforms-npu-resources package operational data.
     
     This YANG module augments the
       Cisco-IOS-XR-platforms-ofa-oper
     module with state data.
     
     Copyright (c) 2013-2020 by Cisco Systems, Inc.
     All rights reserved.";

  revision 2020-10-07 {
    description
      "Updated leaf fields and container stats";
    semver:module-version "3.0.0";
  }
  revision 2019-04-05 {
    description
      "Establish semantic version baseline.";
    semver:module-version "1.0.0";
  }
  revision 2015-11-09 {
    description
      "IOS XR 6.0 revision.";
  }

  typedef Resource {
    type enumeration {
      enum "counter-bank" {
        value 0;
        description
          "counter bank";
      }
      enum "l3-ac-port" {
        value 1;
        description
          "l3 ac port";
      }
      enum "native-fec-entry" {
        value 2;
        description
          "native fec entry";
      }
      enum "stage1-lb-group" {
        value 3;
        description
          "stage1 lb group";
      }
      enum "stage1-lb-member" {
        value 4;
        description
          "stage1 lb member";
      }
      enum "stage2-lb-group" {
        value 5;
        description
          "stage2 lb group";
      }
      enum "stage2-lb-member" {
        value 6;
        description
          "stage2 lb member";
      }
      enum "stage2-protection-monitor" {
        value 7;
        description
          "stage2 protection monitor";
      }
      enum "v4-lpts" {
        value 8;
        description
          "v4 lpts";
      }
      enum "v6-lpts" {
        value 9;
        description
          "v6 lpts";
      }
      enum "lpts-meters" {
        value 10;
        description
          "lpts meters";
      }
      enum "central-em" {
        value 11;
        description
          "central em";
      }
      enum "egress-acl-tcam" {
        value 12;
        description
          "egress acl tcam";
      }
      enum "ingress-acl-tcam" {
        value 13;
        description
          "ingress acl tcam";
      }
      enum "lpm-tcam" {
        value 14;
        description
          "lpm tcam";
      }
      enum "mc-emdb" {
        value 15;
        description
          "mc emdb";
      }
      enum "ipv6-compressed-sips" {
        value 16;
        description
          "ipv6 compressed sips";
      }
      enum "egress-large-encap" {
        value 17;
        description
          "egress large encap";
      }
      enum "egress-small-encap" {
        value 18;
        description
          "egress small encap";
      }
      enum "tunnel-termination" {
        value 19;
        description
          "tunnel termination";
      }
      enum "sipidxtbl" {
        value 20;
        description
          "sipidxtbl";
      }
      enum "myipv4tbl" {
        value 21;
        description
          "myipv4tbl";
      }
      enum "l2-service-port" {
        value 22;
        description
          "l2 service port";
      }
      enum "egress-l3-dlp" {
        value 23;
        description
          "egress l3 dlp";
      }
      enum "protection-group" {
        value 24;
        description
          "protection group";
      }
    }
    description
      "Resource";
  }

  augment "/a1:ofa/a1:stats/a1:nodes/a1:node" {
    description
      "This augment extends the operational data of
       'Cisco-IOS-XR-platforms-ofa-oper'";
    container hw-resources-datas {
      description
        "OFA HW resources stats ";
      list hw-resources-data {
        key "resource";
        description
          "Hardware resources table";
        leaf resource {
          type Resource;
          description
            "Resource type";
        }
        uses OFA-SYSDB-HW-RESOURCE;
      }
    }
  }
}
