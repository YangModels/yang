module Cisco-IOS-XR-sysadmin-fretta-envmon-ui {
  namespace "http://www.cisco.com/ns/yang/Cisco-IOS-XR-sysadmin-fretta-envmon-ui";
  prefix envmon;

  import Cisco-IOS-XR-sysadmin-show-trace {
    prefix show_trace;
  }
  import tailf-xsd-types {
    prefix xs;
  }
  import Cisco-IOS-XR-sysadmin-types {
    prefix calvados;
  }
  import Cisco-IOS-XR-sysadmin-fretta-envmon-types {
    prefix envmon-types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module holds chassis, cards Enviroment data.
     
     Copyright (c) 2012-2020 by Cisco Systems, Inc.
     All rights reserved.";

  revision 2020-11-05 {
    description
      "added leaf named print_header for all-fan-data";
    semver:module-version "2.1.0";
  }
  revision 2019-04-15 {
    description
      "Establish semantic version baseline.";
    semver:module-version "2.0.0";
  }
  revision 2018-11-14 {
    description
      "Namespace change to keep it with accordance to the RFC";
  }
  revision 2018-04-09 {
    description
      "Required changes for ConfD 6.4.5";
  }
  revision 2018-02-06 {
    description
      "Adding CLI input validation for LC priority shutdown feature";
  }
  revision 2018-01-25 {
    description
      "Initial revision of LC priority shutdown feature";
  }
  revision 2017-11-27 {
    description
      "Add graceful shutdown disable CLI.";
  }
  revision 2017-07-31 {
    description
      "Changing the namespace to follow Cisco guidelines on naming convention";
  }
  revision 2017-04-10 {
    description
      "Adding the source leaf to altitude value,
        this is to distinguish the source of the altitude value ";
  }
  revision 2017-03-31 {
    description
      "Renamed module and namespace";
  }
  revision 2017-03-30 {
    description
      "commenting the sensor_attributes callpoints for the oper sensors,
        using only the location based callpoints for sensor_attributes ";
  }
  revision 2016-10-12 {
    description
      "unhide commands and configs. moved to advanced-grp";
  }
  revision 2011-11-24 {
    description
      "Initial revision of show environment commands";
  }

  grouping temp-data {
    container temperatures {
      config false;
      list location {
        key "location";
        leaf location {
          type string;
        }
        list sensor_attributes {
          key "sensor";
          leaf loc_header {
            type boolean;
            default "false";
          }
          leaf print_header {
            type boolean;
            default "false";
          }
          leaf location {
            type string;
          }
          leaf sensor {
            type string;
          }
          leaf sensor_id {
            type string;
          }
          leaf alarm {
            type string;
          }
          leaf temperature_value {
            type string;
          }
          leaf value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping all-temp-data {
    list temperatures {
      key "loc_iden";
      config false;
      leaf loc_iden {
        type string;
      }
      leaf print_header {
        type boolean;
        default "false";
      }
      list sensor_attributes {
        key "sensor";
        leaf sensor {
          type string;
        }
        leaf sensor_id {
          type string;
        }
        leaf alarm {
          type string;
        }
        leaf temperature_value {
          type string;
        }
        leaf value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping volt-data {
    container voltages {
      config false;
      list location {
        key "location";
        leaf location {
          type string;
        }
        list sensor_attributes {
          key "sensor";
          leaf loc_header {
            type boolean;
            default "false";
          }
          leaf print_header {
            type boolean;
            default "false";
          }
          leaf location {
            type string;
          }
          leaf sensor {
            type string;
          }
          leaf sensor_id {
            type string;
          }
          leaf alarm {
            type string;
          }
          leaf value {
            type string;
          }
          leaf temperature_value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping all-volt-data {
    list voltages {
      key "loc_iden";
      config false;
      leaf loc_iden {
        type string;
      }
      leaf print_header {
        type boolean;
        default "false";
      }
      list sensor_attributes {
        key "sensor";
        leaf sensor {
          type string;
        }
        leaf sensor_id {
          type string;
        }
        leaf alarm {
          type string;
        }
        leaf value {
          type string;
        }
        leaf temperature_value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping current-data {
    container current {
      config false;
      list location {
        key "location";
        leaf location {
          type string;
        }
        list sensor_attributes {
          key "sensor";
          leaf loc_header {
            type boolean;
            default "false";
          }
          leaf print_header {
            type boolean;
            default "false";
          }
          leaf location {
            type string;
          }
          leaf sensor {
            type string;
          }
          leaf sensor_id {
            type string;
          }
          leaf alarm {
            type string;
          }
          leaf value {
            type string;
          }
          leaf temperature_value {
            type int32;
          }
        }
      }
    }
  }

  grouping all-current-data {
    list current {
      key "loc_iden";
      config false;
      leaf loc_iden {
        type string;
      }
      leaf print_header {
        type boolean;
        default "false";
      }
      list sensor_attributes {
        key "sensor";
        leaf sensor {
          type string;
        }
        leaf sensor_id {
          type string;
        }
        leaf value {
          type string;
        }
      }
    }
  }

  grouping fan-data {
    container fan {
      config false;
      list location {
        key "location";
        leaf location {
          type string;
        }
        list fan_attributes {
          key "logical_slot";
          leaf print_fan_header {
            type string;
          }
          leaf location {
            type string;
          }
          leaf logical_slot {
            type string;
          }
          leaf fru_PID {
            type string;
          }
          leaf fans_speed {
            type string;
          }
          leaf fan_header {
            type uint32;
          }
          leaf speed_space {
            type uint32;
          }
          leaf loc_header {
            type boolean;
            default "false";
          }
        }
      }
    }
  }

  grouping all-fan-data {
    list fan {
      key "loc_iden";
      config false;
      leaf fan_header {
        type uint32;
      }
      leaf print_header {
        type boolean;
        default "false";
      }
      leaf loc_iden {
        type string;
      }
      list fan_attributes {
        key "logical_slot";
        leaf logical_slot {
          type string;
        }
        leaf fru_PID {
          type string;
        }
        leaf fans_speed {
          type string;
        }
      }
    }
  }

  grouping power-data {
    container power {
      config false;
      list location {
        key "location";
        leaf location {
          type string;
        }
        list pem_attributes {
          key "pem";
          leaf pem {
            type string;
          }
          leaf pem_id {
            type string;
          }
          leaf card_type {
            type string;
          }
          leaf ps_type {
            type string;
          }
          leaf shelf_num {
            type uint16;
          }
          leaf supply_type {
            type string;
          }
          leaf input_voltage {
            type string;
          }
          leaf input_current {
            type string;
          }
          leaf output_voltage {
            type xs:double;
          }
          leaf output_current {
            type xs:double;
          }
          leaf status {
            type string;
          }
          leaf input_power_to_ps {
            type uint32;
          }
          leaf input_current_to_ps {
            type string;
          }
          leaf output_power_from_ps {
            type uint32;
          }
          leaf output_current_from_ps {
            type xs:double;
          }
          leaf power_allocated {
            type uint32;
          }
          leaf power_consumed {
            type string;
          }
          leaf power_status {
            type string;
          }
          leaf confgd_power_redundancy_mode {
            type string;
          }
          leaf usable_power_capacity {
            type uint32;
          }
          leaf protection_power_capacity {
            type uint32;
          }
          leaf power_resrv_and_alloc {
            type uint32;
          }
          leaf system_power_used {
            type uint32;
          }
          leaf system_power_input {
            type uint32;
          }
          leaf power_level {
            type uint16;
          }
          leaf output_header {
            type uint16;
          }
          leaf output_footer {
            type uint16;
          }
          leaf ps_sum_footer {
            type uint16;
          }
        }
      }
    }
  }

  grouping all-power-data {
    list power {
      key "loc_iden";
      config false;
      leaf loc_iden {
        type string;
      }
      list pem_attributes {
        key "pem";
        leaf pem {
          type string;
        }
        leaf pem_id {
          type string;
        }
        leaf card_type {
          type string;
        }
        leaf ps_type {
          type string;
        }
        leaf shelf_num {
          type uint16;
        }
        leaf supply_type {
          type string;
        }
        leaf input_voltage {
          type string;
        }
        leaf input_current {
          type string;
        }
        leaf output_voltage {
          type xs:double;
        }
        leaf output_current {
          type xs:double;
        }
        leaf status {
          type string;
        }
        leaf input_power_to_ps {
          type uint32;
        }
        leaf input_current_to_ps {
          type string;
        }
        leaf output_power_from_ps {
          type uint32;
        }
        leaf output_current_from_ps {
          type xs:double;
        }
        leaf power_allocated {
          type uint32;
        }
        leaf power_consumed {
          type string;
        }
        leaf power_status {
          type string;
        }
        leaf confgd_power_redundancy_mode {
          type string;
        }
        leaf usable_power_capacity {
          type uint32;
        }
        leaf protection_power_capacity {
          type uint32;
        }
        leaf power_resrv_and_alloc {
          type uint32;
        }
        leaf system_power_used {
          type uint32;
        }
        leaf system_power_input {
          type uint32;
        }
        leaf power_level {
          type uint16;
        }
        leaf output_header {
          type uint16;
        }
        leaf output_footer {
          type uint16;
        }
        leaf ps_sum_footer {
          type uint16;
        }
      }
    }
  }

  grouping altitude-data {
    container altitude {
      config false;
      list location {
        key "location";
        leaf location {
          type string;
        }
        list alt_attributes {
          key "sensor";
          leaf sensor {
            type string;
          }
          leaf rack {
            type uint32;
          }
          leaf sensor_value {
            type string;
          }
          leaf source {
            type string;
          }
          leaf print_header {
            type boolean;
            default "false";
          }
        }
      }
    }
  }

  grouping all-altitude-data {
    list altitude {
      key "loc_iden";
      config false;
      leaf loc_iden {
        type string;
      }
      list alt_attributes {
        key "sensor";
        leaf print_header {
          type boolean;
          default "false";
        }
        leaf sensor {
          type string;
        }
        leaf rack {
          type uint32;
        }
        leaf sensor_value {
          type string;
        }
        leaf source {
          type string;
        }
      }
    }
  }

  grouping rack-location {
    leaf all {
      type empty;
    }
    list location {
      key "rackId";
      leaf rackId {
        type calvados:rack-id;
      }
    }
  }

  grouping router-group {
    container router {
      container altitude {
        container all {
          leaf num_meters {
            type uint32 {
              range "1..4000";
            }
          }
        }
        container rack_loc {
          list location {
            key "rackId";
            leaf rackId {
              type calvados:rack-id;
            }
            leaf num_meters {
              type uint32 {
                range "1..4000";
              }
            }
          }
        }
      }
    }
  }

  grouping air-filter-group {
    container air-filter {
      container replaced {
        container all {
          leaf date {
            type xs:date;
          }
        }
        container rack_loc {
          list location {
            key "rackId";
            leaf rackId {
              type calvados:rack-id;
            }
            leaf date {
              type xs:date;
            }
          }
        }
      }
    }
  }

  grouping fan-ctrl-group {
    container fan-ctrl {
      container disable {
        container rack_loc {
          uses rack-location;
        }
      }
    }
  }

  grouping temp-monitor-group {
    container temperature {
      container disable {
        container rack_loc {
          uses rack-location;
        }
      }
    }
  }

  grouping env-monitor-group {
    container monitoring {
      container disable {
        container rack_loc {
          uses rack-location;
        }
      }
    }
  }

  grouping power-mgmt-group {
    container action {
      container disable {
        container rack_loc {
          uses rack-location;
        }
      }
    }
    container single-feed-mode {
      container enable {
        container rack_loc {
          uses rack-location;
        }
      }
    }
    container extended-temp {
      container enable {
        container rack_loc {
          uses rack-location;
        }
      }
    }
    container redundancy-num-pms {
      container all {
        leaf num_pm {
          type envmon-types:num_pm;
        }
      }
      container rack_loc {
        list location {
          key "rackId";
          leaf rackId {
            type calvados:rack-id;
          }
          leaf num_pm {
            type envmon-types:num_pm;
          }
        }
      }
    }
  }

  grouping cmd_types {
    container oper {
      config false;
      description
        "environment operational (show) data";
      uses temp-data;
      uses volt-data;
      uses current-data;
      uses fan-data;
      uses power-data;
      uses altitude-data;
    }
    container all {
      config false;
      list location {
        key "location";
        leaf location {
          type string;
        }
        uses all-temp-data;
        uses all-volt-data;
        uses all-current-data;
        uses all-fan-data;
        uses all-power-data;
        uses all-altitude-data;
      }
    }
    container config {
      description
        "environment configurational data";
      uses router-group;
      uses air-filter-group;
      uses fan-ctrl-group;
      uses temp-monitor-group;
      uses env-monitor-group;
      uses envmon-types:fan-speed-group;
      uses envmon-types:fan-ctrl-optics-group;
      uses envmon-types:vin-uv-shut-group;
    }
  }

  container environment {
    uses cmd_types;
    uses show_trace:traceable;
  }
  container power-mgmt {
    container config {
      description
        "Power Trays and PEMs configurational data";
      uses power-mgmt-group;
    }
  }
}
