module Cisco-IOS-XR-switch-act {
  namespace "http://cisco.com/ns/yang/Cisco-IOS-XR-switch-act";
  prefix switch-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller ethernet switch.
     
     Copyright (c) 2019-2020 by Cisco Systems, Inc.
     All rights reserved.";

  revision 2020-03-26 {
    description
      "Added an entry for clear controller switch txq.";
    semver:module-version "1.0.0";
  }
  revision 2019-04-05 {
    description
      "Establish semantic version baseline.";
  }
  revision 2019-02-14 {
    description
      "Initial revision.";
  }

  rpc clear-switch-bridge-statistics {
    description
      "Clear switch bridge statistics";
    input {
      leaf instance {
        type string;
        mandatory true;
        description
          "Location information for switch, XR node identifier e.g. 0/RP0/CPU0, 0/0/CPU0";
      }
    }
  }
  rpc clear-switch-fdb {
    description
      "Clear switch forwarding database";
    input {
      leaf instance {
        type string;
        mandatory true;
        description
          "Location information for switch, XR node identifier e.g. 0/RP0/CPU0, 0/0/CPU0";
      }
    }
  }
  rpc clear-switch-policing-statistics {
    description
      "Clear switch policing statistics";
    input {
      leaf instance {
        type string;
        mandatory true;
        description
          "Location information for switch, XR node identifier e.g. 0/RP0/CPU0, 0/0/CPU0";
      }
      leaf port {
        type uint16 {
          range "0..65534";
        }
        description
          "Port number";
      }
    }
  }
  rpc clear-switch-statistics {
    description
      "Clear switch statistics";
    input {
      leaf instance {
        type string;
        mandatory true;
        description
          "Location information for switch, XR node identifier e.g. 0/RP0/CPU0, 0/0/CPU0";
      }
    }
  }
  rpc set-switch-port-reset {
    description
      "Set port reset";
    input {
      leaf instance {
        type string;
        mandatory true;
        description
          "Location information for switch, XR node identifier e.g. 0/RP0/CPU0, 0/0/CPU0";
      }
      leaf port {
        type uint16 {
          range "0..65534";
        }
        mandatory true;
        description
          "Port number";
      }
    }
  }
  rpc clear-switch-txq-statistics {
    description
      "Clear switch txq statistics";
    input {
      leaf instance {
        type string;
        mandatory true;
        description
          "Location information for switch, XR node identifier e.g. 0/RP0/CPU0, 0/0/CPU0";
      }
      leaf port {
        type uint16 {
          range "0..65534";
        }
        description
          "Port number";
      }
    }
  }
}
