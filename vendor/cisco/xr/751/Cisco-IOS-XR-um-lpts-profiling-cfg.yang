module Cisco-IOS-XR-um-lpts-profiling-cfg {
  namespace "http://cisco.com/ns/yang/Cisco-IOS-XR-um-lpts-profiling-cfg";
  prefix um-lpts-profiling-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lpts-profiling package configuration.
     
     This YANG module augments the
     modules with configuration data.
     
     Copyright (c) 2021 by Cisco Systems, Inc.
     All rights reserved.";

  revision 2021-05-10 {
    description
      "Initial release";
    semver:module-version "1.0.0";
  }

  container lpts {
    description
      "lpts configuration commands";
    container profiling {
      description
        "profiling configuration commands";
      container disable {
        presence "Indicates a disable node is configured.";
        description
          "disable lpts profiling";
      }
    }
  }
}
