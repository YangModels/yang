module Cisco-IOS-XR-ipv4-acl-oper {
  namespace "http://cisco.com/ns/yang/Cisco-IOS-XR-ipv4-acl-oper";
  prefix ipv4-acl-oper;

  import Cisco-IOS-XR-types {
    prefix xr;
  }
  import cisco-semver {
    prefix semver;
  }
  import Cisco-IOS-XR-common-acl-datatypes {
    prefix dt1;
  }
  include Cisco-IOS-XR-ipv4-acl-oper-sub1 {
    revision-date 2021-03-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-acl package operational data.
     
     This module contains definitions
     for the following management objects:
       ipv4-acl-and-prefix-list: Root class of IPv4 Oper schema tree
     
     Copyright (c) 2013-2021 by Cisco Systems, Inc.
     All rights reserved.";

  revision 2021-03-05 {
    description
      "Adding a new policer stats field.CSCvx54997";
    semver:module-version "1.2.0";
  }
  revision 2020-11-13 {
    description
      "Adding policer and priority.";
    semver:module-version "1.1.0";
  }
  revision 2019-04-05 {
    description
      "Establish semantic version baseline.";
    semver:module-version "1.0.1";
  }
  revision 2019-02-12 {
    description
      "Fixing CSCvn61905.";
  }
  revision 2017-05-01 {
    description
      "Fixing backward compatibility error in module.";
  }
  revision 2015-11-09 {
    description
      "IOS XR 6.0 revision.";
  }

  container ipv4-acl-and-prefix-list {
    config false;
    description
      "Root class of IPv4 Oper schema tree";
    container access-list-manager {
      description
        "Access list manager containing access lists and
         prefix lists";
      container prefixes {
        description
          "Table of prefix lists";
        list prefix {
          key "prefix-list-name";
          description
            "Name of the prefix list";
          container prefix-list-sequences {
            description
              "Table of all the SequenceNumbers per prefix
               list";
            list prefix-list-sequence {
              key "sequence-number";
              description
                "Sequence Number of a prefix list entry";
              leaf sequence-number {
                type dt1:Acl-sequence-number-range;
                description
                  "Sequence Number of the prefix list entry";
              }
              uses IPV4-PFX-EDM-ACE;
            }
          }
          leaf prefix-list-name {
            type xr:Cisco-ios-xr-string {
              length "1..32";
            }
            description
              "Name of the prefix list";
          }
        }
      }
      container accesses {
        description
          "Access listL class displaying Usage and Entries";
        list access {
          key "access-list-name";
          description
            "Name of the Access List";
          container access-list-sequences {
            description
              "Table of all the SequenceNumbers per access
               list";
            list access-list-sequence {
              key "sequence-number";
              description
                "Sequence Number of an access list entry";
              leaf sequence-number {
                type dt1:Acl-sequence-number-range;
                description
                  "ACLEntry Sequence Number";
              }
              uses IPV4-ACL-EDM-ACE;
            }
          }
          container object-group {
            description
              "Object Group in an Access list";
            uses IPV4-ACL-EDM-OBJGRP;
          }
          leaf access-list-name {
            type xr:Cisco-ios-xr-string {
              length "1..64";
            }
            description
              "Name of the Access List";
          }
        }
      }
      container usages {
        description
          "Table of Usage statistics of access lists at
           different nodes";
        list usage {
          description
            "Usage statistics of an access list at a node";
          leaf node-name {
            type xr:Node-id;
            description
              "Node where access list is applied";
          }
          leaf application-id {
            type dt1:Acl-usage-app-id-enum;
            description
              "Application ID";
          }
          leaf access-list-name {
            type xr:Cisco-ios-xr-string {
              length "1..64";
            }
            description
              "Name of the access list";
          }
          leaf usage-details {
            type string;
            mandatory true;
            description
              "Usage Statistics Details";
          }
        }
      }
    }
    container oor {
      description
        "Out Of Resources, Limits to the resources
         allocatable";
      container details {
        description
          "Details of the Overall Out Of Resources Limits";
        uses IPV4-ACL-EDM-OOR-DETAIL;
      }
      container oor-prefixes {
        description
          "Resource occupation details for prefix lists";
        list oor-prefix {
          key "prefix-list-name";
          description
            "Resource occupation details for a particular
             prefix list";
          leaf prefix-list-name {
            type xr:Cisco-ios-xr-string {
              length "1..32";
            }
            description
              "Name of a prefix list";
          }
          uses IPV4-ACL-EDM-OOR-DETAIL;
        }
      }
      container oor-accesses {
        description
          "Resource occupation details for access lists";
        list oor-access {
          key "access-list-name";
          description
            "Resource occupation details for a particular
             access list";
          leaf access-list-name {
            type xr:Cisco-ios-xr-string {
              length "1..64";
            }
            description
              "Name of the Access List";
          }
          uses IPV4-ACL-EDM-OOR-DETAIL;
        }
      }
      container access-list-summary {
        description
          "Resource limits pertaining to access lists only";
        container details {
          description
            "Details containing the resource limits of the
             access lists";
          uses IPV4-ACL-EDM-OOR-DETAIL;
        }
      }
      container prefix-list-summary {
        description
          "Summary of the prefix Lists resource
           utilization";
        container details {
          description
            "Summary Detail of the prefix list Resource
             Utilisation";
          uses IPV4-ACL-EDM-OOR-DETAIL;
        }
      }
    }
  }
}
