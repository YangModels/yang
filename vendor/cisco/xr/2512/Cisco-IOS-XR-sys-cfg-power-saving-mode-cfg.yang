module Cisco-IOS-XR-sys-cfg-power-saving-mode-cfg {
  namespace "http://cisco.com/ns/yang/Cisco-IOS-XR-sys-cfg-power-saving-mode-cfg";
  prefix sys-cfg-power-saving-mode-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sys-cfg-power-saving-mode package configuration.
     
     This module contains definitions
     for the following management objects:
       root: none
     
     Copyright (c) 2013-2024 by Cisco Systems, Inc.
     All rights reserved.";

  revision 2024-02-05 {
    description
      "Yang Schema Initial Draft";
    semver:module-version "1.0.0";
  }
  revision 2019-04-05 {
    description
      "Establish semantic version baseline.";
  }
  revision 2015-11-09 {
    description
      "IOS XR 6.0 revision.";
  }

  typedef En-dis-enum {
    type enumeration {
      enum "disable" {
        value 0;
        description
          "Disable";
      }
      enum "enable" {
        value 1;
        description
          "Enable";
      }
    }
    description
      "En dis enum";
  }

  typedef Sub-cat-enum {
    type enumeration {
      enum "optics" {
        value 1;
        description
          "optics";
      }
      enum "phy" {
        value 2;
        description
          "phy";
      }
      enum "npu" {
        value 3;
        description
          "npu";
      }
      enum "fabric" {
        value 4;
        description
          "fabric";
      }
      enum "psu" {
        value 5;
        description
          "psu";
      }
      enum "fan" {
        value 6;
        description
          "fan";
      }
    }
    description
      "Sub cat enum";
  }

  container root {
    description
      "none";
    container psm {
      description
        "System power saving mode";
      container sub-cat-types {
        description
          "Sub-category List";
        list sub-cat-type {
          key "category";
          description
            "Sub Category";
          container features {
            description
              "Feature List";
            leaf features-all {
              type En-dis-enum;
              description
                "Enable or Disable";
            }
          }
          container features-npu-fabric {
            description
              "Feature List";
            leaf features-power-profile {
              type En-dis-enum;
              description
                "Power-Profile Features";
            }
          }
          leaf category {
            type Sub-cat-enum;
            description
              "Sub Category";
          }
        }
      }
      leaf eco {
        type En-dis-enum;
        description
          "Power optimized mode";
      }
    }
  }
}
