submodule Cisco-IOS-XR-pbr-fwd-stats-oper-sub2 {
  belongs-to Cisco-IOS-XR-pbr-fwd-stats-oper {
    prefix Cisco-IOS-XR-pbr-fwd-stats-oper;
  }

  import cisco-semver {
    prefix semver;
  }
  include Cisco-IOS-XR-pbr-fwd-stats-oper-sub1 {
    revision-date 2024-09-11;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pbr-fwd-stats package operational data.
     
     Copyright (c) 2013-2024 by Cisco Systems, Inc.
     All rights reserved.";

  revision 2024-09-11 {
    description
      "Stats feature update";
    semver:module-version "1.0.0";
  }
  revision 2024-05-08 {
    description
      "CSCwj03306 : Meta EBB - PBR Stats feature";
  }
  revision 2019-04-05 {
    description
      "Establish semantic version baseline.";
  }
  revision 2015-11-09 {
    description
      "IOS XR 6.0 revision.";
  }

  typedef Path-group-name {
    type string {
      length "0..128";
    }
    description
      "Path group name";
  }

  typedef Policy-sl-action {
    type enumeration {
      enum "path-grp" {
        value 1;
        description
          "path grp";
      }
      enum "stats" {
        value 2;
        description
          "stats";
      }
    }
    description
      "PBR sl policy actions";
  }

  grouping POLICY-ACTION-UN {
    description
      "Union of actions";
    leaf type {
      type Policy-sl-action;
      description
        "type";
    }
    leaf stats-enabled {
      when "../type = 'stats'" {
        description
          "../type = 'Stats'";
      }
      type uint32;
      description
        "Stats Enabled";
    }
    leaf path-grp-name {
      when "../type = 'path-grp'" {
        description
          "../type = 'PATH_GRP'";
      }
      type Path-group-name;
      description
        "PathGrpName";
    }
  }

  grouping POLICY-RULE-ACTION {
    description
      "Per class action structure";
    list policy-rule-action {
      description
        "policy rule action";
      container act-un {
        description
          "act un";
        uses POLICY-ACTION-UN;
      }
    }
  }

  grouping PBR-POLICY-RULE-STATS {
    description
      "policy map rule stats info";
    container paction {
      description
        "paction";
      uses POLICY-RULE-ACTION;
    }
    container fib-stats {
      description
        "fib stats";
      uses FIB-INSIGHT-FWD-STATS;
    }
  }
}
