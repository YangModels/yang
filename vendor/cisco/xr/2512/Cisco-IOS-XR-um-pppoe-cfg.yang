module Cisco-IOS-XR-um-pppoe-cfg {
  namespace "http://cisco.com/ns/yang/Cisco-IOS-XR-um-pppoe-cfg";
  prefix um-pppoe-cfg;

  import Cisco-IOS-XR-types {
    prefix xr;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pppoe package configuration.
     
     This YANG module augments the
     modules with configuration data.
     
     Copyright (c) 2020-2022 by Cisco Systems, Inc.
     All rights reserved.";

  revision 2022-07-11 {
    description
      "Added missing description statement to nodes";
    semver:module-version "1.1.0";
  }
  revision 2020-12-14 {
    description
      "Initial release";
    semver:module-version "1.0.0";
  }

  grouping IF-BODY {
    description
      "Grouping for interface";
    container pppoe {
      description
        "PPP over Ethernet";
      container enable {
        presence "Indicates a enable node is configured.";
        description
          "Enable PPPoE on the interface";
        leaf bba-group {
          type xr:Cisco-ios-xr-string {
            length "1..800" {
              description
                "The bba-group to use";
            }
          }
          description
            "Specify the bba-group to use with the interface";
        }
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  container pppoe {
    description
      "PPPoE";
    list bba-group {
      key "bba-group-name";
      description
        "BBA-Group";
      leaf bba-group-name {
        type union {
          type string {
            pattern "global" {
              description
                "Configures global bba-group for the device.";
            }
          }
          type xr:Cisco-ios-xr-string {
            length "1..32" {
              description
                "Enter group name";
            }
          }
        }
        description
          "BBA-Group name";
      }
      container control-packets {
        description
          "Change control-packets configuration";
        leaf priority {
          type uint32 {
            range "0..7" {
              description
                "Priority bits for outgoing PPPoE and PPP control packets";
            }
          }
          description
            "Set the CoS Priority to use in PPPoE and PPP control packets.";
        }
      }
      container pado {
        description
          "Configure the PADO response to PADIs";
        container delay {
          description
            "Configure the PADO response to PADIs";
          leaf default {
            type uint32 {
              range "0..10000" {
                description
                  "PADO delay (in milliseconds)";
              }
            }
            description
              "Delay the PADO response";
          }
          leaf circuit-id {
            type uint32 {
              range "0..10000" {
                description
                  "PADO delay (in milliseconds)";
              }
            }
            description
              "Configure PADO delay dependent on the received Circuit ID";
          }
          container circuit-id-strings {
            description
              "Delay the PADO response when there is an exact match on the received Circuit ID";
            list circuit-id-string {
              key "string";
              description
                "Delay the PADO response when there is an exact match on the received Circuit ID";
              leaf string {
                type xr:Cisco-ios-xr-string {
                  length "1..1024" {
                    description
                      "The string to exactly match the received Circuit ID";
                  }
                }
                description
                  "The string to exactly match the received Circuit ID";
              }
              leaf delay {
                type uint32 {
                  range "0..10000" {
                    description
                      "PADO delay (in milliseconds)";
                  }
                }
                mandatory true;
                description
                  "Delay the PADO response when there is an exact match on the received Circuit ID";
              }
            }
          }
          container circuit-id-substrings {
            description
              "Delay the PADO response when the received Circuit ID contains the given string";
            list circuit-id-substring {
              key "substring";
              description
                "Delay the PADO response when the received Circuit ID contains the given string";
              leaf substring {
                type xr:Cisco-ios-xr-string {
                  length "1..1024" {
                    description
                      "The string to be contained within the received Circuit ID";
                  }
                }
                description
                  "The string to be contained within the received Circuit ID";
              }
              leaf delay {
                type uint32 {
                  range "0..10000" {
                    description
                      "PADO delay (in milliseconds)";
                  }
                }
                description
                  "Delay the PADO response when the received Circuit ID contains the given string";
              }
            }
          }
          leaf remote-id {
            type uint32 {
              range "0..10000" {
                description
                  "PADO delay (in milliseconds)";
              }
            }
            description
              "Configure PADO delay dependent on the received Remote ID";
          }
          container remote-id-strings {
            description
              "Delay the PADO response when there is an exact match on the received Remote ID";
            list remote-id-string {
              key "string";
              description
                "Delay the PADO response when there is an exact match on the received Remote ID";
              leaf string {
                type xr:Cisco-ios-xr-string {
                  length "1..1024" {
                    description
                      "The string to exactly match the received Remote ID";
                  }
                }
                description
                  "The string to exactly match the received Remote ID";
              }
              leaf delay {
                type uint32 {
                  range "0..10000" {
                    description
                      "PADO delay (in milliseconds)";
                  }
                }
                description
                  "Delay the PADO response when there is an exact match on the received Remote ID";
              }
            }
          }
          container remote-id-substrings {
            description
              "Delay the PADO response when the received Remote ID contains the given string";
            list remote-id-substring {
              key "substring";
              description
                "Delay the PADO response when the received Remote ID contains the given string";
              leaf substring {
                type xr:Cisco-ios-xr-string {
                  length "1..1024" {
                    description
                      "The string to be contained within the received Remote ID";
                  }
                }
                description
                  "The string to be contained within the received Remote ID";
              }
              leaf delay {
                type uint32 {
                  range "0..10000" {
                    description
                      "PADO delay (in milliseconds)";
                  }
                }
                description
                  "Delay the PADO response when the received Remote ID contains the given string";
              }
            }
          }
          container service-name-strings {
            description
              "Configure PADO delay dependent on the received Service Name";
            list service-name-string {
              key "string";
              description
                "Delay the PADO response when there is an exact match on the received Service Name";
              leaf string {
                type xr:Cisco-ios-xr-string {
                  length "1..1024" {
                    description
                      "The string to exactly match the received Service Name";
                  }
                }
                description
                  "The string to exactly match the received Service Name";
              }
              leaf delay {
                type uint32 {
                  range "0..10000" {
                    description
                      "PADO delay (in milliseconds)";
                  }
                }
                description
                  "Delay the PADO response when there is an exact match on the received Service Name";
              }
            }
          }
          container service-name-substrings {
            description
              "Delay the PADO response when the received Service Name contains the given string";
            list service-name-substring {
              key "substring";
              description
                "Delay the PADO response when the received Service Name contains the given string";
              leaf substring {
                type xr:Cisco-ios-xr-string {
                  length "1..1024" {
                    description
                      "The string to be contained within the received Service Name";
                  }
                }
                description
                  "The string to be contained within the received Service Name";
              }
              leaf delay {
                type uint32 {
                  range "0..10000" {
                    description
                      "PADO delay (in milliseconds)";
                  }
                }
                description
                  "Delay the PADO response when the received Service Name contains the given string";
              }
            }
          }
        }
      }
      container sessions {
        description
          "Change sessions configuration";
        container max {
          description
            "Set a per-card session limit";
          container limit {
            description
              "Set a per-card session limit";
            leaf session-limit {
              type union {
                type uint32 {
                  range "1..128000" {
                    description
                      "Max session limit";
                  }
                }
                type uint32 {
                  range "1..65535" {
                    description
                      "Max session limit";
                  }
                }
              }
              description
                "Max session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
        }
        container access-interface {
          description
            "Limit PPPoE sessions on any one access interface";
          container limit {
            description
              "Limit PPPoE sessions on any one access interface";
            leaf session-limit {
              type union {
                type uint32 {
                  range "1..128000" {
                    description
                      "Access-interface session limit";
                  }
                }
                type uint32 {
                  range "1..65535" {
                    description
                      "Access-interface session limit";
                  }
                }
              }
              description
                "Access-interface session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
        }
        container mac {
          description
            "Limit or throttle PPPoE sessions from any one MAC address";
          container limit {
            description
              "Limit PPPoE sessions from any one MAC address";
            leaf session-limit {
              type union {
                type uint32 {
                  range "1..128000" {
                    description
                      "MAC session limit";
                  }
                }
                type uint32 {
                  range "1..65535" {
                    description
                      "MAC session limit";
                  }
                }
              }
              description
                "MAC session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          container access-interface {
            description
              "Limit or throttle PPPoE sessions from any one MAC/Access-interface pair";
            container limit {
              description
                "Limit PPPoE sessions from any one MAC/Access-interface pair";
              leaf session-limit {
                type union {
                  type uint32 {
                    range "1..128000" {
                      description
                        "MAC session limit";
                    }
                  }
                  type uint32 {
                    range "1..65535" {
                      description
                        "MAC session limit";
                    }
                  }
                }
                description
                  "MAC session limit";
              }
              leaf threshold {
                type union {
                  type uint32 {
                    range "1..128000" {
                      description
                        "Warning message threshold";
                    }
                  }
                  type uint32 {
                    range "1..65535" {
                      description
                        "Warning message threshold";
                    }
                  }
                }
                must "../session-limit";
                description
                  "Specify the threshold after which a warning will be displayed";
              }
            }
            leaf throttle {
              type uint32 {
                range "1..65535" {
                  description
                    "Number of requests at which to throttle";
                }
              }
              must "../throttle-blocking-period and ../throttle-request-period";
              description
                "Throttle PPPoE sessions from any one MAC/Access-interface pair";
            }
            leaf throttle-request-period {
              type uint32 {
                range "1..100" {
                  description
                    "Throttle request period";
                }
              }
              must "../throttle and ../throttle-blocking-period";
              description
                "Throttle request period";
            }
            leaf throttle-blocking-period {
              type uint32 {
                range "1..100" {
                  description
                    "Throttle blocking period";
                }
              }
              must "../throttle and ../throttle-request-period";
              description
                "Throttle blocking period";
            }
          }
          leaf throttle {
            type uint32 {
              range "1..65535" {
                description
                  "Number of requests at which to throttle";
              }
            }
            must "../throttle-blocking-period and ../throttle-request-period";
            description
              "Throttle PPPoE sessions from any one MAC address";
          }
          leaf throttle-request-period {
            type uint32 {
              range "1..100" {
                description
                  "Throttle request period";
              }
            }
            must "../throttle and ../throttle-blocking-period";
            description
              "Throttle request period";
          }
          leaf throttle-blocking-period {
            type uint32 {
              range "1..100" {
                description
                  "Throttle blocking period";
              }
            }
            must "../throttle and ../throttle-request-period";
            description
              "Throttle blocking period";
          }
        }
        container mac-iwf {
          description
            "Limit or throttle IWF PPPoE sessions from any one MAC address";
          container limit {
            description
              "Limit IWF PPPoE sessions from any one MAC address";
            leaf session-limit {
              type union {
                type uint32 {
                  range "1..128000" {
                    description
                      "MAC IWF session limit";
                  }
                }
                type uint32 {
                  range "1..65535" {
                    description
                      "MAC IWF session limit";
                  }
                }
              }
              description
                "MAC IWF session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          container access-interface {
            description
              "Limit or throttle IWF PPPoE sessions from any one MAC/Access-interface pair";
            container limit {
              description
                "Limit IWF PPPoE sessions from any one MAC/Access-interface pair";
              leaf session-limit {
                type union {
                  type uint32 {
                    range "1..128000" {
                      description
                        "MAC IWF session limit";
                    }
                  }
                  type uint32 {
                    range "1..65535" {
                      description
                        "MAC IWF session limit";
                    }
                  }
                }
                description
                  "MAC IWF session limit";
              }
              leaf threshold {
                type union {
                  type uint32 {
                    range "1..128000" {
                      description
                        "Warning message threshold";
                    }
                  }
                  type uint32 {
                    range "1..65535" {
                      description
                        "Warning message threshold";
                    }
                  }
                }
                must "../session-limit";
                description
                  "Specify the threshold after which a warning will be displayed";
              }
            }
            leaf throttle {
              type uint32 {
                range "1..65535" {
                  description
                    "Number of requests at which to throttle";
                }
              }
              must "../throttle-blocking-period and ../throttle-request-period";
              description
                "Throttle IWF PPPoE sessions from any one MAC/Access-interface pair";
            }
            leaf throttle-request-period {
              type uint32 {
                range "1..100" {
                  description
                    "Throttle request period";
                }
              }
              must "../throttle and ../throttle-blocking-period";
              description
                "Throttle request period";
            }
            leaf throttle-blocking-period {
              type uint32 {
                range "1..100" {
                  description
                    "Throttle blocking period";
                }
              }
              must "../throttle and ../throttle-request-period";
              description
                "Throttle blocking period";
            }
          }
        }
        container circuit-id {
          description
            "Limit or throttle PPPoE sessions with any one circuit ID";
          container limit {
            description
              "Limit PPPoE sessions with any one circuit ID";
            leaf session-limit {
              type union {
                type uint32 {
                  range "1..128000" {
                    description
                      "Circuit-ID session limit";
                  }
                }
                type uint32 {
                  range "1..65535" {
                    description
                      "Circuit-ID session limit";
                  }
                }
              }
              description
                "Circuit-ID session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          leaf throttle {
            type uint32 {
              range "1..65535" {
                description
                  "Number of requests at which to throttle";
              }
            }
            must "../throttle-blocking-period and ../throttle-request-period";
            description
              "Throttle PPPoE sessions from any one circuit ID";
          }
          leaf throttle-request-period {
            type uint32 {
              range "1..100" {
                description
                  "Throttle request period";
              }
            }
            must "../throttle and ../throttle-blocking-period";
            description
              "Throttle request period";
          }
          leaf throttle-blocking-period {
            type uint32 {
              range "1..100" {
                description
                  "Throttle blocking period";
              }
            }
            must "../throttle and ../throttle-request-period";
            description
              "Throttle blocking period";
          }
        }
        container remote-id {
          description
            "Limit or throttle PPPoE sessions with any one remote ID";
          container limit {
            description
              "Limit PPPoE sessions with any one remote ID";
            leaf session-limit {
              type union {
                type uint32 {
                  range "1..128000" {
                    description
                      "remote-ID session limit";
                  }
                }
                type uint32 {
                  range "1..65535" {
                    description
                      "remote-ID session limit";
                  }
                }
              }
              description
                "remote-ID session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          leaf throttle {
            type uint32 {
              range "1..65535" {
                description
                  "Number of requests at which to throttle";
              }
            }
            must "../throttle-blocking-period and ../throttle-request-period";
            description
              "Throttle PPPoE sessions from any one remote ID";
          }
          leaf throttle-request-period {
            type uint32 {
              range "1..100" {
                description
                  "Throttle request period";
              }
            }
            must "../throttle and ../throttle-blocking-period";
            description
              "Throttle request period";
          }
          leaf throttle-blocking-period {
            type uint32 {
              range "1..100" {
                description
                  "Throttle blocking period";
              }
            }
            must "../throttle and ../throttle-request-period";
            description
              "Throttle blocking period";
          }
        }
        container vlan {
          description
            "Limit or throttle PPPoE sessions with matching vlan IDs";
          container limit {
            description
              "Limit PPPoE sessions with matching vlan IDs";
            leaf session-limit {
              type union {
                type uint32 {
                  range "1..128000" {
                    description
                      "Vlan ID session limit";
                  }
                }
                type uint32 {
                  range "1..65535" {
                    description
                      "Vlan ID session limit";
                  }
                }
              }
              description
                "Vlan ID session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          leaf throttle {
            type uint32 {
              range "1..65535" {
                description
                  "Number of requests at which to throttle";
              }
            }
            must "../throttle-blocking-period and ../throttle-request-period";
            description
              "Throttle PPPoE sessions from matching vlan IDs";
          }
          leaf throttle-request-period {
            type uint32 {
              range "1..100" {
                description
                  "Throttle request period";
              }
            }
            must "../throttle and ../throttle-blocking-period";
            description
              "Throttle request period";
          }
          leaf throttle-blocking-period {
            type uint32 {
              range "1..100" {
                description
                  "Throttle blocking period";
              }
            }
            must "../throttle and ../throttle-request-period";
            description
              "Throttle blocking period";
          }
        }
        container inner-vlan {
          description
            "Limit or throttle PPPoE sessions with any one inner vlan ID";
          container limit {
            description
              "Limit PPPoE sessions with any one inner vlan ID";
            leaf session-limit {
              type union {
                type uint32 {
                  range "1..128000" {
                    description
                      "Inner vlan ID session limit";
                  }
                }
                type uint32 {
                  range "1..65535" {
                    description
                      "Inner vlan ID session limit";
                  }
                }
              }
              description
                "Inner vlan ID session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          leaf throttle {
            type uint32 {
              range "1..65535" {
                description
                  "Number of requests at which to throttle";
              }
            }
            must "../throttle-blocking-period and ../throttle-request-period";
            description
              "Throttle PPPoE sessions from any one inner vlan ID";
          }
          leaf throttle-request-period {
            type uint32 {
              range "1..100" {
                description
                  "Throttle request period";
              }
            }
            must "../throttle and ../throttle-blocking-period";
            description
              "Throttle request period";
          }
          leaf throttle-blocking-period {
            type uint32 {
              range "1..100" {
                description
                  "Throttle blocking period";
              }
            }
            must "../throttle and ../throttle-request-period";
            description
              "Throttle blocking period";
          }
        }
        container outer-vlan {
          description
            "Limit or throttle PPPoE sessions with any one outer vlan ID";
          container limit {
            description
              "Limit PPPoE sessions with any one outer vlan ID";
            leaf session-limit {
              type union {
                type uint32 {
                  range "1..128000" {
                    description
                      "Outer vlan ID session limit";
                  }
                }
                type uint32 {
                  range "1..65535" {
                    description
                      "Outer vlan ID session limit";
                  }
                }
              }
              description
                "Outer vlan ID session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          leaf throttle {
            type uint32 {
              range "1..65535" {
                description
                  "Number of requests at which to throttle";
              }
            }
            must "../throttle-blocking-period and ../throttle-request-period";
            description
              "Throttle PPPoE sessions from any one outer vlan ID";
          }
          leaf throttle-request-period {
            type uint32 {
              range "1..100" {
                description
                  "Throttle request period";
              }
            }
            must "../throttle and ../throttle-blocking-period";
            description
              "Throttle request period";
          }
          leaf throttle-blocking-period {
            type uint32 {
              range "1..100" {
                description
                  "Throttle blocking period";
              }
            }
            must "../throttle and ../throttle-request-period";
            description
              "Throttle blocking period";
          }
        }
        container circuit-id-and-remote-id {
          description
            "Limit or throttle PPPoE sessions by circuit ID and remote ID";
          container limit {
            description
              "Limit PPPoE sessions with matching circuit ID and remote ID";
            leaf session-limit {
              type union {
                type uint32 {
                  range "1..128000" {
                    description
                      "Circuit-ID and Remote-ID session limit";
                  }
                }
                type uint32 {
                  range "1..65535" {
                    description
                      "Circuit-ID and Remote-ID session limit";
                  }
                }
              }
              description
                "Circuit-ID and Remote-ID session limit";
            }
            leaf threshold {
              type union {
                type uint32 {
                  range "1..128000" {
                    description
                      "Warning message threshold";
                  }
                }
                type uint32 {
                  range "1..65535" {
                    description
                      "Warning message threshold";
                  }
                }
              }
              must "../session-limit";
              description
                "Specify the threshold after which a warning will be displayed";
            }
          }
          leaf throttle {
            type uint32 {
              range "1..65535" {
                description
                  "Number of requests at which to throttle";
              }
            }
            must "../throttle-blocking-period and ../throttle-request-period";
            description
              "Throttle PPPoE sessions matching circuit ID and remote ID";
          }
          leaf throttle-request-period {
            type uint32 {
              range "1..100" {
                description
                  "Throttle request period";
              }
            }
            must "../throttle and ../throttle-blocking-period";
            description
              "Throttle request period";
          }
          leaf throttle-blocking-period {
            type uint32 {
              range "1..100" {
                description
                  "Throttle blocking period";
              }
            }
            must "../throttle and ../throttle-request-period";
            description
              "Throttle blocking period";
          }
        }
      }
      container ac {
        description
          "Modify Access Concentrator config";
        leaf name {
          type xr:Cisco-ios-xr-string {
            length "1..256" {
              description
                "New name";
            }
          }
          description
            "Change the name to include in the AC tag";
        }
      }
      container service {
        description
          "Modify service config";
        container service-names {
          description
            "Change the service name";
          list service-name {
            key "name";
            description
              "Change the service name";
            leaf name {
              type xr:Cisco-ios-xr-string {
                length "1..256" {
                  description
                    "New name";
                }
              }
              description
                "Change the service name";
            }
          }
        }
        container selection {
          description
            "Disable advertising of unrequested service names";
          container disable {
            presence "Indicates a disable node is configured.";
            description
              "Disable advertising of unrequested service names";
          }
        }
      }
      container tag {
        description
          "Change tag configuration";
        container ppp-max-payload {
          description
            "Change the ppp-max-payload configuration";
          container deny {
            presence "Indicates a deny node is configured.";
            description
              "Ignore the ppp-max-payload tag";
          }
          leaf minimum {
            type uint32 {
              range "500..2000" {
                description
                  "Minimum payload";
              }
            }
            must "../maximum";
            description
              "Configure minimum payload";
          }
          leaf maximum {
            type uint32 {
              range "500..2000" {
                description
                  "Maximum payload";
              }
            }
            must "../minimum";
            description
              "Configure maximum payload";
          }
        }
      }
      container pppoe {
        description
          "Process PPPoE packets";
        container padr {
          description
            "PADR packet";
          container invalid-payload {
            description
              "Invalid-payload in PADR packet";
            container allow {
              presence "Indicates a allow node is configured.";
              description
                "Allow sessions to come up";
            }
          }
          container session-unique {
            description
              "session-unique";
            container relay-session-id {
              presence "Indicates a relay-session-id node is configured.";
              description
                "Allow sessions to come up with unique relay-session-id in padr";
            }
          }
        }
      }
      container invalid-session-id {
        description
          "Specify behaviour for when a packet with an invalid session ID is received";
        container log {
          must "not(../drop)";
          presence "Indicates a log node is configured.";
          description
            "Log packets with an invalid session ID.";
        }
        container drop {
          must "not(../log)";
          presence "Indicates a drop node is configured.";
          description
            "Silently drop packets with an invalid session ID.";
        }
      }
      leaf mtu {
        type uint32 {
          range "500..2000" {
            description
              "Default maximum payload";
          }
        }
        description
          "Change default maximum payload";
      }
      container timeout {
        description
          "Change session completion timeout.";
        leaf completion {
          type uint32 {
            range "30..600" {
              description
                "Timeout period in seconds.";
            }
          }
          description
            "Change session completion timeout.";
        }
      }
      container padt-after-shutdown {
        presence "Indicates a padt-after-shutdown node is configured.";
        description
          "PADT is sent after ppp shutdown";
      }
      container padi {
        description
          "Configure the response to PADIs coming from existing hosts";
        container host-uniq-disconnect {
          presence "Indicates a host-uniq-disconnect node is configured.";
          description
            "Disconnect the session when a padi received with existing host_uniq session";
        }
      }
    }
    container session-id {
      description
        "Disable per-parent session ID spaces";
      container space {
        description
          "Disable per-parent session ID spaces";
        container flat {
          presence "Indicates a flat node is configured.";
          description
            "Disable per-parent session ID spaces";
        }
      }
    }
    leaf in-flight-window {
      type uint32 {
        range "1..20000" {
          description
            "PPPoE in-flight window size";
        }
      }
      description
        "Set the PPPoE in-flight window size";
    }
  }
}
