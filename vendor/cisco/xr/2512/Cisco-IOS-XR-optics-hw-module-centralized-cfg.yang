module Cisco-IOS-XR-optics-hw-module-centralized-cfg {
  namespace "http://cisco.com/ns/yang/Cisco-IOS-XR-optics-hw-module-centralized-cfg";
  prefix optics-hw-module-centralized-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-hw-module-centralized package configuration.
     
     This module contains definitions
     for the following management objects:
       port-mode-configs: none
     
     Copyright (c) 2013-2023 by Cisco Systems, Inc.
     All rights reserved.";

  revision 2023-10-05 {
    description
      "Initial revision";
    semver:module-version "1.0.0";
  }
  revision 2019-04-05 {
    description
      "Establish semantic version baseline.";
  }
  revision 2015-11-09 {
    description
      "IOS XR 6.0 revision.";
  }

  container port-mode-configs {
    description
      "none";
    container locations {
      description
        "Configure port mode.";
      list location {
        key "nodeid";
        description
          "Node Id of portmode configuration";
        leaf fw-init-recovery {
          type empty;
          description
            "Configure Speed";
        }
        leaf nodeid {
          type xr:Node-id;
          description
            "Specify location";
        }
      }
    }
  }
}
