submodule Cisco-IOS-XR-wd-proc-state-oper-sub1 {
  belongs-to Cisco-IOS-XR-wd-proc-state-oper {
    prefix Cisco-IOS-XR-wd-proc-state-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR wd-proc-state package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping PROCESS-DEATH-INFO-BAG {
    description
      "Detail of process death event";
    leaf location {
      type string;
      description
        "Location where process death occured";
      xr:event-telemetry "Subscribe Telemetry Event";
    }
    leaf process-name {
      type string;
      description
        "Process Name";
      xr:event-telemetry "Subscribe Telemetry Event";
    }
    leaf pid {
      type uint32;
      description
        "Process PID";
      xr:event-telemetry "Subscribe Telemetry Event";
    }
    leaf jid {
      type uint32;
      description
        "Process JobID";
      xr:event-telemetry "Subscribe Telemetry Event";
    }
  }
}
