module Cisco-IOS-XR-sysadmin-sm-hw-mod {
  namespace "http://www.cisco.com/ns/yang/Cisco-IOS-XR-sysadmin-sm-hw-mod";
  prefix shelf_sm_hw_mod;

  import tailf-common {
    prefix tailf;
  }
  import Cisco-IOS-XR-sysadmin-types {
    prefix calvados;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module holds Shelf Management HW module data.
     
     Copyright (c) 2012-2020 by Cisco Systems, Inc.
     All rights reserved.";

  revision 2023-10-30 {
    description
      "Added new config hw-module fault-recovery";
    semver:module-version "1.2.0";
  }
  revision 2020-10-08 {
    description
      "Added support to power reset a hardware module";
    semver:module-version "1.1.0";
  }
  revision 2019-04-15 {
    description
      "Establish semantic version baseline.";
    semver:module-version "1.0.0";
  }
  revision 2017-04-12 {
    description
      "Changed namespace and module name";
  }
  revision 2012-10-24 {
    description
      "Initial revision of the partition from sm.yang";
  }

  grouping hw-module-config-group {
    description
      "hw module configuration commands available are
       1.shutdown 2.Auto-reset disablement 3.offline
       4.Fault recovery config";
    uses hw-module-shutdown-config-group;
    uses hw-module-reset-auto-disable-config-group;
    uses hw-module-offline-config-group;
    uses hw-module-fault-recovery-config-group;
  }

  grouping hw-module-shutdown-config-group {
    description
      "Config to shutdown a location";
    container shutdown {
      description
        "Shut down a hardware module";
      list location {
        key "location";
        description
          "Location of hardware module";
        leaf location {
          type calvados:location-id;
          mandatory true;
          description
            "location to (keep) shut down";
        }
      }
    }
  }

  grouping hw-module-reset-auto-disable-config-group {
    description
      "Config to disable auto reset on a location";
    container reset {
      description
        "Do not auto-reset a hardware module on fault";
      container auto {
        description
          "Do not auto-reset a hardware module on fault";
        container disable {
          description
            "Do not auto-reset a hardware module on fault";
          list location {
            key "location";
            description
              "Location of hardware module";
            leaf location {
              type calvados:location-id;
              mandatory true;
              description
                "Location to disable auto reset recovery";
            }
          }
        }
      }
    }
  }

  grouping hw-module-offline-config-group {
    description
      "Config to put a location to offline state for diagnostics";
    container offline {
      description
        "Keep a hardware module off line for diagnostics";
      list location {
        key "location";
        description
          "Location of hardware module";
        leaf location {
          type calvados:location-id;
          mandatory true;
          description
            "Location to (keep) off line";
        }
      }
    }
  }

  grouping hw-module-fault-recovery-config-group {
    description
      "Config to define maximum faults a location can recover from
       using reloads. After the configured number of reloads, the
       location will be shut.";
    container fault-recovery {
      description
        "Fault recovery";
      list location {
        key "location";
        description
          "Fault recovery location";
        leaf count {
          type uint32;
          mandatory true;
          description
            "Fault recovery count";
        }
        leaf location {
          type calvados:location-id;
          mandatory true;
          description
            "Location configured for fault recovery";
        }
      }
    }
  }

  grouping hw-module-action-group {
    description
      "hw module action CLI's include 1.Reload 2.Bootmedia reload
       3.Exec shutdown 4.Offline 5.Online 6.Delayed reboot
       7.Power reset";
    uses hw-module-reload-action-group;
    uses hw-module-bootmedia-action-group;
    uses hw-module-shutdown-action-group;
    uses hw-module-offline-action-group;
    uses hw-module-online-action-group;
    uses hw-module-delayed-reboot-action-group;
    uses hw-module-reset-action-group;
  }

  grouping hw-module-bootmedia-action-group {
    description
      "CLI for bootmedia reload of a location";
    container cbootmedia {
      config false;
      description
        "Bootmedia reload";
      list bootmedia {
        key "bootmedium";
        config false;
        description
          "Select boot media to load image from";
        leaf bootmedium {
          type string;
          description
            "bootmedium";
        }
        tailf:action "reload" {
          output {
            leaf result {
              type string;
              mandatory true;
              description
                "Result";
            }
          }
        }
      }
    }
  }

  grouping hw-module-reload-action-group {
    description
      "CLI for reload of a location";
    tailf:action "reload" {
      description
        "Reload a hardware module";
      input {
        leaf force {
          type empty;
          description
            "Do not wait for an orderly shutdown";
        }
        leaf noprompt {
          type empty;
          description
            "Do not prompt user for confirmation";
        }
        leaf warm {
          type empty;
          description
            "Fast reload";
        }
      }
      output {
        leaf result {
          type string;
          mandatory true;
          description
            "Result";
        }
      }
    }
  }

  grouping hw-module-delayed-reboot-action-group {
    description
      "CLI for delayed reload of a location";
    tailf:action "delayed_reload" {
      input {
        choice delayed_reboot {
          mandatory true;
          description
            "Delayed reboot";
          case delayed_reload {
            leaf delay_time {
              type uint64;
              default "0";
              description
                "Time in nano seconds to reboot";
            }
            leaf reboottype {
              type enumeration {
                enum "Cold" {
                  description
                    "Cold delayed reload";
                }
                enum "Warm" {
                  description
                    "Warm delayed reload";
                }
                enum "Shutdown" {
                  description
                    "Shutdown post delayed reload";
                }
              }
              default "Cold";
              description
                "Type of reload";
            }
            leaf reboot_reason {
              type string;
              description
                "Reason for reboot";
            }
            leaf force {
              type boolean;
              description
                "Forced reload";
            }
            leaf noprompt {
              type empty;
              description
                "Do not prompt user for confirmation";
            }
          }
        }
      }
      output {
        leaf result {
          type string;
          mandatory true;
          description
            "Result";
        }
      }
    }
  }

  grouping hw-module-shutdown-action-group {
    description
      "CLI for shutdown of a location";
    tailf:action "shutdown" {
      description
        "Shut down a hardware module";
      input {
        choice shutdown_polarity {
          description
            "Shutdown or powerup a location";
          case shutdown {
            leaf force {
              type empty;
              description
                "Do not wait for an orderly shutdown";
            }
          }
          case powerup {
            leaf disable {
              type empty;
              description
                "Bring the module back up";
            }
          }
        }
      }
      output {
        leaf result {
          type string;
          mandatory true;
          description
            "Result";
        }
      }
    }
  }

  grouping hw-module-offline-action-group {
    description
      "CLI for making a location state to go offline for diagnostics";
    tailf:action "offline" {
      description
        "Take a hardware module offline for diagnostics";
      output {
        leaf result {
          type string;
          mandatory true;
          description
            "Result";
        }
      }
    }
  }

  grouping hw-module-online-action-group {
    description
      "CLI for bringing a location back to online after it was
       taken offline for diagnostics";
    tailf:action "online" {
      description
        "Take a hardware module online for normal operation";
      output {
        leaf result {
          type string;
          mandatory true;
          description
            "Result";
        }
      }
    }
  }

  grouping hw-module-reset-action-group {
    description
      "CLI for power resetting a location";
    tailf:action "reset" {
      output {
        leaf result {
          type string;
          mandatory true;
          description
            "Result";
        }
      }
    }
  }
}
