module Cisco-IOS-XR-pbr-fwd-stats-oper {
  namespace "http://cisco.com/ns/yang/Cisco-IOS-XR-pbr-fwd-stats-oper";
  prefix pbr-fwd-stats-oper;

  import Cisco-IOS-XR-types {
    prefix xr;
  }
  import cisco-semver {
    prefix semver;
  }
  include Cisco-IOS-XR-pbr-fwd-stats-oper-sub2 {
    revision-date 2024-09-11;
  }
  include Cisco-IOS-XR-pbr-fwd-stats-oper-sub1 {
    revision-date 2024-09-11;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pbr-fwd-stats package operational data.
     
     This module contains definitions
     for the following management objects:
       pbr-stats: Retrieve PBR Stats data from Insight
     
     Copyright (c) 2013-2024 by Cisco Systems, Inc.
     All rights reserved.";

  revision 2024-09-11 {
    description
      "Stats feature update";
    semver:module-version "1.0.0";
  }
  revision 2024-05-08 {
    description
      "CSCwj03306 : Meta EBB - PBR Stats feature";
  }
  revision 2019-04-05 {
    description
      "Establish semantic version baseline.";
  }
  revision 2015-11-09 {
    description
      "IOS XR 6.0 revision.";
  }

  container pbr-stats {
    config false;
    description
      "Retrieve PBR Stats data from Insight";
    container policy-maps {
      description
        "Stats for a given Policy";
      list policy-map {
        key "policy-name";
        description
          "Name of the PolicyMap";
        container rule-names {
          description
            "Stats for a given Rule within the Policy";
          list rule-name {
            key "rule-name";
            description
              "PBR Stats for a Rule";
            leaf rule-name {
              type xr:Cisco-ios-xr-string;
              description
                "The RuleName";
            }
            uses PBR-POLICY-RULE-STATS;
          }
        }
        leaf policy-name {
          type xr:Cisco-ios-xr-string;
          description
            "The PolicyMap";
        }
      }
    }
  }
}
