module Cisco-IOS-XR-tunnel-ip-ma-oper {
  namespace "http://cisco.com/ns/yang/Cisco-IOS-XR-tunnel-ip-ma-oper";
  prefix tunnel-ip-ma-oper;

  import ietf-inet-types {
    prefix inet;
  }
  import Cisco-IOS-XR-types {
    prefix xr;
  }
  import cisco-semver {
    prefix semver;
  }
  import Cisco-IOS-XR-tunnel-gre-datatypes {
    prefix dt1;
  }
  include Cisco-IOS-XR-tunnel-ip-ma-oper-sub1 {
    revision-date 2025-01-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tunnel-ip-ma package operational data.
     
     This module contains definitions
     for the following management objects:
       tunnel-ip-ma: Tunnel Ip ma parameters
     
     Copyright (c) 2013-2025 by Cisco Systems, Inc.
     All rights reserved.";

  revision 2025-01-27 {
    description
      "Added an entry for tunnel interface vrf
       2022-08-25
         Added an entry for tunnel destination address group
       2022-02-26
         Added a field in tunl_gre_ma_edm_idb structure for source direct address
       2021-09-23
         Added entries for ipsec related params in interface database bag";
    semver:module-version "2.0.0";
  }
  revision 2021-02-25 {
    description
      "Added an entry for src addr db in bag";
    semver:module-version "1.1.0";
  }
  revision 2019-04-05 {
    description
      "Establish semantic version baseline.";
    semver:module-version "1.0.1";
  }
  revision 2018-10-09 {
    description
      "Modified hierarchy for endpoints, gspnode-db and application-db-stats";
  }
  revision 2015-11-09 {
    description
      "IOS XR 6.0 revision.";
  }

  grouping SUMMARY {
    description
      "Common node of database, standby-database";
    container summary {
      description
        "Tunnel IP MA summary";
      uses TUNL-IP-MA-SUM;
    }
  }

  container tunnel-ip-ma {
    config false;
    description
      "Tunnel Ip ma parameters";
    container gsp-node-db-summary {
      description
        "GRE MA GSP Node DB summary";
      uses TUNL-P2MP-MA-EDM-GSPDB-ARRAY;
    }
    container database {
      description
        "Tunnel Ip ma parameters";
      container transport-vrf-datas {
        description
          "GRE/IPinIP Tunnel Transport VRF DB";
        list transport-vrf-data {
          description
            "GRE/IPinIP Tunnel Transport VRF DB";
          leaf vrf-name {
            type xr:Cisco-ios-xr-string;
            description
              "VRF Name";
          }
          leaf address-family {
            type dt1:Tunl-addr-family-list;
            description
              "Address Family";
          }
          uses TUNL-IP-MA-EDM-IDB-ARRAY;
        }
      }
      container tunnel-ids {
        description
          "MA database parameters";
        list tunnel-id {
          key "tid";
          description
            "Tunnel ID";
          leaf tid {
            type dt1:Tunl-id-range;
            description
              "Tunnel ID";
          }
          uses TUNL-IP-MA-EDM-IDB-ARRAY;
        }
      }
      container interface-handles {
        description
          "GRE/IPinIP Tunnel ifhandle DB";
        list interface-handle {
          key "if-handle";
          description
            "GRE/IPinIP Tunnel ifhandle DB";
          leaf if-handle {
            type xr:Interface-name;
            description
              "Interface Handle value";
          }
          uses TUNL-IP-MA-EDM-IDB-ARRAY;
        }
      }
      container keep-alives {
        description
          "show tunnel ip keepalive data";
        list keep-alive {
          description
            "Show tunnel ip keepalive data";
          leaf interface-name {
            type xr:Interface-name;
            description
              "Interface Handle value";
          }
          leaf tunnel-id {
            type dt1:Tunl-id-range;
            description
              "Tunnel ID";
          }
          uses TUNL-IP-MA-EDM-KA;
        }
      }
      container rib-convergences {
        description
          "GRE/IPinIP Tunnel RIB converge DB";
        list rib-convergence {
          key "table-id";
          description
            "GRE/IPinIP Tunnel RIB converge DB";
          leaf table-id {
            type uint32;
            description
              "RSI Table ID";
          }
          uses TUNL-IP-MA-EDM-RIB-CONV;
        }
      }
      container tunnel-sources {
        description
          "GRE/IPinIP Tunnel Source interface name DB";
        list tunnel-source {
          description
            "GRE/IPinIP Tunnel Source interface name DB";
          leaf interface-name {
            type xr:Interface-name;
            description
              "Tunnel Source Interface Name";
          }
          leaf address-family {
            type dt1:Tunl-addr-family-list;
            description
              "AddressFamily";
          }
          uses TUNL-IP-MA-EDM-IDB-ARRAY;
        }
      }
      container check-points {
        description
          "GRE MA Checkpoint";
        list check-point {
          key "check-point-id";
          description
            "GRE MA Checkpoint";
          leaf check-point-id {
            type uint32;
            description
              "Object-ID of GRE MA checkpoint record";
          }
          uses TUNL-IP-MA-EDM-CHKPT;
        }
      }
      container tunnel-destinations {
        description
          "GRE/IPinIP Tunnel Destination DB";
        list tunnel-destination {
          description
            "GRE/IPinIP Tunnel Destination DB";
          leaf ip {
            type inet:ip-address-no-zone;
            description
              "Tunnel Destination IP Address";
          }
          leaf length {
            type dt1:Tunl-addr-length-range;
            description
              "Destination Address Length";
          }
          leaf vrf {
            type xr:Cisco-ios-xr-string;
            description
              "Transport VRF Name";
          }
          uses TUNL-IP-MA-EDM-IDB-ARRAY;
        }
      }
      uses SUMMARY;
    }
    container application-db-stats {
      description
        "GRE MA APP DB summary";
      uses TUNL-P2MP-MA-EDM-APP-PROD-ARRAY;
    }
    container standby-database {
      description
        "Tunnel Ip ma parameters";
      uses SUMMARY;
    }
    container endpoints {
      description
        "GRE MA DB endpoints";
      list endpoint {
        description
          "GRE MA DB endpoints";
        leaf tunnel-id {
          type dt1:Tunl-id-range;
          description
            "Tunnel ID";
        }
        leaf transport-ip-address {
          type inet:ip-address-no-zone;
          description
            "Transport IP Address";
        }
        leaf overlay-ip-address {
          type inet:ip-address-no-zone;
          description
            "Overlay IP Address";
        }
        uses TUNL-P2MP-MA-EDM-TED-DB-ARRAY;
      }
    }
  }
}
