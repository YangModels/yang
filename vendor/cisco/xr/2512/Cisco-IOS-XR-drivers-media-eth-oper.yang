module Cisco-IOS-XR-drivers-media-eth-oper {
  namespace "http://cisco.com/ns/yang/Cisco-IOS-XR-drivers-media-eth-oper";
  prefix drivers-media-eth-oper;

  import Cisco-IOS-XR-types {
    prefix xr;
  }
  import cisco-semver {
    prefix semver;
  }
  include Cisco-IOS-XR-drivers-media-eth-oper-sub1 {
    revision-date 2024-10-28;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR drivers-media-eth package operational data.
     
     This module contains definitions
     for the following management objects:
       ethernet-interface: Ethernet operational data
     
     Copyright (c) 2013-2024 by Cisco Systems, Inc.
     All rights reserved.";

  revision 2024-10-28 {
    description
      "Removed state transition count field
       2024-10-14
         Added ETHERNET_100GBASE_BX20_BD
       2024-10-11
         Added state transition count and link flap fields
       2024-08-06
         Added new media type definination for 25G/50G LR-S optics
       2024-07-19
         Added additional PRBS support parameters
       2024-05-31
         Added ETHERNET_100GBASE_BX40_BD
       2024-03-01
         Added support for SFP-50G-ER-I, SFP-50G-BX40U, SFP-50G-BX40D
       2024-01-23
         Added support for Pre FEC and Post FEC BER
       2023-12-13
         Added new Ethernet media type definition for QSFP-DD 400G SR4-BD
       2023-11-16
         Add pfc_statistics and pfc_watchdog_statistics
       2023-11-07
         Addition of Base-R fec type
       2023-08-24
         Added new pfc type definition
       2022-12-20
         Added new Ethernet media type definition
       2022-12-02
         Added new Ethernet media type definition for 100GE SR_1.2 optics
       2022-10-15
         Added new Ethernet media type definition for 400G Bright ZRP
       2022-09-10
         Added new Ethernet media type definition for 2x400G LR4 optics
       2022-08-26
         Added new Ethernet media type definition for 100GE ZR optics
       2022-08-10
         Added new Ethernet media type definition for SFP 10/25G BXD-I, BXU-I optics
       2022-06-08
         Added new Ethernet media type definition for 1G LH optics
       2022-05-10
         Added new Ethernet media type definition for Credo 800G AEC
       2022-04-25
         Added new Ethernet media type definition for 100GE ZR4S optics
       2022-04-22
         Start timestamp and validity support added for ethernet ports.
       2022-04-22
         Added new Ethernet media type definition for 8x100G FR
       2022-03-14
         Updated media type string
       2022-03-07
         Added new Ethernet media type definition for SFP 25G SL
       2021-11-19
         Added new Ethernet media type definition for 24GE ER-I optics
       2021-11-04
         Enums added for new module 800G Passive Loopback
       2021-10-07
         Enums added for new module 2x400G FR4 and 8x100G DR.
       2021-09-30
         Added new Ethernet media type definition.";
    semver:module-version "3.0.0";
  }
  revision 2021-09-29 {
    description
      "Removed list rx_drop_data_frames_per_tc and added leaf total_rx_drop_data_frames.
       2021-08-24
          Support added for last data time for generic stats.
       2021-08-16
          Added new Ethernet media type definition.
       2021-07-19
          Removed leaf total_rx_drop_data_frames and added list rx_drop_data_frames_per_tc to maintain backward compatibility.
       2021-07-01
          Support added for hardware timestamp for generic stats.";
    semver:module-version "2.1.0";
  }
  revision 2021-02-12 {
    description
      "Added support for PFC per TC Rx drop Data Frames.
       2020-11-04
           Added support for SER alarms.
       2020-09-08
           Added new ethernet speed values.";
    semver:module-version "2.0.0";
  }
  revision 2020-02-19 {
    description
      "Description updated.
       2019-11-27
         Adding operational value for power m-factor.
       2019-08-15
         Adding PFC watchdog support.";
    semver:module-version "1.2.0";
  }
  revision 2019-05-21 {
    description
      "Added new leaf for frame preemption configuration.";
    semver:module-version "1.1.0";
  }
  revision 2019-04-05 {
    description
      "Establish semantic version baseline.";
    semver:module-version "1.0.0";
  }
  revision 2017-05-01 {
    description
      "Fixing backward compatibility error in module.";
  }
  revision 2017-04-04 {
    description
      "Added new fields to phy data.";
  }
  revision 2015-01-07 {
    description
      "IOS XR 5.3.1 revision.";
  }

  container ethernet-interface {
    config false;
    description
      "Ethernet operational data";
    container statistics {
      description
        "Ethernet controller statistics table";
      list statistic {
        key "interface-name";
        description
          "Ethernet layer 2 controller statistics
           information";
        leaf interface-name {
          type xr:Interface-name;
          description
            "The name of the interface";
        }
        uses ETHERNET-L2-CONTROLLER-STATS;
      }
    }
    container pfc-statistics {
      description
        "PFC statistics information";
      list pfc-statistic {
        key "interface-name";
        description
          "PFC statistics information";
        leaf interface-name {
          type xr:Interface-name;
          description
            "The name of the interface";
        }
        uses ETHER-PFC-DETAILS-V2;
      }
    }
    container interfaces {
      description
        "Ethernet controller info table";
      list interface {
        key "interface-name";
        description
          "Ethernet controller information";
        leaf interface-name {
          type xr:Interface-name;
          description
            "The name of the interface";
        }
        uses ETHERNET-CONTROLLER-DRIVER-BAG-V2-TYPE;
      }
    }
    container pfc-watch-dog-statistics {
      description
        "PFC statistics information";
      list pfc-watch-dog-statistic {
        key "interface-name";
        description
          "PFC watchdog statistics information";
        leaf interface-name {
          type xr:Interface-name;
          description
            "The name of the interface";
        }
        uses ETHER-PFC-WD-DETAILS-V2;
      }
    }
    container berts {
      description
        "Ethernet controller BERT table";
      list bert {
        key "interface-name";
        description
          "Ethernet BERT information";
        leaf interface-name {
          type xr:Interface-name;
          description
            "The name of the interface";
        }
        uses ETH-SHOWCTRL-BERT;
      }
    }
  }
}
