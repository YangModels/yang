submodule Cisco-IOS-XR-procmem-oper-sub1 {
  belongs-to Cisco-IOS-XR-procmem-oper {
    prefix Cisco-IOS-XR-procmem-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR procmem package operational data.
     
     Copyright (c) 2013-2019 by Cisco Systems, Inc.
     All rights reserved.";

  revision 2019-04-05 {
    description
      "Establish semantic version baseline.";
    semver:module-version "1.0.0";
  }
  revision 2019-03-04 {
    description
      "Moved proccess id from integer to range.";
  }
  revision 2017-09-07 {
    description
      "Fixed type translation error.";
  }
  revision 2017-05-01 {
    description
      "Fixing backward compatibility error in module.";
  }
  revision 2015-11-09 {
    description
      "IOS XR 6.0 revision.";
  }
  revision 2015-07-30 {
    description
      "IOS XR 6.0.0 revision.";
  }

  grouping PROCESSESMEMORY-ENTRY {
    description
      " Per Process Information";
    leaf name {
      type string;
      description
        "Process name";
    }
    leaf jid {
      type uint32;
      description
        "Job ID";
    }
    leaf pid {
      type uint32;
      description
        "Process ID";
    }
    leaf text-seg-size {
      type uint32;
      description
        "Text Segment Size in KB";
    }
    leaf data-seg-size {
      type uint32;
      description
        "Data Segment Size in KB";
    }
    leaf stack-seg-size {
      type uint32;
      description
        "Stack Segment Size in KB";
    }
    leaf malloc-size {
      type uint32;
      description
        "Malloced Memory Size in KB";
    }
    leaf dyn-limit {
      type uint32;
      description
        "Dynamic memory limit in KB (4294967295 for
         RLIM_INFINITY)";
    }
    leaf shared-mem {
      type uint32;
      description
        "Shared memory size in KB";
    }
    leaf physical-mem {
      type uint32;
      description
        "Physical memory size in KB";
    }
  }
}
