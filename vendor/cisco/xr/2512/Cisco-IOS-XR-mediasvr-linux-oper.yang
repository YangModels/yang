module Cisco-IOS-XR-mediasvr-linux-oper {
  namespace "http://cisco.com/ns/yang/Cisco-IOS-XR-mediasvr-linux-oper";
  prefix mediasvr-linux-oper;

  import Cisco-IOS-XR-types {
    prefix xr;
  }
  import cisco-semver {
    prefix semver;
  }
  include Cisco-IOS-XR-mediasvr-linux-oper-sub1 {
    revision-date 2020-07-11;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mediasvr-linux package operational data.
     
     This module contains definitions
     for the following management objects:
       media-svr: Media server CLI operations
     
     Copyright (c) 2013-2020 by Cisco Systems, Inc.
     All rights reserved.";

  revision 2020-07-11 {
    description
      "Breaking show media result string into fields";
    semver:module-version "2.0.0";
  }
  revision 2019-04-05 {
    description
      "Establish semantic version baseline.";
  }
  revision 2015-11-09 {
    description
      "IOS XR 6.0 revision.";
  }

  container media-svr {
    config false;
    description
      "Media server CLI operations";
    container nodes {
      description
        "Media Info for All Nodes";
      list node {
        key "node";
        description
          "Media Info for a Node";
        leaf node {
          type xr:Node-id;
          description
            "Node Location";
        }
        list partition {
          key "name";
          description
            "Media Partition Info";
          leaf name {
            type xr:Cisco-ios-xr-string;
            description
              "Partition Name";
          }
          uses SHOW-MEDIA-EDM-PARTITION;
        }
      }
    }
  }
}
