submodule Cisco-IOS-XR-npu-fsdb-stats-oper-sub1 {
  belongs-to Cisco-IOS-XR-npu-fsdb-stats-oper {
    prefix Cisco-IOS-XR-npu-fsdb-stats-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR npu-fsdb-stats package operational data.
     
     Copyright (c) 2013-2025 by Cisco Systems, Inc.
     All rights reserved.";

  revision 2025-01-20 {
    description
      "Added counters-brief option to debug-utils
       2024-03-14
         Updated and fixed the model for debug-utils options
       2023-10-13
         Updated the model for debug-utils options
       2022-03-03
         Updated the yang model for link FSM entry
       2022-02-11
         Added weight distribution to npu driver info";
    semver:module-version "3.0.0";
  }
  revision 2021-05-14 {
    description
      "Updated the type of fabric operational mode in the yang model";
    semver:module-version "2.0.0";
  }
  revision 2020-10-10 {
    description
      "Yang Schema for npu driver link info";
    semver:module-version "1.0.0";
  }
  revision 2019-04-05 {
    description
      "Establish semantic version baseline.";
  }
  revision 2015-11-09 {
    description
      "IOS XR 6.0 revision.";
  }

  grouping NPU-FE-COUNTERS-DROP-INFO {
    description
      "FE asics drop counters";
    leaf rsi {
      type string;
      description
        "Rack/Slot/Asic";
    }
    leaf counter-name {
      type string;
      description
        "Counter Name";
    }
    leaf counter-desc {
      type string;
      description
        "Counter Description";
    }
    leaf value {
      type uint64;
      description
        "Counter value";
    }
    leaf severity {
      type uint32;
      description
        "severity";
    }
    leaf update-time {
      type uint64;
      description
        "Counter last update time";
    }
  }
}
