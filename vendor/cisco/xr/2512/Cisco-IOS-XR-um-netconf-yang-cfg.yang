module Cisco-IOS-XR-um-netconf-yang-cfg {
  namespace "http://cisco.com/ns/yang/Cisco-IOS-XR-um-netconf-yang-cfg";
  prefix um-netconf-yang-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR netconf-yang package configuration.
     
     This YANG module augments the
     modules with configuration data.
     
     Copyright (c) 2019-2023 by Cisco Systems, Inc.
     All rights reserved.";

  revision 2023-10-20 {
    description
      "Added netconf1.0 container at netconf-yang agent level
       2021-11-22
         Added submod-enter at netconf-yang agent level";
    semver:module-version "2.1.0";
  }
  revision 2020-03-06 {
    description
      "- Removed models/openconfig/disable as the config has been deprecated.
       - Added a new container to enable with-defaults support.";
    semver:module-version "2.0.0";
  }
  revision 2019-06-10 {
    description
      "Establish semantic version baseline.";
    semver:module-version "1.0.1";
  }
  revision 2019-03-30 {
    description
      "Initial version";
  }

  typedef nc10-support {
    type enumeration {
      enum "enabled" {
        value 1;
        description
          "Enable Netconf 1.0";
      }
      enum "1.0-only" {
        value 2;
        description
          "Enable Netconf 1.0 and disable 1.1";
      }
    }
    description
      "NETCONF 1.0 support type";
  }

  container netconf-yang {
    description
      "NETCONF YANG configuration commands";
    container agent {
      presence "Indicates a agent node is configured.";
      description
        "Enable NETCONF agent or configure NETCONF agent subcommands";
      container ssh {
        presence "Indicates a ssh node is configured.";
        description
          "Enable NETCONF-YANG agent over SSH connection";
      }
      container with-defaults-support {
        description
          "with-defaults support enabled";
        container enable {
          presence "Indicates a enable node is configured.";
          description
            "Enable with-defaults support";
        }
      }
      leaf rate-limit {
        type uint32 {
          range "4096..4294967295" {
            description
              "Number of bytes to process per sec";
          }
        }
        description
          "Rate limit";
      }
      container session {
        description
          "Session settings";
        leaf limit {
          type uint32 {
            range "1..50" {
              description
                "Count of allowable concurrent netconf-yang sessions (default = 50)";
            }
          }
          description
            "Maximum count of concurrent sessions (default = 50)";
        }
        leaf idle-timeout {
          type uint32 {
            range "1..1440" {
              description
                "Idle timeout in minutes";
            }
          }
          description
            "Non-active session lifetime";
        }
        leaf absolute-timeout {
          type uint32 {
            range "1..1440" {
              description
                "Absolute timeout in minutes";
            }
          }
          description
            "Absolute session lifetime";
        }
      }
      container netconf1.0 {
        presence "Indicates a netconf1.0 node is configured.";
        description
          "NETCONF protocol version 1.0 (RFC4741 & 4742)";
        leaf support {
          type nc10-support;
          mandatory true;
          description
            "Enable NETCONF1.0 support";
        }
        leaf streaming-disabled {
          type empty;
          description
            "Disable rpc-reply data streaming";
        }
      }
    }
  }
}
