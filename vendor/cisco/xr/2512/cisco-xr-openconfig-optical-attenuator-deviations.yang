//*************  DO-NOT EDIT  **************
//*********** Auto-generated file ********** 

 module cisco-xr-openconfig-optical-attenuator-deviations {

  prefix  "oc-opt-attdevs";

  namespace "http://cisco.com/ns/yang/cisco-xr-openconfig-optical-attenuator-deviations";

  import openconfig-optical-attenuator { prefix oc-opt-att; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-optical-attenuator.yang@2019-07-19 

     on Cisco IOS-XR devices.

     Copyright (c) 2017, 2024 by Cisco Systems, Inc.
     All rights reserved.";

  revision "2023-05-08" {
    description
      "Initial revision applicable to IOS-XR 6.4.1";
  }

  deviation /oc-opt-att:optical-attenuator/oc-opt-att:attenuators/oc-opt-att:attenuator/oc-opt-att:config/oc-opt-att:name {
    deviate not-supported;
  }
  deviation /oc-opt-att:optical-attenuator/oc-opt-att:attenuators/oc-opt-att:attenuator/oc-opt-att:config/oc-opt-att:attenuation-mode {
    deviate not-supported;
  }
  deviation /oc-opt-att:optical-attenuator/oc-opt-att:attenuators/oc-opt-att:attenuator/oc-opt-att:config/oc-opt-att:enabled {
    deviate not-supported;
  }
  deviation /oc-opt-att:optical-attenuator/oc-opt-att:attenuators/oc-opt-att:attenuator/oc-opt-att:state/oc-opt-att:ingress-port {
    deviate not-supported;
  }
  deviation /oc-opt-att:optical-attenuator/oc-opt-att:attenuators/oc-opt-att:attenuator/oc-opt-att:state/oc-opt-att:egress-port {
    deviate not-supported;
  }
  deviation /oc-opt-att:optical-attenuator/oc-opt-att:attenuators/oc-opt-att:attenuator/oc-opt-att:state/oc-opt-att:actual-attenuation/oc-opt-att:avg {
    deviate not-supported;
  }
  deviation /oc-opt-att:optical-attenuator/oc-opt-att:attenuators/oc-opt-att:attenuator/oc-opt-att:state/oc-opt-att:actual-attenuation/oc-opt-att:min {
    deviate not-supported;
  }
  deviation /oc-opt-att:optical-attenuator/oc-opt-att:attenuators/oc-opt-att:attenuator/oc-opt-att:state/oc-opt-att:actual-attenuation/oc-opt-att:max {
    deviate not-supported;
  }
  deviation /oc-opt-att:optical-attenuator/oc-opt-att:attenuators/oc-opt-att:attenuator/oc-opt-att:state/oc-opt-att:actual-attenuation/oc-opt-att:interval {
    deviate not-supported;
  }
  deviation /oc-opt-att:optical-attenuator/oc-opt-att:attenuators/oc-opt-att:attenuator/oc-opt-att:state/oc-opt-att:actual-attenuation/oc-opt-att:min-time {
    deviate not-supported;
  }
  deviation /oc-opt-att:optical-attenuator/oc-opt-att:attenuators/oc-opt-att:attenuator/oc-opt-att:state/oc-opt-att:actual-attenuation/oc-opt-att:max-time {
    deviate not-supported;
  }

}
//Total Deviations:11
