module Cisco-IOS-XR-um-http-client-cfg {
  namespace "http://cisco.com/ns/yang/Cisco-IOS-XR-um-http-client-cfg";
  prefix um-http-client-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR http-client package configuration.
     
     This YANG module augments the
     modules with configuration data.
     
     Copyright (c) 2022-2024 by Cisco Systems, Inc.
     All rights reserved.";

  revision 2024-06-18 {
    description
      "Added tls1.3 option
       2023-08-01
         Added tcp-window-scale cli
       2022-02-10
         - Added secure-verify-peer and secure-verify-host. Updated ipv4 and ipv6 under source-interface";
    semver:module-version "1.1.0";
  }
  revision 2020-09-22 {
    description
      "Initial release";
    semver:module-version "1.0.0";
  }

  container http {
    description
      "HTTP Application";
    container client {
      description
        "HTTP Client Application";
      leaf vrf {
        type xr:Cisco-ios-xr-string {
          length "1..32" {
            description
              "Name of vrf";
          }
        }
        description
          "Name of vrf";
      }
      container secure-verify-peer {
        description
          "Verify authenticity of the peer's certificate";
        container disable {
          presence "Indicates a disable node is configured.";
          description
            "Disable verifying peer's certificate";
        }
      }
      container secure-verify-host {
        description
          "Verify that if server certificate is for the serverit is known as";
        container disable {
          presence "Indicates a disable node is configured.";
          description
            "Disable verifying host in peer's certificate";
        }
      }
      container response {
        description
          "How long HTTP Client waits for a response from the server
           for a request message before giving up";
        leaf timeout {
          type uint32 {
            range "1..300" {
              description
                "HTTP Response time-out value in seconds";
            }
          }
          description
            "Response timeout";
        }
      }
      container connection {
        description
          "Configure HTTP Client connection";
        leaf timeout {
          type uint32 {
            range "1..60" {
              description
                "HTTP connection time-out value in seconds";
            }
          }
          description
            "How long HTTP Client waits for a server connection to
             establish before giving up";
        }
        leaf retry {
          type uint32 {
            range "1..5" {
              description
                "HTTP retry count";
            }
          }
          description
            "Configure retry count in case of connection establishment";
        }
      }
      container source-interface {
        description
          "Specify interface for source address";
        container ipv4 {
          description
            "Choose Ipv4 address from interface";
          leaf interface {
            type xr:Interface-name;
            description
              "Select an soucre interface";
          }
        }
        container ipv6 {
          description
            "Choose Ipv6 address from interface";
          leaf interface {
            type xr:Interface-name;
            description
              "Select an soucre interface";
          }
        }
      }
      container version {
        description
          "HTTP Version to be used in HTTP requests";
        container default {
          must "not(../http1.0 or ../http1.1)";
          presence "Indicates a default node is configured.";
          description
            "libcurl will pick HTTP version automatically";
        }
        container http1.0 {
          must "not(../default or ../http1.1)";
          presence "Indicates a http1.0 node is configured.";
          description
            "force HTTP1.0 to be used for all HTTP requests";
        }
        container http1.1 {
          must "not(../default or ../http1.0)";
          presence "Indicates a http1.1 node is configured.";
          description
            "force HTTP1.1 to be used for all HTTP requests";
        }
      }
      leaf tcp-window-scale {
        type uint32 {
          range "1..14" {
            description
              "Window scale factor";
          }
        }
        description
          "Set tcp window-scale factor for High Latency links";
      }
      container ssl {
        description
          "SSL configuration to be used for HTTPS requests";
        container version {
          description
            "SSL version to be used for HTTPS requests";
          container tls1.0 {
            must
              "not(../tls1.1 or ../tls1.2
               or ../tls1.3)";
            presence "Indicates a tls1.0 node is configured.";
            description
              "Force TLSv1.0 to be used for HTTPS requests";
          }
          container tls1.1 {
            must
              "not(../tls1.0 or ../tls1.2
               or ../tls1.3)";
            presence "Indicates a tls1.1 node is configured.";
            description
              "Force TLSv1.1 to be used for HTTPS requests";
          }
          container tls1.2 {
            must
              "not(../tls1.0 or ../tls1.1
               or ../tls1.3)";
            presence "Indicates a tls1.2 node is configured.";
            description
              "Force TLSv1.2 to be used for HTTPS requests";
          }
          container tls1.3 {
            must
              "not(../tls1.0 or ../tls1.1
               or ../tls1.2)";
            presence "Indicates a tls1.3 node is configured.";
            description
              "Force TLSv1.3 to be used for HTTPS requests";
          }
        }
      }
    }
  }
}
