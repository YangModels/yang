module Cisco-IOS-XR-ppp-ma-ipcp-cfg {
  namespace "http://cisco.com/ns/yang/Cisco-IOS-XR-ppp-ma-ipcp-cfg";
  prefix ppp-ma-ipcp-cfg;

  import ietf-inet-types {
    prefix inet;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ppp-ma-ipcp package configuration.
     
     This YANG module augments the
       Cisco-IOS-XR-ifmgr-cfg
     module with configuration data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/a1:interface-configurations/a1:interface-configuration" {
    description
      "This augment extends the configuration data of
       'Cisco-IOS-XR-ifmgr-cfg'";
    container ppp {
      description
        "Interface PPP configuration data";
      container ipcp {
        description
          "PPP IPCP configuration data";
        container peer-address {
          description
            "IPCP address parameters";
          leaf default {
            type inet:ipv4-address-no-zone;
            description
              "Specify an IP address to assign to peers
               through IPCP";
          }
        }
        container dns {
          description
            "IPCP DNS parameters";
          container dns-addresses {
            description
              "Specify DNS address(es) to provide";
            leaf primary {
              type inet:ipv4-address-no-zone;
              description
                "Primary DNS IP address";
            }
            leaf secondary {
              type inet:ipv4-address-no-zone;
              description
                "Secondary DNS IP address";
            }
          }
        }
        leaf neighbor-route-disable {
          type empty;
          description
            "Disable Neighbor Route installation";
        }
      }
    }
  }
}
