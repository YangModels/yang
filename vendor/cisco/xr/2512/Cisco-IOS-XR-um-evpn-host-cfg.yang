module Cisco-IOS-XR-um-evpn-host-cfg {
  namespace "http://cisco.com/ns/yang/Cisco-IOS-XR-um-evpn-host-cfg";
  prefix um-evpn-host-cfg;

  import Cisco-IOS-XR-um-l2vpn-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR evpn-host package configuration.
     
     This YANG module augments the
     modules with configuration data.
     
     Copyright (c) 2021-2022 by Cisco Systems, Inc.
     All rights reserved.";

  revision 2022-07-11 {
    description
      "Added missing description statement to nodes";
    semver:module-version "1.0.0";
  }
  revision 2021-03-03 {
    description
      "Initial release";
    semver:module-version "1.0.0";
  }

  augment "/a1:evpn" {
    description
      "This augment extends evpn nodes configuration";
    container host {
      description
        "Config host parameters";
      container mac-address {
        description
          "Config the host mac-address parameters";
        container duplicate-detection {
          description
            "Config the host mac-address duplicate detection parameters";
          leaf move-count {
            type uint32 {
              range "1..1000" {
                description
                  "Number of moves. Default is 5.";
              }
            }
            description
              "Number of moves to occur in move-interval seconds before freezing the MAC. Default is 5.";
          }
          leaf move-interval {
            type uint32 {
              range "5..3600" {
                description
                  "MAC move interval in seconds. Default is 180s.";
              }
            }
            description
              "Interval to watch for subsequent moves before freezing the MAC. Default is 180s.";
          }
          leaf freeze-time {
            type uint32 {
              range "5..3600" {
                description
                  "MAC freeze time in seconds. Default is 30s";
              }
            }
            description
              "Length of time to freeze the mac after it has been detected as duplicate. Default is 30s.";
          }
          leaf retry-count {
            type union {
              type uint32 {
                range "0..1000" {
                  description
                    "Retry count. Default is 3 times.";
                }
              }
              type enumeration {
                enum "infinity" {
                  value 1001;
                  description
                    "Infinite retry count. Disable permanent freezing of MACs.";
                }
              }
            }
            description
              "Number of times to unfreeze a MAC before permanently freezing it. Default is 3 times.";
          }
          container disable {
            presence "Indicates a disable node is configured.";
            description
              "Disable duplicate detection for MAC, IPv4 or IPv6 addresses.";
          }
          leaf reset-freeze-count-interval {
            type uint32 {
              range "1..48" {
                description
                  "Interval to reset count of duplicate detection events in hours. Default is 24 hours.";
              }
            }
            description
              "Interval after which the count of duplicate detection events used to determine whether MAC needs to be permanently frozen, is reset. Default is 24 hours.";
          }
        }
      }
      container ipv4-address {
        description
          "Config the host ipv4-address parameters";
        container duplicate-detection {
          description
            "Config the host ipv4-address duplicate detection parameters";
          leaf move-count {
            type uint32 {
              range "1..1000" {
                description
                  "Number of moves. Default is 5.";
              }
            }
            description
              "Number of moves to occur in move-interval seconds before freezing the IP. Default is 5.";
          }
          leaf move-interval {
            type uint32 {
              range "5..3600" {
                description
                  "MAC move interval in seconds. Default is 180s.";
              }
            }
            description
              "Interval to watch for subsequent mac moves before freezing the IP. Default is 180s.";
          }
          leaf freeze-time {
            type uint32 {
              range "5..3600" {
                description
                  "MAC freeze time in seconds. Default is 30s";
              }
            }
            description
              "Length of time to lock the IP address after it has been detected as duplicate. Default is 30s.";
          }
          leaf retry-count {
            type union {
              type uint32 {
                range "0..1000" {
                  description
                    "Retry count. Default is 3 times.";
                }
              }
              type enumeration {
                enum "infinity" {
                  value 1001;
                  description
                    "Infinite retry count. Disable permanent freezing of IPv4s.";
                }
              }
            }
            description
              "Number of times to unfreeze an IP address before permanently freezing it. Default is 3 times.";
          }
          container disable {
            presence "Indicates a disable node is configured.";
            description
              "Disable duplicate detection for MAC, IPv4 or IPv6 addresses.";
          }
          leaf reset-freeze-count-interval {
            type uint32 {
              range "1..48" {
                description
                  "Interval to reset count of duplicate detection events in hours. Default is 24 hours.";
              }
            }
            description
              "Interval after which the count of duplicate detection events used to determine whether IPv4 needs to be permanently frozen, is reset. Default is 24 hours.";
          }
        }
      }
      container ipv6-address {
        description
          "Config the host ipv6-address parameters";
        container duplicate-detection {
          description
            "Config the host ipv6-address duplicate detection parameters";
          leaf move-count {
            type uint32 {
              range "1..1000" {
                description
                  "Number of moves. Default is 5.";
              }
            }
            description
              "Number of moves to occur in move-interval seconds before freezing the IP. Default is 5.";
          }
          leaf move-interval {
            type uint32 {
              range "5..3600" {
                description
                  "MAC move interval in seconds. Default is 180s.";
              }
            }
            description
              "Interval to watch for subsequent mac moves before freezing the IP. Default is 180s.";
          }
          leaf freeze-time {
            type uint32 {
              range "5..3600" {
                description
                  "MAC freeze time in seconds. Default is 30s";
              }
            }
            description
              "Length of time to lock the IP address after it has been detected as duplicate. Default is 30s.";
          }
          leaf retry-count {
            type union {
              type uint32 {
                range "0..1000" {
                  description
                    "Retry count. Default is 3 times.";
                }
              }
              type enumeration {
                enum "infinity" {
                  value 1001;
                  description
                    "Infinite retry count. Disable permanent freezing of IPv6s.";
                }
              }
            }
            description
              "Number of times to unfreeze an IP address before permanently freezing it. Default is 3 times.";
          }
          container disable {
            presence "Indicates a disable node is configured.";
            description
              "Disable duplicate detection for MAC, IPv4 or IPv6 addresses.";
          }
          leaf reset-freeze-count-interval {
            type uint32 {
              range "1..48" {
                description
                  "Interval to reset count of duplicate detection events in hours. Default is 24 hours.";
              }
            }
            description
              "Interval after which the count of duplicate detection events used to determine whether IPv6 needs to be permanently frozen, is reset. Default is 24 hours.";
          }
        }
      }
    }
  }
}
