module Cisco-IOS-XR-controller-cpri-cfg {
  namespace "http://cisco.com/ns/yang/Cisco-IOS-XR-controller-cpri-cfg";
  prefix controller-cpri-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-cpri package configuration.
     
     This YANG module augments the
       Cisco-IOS-XR-ifmgr-cfg
     module with configuration data.
     
     Copyright (c) 2013-2020 by Cisco Systems, Inc.
     All rights reserved.";

  revision 2020-08-03 {
    description
      "RoE profile attach config command and Loopback config command added.";
    semver:module-version "2.1.0";
  }
  revision 2019-12-06 {
    description
      "Few configurations removed for CPRI controller";
    semver:module-version "2.0.0";
  }
  revision 2019-04-05 {
    description
      "Establish semantic version baseline.";
    semver:module-version "1.0.0";
  }
  revision 2015-11-09 {
    description
      "IOS XR 6.0 revision.";
  }

  typedef Cpri-loopback {
    type enumeration {
      enum "none" {
        value 0;
        description
          "None";
      }
      enum "line" {
        value 1;
        description
          "Line Loopback";
      }
      enum "internal" {
        value 4;
        description
          "Internal Loopback";
      }
    }
    description
      "Cpri loopback";
  }

  typedef Cpri-lpbk-mode {
    type enumeration {
      enum "line" {
        value 1;
        description
          "Line Loopback";
      }
      enum "internal" {
        value 4;
        description
          "Internal Loopback";
      }
    }
    description
      "Cpri lpbk mode";
  }

  augment "/a1:interface-configurations/a1:interface-configuration" {
    description
      "This augment extends the configuration data of
       'Cisco-IOS-XR-ifmgr-cfg'";
    container cpri {
      description
        "CPRI port controller configuration";
      container extended-loopback {
        description
          "Configure CPRI port extended loopback level and
           mode";
        leaf level {
          type uint32 {
            range "1..3";
          }
          description
            "ExtendedLoopbackLevel";
        }
        leaf mode {
          type Cpri-lpbk-mode;
          description
            "ExtendedLoopbackMode";
        }
      }
      leaf loopback {
        type Cpri-loopback;
        default "none";
        description
          "Configure CPRI loopback mode ";
      }
      leaf l1-startup-timer {
        type uint32;
        default "0";
        description
          "Configure L1 startup timer value";
      }
      leaf roe-profile {
        type uint32 {
          range "1..255";
        }
        description
          "Attach RoE profile";
      }
    }
  }
}
