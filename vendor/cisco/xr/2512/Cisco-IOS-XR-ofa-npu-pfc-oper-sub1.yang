submodule Cisco-IOS-XR-ofa-npu-pfc-oper-sub1 {
  belongs-to Cisco-IOS-XR-ofa-npu-pfc-oper {
    prefix Cisco-IOS-XR-ofa-npu-pfc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-npu-pfc package operational data.
     
     Copyright (c) 2013-2021 by Cisco Systems, Inc.
     All rights reserved.";

  revision 2021-10-10 {
    description
      "Added PFC related fields, ecn, ecn-max, tc-pause-threshold, tc-ecn-max, tc-prob-per, tc-pause-threshold-unit, tc-headroom-unit, tc-ecn-unit and tc-ecn-max-unit.";
    semver:module-version "1.0.0";
  }
  revision 2021-08-19 {
    description
      "Create the initial priority-flow-control oper yang model.";
  }
  revision 2019-04-05 {
    description
      "Establish semantic version baseline.";
  }
  revision 2015-11-09 {
    description
      "IOS XR 6.0 revision.";
  }

  grouping OFA-PFC-TC-CFG {
    description
      "OFA PFC TC CFG";
    leaf in-use {
      type uint32;
      description
        "Flag to indicate if PFC is configured for the tc";
    }
    leaf tc-pause-threshold {
      type uint32;
      description
        "Pause-threshold configured";
    }
    leaf tc-headroom {
      type uint32;
      description
        "Headroom configured";
    }
    leaf tc-ecn {
      type uint32;
      description
        "ECN configured";
    }
    leaf tc-ecn-max {
      type uint32;
      description
        "ECN Max configured";
    }
    leaf tc-prob-per {
      type uint32;
      description
        "ECN Prob Per configured";
    }
    leaf tc-pause-threshold-unit {
      type string {
        length "0..6";
      }
      description
        "Pause-threshold Unit";
    }
    leaf tc-headroom-unit {
      type string {
        length "0..6";
      }
      description
        "Headroom Unit";
    }
    leaf tc-ecn-unit {
      type string {
        length "0..6";
      }
      description
        "Ecn Unit";
    }
    leaf tc-ecn-max-unit {
      type string {
        length "0..6";
      }
      description
        "Ecn Max Unit";
    }
    leaf tc-reload-state {
      type uint32;
      description
        "Reload State";
    }
  }

  grouping OFA-PFC-CFG {
    description
      "OFA PFC CFG";
    leaf in-use {
      type uint32;
      description
        "Flag to indicate if PFC is configured for the
         line-card";
    }
    leaf pfc-mode {
      type string {
        length "0..16";
      }
      description
        "pfc mode configured";
    }
    leaf evict-lossy-tcs {
      type uint32;
      description
        "evict lossy tcs";
    }
    leaf max-evict-lossy-voq {
      type uint32;
      description
        "max evict lossy voq";
    }
    leaf dflt-max-evict-lossy-voq {
      type uint32;
      description
        "default max evict lossy voq";
    }
    list tc-cfg {
      max-elements "8";
      description
        "Keeps a record of the PFC configuration for the
         line-card";
      uses OFA-PFC-TC-CFG;
    }
  }
}
