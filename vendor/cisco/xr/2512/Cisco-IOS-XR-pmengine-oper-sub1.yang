submodule Cisco-IOS-XR-pmengine-oper-sub1 {
  belongs-to Cisco-IOS-XR-pmengine-oper {
    prefix Cisco-IOS-XR-pmengine-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pmengine package operational data.
     
     Copyright (c) 2013-2025 by Cisco Systems, Inc.
     All rights reserved.";

  revision 2025-04-10 {
    description
      "Format of PM engine layers have been changed to make it consistent.example new format is hour24-fec,minute15-pcs
       2025-04-02
         Added 15-min and 30-sec bucket history support for OTNSEC layer
       2024-09-25
         Added support for 7 days history data for controller ether, odu, otu, fc for 24-hour bucket
       2024-04-24
         New parameters supported for Protect Path
       2023-08-11
         Added support for SLR, SLT, SLR(C+L), SLT(C+L), SLR(s), SLT(s) parameters in Optics layer.
       2023-08-03
         Added support for 7 days history data for 24-hour bucket.
       2023-08-02
         Support added for new parameters like 'raman-br', 'raman-brr' in OTS layer.
       2023-05-15
         Added support for OPBRR parameters in Optics layer.
       2023-04-18
         Added support for SNR-X and SNR-Y parameters in Optics layer.
       2022-10-20
         Added 30-sec bucket history yang support for ODU controllers
       2022-08-16
         Changed data type of some leaf nodes from uint32 to uint64
       2022-05-10
         Removed unsupported parameters for OSC controller
       2022-05-10
         Removed unsupported parameters for OMS controller
       2022-05-10
         Removed unsupported parameters for OCH controller
       2022-05-10
         Removed unsupported parameters for DFB controller
       2022-04-03
         Added opt_min_50dbm_cap caps to set dBm Optics Parameter mininal value to -50.0dBm
       2022-03-06
         Support added for user-defined and pn9 patterns in prbs layer.
       2021-12-17
         Added oper support for Host PM parameters in FEC layer.
       2021-10-13
         Support added for cumulative-bad-sh and cumulative-frm-err in pcs layer.
       2021-10-06
         Support added for new counters in Optics layer.";
    semver:module-version "2.0.0";
  }
  revision 2021-07-09 {
    description
      "Support added for prbs layer for fibre-channel, ocn, stm and ethernet controllers. Support added for cem layer and controller. Container cem added.
       2021-04-26
          Support added for E1 controller.
       2021-04-14
          Support added for pcs and fec layers for fibre-channel controller.
       2021-02-24
          Support added for fc layer and controller. Container fibre-channel added.";
    semver:module-version "1.4.0";
  }
  revision 2020-09-02 {
    description
      "Added PM support for PRBS direction feature.
       2020-07-20
           Added parameter for cumulative BIP count in pcs pmengine bag.
       2020-04-17
           Added Instantaneous Q Margin in fec layer.
       2020-04-07
           Changes made to support TCA for OTU PRBS layer.";
    semver:module-version "1.3.0";
  }
  revision 2019-10-10 {
    description
      "Added support for flexible bin.";
    semver:module-version "1.2.0";
  }
  revision 2019-09-30 {
    description
      "Existing optics parameter PMD is deprecated and SOPMD is added to use instead.
       2019-08-28
         Max and Min time support for fec and optics layer parameters.
       2019-06-01
         Added Range attribute for the history buckets.";
    semver:module-version "1.1.0";
  }
  revision 2019-04-05 {
    description
      "Establish semantic version baseline.";
    semver:module-version "1.0.0";
  }
  revision 2017-09-07 {
    description
      "Fixed type translation error.";
  }
  revision 2017-05-01 {
    description
      "Fixing backward compatibility error in module.";
  }
  revision 2017-03-30 {
    description
      "OTU PRBS Stats Added";
  }
  revision 2015-11-09 {
    description
      "IOS XR 6.0 revision.";
  }

  typedef Pm-sonet-path-width-enum {
    type enumeration {
      enum "none" {
        value 0;
        description
          "Sonet Path Width NONE ";
      }
      enum "sts1" {
        value 1;
        description
          "Sonet Path Width STS1 ";
      }
      enum "sts3c-stm1" {
        value 2;
        description
          "Sonet Path Width sts3cSTM1 ";
      }
      enum "sts12c-stm4" {
        value 3;
        description
          "Sonet Path Width sts12cSTM4 ";
      }
      enum "sts24c" {
        value 4;
        description
          "Sonet Path Width sts24 ";
      }
      enum "sts48c-stm16" {
        value 5;
        description
          "Sonet Path Width sts48cSTM16 ";
      }
      enum "sts192c-stm64" {
        value 6;
        description
          "Sonet Path Width sts192cSTM64 ";
      }
      enum "sts768c-stm256" {
        value 7;
        description
          "Sonet Path Width sts768cSTM256 ";
      }
    }
    description
      "Sonet Path Width Enum";
  }

  typedef Pm-prbs-status-et {
    type enumeration {
      enum "not-applicable" {
        value 0;
        description
          "not applicable";
      }
      enum "locked" {
        value 1;
        description
          "locked";
      }
      enum "un-locked" {
        value 2;
        description
          "unlocked";
      }
    }
    description
      "PM PRBS Status Mode Enum";
  }

  typedef Pm-prbs-pattern-et {
    type enumeration {
      enum "prbs-none" {
        value 0;
        description
          "pn none";
      }
      enum "pn31" {
        value 1;
        description
          "pn31";
      }
      enum "pn23" {
        value 2;
        description
          "pn23";
      }
      enum "pn11" {
        value 4;
        description
          "pn11";
      }
      enum "inv-pn31" {
        value 8;
        description
          "inv pn31";
      }
      enum "inv-pn11" {
        value 16;
        description
          "inv pn11";
      }
      enum "pn15" {
        value 32;
        description
          "pn15";
      }
      enum "pn7" {
        value 64;
        description
          "pn7";
      }
      enum "pn9" {
        value 128;
        description
          "PRBS Pattern pn9";
      }
      enum "user-defined" {
        value 256;
        description
          "User Defined PRBS Pattern";
      }
    }
    description
      "PM PRBS Pattern Mode Enum";
  }

  typedef Pm-prbs-direction-et {
    type enumeration {
      enum "none" {
        value 0;
        description
          "none";
      }
      enum "line" {
        value 1;
        description
          "line";
      }
      enum "system" {
        value 2;
        description
          "system";
      }
    }
    description
      "PM PRBS Direction Mode Enum";
  }

  grouping PM-E1-PARAM {
    description
      "PM E1 PARAM";
    leaf data {
      type uint64;
      description
        "the number in the interval";
    }
    leaf threshold {
      type uint64;
      description
        "the threshold users set";
    }
    leaf tca-report {
      type boolean;
      description
        "enable/disable to report TCA";
    }
    leaf valid {
      type boolean;
      description
        "valid";
    }
  }

  grouping PM-E1-PARAS {
    description
      "all paras in e1";
    container line-code-violations {
      description
        "Line Code Violations";
      uses PM-E1-PARAM;
    }
    container path-code-violations {
      description
        "Path Code Violations";
      uses PM-E1-PARAM;
    }
    container sels {
      description
        "SELS";
      uses PM-E1-PARAM;
    }
    container les {
      description
        "LES";
      uses PM-E1-PARAM;
    }
    container aiss-sef {
      description
        "AISS SEF";
      uses PM-E1-PARAM;
    }
    container fcp {
      description
        "FCP";
      uses PM-E1-PARAM;
    }
    container es {
      description
        "ES ";
      uses PM-E1-PARAM;
    }
    container ses {
      description
        "SES";
      uses PM-E1-PARAM;
    }
    container uas {
      description
        "UAS";
      uses PM-E1-PARAM;
    }
    container es-fe {
      description
        "ES FE";
      uses PM-E1-PARAM;
    }
    container ses-fe {
      description
        "SES FE";
      uses PM-E1-PARAM;
    }
    container uas-fe {
      description
        "UAS FE";
      uses PM-E1-PARAM;
    }
    leaf index {
      type uint32;
      description
        "index";
    }
    leaf valid {
      type boolean;
      description
        "valid";
    }
    leaf timestamp {
      type string;
      description
        "timestamp";
    }
    leaf last-clear-time {
      type string;
      description
        "last clear time";
    }
    leaf last-clear15-min-timep {
      type string;
      description
        "last clear time";
    }
    leaf last-clear24-hr-time {
      type string;
      description
        "last clear time";
    }
  }

  grouping PM-CEM-PARAM {
    description
      "PM CEM PARAM";
    leaf data {
      type uint64;
      description
        "the value contained in the parameter";
    }
    leaf threshold {
      type uint64;
      description
        "the threshold set for the parameter by user";
    }
    leaf tca-report {
      type uint8;
      description
        "flag to enable reporting of TCA";
    }
    leaf supp-flag {
      type uint8;
      description
        "flag to check if parameter is supported";
    }
  }

  grouping PM-CEM-PARAS {
    description
      "PM CEM PARAS";
    container missing-pkts {
      description
        "Number of missing packets";
      uses PM-CEM-PARAM;
    }
    container pkts-reorder {
      description
        "Number of packets detected out of sequence, but
         successfully re-ordered.";
      uses PM-CEM-PARAM;
    }
    container jtr-bfr-under {
      description
        "Number of times a packet needed to be played out
         and the jitter buffer was empty.";
      uses PM-CEM-PARAM;
    }
    container mis-order-drop {
      description
        "Number of packets detected out of order, and
         could not be re-ordered, or could not fit in the
         jitter buffer.";
      uses PM-CEM-PARAM;
    }
    container malformed-pkt {
      description
        "Number of packets detected with unexpected size,
         or bad headers stack.";
      uses PM-CEM-PARAM;
    }
    container es {
      description
        "number of Error Seconds encountered.";
      uses PM-CEM-PARAM;
    }
    container ses {
      description
        "number of Severely Error Seconds";
      uses PM-CEM-PARAM;
    }
    container uas {
      description
        "number of UnAvailable Seconds.";
      uses PM-CEM-PARAM;
    }
    container fc {
      description
        "number of TDM failure events";
      uses PM-CEM-PARAM;
    }
    container input-errs {
      description
        "number of input errors";
      uses PM-CEM-PARAM;
    }
    container output-errs {
      description
        "number of output errors";
      uses PM-CEM-PARAM;
    }
    container jtr-bfr-overrun {
      description
        "Number of jitter buffer overruns.";
      uses PM-CEM-PARAM;
    }
    container tx-lbits {
      description
        "Number of generated lbits.";
      uses PM-CEM-PARAM;
    }
    container tx-rbits {
      description
        "Number of generated rbits.";
      uses PM-CEM-PARAM;
    }
    container rx-lbits {
      description
        "Number of received lbits.";
      uses PM-CEM-PARAM;
    }
    container rx-rbits {
      description
        "Number of received rbits.";
      uses PM-CEM-PARAM;
    }
    container in-pkts {
      description
        "Number of ingress packets.";
      uses PM-CEM-PARAM;
    }
    container eg-pkts {
      description
        "Number of egress packets.";
      uses PM-CEM-PARAM;
    }
    container in-drop {
      description
        "Number of ingress packets dropped.";
      uses PM-CEM-PARAM;
    }
    container eg-drop {
      description
        "Number of egress packets dropped.";
      uses PM-CEM-PARAM;
    }
    container backup-present {
      description
        "Backup path present or not";
      uses PM-CEM-PARAM;
    }
    container backup-missing-packets {
      description
        "Number of missing packets of backup path";
      uses PM-CEM-PARAM;
    }
    container backup-packets-reorder {
      description
        "Number of packets detected out of sequence in
         backup path, but successfully re-ordered.";
      uses PM-CEM-PARAM;
    }
    container backup-jitter-buffer-under {
      description
        "Number of times a packet needed to be played out
         in backup path and the jitter buffer was empty.";
      uses PM-CEM-PARAM;
    }
    container backup-miss-order-drop {
      description
        "Number of packets detected out of order in
         backup path, and could not be re-ordered, or
         could not fit in the jitter buffer.";
      uses PM-CEM-PARAM;
    }
    container backup-malformed-packet {
      description
        "Number of packets detected with unexpected size
         in backup path, or bad headers stack.";
      uses PM-CEM-PARAM;
    }
    container backup-error-seconds {
      description
        "Number of Error Seconds encountered in backup
         path.";
      uses PM-CEM-PARAM;
    }
    container backup-severely-errored-seconds {
      description
        "Number of Severely Error Seconds in backup path";
      uses PM-CEM-PARAM;
    }
    container backup-unavailable-seconds {
      description
        "Number of UnAvailable Seconds in backup path.";
      uses PM-CEM-PARAM;
    }
    container backup-tdm-failure-count {
      description
        "Number of TDM failure events in backup path";
      uses PM-CEM-PARAM;
    }
    container backup-input-errors {
      description
        "Number of input errors in backup path";
      uses PM-CEM-PARAM;
    }
    container backup-output-errors {
      description
        "Number of output errors in backup path";
      uses PM-CEM-PARAM;
    }
    container backup-jitter-buffer-overrun {
      description
        "Number of jitter buffer overruns in backup path.";
      uses PM-CEM-PARAM;
    }
    container backup-tx-lbits {
      description
        "Number of generated lbits in backup path.";
      uses PM-CEM-PARAM;
    }
    container backup-tx-rbits {
      description
        "Number of generated rbits in backup path.";
      uses PM-CEM-PARAM;
    }
    container backup-rx-lbits {
      description
        "Number of received lbits in backup path.";
      uses PM-CEM-PARAM;
    }
    container backup-rx-rbits {
      description
        "Number of received rbits in backup path.";
      uses PM-CEM-PARAM;
    }
    container backup-ingress-packets {
      description
        "Number of ingress packets in backup path.";
      uses PM-CEM-PARAM;
    }
    container backup-egress-packets {
      description
        "Number of egress packets in backup path.";
      uses PM-CEM-PARAM;
    }
    container backup-ingress-drop {
      description
        "Number of ingress packets dropped in backup path
         .";
      uses PM-CEM-PARAM;
    }
    container backup-egress-drop {
      description
        "Number of egress packets dropped in backup path.";
      uses PM-CEM-PARAM;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf sec30-support {
      type boolean;
      description
        "30 sec support";
    }
    leaf flex-bin-support {
      type boolean;
      description
        "flex bin support";
    }
    leaf flex-bin-interval {
      type uint16;
      description
        "flex bin interval";
    }
  }

  grouping PM-OPTICS-PARAMETER-STRING {
    description
      "one parameter in optics";
    leaf valid {
      type boolean;
      description
        "valid";
      xr:event-telemetry "Subscribe Telemetry Event";
    }
    leaf minimum {
      type string;
      description
        "minimum";
      xr:event-telemetry "Subscribe Telemetry Event";
    }
    leaf average {
      type string;
      description
        "average";
      xr:event-telemetry "Subscribe Telemetry Event";
    }
    leaf maximum {
      type string;
      description
        "maximum";
      xr:event-telemetry "Subscribe Telemetry Event";
    }
    leaf minimum-threshold {
      type string;
      description
        "minimun threshold";
      xr:event-telemetry "Subscribe Telemetry Event";
    }
    leaf configured-min-thresh {
      type string;
      description
        "minimunthreshold";
      xr:event-telemetry "Subscribe Telemetry Event";
    }
    leaf minimum-tca-report {
      type boolean;
      description
        "enable/disable to report TCA on min";
      xr:event-telemetry "Subscribe Telemetry Event";
    }
    leaf maximum-threshold {
      type string;
      description
        "maximum threshold";
      xr:event-telemetry "Subscribe Telemetry Event";
    }
    leaf configured-max-thresh {
      type string;
      description
        "maximumthreshold";
      xr:event-telemetry "Subscribe Telemetry Event";
    }
    leaf maximum-tca-report {
      type boolean;
      description
        "enable/disable to report TCA on max";
      xr:event-telemetry "Subscribe Telemetry Event";
    }
    leaf min-time {
      type uint64;
      description
        "minimum time";
      xr:event-telemetry "Subscribe Telemetry Event";
    }
    leaf max-time {
      type uint64;
      description
        "maximum time";
      xr:event-telemetry "Subscribe Telemetry Event";
    }
  }

  grouping PM-OPTICS-PARAMETER {
    description
      "one parameter in optics";
    leaf valid {
      type boolean;
      description
        "valid";
      xr:event-telemetry "Subscribe Telemetry Event";
    }
    leaf minimum {
      type int32;
      description
        "minimum";
      xr:event-telemetry "Subscribe Telemetry Event";
    }
    leaf average {
      type int32;
      description
        "average";
      xr:event-telemetry "Subscribe Telemetry Event";
    }
    leaf maximum {
      type int32;
      description
        "maximum";
      xr:event-telemetry "Subscribe Telemetry Event";
    }
    leaf minimum-threshold {
      type int32;
      description
        "minimun threshold";
      xr:event-telemetry "Subscribe Telemetry Event";
    }
    leaf configured-min-thresh {
      type string;
      description
        "minimunthreshold";
      xr:event-telemetry "Subscribe Telemetry Event";
    }
    leaf minimum-tca-report {
      type boolean;
      description
        "enable/disable to report TCA on min";
      xr:event-telemetry "Subscribe Telemetry Event";
    }
    leaf maximum-threshold {
      type int32;
      description
        "maximum threshold";
      xr:event-telemetry "Subscribe Telemetry Event";
    }
    leaf configured-max-thresh {
      type string;
      description
        "maximumthreshold";
      xr:event-telemetry "Subscribe Telemetry Event";
    }
    leaf maximum-tca-report {
      type boolean;
      description
        "enable/disable to report TCA on max";
      xr:event-telemetry "Subscribe Telemetry Event";
    }
    leaf min-time {
      type uint64;
      description
        "minimum time";
      xr:event-telemetry "Subscribe Telemetry Event";
    }
    leaf max-time {
      type uint64;
      description
        "maximum time";
      xr:event-telemetry "Subscribe Telemetry Event";
    }
  }

  grouping PM-OPTICS-PARAS {
    description
      "all paras in optics";
    container lbc {
      description
        "LBC";
      uses PM-OPTICS-PARAMETER;
    }
    container lbc-pc {
      description
        "LBC in percentage";
      uses PM-OPTICS-PARAMETER-STRING;
    }
    container opt {
      description
        "OPT";
      uses PM-OPTICS-PARAMETER-STRING;
    }
    container opr {
      description
        "OPR";
      uses PM-OPTICS-PARAMETER-STRING;
    }
    container cd {
      description
        "Chromatic Dispersion";
      uses PM-OPTICS-PARAMETER;
    }
    container dgd {
      description
        "Differential group Delay";
      uses PM-OPTICS-PARAMETER-STRING;
    }
    container pmd {
      description
        "Polarization Mode Dispersion , deprecated , use
         sopmd instead which is duplicate of pmd";
      uses PM-OPTICS-PARAMETER-STRING;
    }
    container sopmd {
      description
        "Second order Polarization Mode Dispersion";
      uses PM-OPTICS-PARAMETER-STRING;
    }
    container osnr {
      description
        "Optical Signal to Noise Ratio";
      uses PM-OPTICS-PARAMETER-STRING;
    }
    container center-wavelength {
      description
        "Center Wavelength/Frequency";
      uses PM-OPTICS-PARAMETER-STRING;
    }
    container pdl {
      description
        "Polarization Dependent Loss";
      uses PM-OPTICS-PARAMETER-STRING;
    }
    container pcr {
      description
        "Polarization Change Rate";
      uses PM-OPTICS-PARAMETER-STRING;
    }
    container pn {
      description
        "Phase Noise";
      uses PM-OPTICS-PARAMETER-STRING;
    }
    container rx-sig-pow {
      description
        "Rx signal power";
      uses PM-OPTICS-PARAMETER-STRING;
    }
    container low-sig-freq-off {
      description
        "low freq sig off";
      uses PM-OPTICS-PARAMETER;
    }
    container ampli-gain {
      description
        "Ampli Gain";
      uses PM-OPTICS-PARAMETER-STRING;
    }
    container ampli-gain-tilt {
      description
        "Ampli Gain Tilt";
      uses PM-OPTICS-PARAMETER-STRING;
    }
    container snr {
      description
        "SNR";
      uses PM-OPTICS-PARAMETER-STRING;
    }
    container snrax {
      description
        "SNR AX";
      uses PM-OPTICS-PARAMETER-STRING;
    }
    container snrbx {
      description
        "SNR BX";
      uses PM-OPTICS-PARAMETER-STRING;
    }
    container snray {
      description
        "SNR AY";
      uses PM-OPTICS-PARAMETER-STRING;
    }
    container snrby {
      description
        "SNR BY";
      uses PM-OPTICS-PARAMETER-STRING;
    }
    container sops1 {
      description
        "SOP S1";
      uses PM-OPTICS-PARAMETER-STRING;
    }
    container sops2 {
      description
        "SOP S2";
      uses PM-OPTICS-PARAMETER-STRING;
    }
    container sops3 {
      description
        "SOP S3";
      uses PM-OPTICS-PARAMETER-STRING;
    }
    container opt-cl {
      description
        "TX Power (C+L)";
      uses PM-OPTICS-PARAMETER-STRING;
    }
    container opr-cl {
      description
        "RX Power (C+L)";
      uses PM-OPTICS-PARAMETER-STRING;
    }
    container opt-s {
      description
        "TX Power (S)";
      uses PM-OPTICS-PARAMETER-STRING;
    }
    container opr-s {
      description
        "RX Power (S)";
      uses PM-OPTICS-PARAMETER-STRING;
    }
    container opbr {
      description
        "OPBR";
      uses PM-OPTICS-PARAMETER-STRING;
    }
    container eagn {
      description
        "Egress Ampli Gain";
      uses PM-OPTICS-PARAMETER-STRING;
    }
    container eatl {
      description
        "Egress Ampli Tilt";
      uses PM-OPTICS-PARAMETER-STRING;
    }
    container iagn {
      description
        "Ingress Ampli Gain";
      uses PM-OPTICS-PARAMETER-STRING;
    }
    container iatl {
      description
        "Ingress Ampli Tilt";
      uses PM-OPTICS-PARAMETER-STRING;
    }
    container raman-tot {
      description
        "RAMAN TOT";
      uses PM-OPTICS-PARAMETER-STRING;
    }
    container raman-1 {
      description
        "RAMAN 1";
      uses PM-OPTICS-PARAMETER-STRING;
    }
    container raman-2 {
      description
        "RAMAN 2";
      uses PM-OPTICS-PARAMETER-STRING;
    }
    container raman-3 {
      description
        "RAMAN 3";
      uses PM-OPTICS-PARAMETER-STRING;
    }
    container raman-4 {
      description
        "RAMAN 4";
      uses PM-OPTICS-PARAMETER-STRING;
    }
    container raman-5 {
      description
        "RAMAN 5";
      uses PM-OPTICS-PARAMETER-STRING;
    }
    container snrx {
      description
        "Signal to Noise Ratio of Network Port X";
      uses PM-OPTICS-PARAMETER-STRING;
    }
    container snry {
      description
        "Signal to Noise Ratio of Network Port Y";
      uses PM-OPTICS-PARAMETER-STRING;
    }
    container opbrr {
      description
        "Optical Back Reflection Ratio";
      uses PM-OPTICS-PARAMETER-STRING;
    }
    container raman-br {
      description
        "Raman Back Reflection (dBm)(1/100)";
      uses PM-OPTICS-PARAMETER-STRING;
    }
    container raman-brr {
      description
        "Raman Back Reflection Ratio (dB)(1/100)";
      uses PM-OPTICS-PARAMETER-STRING;
    }
    container tot-span-loss-rx {
      description
        "Total Span Loss Rx in the units of 1/100 dB";
      uses PM-OPTICS-PARAMETER-STRING;
    }
    container tot-span-loss-tx {
      description
        "Total Span Loss Tx in the units of 1/100 dB";
      uses PM-OPTICS-PARAMETER-STRING;
    }
    container tot-span-loss-rx-cl {
      description
        "Total Span Loss Rx (C+L) band in the units of
         1/100 dB";
      uses PM-OPTICS-PARAMETER-STRING;
    }
    container tot-span-loss-tx-cl {
      description
        "Total Span Loss Tx (C+L) band in the units of
         1/100 dB";
      uses PM-OPTICS-PARAMETER-STRING;
    }
    container sig-span-loss-rx {
      description
        "Signal Span Loss Rx in the units of 1/100 dB";
      uses PM-OPTICS-PARAMETER-STRING;
    }
    container sig-span-loss-tx {
      description
        "Signal Span Loss Tx in the units of 1/100 dB";
      uses PM-OPTICS-PARAMETER-STRING;
    }
    leaf index {
      type uint32;
      description
        "index";
    }
    leaf valid {
      type boolean;
      description
        "valid";
    }
    leaf timestamp {
      type string;
      description
        "timestamp";
      xr:event-telemetry "Subscribe Telemetry Event";
    }
    leaf last-clear-time {
      type string;
      description
        "last clear time";
    }
    leaf last-clear15-min-time {
      type string;
      description
        "last clear time";
    }
    leaf last-clear-flex-bin-time {
      type string;
      description
        "last clear time";
    }
    leaf last-clear30-sec-time {
      type string;
      description
        "last clear time";
    }
    leaf last-clear24-hr-time {
      type string;
      description
        "last clear time";
    }
    leaf sec30-support {
      type boolean;
      description
        "30 sec support";
    }
    leaf flex-bin-support {
      type boolean;
      description
        "flex bin support";
    }
    leaf flex-bin-interval {
      type uint16;
      description
        "flex bin interval";
    }
  }

  grouping SONET-FAR-END-LINE-ENTRY {
    description
      "SONET FAR END LINE ENTRY";
    container far-end-line-e-ss {
      description
        "The number of Errored Seconds";
      uses PM-SONET-PARAMETER;
    }
    container far-end-line-se-ss {
      description
        "The number of Severely Errored Seconds";
      uses PM-SONET-PARAMETER;
    }
    container far-end-line-c-vs {
      description
        "The number of Coding Violations";
      uses PM-SONET-PARAMETER;
    }
    container far-end-line-ua-ss {
      description
        "The number of Unavailable Seconds";
      uses PM-SONET-PARAMETER;
    }
    container far-end-line-fc-ls {
      description
        "The number of Failure counts Seconds";
      uses PM-SONET-PARAMETER;
    }
  }

  grouping SONET-LINE-ENTRY {
    description
      "SONET LINE ENTRY";
    container line-e-ss {
      description
        "The number of Errored Seconds";
      uses PM-SONET-PARAMETER;
    }
    container line-se-ss {
      description
        "The number of Severely Errored Seconds";
      uses PM-SONET-PARAMETER;
    }
    container line-c-vs {
      description
        "The number of Coding Violations";
      uses PM-SONET-PARAMETER;
    }
    container line-ua-ss {
      description
        "The number of Unavailable Seconds";
      uses PM-SONET-PARAMETER;
    }
    container line-fc-ls {
      description
        "The number of Failure counts Seconds";
      uses PM-SONET-PARAMETER;
    }
    leaf line-status {
      type int32;
      description
        " status of the interface";
    }
  }

  grouping PM-SONET-PARAMETER {
    description
      "pm one parameter";
    leaf data {
      type uint32;
      description
        "the number in the interval";
    }
    leaf threshold {
      type uint32;
      description
        "the threshold users set";
    }
    leaf tca-report {
      type boolean;
      description
        "enable/disable to report TCA";
    }
  }

  grouping SONET-SECTION-ENTRY {
    description
      "SONET SECTION ENTRY";
    container section-e-ss {
      description
        "The number of Errored Seconds";
      uses PM-SONET-PARAMETER;
    }
    container section-se-ss {
      description
        "The number of Severely Errored Seconds";
      uses PM-SONET-PARAMETER;
    }
    container section-sef-ss {
      description
        "The number of Severely Errored Framing Seconds";
      uses PM-SONET-PARAMETER;
    }
    container section-c-vs {
      description
        "The number of Coding Violations";
      uses PM-SONET-PARAMETER;
    }
    leaf section-status {
      type int32;
      description
        " status of the interface";
    }
  }

  grouping PM-SONET-PARAS {
    description
      "all paras in ocn";
    container section {
      description
        "SECTION";
      uses SONET-SECTION-ENTRY;
    }
    container line {
      description
        "LINE";
      uses SONET-LINE-ENTRY;
    }
    container fe-line {
      description
        "FarEnd LINE";
      uses SONET-FAR-END-LINE-ENTRY;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear24-hr-time {
      type string {
        length "0..64";
      }
      description
        "last clear time";
    }
  }

  grouping SONET-FAR-END-PATH-ENTRY {
    description
      "SONET FAR END PATH ENTRY";
    leaf far-end-path-e-ss {
      type uint32;
      units "second";
      description
        "The number of Errored Seconds";
    }
    leaf far-end-path-se-ss {
      type uint32;
      units "second";
      description
        "The number of Severely Errored Seconds";
    }
    leaf far-end-path-c-vs {
      type uint32;
      description
        "The number of Coding Violations";
    }
    leaf far-end-path-ua-ss {
      type uint32;
      units "second";
      description
        "The number of Unavailable Seconds";
    }
  }

  grouping PM-SONET-PATH-PARAMETER {
    description
      "pm one parameter";
    leaf data {
      type uint32;
      description
        "the number in the interval";
    }
    leaf threshold {
      type uint32;
      description
        "the threshold users set";
    }
    leaf tca-report {
      type boolean;
      description
        "enable/disable to report TCA";
    }
  }

  grouping SONET-PATH-ENTRY {
    description
      "SONET PATH ENTRY";
    container path-e-ss {
      description
        "The number of Errored Seconds";
      uses PM-SONET-PATH-PARAMETER;
    }
    container path-se-ss {
      description
        "The number of Severely Errored Seconds";
      uses PM-SONET-PATH-PARAMETER;
    }
    container path-c-vs {
      description
        "The number of Coding Violations";
      uses PM-SONET-PATH-PARAMETER;
    }
    container path-ua-ss {
      description
        "The number of Unavailable Seconds";
      uses PM-SONET-PATH-PARAMETER;
    }
    leaf path-width {
      type Pm-sonet-path-width-enum;
      description
        "Indicates the type of the SONET/SDH Path";
    }
    leaf path-status {
      type int32;
      description
        " status of the interface";
    }
  }

  grouping PM-SONET-PATH-PARAS {
    description
      "all paras in sts";
    container path {
      description
        "PATH";
      uses SONET-PATH-ENTRY;
    }
    container fe-path {
      description
        "Far End PATH";
      uses SONET-FAR-END-PATH-ENTRY;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear24-hr-time {
      type string {
        length "0..64";
      }
      description
        "last clear time";
    }
  }

  grouping STM-FAR-END-LINE-ENTRY {
    description
      "STM FAR END LINE ENTRY";
    container far-end-line-e-ss {
      description
        "The number of Errored Seconds";
      uses PM-STM-PARAMETER;
    }
    container far-end-line-es-rs {
      description
        "The number of Errored Seconds Ratio";
      uses PM-STM-PARAMETER-RATIO;
    }
    container far-end-line-ebb-es {
      description
        "The number of Background Block Errors";
      uses PM-STM-PARAMETER;
    }
    container far-end-line-bbe-rs {
      description
        "The number of Background Block Errors";
      uses PM-STM-PARAMETER-RATIO;
    }
    container far-end-line-se-ss {
      description
        "The number of Severely Errored Second";
      uses PM-STM-PARAMETER;
    }
    container far-end-line-ses-rs {
      description
        "The number of Severely Errored Second Ratio";
      uses PM-STM-PARAMETER-RATIO;
    }
    container far-end-line-ua-ss {
      description
        "The number of Unavailable Second";
      uses PM-STM-PARAMETER;
    }
    container far-end-line-e-bs {
      description
        "The number of Errored Block Second";
      uses PM-STM-PARAMETER;
    }
  }

  grouping STM-LINE-ENTRY {
    description
      "STM LINE ENTRY";
    container line-e-ss {
      description
        "The number of Errored Seconds";
      uses PM-STM-PARAMETER;
    }
    container line-es-rs {
      description
        "The number of Errored Seconds Ratio";
      uses PM-STM-PARAMETER-RATIO;
    }
    container line-bb-es {
      description
        "The number of Background Block Errors";
      uses PM-STM-PARAMETER;
    }
    container line-bbe-rs {
      description
        "The number of Background Block Errors";
      uses PM-STM-PARAMETER-RATIO;
    }
    container line-se-ss {
      description
        "The number of Severely Errored Second";
      uses PM-STM-PARAMETER;
    }
    container line-ses-rs {
      description
        "The number of Severely Errored Second Ratio";
      uses PM-STM-PARAMETER-RATIO;
    }
    container line-ua-ss {
      description
        "The number of Unavailable Second";
      uses PM-STM-PARAMETER;
    }
    container line-e-bs {
      description
        "The number of Errored Block Second";
      uses PM-STM-PARAMETER;
    }
    leaf line-status {
      type int32;
      description
        " status of the interface";
    }
  }

  grouping PM-STM-PARAMETER-RATIO {
    description
      "pm one parameter";
    leaf data {
      type string {
        length "0..8";
      }
      description
        "the number in the interval";
    }
    leaf threshold {
      type string {
        length "0..8";
      }
      description
        "the threshold users set";
    }
    leaf tca-report {
      type boolean;
      description
        "enable/disable to report TCA";
    }
  }

  grouping PM-STM-PARAMETER {
    description
      "pm one parameter";
    leaf data {
      type uint32;
      description
        "the number in the interval";
    }
    leaf threshold {
      type uint32;
      description
        "the threshold users set";
    }
    leaf tca-report {
      type boolean;
      description
        "enable/disable to report TCA";
    }
  }

  grouping STM-SECTION-ENTRY {
    description
      "STM SECTION ENTRY";
    container section-e-ss {
      description
        "The number of Errored Seconds";
      uses PM-STM-PARAMETER;
    }
    container section-es-rs {
      description
        "The number of Errored Seconds Ratio";
      uses PM-STM-PARAMETER-RATIO;
    }
    container section-bb-es {
      description
        "The number of Background Block Errors";
      uses PM-STM-PARAMETER;
    }
    container section-bbe-rs {
      description
        "The number of Background Block Errors";
      uses PM-STM-PARAMETER-RATIO;
    }
    container section-se-ss {
      description
        "The number of Severely Errored Second";
      uses PM-STM-PARAMETER;
    }
    container section-ses-rs {
      description
        "The number of Severely Errored Second Ratio";
      uses PM-STM-PARAMETER-RATIO;
    }
    container section-ua-ss {
      description
        "The number of Unavailable Second";
      uses PM-STM-PARAMETER;
    }
    container section-e-bs {
      description
        "The number of Errored Block Second";
      uses PM-STM-PARAMETER;
    }
    leaf section-status {
      type int32;
      description
        " status of the interface";
    }
  }

  grouping PM-STM-PARAS {
    description
      "all paras in stm";
    container section {
      description
        "SECTION";
      uses STM-SECTION-ENTRY;
    }
    container line {
      description
        "LINE";
      uses STM-LINE-ENTRY;
    }
    container fe-line {
      description
        "FarEnd LINE";
      uses STM-FAR-END-LINE-ENTRY;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear24-hr-time {
      type string {
        length "0..64";
      }
      description
        "last clear time";
    }
  }

  grouping PM-GFP-PARAM {
    description
      "PM GFP PARAM";
    leaf data {
      type uint64;
      description
        "the number in the interval";
    }
    leaf threshold {
      type uint64;
      description
        "the threshold users set";
    }
    leaf tca-report {
      type boolean;
      description
        "enable/disable to report TCA";
    }
  }

  grouping PM-GFP-PARAS {
    description
      "PM GFP PARAS";
    container rx-bit-err {
      description
        "RX BIT ERR";
      uses PM-GFP-PARAM;
    }
    container rx-inv-typ {
      description
        "RX INV TYP";
      uses PM-GFP-PARAM;
    }
    container rx-crc {
      description
        "RX CRC";
      uses PM-GFP-PARAM;
    }
    container rx-lfd {
      description
        "RX LFD";
      uses PM-GFP-PARAM;
    }
    container rx-csf {
      description
        "RX CSF";
      uses PM-GFP-PARAM;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear-flex-bin-time {
      type string {
        length "0..64";
      }
      description
        "last clear time";
    }
    leaf last-clear30-sec-time {
      type string {
        length "0..64";
      }
      description
        "last clear time";
    }
    leaf last-clear24-hr-time {
      type string {
        length "0..64";
      }
      description
        "last clear time";
    }
    leaf sec30-support {
      type boolean;
      description
        "30 sec support";
    }
    leaf flex-bin-support {
      type boolean;
      description
        "flex bin support";
    }
    leaf flex-bin-interval {
      type uint16;
      description
        "flex bin interval";
    }
  }

  grouping PM-OTNSEC-PARAMETER {
    description
      "otnsec parameter bag";
    leaf data {
      type uint64;
      description
        "PM data";
    }
    leaf threshold {
      type uint64;
      description
        "Configured Threshold";
    }
    leaf tca-report {
      type boolean;
      description
        "Enable/Disable of TCA";
    }
  }

  grouping PM-OTNSEC-PARAS {
    description
      "pm otnsec statistics";
    container in-blocks {
      description
        "Frames";
      uses PM-OTNSEC-PARAMETER;
    }
    container in-blocks-enc {
      description
        "Enc Frames";
      uses PM-OTNSEC-PARAMETER;
    }
    container in-blocks-un-encrypted {
      description
        "UnEnc Frames";
      uses PM-OTNSEC-PARAMETER;
    }
    container in-blocks-protected {
      description
        "Auth Count";
      uses PM-OTNSEC-PARAMETER;
    }
    container in-blocks-un-protected {
      description
        "UnAuth Count";
      uses PM-OTNSEC-PARAMETER;
    }
    container in-blocks-sequence-errors {
      description
        "Trouble";
      uses PM-OTNSEC-PARAMETER;
    }
    container in-blocks-replay-errors {
      description
        "Replay";
      uses PM-OTNSEC-PARAMETER;
    }
    container in-blocks-auth-errors {
      description
        "Auth Fail";
      uses PM-OTNSEC-PARAMETER;
    }
    container in-blocks-zeroed {
      description
        "Null Count";
      uses PM-OTNSEC-PARAMETER;
    }
    container out-blocks {
      description
        "Frames Encrypt";
      uses PM-OTNSEC-PARAMETER;
    }
    container out-blocks-enc {
      description
        "Auth Count";
      uses PM-OTNSEC-PARAMETER;
    }
    container out-blocks-un-encrypted {
      description
        "UnEnc count";
      uses PM-OTNSEC-PARAMETER;
    }
    container out-blocks-sequence-errors {
      description
        "OutBlocksSequenceErrors";
      uses PM-OTNSEC-PARAMETER;
    }
    container out-blocks-zeroed {
      description
        "Null Count";
      uses PM-OTNSEC-PARAMETER;
    }
    container out-blocks-protected {
      description
        "Auth Count";
      uses PM-OTNSEC-PARAMETER;
    }
    container out-blocks-un-protected {
      description
        "UnAuth Count";
      uses PM-OTNSEC-PARAMETER;
    }
    leaf valid {
      type boolean;
      description
        "Bucket state";
    }
    leaf index {
      type uint32;
      description
        "current or history";
    }
    leaf timestamp {
      type string;
      description
        "Bucket timestamp";
    }
    leaf last-clear-time {
      type string;
      description
        "Last Clearing of Bucket";
    }
    leaf flex-bin-interval {
      type uint16;
      description
        "flex bin interval";
    }
  }

  grouping PM-OTN-ALL-CHANS {
    description
      "all channels in otn layer";
    leaf num-chans {
      type uint32;
      description
        "number of otn channels";
    }
    list otn-all-chans {
      description
        "otn channels";
      uses PM-OTN-PARAS;
    }
  }

  grouping PM-OTN-PARAMETER-RATIO {
    description
      "pm one parameter";
    leaf data {
      type string;
      description
        "the number in the interval";
    }
    leaf threshold {
      type string;
      description
        "the threshold users set";
    }
    leaf tca-report {
      type boolean;
      description
        "enable/disable to report TCA";
    }
  }

  grouping PM-OTN-PARAMETER {
    description
      "pm one parameter";
    leaf data {
      type uint64;
      description
        "the number in the interval";
    }
    leaf threshold {
      type uint64;
      description
        "the threshold users set";
    }
    leaf tca-report {
      type boolean;
      description
        "enable/disable to report TCA";
    }
  }

  grouping PM-OTN-PARAS {
    description
      "all paras in otn";
    container lbc {
      description
        "LBC";
      uses PM-OTN-PARAMETER;
    }
    container es-ne {
      description
        "ES SM NE";
      uses PM-OTN-PARAMETER;
    }
    container esr-ne {
      description
        "ESR PM NE";
      uses PM-OTN-PARAMETER-RATIO;
    }
    container ses-ne {
      description
        "SES SM NE";
      uses PM-OTN-PARAMETER;
    }
    container sesr-ne {
      description
        "SESR SM NE";
      uses PM-OTN-PARAMETER-RATIO;
    }
    container uas-ne {
      description
        "UAS SM NE";
      uses PM-OTN-PARAMETER;
    }
    container bbe-ne {
      description
        "BBE SM NE";
      uses PM-OTN-PARAMETER;
    }
    container bber-ne {
      description
        "BBER SM NE";
      uses PM-OTN-PARAMETER-RATIO;
    }
    container fc-ne {
      description
        "FC SM NE";
      uses PM-OTN-PARAMETER;
    }
    container es-fe {
      description
        "ES SM FE";
      uses PM-OTN-PARAMETER;
    }
    container esr-fe {
      description
        "ESR PM FE";
      uses PM-OTN-PARAMETER-RATIO;
    }
    container ses-fe {
      description
        "SES SM FE";
      uses PM-OTN-PARAMETER;
    }
    container sesr-fe {
      description
        "SESR SM FE";
      uses PM-OTN-PARAMETER-RATIO;
    }
    container uas-fe {
      description
        "UAS SM FE";
      uses PM-OTN-PARAMETER;
    }
    container bbe-fe {
      description
        "BBE SM FE";
      uses PM-OTN-PARAMETER;
    }
    container bber-fe {
      description
        "BBER SM FE";
      uses PM-OTN-PARAMETER-RATIO;
    }
    container fc-fe {
      description
        "FC SM FE";
      uses PM-OTN-PARAMETER;
    }
    leaf index {
      type uint32;
      description
        "index";
    }
    leaf valid {
      type boolean;
      description
        "valid";
    }
    leaf timestamp {
      type string;
      description
        "timestamp";
    }
    leaf last-clear-time {
      type string;
      description
        "last clear time";
    }
    leaf last-clear15-min-time {
      type string;
      description
        "last clear time";
    }
    leaf last-clear-flex-bin-time {
      type string;
      description
        "last clear time";
    }
    leaf last-clear30-sec-time {
      type string;
      description
        "last clear time";
    }
    leaf last-clear24-hr-time {
      type string;
      description
        "last clear time";
    }
    leaf sec30-support {
      type boolean;
      description
        "30 sec support";
    }
    leaf flex-bin-support {
      type boolean;
      description
        "flex bin support";
    }
    leaf flex-bin-interval {
      type uint16;
      description
        "flex bin interval";
    }
  }

  grouping PM-PCS-PARAMETER-COUNT {
    description
      "pm pcs parameter count";
    leaf name {
      type string {
        length "0..19";
      }
      description
        "pcs param name";
    }
    leaf data {
      type uint64;
      description
        "the threshold users set";
    }
  }

  grouping PM-PCS-PARAMETER {
    description
      "pm pcs parameter";
    leaf tca-report {
      type boolean;
      description
        "enable/disable to report TCA";
    }
    leaf threshold {
      type uint64;
      description
        "the threshold users set";
    }
    list count {
      description
        "param count";
      uses PM-PCS-PARAMETER-COUNT;
    }
  }

  grouping PM-PCS-PARAS {
    description
      "all paras in pcs";
    container bip {
      description
        "Bip ";
      uses PM-PCS-PARAMETER;
    }
    container frm-err {
      description
        "Frm Err";
      uses PM-PCS-PARAMETER;
    }
    container bad-sh {
      description
        "Bad Sh";
      uses PM-PCS-PARAMETER;
    }
    container es-ne {
      description
        "Es Ne";
      uses PM-PCS-PARAMETER;
    }
    container ses-ne {
      description
        "Ses Ne";
      uses PM-PCS-PARAMETER;
    }
    container uas-ne {
      description
        "Uas Ne";
      uses PM-PCS-PARAMETER;
    }
    container es-fe {
      description
        "Es Fe";
      uses PM-PCS-PARAMETER;
    }
    container ses-fe {
      description
        "Ese Fe";
      uses PM-PCS-PARAMETER;
    }
    container uas-fe {
      description
        "Uas Fe";
      uses PM-PCS-PARAMETER;
    }
    leaf index {
      type uint32;
      description
        "index";
    }
    leaf valid {
      type boolean;
      description
        "valid";
    }
    leaf timestamp {
      type string;
      description
        "timestamp";
    }
    leaf last-clear-time {
      type string;
      description
        "last clear time";
    }
    leaf flex-bin-interval {
      type uint16;
      description
        "flex bin interval";
    }
    leaf cumulative-bip {
      type uint64;
      description
        "Cumulative Bip";
    }
    leaf cumulative-frm-err {
      type uint64;
      description
        "Cumulative Frm Err";
    }
    leaf cumulative-bad-sh {
      type uint64;
      description
        "Cumulative Bad Sh";
    }
  }

  grouping PM-PRBS-STATUS-PARAMETER {
    description
      "one parameter in optics";
    leaf valid {
      type boolean;
      description
        "valid";
    }
    leaf prbs-status {
      type Pm-prbs-status-et;
      description
        "Prbs Status";
    }
  }

  grouping PM-PRBS-PARAMETER {
    description
      "one parameter in optics";
    leaf valid {
      type boolean;
      description
        "valid";
    }
    leaf rcv-patt {
      type Pm-prbs-pattern-et;
      description
        "RCVD PTRN";
    }
  }

  grouping PM-PRBS-TCA-PARAMETER {
    description
      "one parameter in optics";
    leaf threshold {
      type uint64;
      description
        "the threshold users set";
      xr:event-telemetry "Subscribe Telemetry Event";
    }
    leaf tca-report {
      type boolean;
      description
        "enable/disable to report TCA";
      xr:event-telemetry "Subscribe Telemetry Event";
    }
  }

  grouping PM-PRBS-PARAS {
    description
      "all paras in prbs";
    container ebc-tca {
      description
        "EBC TCA";
      uses PM-PRBS-TCA-PARAMETER;
    }
    container found-count-tca {
      description
        "FOUND COUNT TCA";
      uses PM-PRBS-TCA-PARAMETER;
    }
    container lost-count-tca {
      description
        "LOST COUNT TCA";
      uses PM-PRBS-TCA-PARAMETER;
    }
    container rcv-patt {
      description
        "RCVD PTRN";
      uses PM-PRBS-PARAMETER;
    }
    container prbs-status {
      description
        "PRBS STATUS";
      uses PM-PRBS-STATUS-PARAMETER;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear24-hr-time {
      type string {
        length "0..64";
      }
      description
        "last clear time";
    }
    leaf last-clear-flex-bin-time {
      type string {
        length "0..64";
      }
      description
        "last clear time";
    }
    leaf last-clear30-sec-time {
      type string {
        length "0..64";
      }
      description
        "last clear time";
    }
    leaf flex-bin-interval {
      type uint16;
      description
        "flex bin interval";
    }
    leaf prbs-direction {
      type Pm-prbs-direction-et;
      description
        "prbs direction";
    }
    leaf ebc {
      type uint64;
      description
        "EBC";
    }
    leaf found-count {
      type uint32;
      description
        "FOUND COUNT";
    }
    leaf lost-count {
      type uint32;
      description
        "LOST COUNT";
    }
    leaf found-at-time {
      type uint64;
      description
        "FOUND AT TS";
    }
    leaf lost-at-time {
      type uint64;
      description
        "LOST AT TS";
    }
    leaf conf-patt {
      type Pm-prbs-pattern-et;
      description
        "CONFIG PTRN";
    }
    leaf user-pattern {
      type uint64;
      description
        "PRBS user pattern configured";
    }
  }

  grouping PM-FC-PARAM {
    description
      "PM FC PARAM";
    leaf data {
      type uint64;
      description
        "the number in the interval";
    }
    leaf threshold {
      type uint64;
      description
        "the threshold users set";
    }
    leaf tca-report {
      type boolean;
      description
        "enable/disable to report TCA";
    }
    leaf supp-flag {
      type boolean;
      description
        "Support Flag";
    }
    leaf valid {
      type boolean;
      description
        "valid";
    }
  }

  grouping PM-FC-PARAS {
    description
      "PM FC PARAS";
    container if-in-octets {
      description
        "Number of bytes received since the last counter
         reset.";
      uses PM-FC-PARAM;
    }
    container rx-pkt {
      description
        "Total number of receive packets.";
      uses PM-FC-PARAM;
    }
    container if-in-errors {
      description
        "Total number of receive errors.";
      uses PM-FC-PARAM;
    }
    container rx-bad-fcs {
      description
        "Number of Rx frames with bad FCS, no coding
         error";
      uses PM-FC-PARAM;
    }
    container if-out-octets {
      description
        "The total number of octets transmitted out of
         the interface, including framing characters.";
      uses PM-FC-PARAM;
    }
    container tx-pkt {
      description
        "Total number of transmitted packets.";
      uses PM-FC-PARAM;
    }
    container tx-bad-fcs {
      description
        "Number of Tx frames with bad FCS, no coding
         error";
      uses PM-FC-PARAM;
    }
    container rx-frames-too-long {
      description
        "Number of too long rx frames.";
      uses PM-FC-PARAM;
    }
    container rx-frames-trunc {
      description
        "Number of truncated rx frames.";
      uses PM-FC-PARAM;
    }
    container tx-frames-too-long {
      description
        "Number of too long tx frames.";
      uses PM-FC-PARAM;
    }
    container tx-frames-trunc {
      description
        "Number of truncated tx frames.";
      uses PM-FC-PARAM;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear 15-min interval time";
    }
    leaf last-clear-flex-bin-time {
      type string {
        length "0..64";
      }
      description
        "last clear flex-bin interval time";
    }
    leaf last-clear30-sec-time {
      type string {
        length "0..64";
      }
      description
        "last clear 30-sec interval time";
    }
    leaf last-clear24-hr-time {
      type string {
        length "0..64";
      }
      description
        "last clear  25-hour interval time";
    }
    leaf sec30-support {
      type boolean;
      description
        "30 sec support";
    }
    leaf flex-bin-support {
      type boolean;
      description
        "flex bin support";
    }
    leaf flex-bin-interval {
      type uint16;
      description
        "flex bin interval";
    }
  }

  grouping PM-FEC-PARAMETER-COUNT {
    description
      "pm fec parameter count";
    leaf name {
      type string {
        length "0..32";
      }
      description
        "fec lane parameter name";
    }
    leaf minimum {
      type string {
        length "0..20";
      }
      description
        "minimum value of the parameter in the bucket";
    }
    leaf average {
      type string {
        length "0..20";
      }
      description
        "average value of the parameter in the bucket";
    }
    leaf maximum {
      type string {
        length "0..20";
      }
      description
        "maximum value of the parameter in the bucket";
    }
    leaf valid {
      type boolean;
      description
        "Flag indicating validity of the parameter";
      xr:event-telemetry "Subscribe Telemetry Event";
    }
    leaf min-time {
      type uint64;
      description
        "time in nsec when minimum value was captured";
      xr:event-telemetry "Subscribe Telemetry Event";
    }
    leaf max-time {
      type uint64;
      description
        "time in nsec when maximum value was captured";
      xr:event-telemetry "Subscribe Telemetry Event";
    }
  }

  grouping PM-FEC-PARAM-LANES-STRING {
    description
      "pm fec lanes parameter";
    leaf minimum-threshold {
      type string {
        length "0..20";
      }
      description
        "minimum threshold";
    }
    leaf minimum-tca-report {
      type boolean;
      description
        "enable/disable to report TCA on min";
    }
    leaf maximum-threshold {
      type string {
        length "0..20";
      }
      description
        "maximum threshold";
    }
    leaf maximum-tca-report {
      type boolean;
      description
        "enable/disable to report TCA on max";
    }
    list count {
      description
        "parameter count";
      uses PM-FEC-PARAMETER-COUNT;
    }
  }

  grouping PM-FEC-PARAM-STRING {
    description
      "pm avg fec parameter";
    leaf minimum {
      type string;
      description
        "minimum";
      xr:event-telemetry "Subscribe Telemetry Event";
    }
    leaf average {
      type string;
      description
        "average";
      xr:event-telemetry "Subscribe Telemetry Event";
    }
    leaf maximum {
      type string;
      description
        "maximum";
      xr:event-telemetry "Subscribe Telemetry Event";
    }
    leaf minimum-threshold {
      type string;
      description
        "minimun threshold";
      xr:event-telemetry "Subscribe Telemetry Event";
    }
    leaf minimum-tca-report {
      type boolean;
      description
        "enable/disable to report TCA on min";
      xr:event-telemetry "Subscribe Telemetry Event";
    }
    leaf maximum-threshold {
      type string;
      description
        "maximum threshold";
      xr:event-telemetry "Subscribe Telemetry Event";
    }
    leaf maximum-tca-report {
      type boolean;
      description
        "enable/disable to report TCA";
      xr:event-telemetry "Subscribe Telemetry Event";
    }
    leaf valid {
      type boolean;
      description
        "valid";
      xr:event-telemetry "Subscribe Telemetry Event";
    }
    leaf min-time {
      type uint64;
      description
        "minimum time";
      xr:event-telemetry "Subscribe Telemetry Event";
    }
    leaf max-time {
      type uint64;
      description
        "maximum time";
      xr:event-telemetry "Subscribe Telemetry Event";
    }
  }

  grouping PM-FEC-PARAM {
    description
      "pm avg fec param";
    leaf data {
      type uint64;
      description
        "the number in the interval";
      xr:event-telemetry "Subscribe Telemetry Event";
    }
    leaf threshold {
      type uint64;
      description
        "the threshold users set";
      xr:event-telemetry "Subscribe Telemetry Event";
    }
    leaf tca-report {
      type boolean;
      description
        "enable/disable to report TCA";
      xr:event-telemetry "Subscribe Telemetry Event";
    }
    leaf valid {
      type boolean;
      description
        "valid";
      xr:event-telemetry "Subscribe Telemetry Event";
    }
  }

  grouping PM-FEC-PARAS {
    description
      "all paras in fec";
    container ec-bits {
      description
        "EC BITS";
      uses PM-FEC-PARAM;
    }
    container uc-words {
      description
        "UC WORDS";
      uses PM-FEC-PARAM;
    }
    container pre-fec-ber {
      description
        "Pre FEC BER";
      uses PM-FEC-PARAM-STRING;
    }
    container post-fec-ber {
      description
        "Post FEC BER";
      uses PM-FEC-PARAM-STRING;
    }
    container q {
      description
        "Q";
      uses PM-FEC-PARAM-STRING;
    }
    container qmargin {
      description
        "Q Margin";
      uses PM-FEC-PARAM-STRING;
    }
    container qmargin-inst {
      description
        "Q Margin Instantaneous";
      uses PM-FEC-PARAM-STRING;
    }
    container ec-words {
      description
        "EC Words";
      uses PM-FEC-PARAM;
    }
    container ber-lane {
      description
        "Lane details of Bit Error Rate";
      uses PM-FEC-PARAM-LANES-STRING;
    }
    container ferc-lane {
      description
        "Lane details of Frame Error Count";
      uses PM-FEC-PARAM-LANES-STRING;
    }
    leaf index {
      type uint32;
      description
        "index";
    }
    leaf valid {
      type boolean;
      description
        "valid";
    }
    leaf timestamp {
      type string;
      description
        "timestamp";
      xr:event-telemetry "Subscribe Telemetry Event";
    }
    leaf last-clear-time {
      type string;
      description
        "last clear time";
    }
    leaf last-clear15-min-time {
      type string;
      description
        "last clear time";
    }
    leaf last-clear-flex-bin-time {
      type string;
      description
        "last clear time";
    }
    leaf last-clear30-sec-time {
      type string;
      description
        "last clear time";
    }
    leaf last-clear24-hr-time {
      type string;
      description
        "last clear time";
    }
    leaf sec30-support {
      type boolean;
      description
        "30 sec support";
    }
    leaf flex-bin-support {
      type boolean;
      description
        "flex bin support";
    }
    leaf flex-bin-interval {
      type uint16;
      description
        "flex bin interval";
    }
  }

  grouping HO-VC-FAR-END-PATH-ENTRY {
    description
      "HO VC FAR END PATH ENTRY";
    leaf far-end-path-e-ss {
      type uint32;
      units "second";
      description
        "The number of Errored Seconds";
    }
    leaf far-end-path-se-ss {
      type uint32;
      units "second";
      description
        "The number of Severely Errored Seconds";
    }
    leaf far-end-path-c-vs {
      type uint32;
      description
        "The number of Coding Violations";
    }
    leaf far-end-path-ua-ss {
      type uint32;
      units "second";
      description
        "The number of Unavailable Seconds";
    }
  }

  grouping PM-HO-VC-PARAMETER-RATIO {
    description
      "pm one parameter";
    leaf data {
      type string {
        length "0..8";
      }
      description
        "the number in the interval";
    }
    leaf threshold {
      type string {
        length "0..8";
      }
      description
        "the threshold users set";
    }
    leaf tca-report {
      type boolean;
      description
        "enable/disable to report TCA";
    }
  }

  grouping PM-HO-VC-PARAMETER {
    description
      "pm one parameter";
    leaf data {
      type uint32;
      description
        "the number in the interval";
    }
    leaf threshold {
      type uint32;
      description
        "the threshold users set";
    }
    leaf tca-report {
      type boolean;
      description
        "enable/disable to report TCA";
    }
  }

  grouping HO-VC-ENTRY {
    description
      "HO VC ENTRY";
    container path-e-ss {
      description
        "The number of Errored Seconds";
      uses PM-HO-VC-PARAMETER;
    }
    container path-es-rs {
      description
        "The number of Errored Seconds";
      uses PM-HO-VC-PARAMETER-RATIO;
    }
    container path-se-ss {
      description
        "The number of Severely Errored Seconds";
      uses PM-HO-VC-PARAMETER;
    }
    container path-ses-rs {
      description
        "The number of Severely Errored Seconds";
      uses PM-HO-VC-PARAMETER-RATIO;
    }
    container path-e-bs {
      description
        "The number of Errored blocks";
      uses PM-HO-VC-PARAMETER;
    }
    container path-ua-ss {
      description
        "The number of Unavailable Seconds";
      uses PM-HO-VC-PARAMETER;
    }
    container path-bb-es {
      description
        "The number of background block errors";
      uses PM-HO-VC-PARAMETER;
    }
    container path-bbe-rs {
      description
        "The number of background block errors";
      uses PM-HO-VC-PARAMETER-RATIO;
    }
    leaf path-status {
      type int32;
      description
        " status of the interface";
    }
  }

  grouping PM-HO-VC-PARAS {
    description
      "all paras in ho_vc";
    container path {
      description
        "PATH";
      uses HO-VC-ENTRY;
    }
    container fe-path {
      description
        "Far End PATH";
      uses HO-VC-FAR-END-PATH-ENTRY;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear24-hr-time {
      type string {
        length "0..64";
      }
      description
        "last clear time";
    }
  }

  grouping PM-SECY-TX-PARAM {
    description
      "PM SECY TX PARAM";
    leaf data {
      type uint64;
      description
        "the number in the interval";
    }
    leaf threshold {
      type uint64;
      description
        "the threshold users set";
    }
    leaf tca-report {
      type boolean;
      description
        "enable/disable to report TCA";
    }
    leaf valid {
      type boolean;
      description
        "valid";
    }
  }

  grouping PM-SECY-TX-PARAS {
    description
      "PM SECY TX PARAS";
    container out-pkts-protected {
      description
        "Out Packets Protected";
      uses PM-SECY-TX-PARAM;
    }
    container out-pkts-encrypted {
      description
        "Out Packets Encrypted";
      uses PM-SECY-TX-PARAM;
    }
    container out-octets-protected {
      description
        "Out Octets Protected ";
      uses PM-SECY-TX-PARAM;
    }
    container out-octets-encrypted {
      description
        "Out Octets Encrypted";
      uses PM-SECY-TX-PARAM;
    }
    container out-pkts-too-long {
      description
        "Out Packets Too Long";
      uses PM-SECY-TX-PARAM;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear-flex-bin-time {
      type string {
        length "0..64";
      }
      description
        "last clear time";
    }
    leaf last-clear30-sec-time {
      type string {
        length "0..64";
      }
      description
        "last clear time";
    }
    leaf last-clear24-hr-time {
      type string {
        length "0..64";
      }
      description
        "last clear time";
    }
    leaf sec30-support {
      type boolean;
      description
        "30 sec support";
    }
    leaf flex-bin-support {
      type boolean;
      description
        "flex bin support";
    }
    leaf flex-bin-interval {
      type uint16;
      description
        "flex bin interval";
    }
    leaf sample-count {
      type uint64;
      description
        "Running Sample Count";
    }
  }

  grouping PM-SECY-RX-PARAM {
    description
      "PM SECY RX PARAM";
    leaf data {
      type uint64;
      description
        "the number in the interval";
    }
    leaf threshold {
      type uint64;
      description
        "the threshold users set";
    }
    leaf tca-report {
      type boolean;
      description
        "enable/disable to report TCA";
    }
    leaf valid {
      type boolean;
      description
        "valid";
    }
  }

  grouping PM-SECY-RX-PARAS {
    description
      "PM SECY RX PARAS";
    container in-pkts-unchecked {
      description
        "In Packet Unchecked";
      uses PM-SECY-RX-PARAM;
    }
    container in-pkts-delayed {
      description
        "In Packet Delay";
      uses PM-SECY-RX-PARAM;
    }
    container in-pkts-late {
      description
        "In Packet Late";
      uses PM-SECY-RX-PARAM;
    }
    container in-pkts-ok {
      description
        "In Packet Ok";
      uses PM-SECY-RX-PARAM;
    }
    container in-pkts-invalid {
      description
        "In Packet Invalid";
      uses PM-SECY-RX-PARAM;
    }
    container in-pkts-not-valid {
      description
        "In Packet Not Valid";
      uses PM-SECY-RX-PARAM;
    }
    container in-pkts-not-using-sa {
      description
        "In Packet Not Using SA";
      uses PM-SECY-RX-PARAM;
    }
    container in-pkts-unused-sa {
      description
        "In Packet Unused SA";
      uses PM-SECY-RX-PARAM;
    }
    container in-pkts-untagged-hit {
      description
        "In Packet Untagged Hit";
      uses PM-SECY-RX-PARAM;
    }
    container in-octets-validated {
      description
        "In Octet Validated";
      uses PM-SECY-RX-PARAM;
    }
    container in-octets-decrypted {
      description
        "In Octet Decrypted";
      uses PM-SECY-RX-PARAM;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear-flex-bin-time {
      type string {
        length "0..64";
      }
      description
        "last clear time";
    }
    leaf last-clear30-sec-time {
      type string {
        length "0..64";
      }
      description
        "last clear time";
    }
    leaf last-clear24-hr-time {
      type string {
        length "0..64";
      }
      description
        "last clear time";
    }
    leaf sec30-support {
      type boolean;
      description
        "30 sec support";
    }
    leaf flex-bin-support {
      type boolean;
      description
        "flex bin support";
    }
    leaf flex-bin-interval {
      type uint16;
      description
        "flex bin interval";
    }
    leaf sample-count {
      type uint64;
      description
        "Running Sample Count";
    }
  }

  grouping PM-SECY-IF-PARAM {
    description
      "PM SECY IF PARAM";
    leaf data {
      type uint64;
      description
        "the number in the interval";
    }
    leaf threshold {
      type uint64;
      description
        "the threshold users set";
    }
    leaf tca-report {
      type boolean;
      description
        "enable/disable to report TCA";
    }
    leaf valid {
      type boolean;
      description
        "valid";
    }
  }

  grouping PM-SECY-IF-PARAS {
    description
      "PM SECY IF PARAS";
    container in-pkts-untagged {
      description
        "In Packet Untagged";
      uses PM-SECY-IF-PARAM;
    }
    container in-pkts-no-tag {
      description
        "In Packet No tag";
      uses PM-SECY-IF-PARAM;
    }
    container in-pkts-bad-tag {
      description
        "In Packet Bad tag";
      uses PM-SECY-IF-PARAM;
    }
    container in-pkts-unknown-sci {
      description
        "In Packet Unknown sci";
      uses PM-SECY-IF-PARAM;
    }
    container in-pkts-no-sci {
      description
        "In Packet No sci";
      uses PM-SECY-IF-PARAM;
    }
    container in-pkts-overrun {
      description
        "In Packet Overrun";
      uses PM-SECY-IF-PARAM;
    }
    container in-octets-validated {
      description
        "In Octet Validated";
      uses PM-SECY-IF-PARAM;
    }
    container in-octets-decrypted {
      description
        "In Octet Decrypted";
      uses PM-SECY-IF-PARAM;
    }
    container out-pkts-untagged {
      description
        "Out Packet Untagged";
      uses PM-SECY-IF-PARAM;
    }
    container out-pkts-too-long {
      description
        "Out Packet Too Long";
      uses PM-SECY-IF-PARAM;
    }
    container out-octets-protected {
      description
        "Out Octet Protected";
      uses PM-SECY-IF-PARAM;
    }
    container out-octets-encrypted {
      description
        "Out Octet encrypted";
      uses PM-SECY-IF-PARAM;
    }
    leaf index {
      type uint32;
      description
        "index";
    }
    leaf valid {
      type boolean;
      description
        "valid";
    }
    leaf timestamp {
      type string {
        length "0..64";
      }
      description
        "timestamp";
    }
    leaf last-clear-time {
      type string {
        length "0..64";
      }
      description
        "last clear time";
    }
    leaf last-clear15-min-time {
      type string {
        length "0..64";
      }
      description
        "last clear time";
    }
    leaf last-clear-flex-bin-time {
      type string {
        length "0..64";
      }
      description
        "last clear time";
    }
    leaf last-clear30-sec-time {
      type string {
        length "0..64";
      }
      description
        "last clear time";
    }
    leaf last-clear24-hr-time {
      type string {
        length "0..64";
      }
      description
        "last clear time";
    }
    leaf sec30-support {
      type boolean;
      description
        "30 sec support";
    }
    leaf flex-bin-support {
      type boolean;
      description
        "flex bin support";
    }
    leaf flex-bin-interval {
      type uint16;
      description
        "flex bin interval";
    }
    leaf sample-count {
      type uint64;
      description
        "Running Sample Count";
    }
  }

  grouping PM-ETHER-PARAM-STRING {
    description
      "PM ETHER PARAM STRING";
    leaf data {
      type string;
      description
        "the number in the interval";
    }
    leaf threshold {
      type string;
      description
        "the threshold users set";
    }
    leaf tca-report {
      type boolean;
      description
        "enable/disable to report TCA";
    }
    leaf valid {
      type boolean;
      description
        "valid";
    }
  }

  grouping PM-ETHER-PARAM {
    description
      "PM ETHER PARAM";
    leaf data {
      type uint64;
      description
        "the number in the interval";
    }
    leaf threshold {
      type uint64;
      description
        "the threshold users set";
    }
    leaf tca-report {
      type boolean;
      description
        "enable/disable to report TCA";
    }
    leaf valid {
      type boolean;
      description
        "valid";
    }
  }

  grouping PM-ETHERNET-PARAS {
    description
      "all paras in ether";
    container rx-pkt {
      description
        "RX PKT";
      uses PM-ETHER-PARAM;
    }
    container stat-pkt {
      description
        "STAT PKT";
      uses PM-ETHER-PARAM;
    }
    container octet-stat {
      description
        "OCTET STAT";
      uses PM-ETHER-PARAM;
    }
    container oversize-pkt-stat {
      description
        "OVERSIZE PKT";
      uses PM-ETHER-PARAM;
    }
    container fcs-errors-stat {
      description
        "FCS ERR";
      uses PM-ETHER-PARAM;
    }
    container long-frames-stat {
      description
        "LONG FRAMES";
      uses PM-ETHER-PARAM;
    }
    container jabber-stat {
      description
        "JABBER STATS";
      uses PM-ETHER-PARAM;
    }
    container ether64-octets {
      description
        "SIXTY FOUR OCTET";
      uses PM-ETHER-PARAM;
    }
    container ether65127-octet {
      description
        "OCTET";
      uses PM-ETHER-PARAM;
    }
    container ether128255-octet {
      description
        "TFF OCTET";
      uses PM-ETHER-PARAM;
    }
    container ether256511-octet {
      description
        "FOO OCTET";
      uses PM-ETHER-PARAM;
    }
    container ether5121023-octet {
      description
        "OZTT OCTET";
      uses PM-ETHER-PARAM;
    }
    container ether10241518-octet {
      description
        "OFO OCTET";
      uses PM-ETHER-PARAM;
    }
    container in-ucast-pkt {
      description
        "IN UCAST";
      uses PM-ETHER-PARAM;
    }
    container in-mcast-pkt {
      description
        "IN MCAST";
      uses PM-ETHER-PARAM;
    }
    container in-bcast-pkt {
      description
        "IN BCAST";
      uses PM-ETHER-PARAM;
    }
    container out-ucast-pkt {
      description
        "OUT UCAST";
      uses PM-ETHER-PARAM;
    }
    container out-bcast-pkt {
      description
        "OUT BCAST";
      uses PM-ETHER-PARAM;
    }
    container out-mcast-pkt {
      description
        "OUT MCAST";
      uses PM-ETHER-PARAM;
    }
    container tx-pkt {
      description
        "TX PKT";
      uses PM-ETHER-PARAM;
    }
    container if-in-errors {
      description
        "IFIN ERRORS";
      uses PM-ETHER-PARAM;
    }
    container if-in-octets {
      description
        "IFIN OCTETS";
      uses PM-ETHER-PARAM;
    }
    container ether-stat-multicast-pkt {
      description
        "ETHER STAT MULTICAST PKT";
      uses PM-ETHER-PARAM;
    }
    container ether-stat-broadcast-pkt {
      description
        "ETHER STAT BROADCAST PKT";
      uses PM-ETHER-PARAM;
    }
    container ether-stat-undersized-pkt {
      description
        "ETHER STAT UNDERSIZED PKT";
      uses PM-ETHER-PARAM;
    }
    container out-octets {
      description
        "OUT OCTET";
      uses PM-ETHER-PARAM;
    }
    container in-pause-frame {
      description
        "INPUT PAUSE FRAME";
      uses PM-ETHER-PARAM;
    }
    container in-good-bytes {
      description
        "INPUT GOOD BYTES";
      uses PM-ETHER-PARAM;
    }
    container in8021q-frames {
      description
        "INPUT 802 1Q FRAMES";
      uses PM-ETHER-PARAM;
    }
    container in-pkts1519-max-octets {
      description
        "INPUT PKTS 1519MAX OCTETS";
      uses PM-ETHER-PARAM;
    }
    container in-good-pkts {
      description
        "INPUT GOOD PKTS";
      uses PM-ETHER-PARAM;
    }
    container in-drop-overrun {
      description
        "INPUT DROP OVERRUN";
      uses PM-ETHER-PARAM;
    }
    container in-drop-abort {
      description
        "INPUT DROP ABORT";
      uses PM-ETHER-PARAM;
    }
    container in-drop-invalid-vlan {
      description
        "INPUT DROP INVALID VLAN";
      uses PM-ETHER-PARAM;
    }
    container in-drop-invalid-dmac {
      description
        "INPUT DROP INVALID DMAC";
      uses PM-ETHER-PARAM;
    }
    container in-drop-invalid-encap {
      description
        "INPUT DROP INVALID ENCAP";
      uses PM-ETHER-PARAM;
    }
    container in-drop-other {
      description
        "INPUT DROP OTHER";
      uses PM-ETHER-PARAM;
    }
    container in-mib-giant {
      description
        "INPUT MIB GIANT";
      uses PM-ETHER-PARAM;
    }
    container in-mib-jabber {
      description
        "INPUT MIB JABBER";
      uses PM-ETHER-PARAM;
    }
    container in-mibcrc {
      description
        "IN MIB CRC";
      uses PM-ETHER-PARAM;
    }
    container in-error-collisions {
      description
        "IN ERROR COLLISIONS";
      uses PM-ETHER-PARAM;
    }
    container in-error-symbol {
      description
        "IN ERROR SYMBOL";
      uses PM-ETHER-PARAM;
    }
    container out-good-bytes {
      description
        "OUT GOOD BYTES";
      uses PM-ETHER-PARAM;
    }
    container out8021q-frames {
      description
        "OUT 802 1Q FRAMES";
      uses PM-ETHER-PARAM;
    }
    container out-pause-frames {
      description
        "OUT PAUSE FRAMES";
      uses PM-ETHER-PARAM;
    }
    container out-pkts1519-max-octets {
      description
        "OUT PKTS 1519 MAX OCTETS";
      uses PM-ETHER-PARAM;
    }
    container out-good-pkts {
      description
        "OUT GOOD PKTS";
      uses PM-ETHER-PARAM;
    }
    container out-drop-underrun {
      description
        "OUT DROP UNDERRUN";
      uses PM-ETHER-PARAM;
    }
    container out-drop-abort {
      description
        "OUT DROP ABORT";
      uses PM-ETHER-PARAM;
    }
    container out-drop-other {
      description
        "OUT DROP OTHER";
      uses PM-ETHER-PARAM;
    }
    container out-error-other {
      description
        "OUT ERROR OTHER";
      uses PM-ETHER-PARAM;
    }
    container in-error-giant {
      description
        "IN ERROR GIANT";
      uses PM-ETHER-PARAM;
    }
    container in-error-runt {
      description
        "IN ERROR RUNT";
      uses PM-ETHER-PARAM;
    }
    container in-error-jabbers {
      description
        "IN ERROR JABBERS";
      uses PM-ETHER-PARAM;
    }
    container in-error-fragments {
      description
        "IN ERROR FRAGMENTS";
      uses PM-ETHER-PARAM;
    }
    container in-error-other {
      description
        "IN ERROR OTHER";
      uses PM-ETHER-PARAM;
    }
    container in-pkt64-octet {
      description
        "IN PKT 64 OCTET";
      uses PM-ETHER-PARAM;
    }
    container in-pkts65-to127-octets {
      description
        "IN PKTS 65 127OCTETS";
      uses PM-ETHER-PARAM;
    }
    container in-pkts128-to255-octets {
      description
        "IN PKTS 128 255 OCTETS";
      uses PM-ETHER-PARAM;
    }
    container in-pkts256-to511-octets {
      description
        "IN PKTS 256 511 OCTETS";
      uses PM-ETHER-PARAM;
    }
    container in-pkts512-to1023-octets {
      description
        "IN PKTS 512 1023 OCTETS";
      uses PM-ETHER-PARAM;
    }
    container in-pkts1024-to1518-octets {
      description
        "IN PKTS 1024 1518 OCTETS";
      uses PM-ETHER-PARAM;
    }
    container outpkt64octet {
      description
        "OUT PKT 64 OCTET";
      uses PM-ETHER-PARAM;
    }
    container out-pkts65127-octets {
      description
        "OUT PKTS 65 127OCTETS";
      uses PM-ETHER-PARAM;
    }
    container out-pkts128255-octets {
      description
        "OUT PKTS 128 255 OCTETS";
      uses PM-ETHER-PARAM;
    }
    container out-pkts256511-octets {
      description
        "OUT PKTS 256 511 OCTETS";
      uses PM-ETHER-PARAM;
    }
    container out-pkts5121023-octets {
      description
        "OUT PKTS 512 1023 OCTETS";
      uses PM-ETHER-PARAM;
    }
    container out-pkts10241518-octets {
      description
        "OUT PKTS 1024 1518 OCTETS";
      uses PM-ETHER-PARAM;
    }
    container rx-util {
      description
        "Rx Utilization in Percent";
      uses PM-ETHER-PARAM-STRING;
    }
    container tx-util {
      description
        "Tx Utilization in Percent";
      uses PM-ETHER-PARAM-STRING;
    }
    container tx-undersized-pkt {
      description
        "TX Undersized Pkt";
      uses PM-ETHER-PARAM;
    }
    container tx-oversized-pkt {
      description
        "TX Oversized Pkt";
      uses PM-ETHER-PARAM;
    }
    container tx-fragments {
      description
        "TX Fragments";
      uses PM-ETHER-PARAM;
    }
    container tx-jabber {
      description
        "TX Jabber";
      uses PM-ETHER-PARAM;
    }
    container tx-bad-fcs {
      description
        "TX Bad Fcs";
      uses PM-ETHER-PARAM;
    }
    leaf index {
      type uint32;
      description
        "index";
    }
    leaf valid {
      type boolean;
      description
        "valid";
    }
    leaf timestamp {
      type string {
        length "0..64";
      }
      description
        "timestamp";
    }
    leaf last-clear-time {
      type string;
      description
        "last clear time";
    }
    leaf last-clear-flex-bin-time {
      type string;
      description
        "last clear time";
    }
    leaf last-clear30-sec-time {
      type string;
      description
        "last clear time";
    }
    leaf last-clear15-min-time {
      type string;
      description
        "last clear time";
    }
    leaf last-clear24-hr-time {
      type string;
      description
        "last clear time";
    }
    leaf flex-bin-support {
      type boolean;
      description
        "flex bin support";
    }
    leaf flex-bin-interval {
      type uint16;
      description
        "flex bin interval";
    }
    leaf sec30-support {
      type boolean;
      description
        "30 sec support";
    }
  }
}
