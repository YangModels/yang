submodule Cisco-IOS-XR-mpls-te-oper-sub6 {
  belongs-to Cisco-IOS-XR-mpls-te-oper {
    prefix Cisco-IOS-XR-mpls-te-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR mpls-te package operational data.
     
     Copyright (c) 2013-2025 by Cisco Systems, Inc.
     All rights reserved.";

  revision 2025-06-02 {
    description
      "Added the backup local label to the label rewrite database
       2025-05-28
         Added path-error hops in the PCE log
       2025-03-26
         Added head end down and admin down to the tunnel summary info
       2025-01-09
         Added autoroute-announce-ipv6-destination under announce-tunnels-info
       2024-11-28
         Modified PCE log
       2024-10-28
         Added PCE log
       2024-10-22
         Removed mpls-pce/tunnels
       2024-10-02
         Added PCE total success and failed computations
       2024-09-30
         Enhanced s2l-output-rewrite timestamps to uint64_t from uint32_t
       2024-09-22
         Added interface handle under link information
       2024-07-20
         Changed link bandwidth related leafs to support displaying 64 bit bandwidths
       2024-07-09
         Added path hop SRLG info
       2024-03-06
         Path protection enhancements
       2024-02-14
         Added metric for forwarding adjacency
       2023-12-12
         Added auto-bw and soft-preemption to p2mp-te attribute-set
       2023-10-10
         Added source address to configured P2MP tunnel data
       2023-07-05
         Add knob to configure Autoroute Announce exclude all SR traffic
       2023-06-19
         Added flooding reason stats
       2023-04-24
         Add back TunnelAttributeSetStatic for backward compatibility
       2023-02-02
         Remove hidden commands
       2022-11-07
         Add TE++ over numbered tunnel feature
       2022-08-30
         Extending self-ping statistics bag
       2022-07-07
         Removed TunnelAttributeSetStatic from TunnelAttributeSetType
       2022-03-18
         Added self-ping under named-tunnels";
    semver:module-version "2.0.0";
  }
  revision 2021-08-09 {
    description
      "Added load-interval attribute in the tunnel class. IosSetYangSchemaRev Cisco-IOS-XR-mpls-te-oper";
    semver:module-version "1.2.0";
  }
  revision 2021-01-19 {
    description
      "Added bandwidth-protection for auto-backups. Added signalled-bandwidth and soft-preemption for attribute set of autobackups.
       2020-11-05
           Added secondary router id for TE nodes.";
    semver:module-version "1.1.0";
  }
  revision 2020-03-28 {
    description
      "Added dark bandwidth accounting related oper info. Added stateful PCE static delegation related oper info. Added P2MP TE realted oper info. Added new operational leaves sim-rate-set sim-rate pce-address rewrite-lsd-queue tunnel-id-xr controller-handle backup-tunnel-sig-name protected-interface attribute-set-crc32 error delegation-status error context rewrite-lsd-queue simrate-enabled-in-last-application tunnel-id-xr p2mp-id-xr lsp-id-xr source-address-xr simrate-enabled-in-last-application is-expand-timer-running expand-timer-duration expand-timer-remain egress-interface-handle ingress-interface-handle srdb-check-enabled destination-create-time link-if-index create-time is-config-pending attribute-set-crc32 destination-list-crc32 maximum-destination-count maximum-tunnel-count srlg-number-xr tunnel-interface-name lsp-id-xr tunnel-rewrite-ctype tunnel-load-share tunnel-policy-class tunnel-forward-class lmp-is-allocated topology-node-igp-id topology-node-igp-area topology-node-is-router link-id classification-flags current-lsp-bandwidth-requested current-lsp-bandwidth-requested-type standby-lsp-bandwidth-requested standby-lsp-bandwidth-requested-type reopt-lsp-bandwidth-requested reopt-lsp-bandwidth-requested-type standby-reopt-lsp-bandwidth-requested standby-reopt-lsp-bandwidth-requested-type destination-address error tunnel-name-xr interface-name-xr interface-name";
    semver:module-version "1.0.0";
  }
  revision 2019-04-05 {
    description
      "Establish semantic version baseline.";
    semver:module-version "1.0.0";
  }
  revision 2018-08-01 {
    description
      "Removed empty groupings.";
  }
  revision 2017-09-07 {
    description
      "Fixed type translation error.";
  }
  revision 2017-05-01 {
    description
      "Fixing backward compatibility error in module.";
  }
  revision 2015-11-09 {
    description
      "IOS XR 6.0 revision.";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef Igpte-link-encoding-protocol {
    type enumeration {
      enum "link-encoding-protocol-none" {
        value 0;
        description
          "None";
      }
      enum "link-encoding-protocol-p-acket" {
        value 1;
        description
          "Packet";
      }
      enum "link-encoding-protocol-ethernet" {
        value 2;
        description
          "Ethernet";
      }
      enum "link-encoding-protocol-ansi-etsi-pdh" {
        value 3;
        description
          "ANSI ETSI PDH";
      }
      enum "link-encoding-protocol-reserved4" {
        value 4;
        description
          "Reserved";
      }
      enum "link-encoding-protocol-sdh-sonet" {
        value 5;
        description
          "SDH SONET";
      }
      enum "link-encoding-protocol-reserved6" {
        value 6;
        description
          "Reserved";
      }
      enum "link-encoding-protocol-digital-wrapper" {
        value 7;
        description
          "Digital Wrapper";
      }
      enum "link-encoding-protocol-lambda-photonic" {
        value 8;
        description
          "Lambda Photonic";
      }
      enum "link-encoding-protocol-fiber" {
        value 9;
        description
          "Fiber";
      }
      enum "link-encoding-protocol-reserved10" {
        value 10;
        description
          "Reserved";
      }
      enum "link-encoding-protocol-fiber-channel" {
        value 11;
        description
          "Fiber Channel";
      }
      enum "link-encoding-protocol-g709otn" {
        value 12;
        description
          "G709 OTN";
      }
      enum "link-encoding-protocol-ethernet-type2" {
        value 14;
        description
          "Ethernet Type 2";
      }
      enum "link-encoding-protocol-passive-internal" {
        value 200;
        description
          "Derived from ingress node";
      }
    }
    description
      "Link protocol switching capabilities";
  }

  typedef Igpte-link-switch-capability {
    type enumeration {
      enum "link-switching-capability-none" {
        value 0;
        description
          "None";
      }
      enum "link-switching-capability-psc1" {
        value 1;
        description
          "Packet (level 1)";
      }
      enum "link-switching-capability-psc2" {
        value 2;
        description
          "Packet (level 2)";
      }
      enum "link-switching-capability-psc3" {
        value 3;
        description
          "Packet (level 3)";
      }
      enum "link-switching-capability-psc4" {
        value 4;
        description
          "Packet (level 4)";
      }
      enum "link-switching-capability-l2sc" {
        value 51;
        description
          "Layer 2";
      }
      enum "link-switching-capability-tdm" {
        value 100;
        description
          "TDM";
      }
      enum "link-switching-capability-otn-tdm" {
        value 110;
        description
          "OTN TDM";
      }
      enum "link-switching-capability-dcsc" {
        value 125;
        description
          "DCSC";
      }
      enum "link-switching-capability-lsc" {
        value 150;
        description
          "LSC";
      }
      enum "link-switching-capability-fsc" {
        value 200;
        description
          "FSC";
      }
    }
    description
      "Link protocol switching capabilities";
  }

  typedef Otu {
    type enumeration {
      enum "non-otu" {
        description
          "Type Non OTU";
      }
      enum "otu1" {
        description
          "Type OTU1";
      }
      enum "otu1e" {
        description
          "Type OTU1E";
      }
      enum "otu1f" {
        description
          "Type OTU1F";
      }
      enum "otu2" {
        description
          "Type OTU2";
      }
      enum "otu3" {
        description
          "Type 0TU3";
      }
      enum "otu4" {
        description
          "Type OTU4";
      }
      enum "otu2e" {
        description
          "Type OTU2E";
      }
      enum "otu2f" {
        description
          "Type OTU2F";
      }
      enum "otu3e1" {
        description
          "Type OTU3E1";
      }
      enum "otu3e2" {
        description
          "Type OTU3E2";
      }
      enum "otuc2" {
        description
          "Type OTUC2";
      }
      enum "otuc4" {
        description
          "Type OTUC4";
      }
    }
    description
      "OTU types";
  }

  typedef Te-affinity-table {
    type enumeration {
      enum "affinity-table-mapping" {
        value 0;
        description
          "Mapping affinity table";
      }
      enum "affinity-table-forward-reference" {
        value 1;
        description
          "Forward reference affinity table";
      }
      enum "affinity-table-count" {
        value 2;
        description
          "Number of affinity tables";
      }
    }
    description
      "Affinity Table IDs";
  }

  typedef Te-serv-tun-client {
    type enumeration {
      enum "te-serv-auto-tun-client-invalid" {
        description
          "te serv auto tun client invalid";
      }
      enum "te-serv-p2mp-tun-client-mvpn" {
        description
          "te serv p2mp tun client mvpn";
      }
      enum "te-serv-p2mp-tun-client-vpls" {
        description
          "te serv p2mp tun client vpls";
      }
      enum "te-serv-p2mp-tun-client-mvpn6" {
        description
          "te serv p2mp tun client mvpn6";
      }
      enum "te-serv-p2p-tun-client-bgp" {
        description
          "te serv p2p tun client bgp";
      }
      enum "te-serv-p2p-tun-client-staticv4" {
        description
          "te serv p2p tun client staticv4";
      }
      enum "te-serv-p2p-tun-client-staticv6" {
        description
          "te serv p2p tun client staticv6";
      }
      enum "te-serv-p2p-tun-client-isis" {
        description
          "te serv p2p tun client isis";
      }
      enum "te-serv-p2p-tun-client-ospf" {
        description
          "te serv p2p tun client ospf";
      }
      enum "te-serv-auto-tun-client-count" {
        description
          "te serv auto tun client count";
      }
    }
    description
      "Te serv tun client";
  }

  typedef Igpte-aa-metric-mode {
    type enumeration {
      enum "metric-mode-none" {
        description
          "No metric type specified";
      }
      enum "relative" {
        description
          "Relative metric";
      }
      enum "absolute" {
        description
          "Absolute metric";
      }
      enum "constant" {
        description
          "Constant metric";
      }
    }
    description
      "Autoroute-announce metric type";
  }

  typedef Te-odu-capability {
    type enumeration {
      enum "not-set" {
        description
          "Odu capability Type Not Set";
      }
      enum "fixed" {
        description
          "Fixed ODUs";
      }
      enum "flex" {
        description
          "Flex ODUs";
      }
    }
    description
      "Te ODU Capability Types";
  }

  typedef Rrr-dste-migration-mode {
    type enumeration {
      enum "rrr-dste-mode-none" {
        value 0;
        description
          "No DSTE mode set";
      }
      enum "rrr-dste-mode-prestandard" {
        value 1;
        description
          "Pre-standard DSTE";
      }
      enum "rrr-dste-mode-standard" {
        value 3;
        description
          "IETF-standard DSTE";
      }
    }
    description
      "DS-TE migration mode";
  }

  typedef Igpte-lib-bw-model {
    type enumeration {
      enum "rdm" {
        value 0;
        description
          "Russian Dolls Model";
      }
      enum "mam" {
        value 1;
        description
          "Maximum Allocation Model";
      }
      enum "not-set" {
        value 2;
        description
          "No model set";
      }
    }
    description
      "Bandwidth model";
  }

  typedef Igp-subnet {
    type enumeration {
      enum "igp-subnet-type-none" {
        description
          "No subnet type specified";
      }
      enum "p2p" {
        description
          "Point-to-point subnet";
      }
      enum "broadcast" {
        description
          "Broadcast subnet";
      }
      enum "non-broadcast-multiaccess" {
        description
          "Non-broadcast multi-access subnet";
      }
      enum "p2mp" {
        description
          "Point-to-multipoint subnet";
      }
      enum "loopback" {
        description
          "Loopback subnet";
      }
    }
    description
      "Subnet type";
  }

  typedef Igp-ospf-area-format {
    type enumeration {
      enum "igp-area-format-number" {
        description
          "Numbered area format";
      }
      enum "igp-area-format-ip-addr" {
        description
          "IP address area format";
      }
    }
    description
      "OSPF area format";
  }

  typedef Igp-protocol {
    type enumeration {
      enum "none" {
        description
          "No IGP protocol specified";
      }
      enum "isis" {
        description
          "IS IS";
      }
      enum "ospf" {
        description
          "OSPF";
      }
    }
    description
      "IGP type";
  }

  typedef Mpls-te-uni {
    type enumeration {
      enum "none" {
        description
          "Uni-Type none";
      }
      enum "xc" {
        description
          "Uni-Type type XC";
      }
      enum "term" {
        description
          "Uni-Type Termination";
      }
    }
    description
      "Uni-Type type";
  }

  typedef Mpls-te-termination {
    type enumeration {
      enum "none" {
        description
          "Local termination none";
      }
      enum "ether" {
        description
          "Local termination type Ether";
      }
    }
    description
      "Termination type";
  }

  typedef Te-meshgroup {
    type enumeration {
      enum "meshgroup-type-automesh" {
        value 0;
        description
          "automesh type of Meshgroup";
      }
      enum "meshgroup-type-onehop" {
        value 1;
        description
          "onehop type of Meshgroup";
      }
    }
    description
      "Te meshgroup";
  }

  typedef Auto-backup-srlg-mode {
    type enumeration {
      enum "srlg-not-set" {
        description
          "Autobackup SRLG type not set";
      }
      enum "srlg-strict" {
        description
          "Autobackup SRLG Strict";
      }
      enum "srlg-preferred" {
        description
          "Autobackup SRLG Preferred";
      }
      enum "srlg-weighted" {
        description
          "Autobackup Weighted SRLG";
      }
    }
    description
      "Auto backup srlg mode";
  }

  typedef Auto-backup-protection {
    type enumeration {
      enum "protection-none" {
        description
          "No Autobackup Protection";
      }
      enum "protection-next-hop" {
        description
          "NHOP Autobackup Protection";
      }
      enum "protection-next-next-hop" {
        description
          "NNHOP Autobackup Protection";
      }
      enum "protection-next-hop-bandwidth" {
        description
          "NHOP Autobackup Protection";
      }
      enum "protection-next-next-hop-bandwidth" {
        description
          "NNHOP Autobackup Protection";
      }
    }
    description
      "Auto backup protection";
  }

  typedef Te-p2mp-s2l-deletion-subcause {
    type enumeration {
      enum "no-subcause" {
        description
          "No subcause recorded";
      }
      enum "cleanup-req" {
        description
          "Normal cleanup requested";
      }
      enum "invalid-data" {
        description
          "Invalid Data passed";
      }
      enum "fsm-inv-ctxt" {
        description
          "Invalid FSM context passed in";
      }
      enum "fsm-inv-ctxt-data" {
        description
          "Invalid data passed in FSM context";
      }
      enum "fsm-inv-role" {
        description
          "Failed due to Invalid Role";
      }
      enum "ll-failure" {
        description
          "Local Label get failed";
      }
      enum "ll-rel-fail" {
        description
          "Local Label release failed";
      }
      enum "ll-mismatch" {
        description
          "Local label mismatch detected";
      }
      enum "ll-invalid" {
        description
          "Local label invalid";
      }
      enum "ll-set-failure" {
        description
          "Local Label set failed";
      }
      enum "bad-out-label" {
        description
          "Bad label received from neighbor";
      }
      enum "sl-err" {
        description
          "Failed to process suggested label received from
           neighbor";
      }
      enum "rl-mismatch" {
        description
          "Incorrect recovery label received from neighbor";
      }
      enum "sl-alloc-err" {
        description
          "Failed to allocate suggested/ acceptable label";
      }
      enum "upstream-downstream-label-mismatch" {
        description
          "Upstream label does not match downstream label";
      }
      enum "upstream-label-failure" {
        description
          "Upstream Label get failed";
      }
      enum "upstream-label-rel-fail" {
        description
          "Upstream Label release failed";
      }
      enum "upstream-label-mismatch" {
        description
          "Upstream label mismatch detected";
      }
      enum "upstream-label-invalid" {
        description
          "Upstream label invalid";
      }
      enum "bad-upstream-label" {
        description
          "Bad Upstream label";
      }
      enum "ul-set-failure" {
        description
          "Upstream Label set failed";
      }
      enum "gmpls-label-alloc-err" {
        description
          "Failed to allocate GMPLS Label";
      }
      enum "gmpls-label-clone-err" {
        description
          "Failed to clone GMPLS Label";
      }
      enum "rw-err" {
        description
          "Unable to perform RW operation";
      }
      enum "up-rw-err" {
        description
          "Unable to perform upstream RW operation";
      }
      enum "path-admit" {
        description
          "Path admission failure";
      }
      enum "bw" {
        description
          "BW allocation failure";
      }
      enum "admit-resv" {
        description
          "Reservation admission failure";
      }
      enum "rrrm-err" {
        description
          "Resource Reservation removal error";
      }
      enum "hardware-out-of-resources" {
        description
          "NPU HW-OOR";
      }
      enum "comp-rid" {
        description
          "Failure to compute RID";
      }
      enum "comp-lcl-rid" {
        description
          "Failure to compute local RID";
      }
      enum "comp-up-rid" {
        description
          "Failure to compute upstream RID";
      }
      enum "comp-down-rid" {
        description
          "Failure to compute downstream RID";
      }
      enum "rest-if-hop" {
        description
          "Failure to reset IF or HOP";
      }
      enum "inv-in-if" {
        description
          "Invalid Ingress IF";
      }
      enum "nh-err" {
        description
          "Outgoing IF or Next Hop failure";
      }
      enum "inv-in-ero" {
        description
          "Invalid incoming ERO";
      }
      enum "out-ero-fail" {
        description
          "Outcoming ERO failure";
      }
      enum "frr-bk-asssign" {
        description
          "Frr backup assignment failure";
      }
      enum "frr-bk-rm" {
        description
          "Frr backup removal failure";
      }
      enum "frr-bk-send" {
        description
          "Frr backup send to RSVP failed";
      }
      enum "frr-needs-del" {
        description
          "FRR deletion required";
      }
      enum "frr-reopt-lsp" {
        description
          "FRR not allowed on reopt LSP";
      }
      enum "rsvp-api-h" {
        description
          "RSVP API Handler Failure";
      }
      enum "insane-path" {
        description
          "Invalid Path message";
      }
      enum "remerge-chk-fail" {
        description
          "Failed in finding remerge";
      }
      enum "remerge-detected" {
        description
          "Remerge detected";
      }
      enum "xro" {
        description
          "XRO processing failed";
      }
      enum "resv-bw-set" {
        description
          "Failed to set Resv Bandwidth";
      }
      enum "resv-prep-fail" {
        description
          "Failed to prepare out Resv";
      }
      enum "path-ch-proc" {
        description
          "Failure in path change Processing";
      }
      enum "path-ch-frr" {
        description
          "Failure in path change for FRR";
      }
      enum "path-ch-sess-attri-fl" {
        description
          "Failure in path change for session attribute
           flags";
      }
      enum "path-ch-bw-ch" {
        description
          "Failure in path change: Bandwidth change not
           allowed";
      }
      enum "path-err-proc" {
        description
          "Failure in path Error Processing";
      }
      enum "path-err" {
        description
          "Path Error Rcvd";
      }
      enum "path-err-wpsr" {
        description
          "Path Error with PSR flag Rcvd";
      }
      enum "path-del" {
        description
          "Path Delete request";
      }
      enum "resv-ch-proc" {
        description
          "Failure in Resv change processing";
      }
      enum "resv-ch-rro" {
        description
          "Failure in Resv change RRO";
      }
      enum "resv-del" {
        description
          "Resv Delete processing";
      }
      enum "resv-err" {
        description
          "Resv Error processing";
      }
      enum "perr-send-fail" {
        description
          "Failed to send Path Error";
      }
      enum "perr-proc-fail" {
        description
          "Failed to process Path Error";
      }
      enum "perr-rcv" {
        description
          "Received Path Error";
      }
      enum "resv-err-rcv" {
        description
          "Received Resv Error";
      }
      enum "flowspec" {
        description
          "Flowspec failure";
      }
      enum "setup-conn-api-fail" {
        description
          "S2L State set API failed";
      }
      enum "path-not-replayed" {
        description
          "RSVP did not replay the path";
      }
      enum "resv-not-replayed" {
        description
          "RSVP did not replay the resv";
      }
      enum "rewrite-not-replayed" {
        description
          "LMRIB did not replay rewrite";
      }
      enum "label-not-replayed" {
        description
          "RW mgr did not replay rewrite";
      }
      enum "connection-not-ready" {
        description
          "TE connection is not ready with LSD/LMRIB/RSVP";
      }
      enum "master-did-not-replay" {
        description
          "The master TE did not replay this S2L";
      }
      enum "head-s2l-has-no-vif" {
        description
          "S2L head has no associated tunnel VIF";
      }
      enum "frr-assigned-s2l-has-no-backup" {
        description
          "FRR-assigned S2L has no backup";
      }
      enum "frr-assigned-s2l-has-down-backup" {
        description
          "FRR-assigned S2L has down backup";
      }
      enum "out-link-down-and-no-frr" {
        description
          "Outgoing link is down and there is no FRR";
      }
      enum "collaborator-timeout-rsvp" {
        description
          "RSVP connection timed out";
      }
      enum "collaborator-timeout-lsd" {
        description
          "LSD connection timed out";
      }
      enum "collaborator-timeout-lmrib" {
        description
          "LMRIB connection time dout";
      }
      enum "collaborator-timeout-im" {
        description
          "IM connection timed out";
      }
      enum "collaborator-timeout-error" {
        description
          "Error in processing connection timeout";
      }
      enum "topo-flush" {
        description
          "Topology Failure";
      }
      enum "area-shut" {
        description
          "IGP Area Shutdown";
      }
      enum "active-po-del" {
        description
          "active pathoption deleted";
      }
      enum "path-verify-failed" {
        description
          "Path verification failed";
      }
      enum "srlg-path-verify-failed" {
        description
          "Srlg Path verification failed";
      }
      enum "affinity-path-verify-failed" {
        description
          "Affinity Path verification failed";
      }
      enum "aff-fail-delayed-tear-timeout-failed" {
        description
          "Affinity Failure Delayed Tear timeout failed";
      }
      enum "cost-limit-verify-failed" {
        description
          "Cost Limit verification failed";
      }
      enum "delay-limit-verify-failed" {
        description
          "Delay Limit verification failed";
      }
      enum "lockout-metric-verify-failed" {
        description
          "Lockout metric verification failed";
      }
      enum "path-setup-timeout" {
        description
          "Path Setup Timed out";
      }
      enum "vif-destroyed" {
        description
          "tunnel IF destroyed";
      }
      enum "vif-shut" {
        description
          "tunnel IF shutdown";
      }
      enum "lsp-shut" {
        description
          "LSP shutdown";
      }
      enum "gmpls-uni-head" {
        description
          "link configured to run as GMPLS-UNI head";
      }
      enum "head-resetup" {
        description
          "tunnel is to be resetup";
      }
      enum "none-head-resetup" {
        description
          "mid or tail tunnel is to be resetup";
      }
      enum "dest-disabled" {
        description
          "Destination disabled";
      }
      enum "iep-ch-act-po" {
        description
          "Explicit Path changed for inuse path-option";
      }
      enum "iep-ch-reopt" {
        description
          "Reopt LSP affected by Explicit Path change";
      }
      enum "iep-ch-standby" {
        description
          "Standby LSP affected by Explicit Path change";
      }
      enum "dste-mode-ch" {
        description
          "DSTE mode change";
      }
      enum "reopt-del-frr-act" {
        description
          "Deleting reopt LSP on FRR active";
      }
      enum "new-reopt-tear-old" {
        description
          "New Reopt is in progress, tearing old reopt LSP";
      }
      enum "reopt-failed-verify" {
        description
          "Reopt LSP failed verification";
      }
      enum "reopt-failed-install" {
        description
          "Reopt LSP failed at install time";
      }
      enum "reopt-failed-rw" {
        description
          "Rewrite failed for Reopt LSP";
      }
      enum "reopt-failed-not-superset" {
        description
          "Reopt LSP has less number of destinations Up
           than the current LSP.";
      }
      enum "dclean-at-install-time" {
        description
          "Tear delayed clean LSP at install time";
      }
      enum "dclean-at-clean-timer" {
        description
          "Tear delayed clean LSP at cleanup timer expiry";
      }
      enum "dclean-at-reopt-active" {
        description
          "Tear delayed clean LSP at Reopt Activation";
      }
      enum "lcl-notif-head" {
        description
          "Local Link Failure";
      }
      enum "in-if-fail" {
        description
          "Failure of ingress IF";
      }
      enum "out-if-fail" {
        description
          "Failure of egress IF";
      }
      enum "if-fail-lc-oir" {
        description
          "Failure of IF on LC OIR";
      }
      enum "te-rid-rm" {
        description
          "TE RID removed";
      }
      enum "te-rsvp-oos-bkup" {
        description
          "TE and RSVP are OOS for backup assignment";
      }
      enum "in-if-fail-exp-null-cfg-ch" {
        description
          "Explicit null config changed";
      }
      enum "new-curr-lsp-sig" {
        description
          "Signaling new current LSP, cleanup old LSP";
      }
      enum "new-reopt-lsp-sig" {
        description
          "Signaling new reopt LSP, cleanup old LSP";
      }
      enum "new-stdby-lsp-sig" {
        description
          "Signaling new standby LSP, cleanup old LSP";
      }
      enum "new-restore-lsp-sig" {
        description
          "Signaling new restore LSP, cleanup old LSP";
      }
      enum "new-cl-pp-lsp-sig" {
        description
          "Signaling new clean path-protect LSP, cleanup
           old LSP";
      }
      enum "chkpt-recovery-failed" {
        description
          "Failed to recover LSP from check-point";
      }
      enum "stdby-cr-failed" {
        description
          "Failed to create standby LSP";
      }
      enum "reopt-lsp-rej" {
        description
          "Reopt LSP is rejected";
      }
      enum "reopt-po-sw-failed" {
        description
          "Reopt Path-option switchover failed";
      }
      enum "failed-to-find-path" {
        description
          "Failed to find a Path";
      }
      enum "sig-rcv-fail-path-cr-ch" {
        description
          "Signaling API failed to proc Path change or
           create";
      }
      enum "lsp-db-shut" {
        description
          "LSP database shutdown";
      }
      enum "reopt-hold-start" {
        description
          "Starting holddown for Reopt LSP";
      }
      enum "vif-lspid-mismatch" {
        description
          "VIF has no LSP with this ID";
      }
      enum "s2l-has-no-vif" {
        description
          "Headend S2L with no associated VIF";
      }
      enum "overload-reopt-timeout" {
        description
          "Reoptimization timeout with OL-bit set at
           midpoint";
      }
      enum "hop-limit-exceeded" {
        description
          "Hop Limit Exceeded";
      }
      enum "lingering-current-lsp" {
        description
          "Cleanup lingering current LSP";
      }
      enum "lingering-standby-lsp" {
        description
          "Cleanup lingering standby LSP";
      }
      enum "lingering-restore-lsp" {
        description
          "Cleanup lingering restore LSP";
      }
      enum "double-lockout" {
        description
          "Double lock out on the tunnel";
      }
      enum "lockout-no-protection" {
        description
          "Lock out on the tunnel with no protection
           available";
      }
      enum "lockout-cleanup" {
        description
          "Lock out on reopt or delayed clean lsp";
      }
      enum "te-ppsw-lsp-mismatch" {
        description
          "LSP id of the current mismatched with the PP
           LSP id in standby";
      }
      enum "te-stdbyup-no-curr-lsp" {
        description
          "Standby LSP up but current LSP not found";
      }
      enum "stdby-failed-rw" {
        description
          "Rewrite failed for Standby LSP";
      }
      enum "reopt-lsp-tear-ppsw" {
        description
          "Reopt LSP teardown because of path protection
           switchover";
      }
      enum "delay-pp-lsp-tear-ppsw" {
        description
          "Delay PP LSP teardown on rew results of path
           protection switchover";
      }
      enum "stdby-failed-verify" {
        description
          "Stdby LSP failed verification";
      }
      enum "stdby-not-needed-due-to-restore" {
        description
          "Stdby is not needed since the restore LSP is
           installed";
      }
      enum "restore-failed-verify" {
        description
          "Restore LSP failed verification";
      }
      enum "restore-failed-install" {
        description
          "Restore LSP failed at install time";
      }
      enum "restore-failed-rewrite" {
        description
          "Restore LSP failed at rewrite";
      }
      enum "te-ppsw-cfg-rmvd" {
        description
          "Path protection configuration remove under the
           tunnel I/F";
      }
      enum "te-ppsw-manual-ppsw" {
        description
          "Manual Path protection switchover";
      }
      enum "te-ppsw-bidir-p-chg-ppsw" {
        description
          "Bidirectional Path Change protection switchover";
      }
      enum "te-ppsw-bidir-lockout-ppsw" {
        description
          "Flex LSP lockout metric protection switchover";
      }
      enum "dclean-at-pp-clean-timer" {
        description
          "Tear delayed pp clean LSP at pp cleanup timer
           expiry";
      }
      enum "reopt-standby-failed" {
        description
          "Creating the reopt standby failed";
      }
      enum "standby-reoptimized" {
        description
          "Tear down old standby LSP because standby
           reoptimized";
      }
      enum "standby-reoptimize-aborted" {
        description
          "Tear down new standby LSP because switchover is
           underway";
      }
      enum "te-reoptup-no-curr-lsp" {
        description
          "Reopt LSP up but current LSP not found";
      }
      enum "te-reopt-curr-lsp-down" {
        description
          "destroying reopt as current LSP torn";
      }
      enum "te-cleanedt-curr-lsp-down" {
        description
          "Destroying cleaned as current LSP torn";
      }
      enum "te-delay-lsp-up" {
        description
          "Delay clean or pp clean LSP came up";
      }
      enum "no-route-due-to-affinity" {
        description
          "No route, no RIB due to affinity";
      }
      enum "no-rib-lkup-bad-ero-gmpls" {
        description
          "Skipping RIB Lookup, Bad GMPLS ERO";
      }
      enum "cleanup-lingering" {
        description
          "Cleanup in lingering state";
      }
      enum "te-s2l-del-sc-soft-preemption-timeout" {
        description
          "Soft preemption timed out";
      }
      enum "te-s2l-del-sc-soft-preempted-non-current" {
        description
          "The head S2L was soft preempted while it is not
           current";
      }
      enum "te-s2l-del-sc-vif-sync-lsp-del" {
        description
          "The head S2L was deleted due to LSP deleted in
           VIF Sync";
      }
      enum "rsvp-api-cleanup-req" {
        description
          "RSVP API cleanup requested";
      }
      enum "te-s2l-del-sc-frr-wrong-backup" {
        description
          "TE and RSVP FRR active on different backups";
      }
      enum "te-s2l-del-sc-bfd-session-create-failed" {
        description
          "The BFD session create failed";
      }
      enum "te-s2l-del-sc-bfd-session-bringup-timeout" {
        description
          "The BFD session failed to up before bringup
           timer timeout";
      }
      enum "te-s2l-del-sc-bfd-session-down" {
        description
          "The BFD session went down";
      }
      enum "te-s2l-del-sc-bfd-session-not-replayed" {
        description
          "BFD did not replay the session";
      }
      enum "te-s2l-del-sc-reopt-p2mp-egress-info-fail" {
        description
          "P2MP egress information programming failed for
           reoptimized LSP";
      }
      enum "non-curr-frr-lcl-notif-event" {
        description
          "FRR local notification event on non-current LSP";
      }
      enum "unsupported-encoding" {
        description
          "The encoding type is not supported";
      }
      enum "unsupported-gpid" {
        description
          "The GPID is not supported";
      }
      enum "unsupported-switching-type" {
        description
          "The switching type is not supported";
      }
      enum "upstream-label-change-not-permitted" {
        description
          "Upstream label change is not allowed";
      }
      enum "encoding-type-change-not-permitted" {
        description
          "Encoding Type change is not allowed";
      }
      enum "aps-protect-info-change-failed" {
        description
          "Failed to process APS Protect info change";
      }
      enum "incorrect-lsp-type" {
        description
          "Incorrect or unsupported connection type";
      }
      enum "local-hop-error" {
        description
          "Failed to compute local hop";
      }
      enum "unsupported-gmpls-attributes" {
        description
          "Incorrect or unsupported GMPLS attributes";
      }
      enum "gmpls-uni-reopt-triggered" {
        description
          "GMPLS-UNI reoptimization triggered from network";
      }
      enum "maximum-acceptable-label-retries" {
        description
          "Maxed out acceptable upstream label retries";
      }
      enum "invalid-direction" {
        description
          "Invalid direction for GMPLS LSP";
      }
      enum "invalid-rewrite-context" {
        description
          "Invalid RW context in callback";
      }
      enum "invalid-label-context" {
        description
          "Invalid Label context in callback";
      }
      enum "dwdm-capability-changed" {
        description
          "DWDM Capability for TE link changed";
      }
      enum "dwdm-capability-removed" {
        description
          "DWDM Capability for TE link removed";
      }
      enum "dwdm-wavelength-removed" {
        description
          "DWDM wavelength channel attribute for TE link
           removed";
      }
      enum "gmpls-uni-multilayer-restoration" {
        description
          "GMPLS-UNI multilayer restoration";
      }
      enum "gmpls-uni-user-triggered-reoptimization" {
        description
          "User-triggered GMPLS-UNI reoptimization";
      }
      enum "gmpls-uni-active-path-change-triggered-reopt" {
        description
          "GMPLS-UNI reoptimization triggered by Active
           Path change";
      }
      enum "passive-match-err" {
        description
          "Failed in finding a matching passive vif";
      }
      enum "egress-control-err" {
        description
          "Failed in egress control";
      }
      enum "egress-control-map-err" {
        description
          "Could not resolve egress control";
      }
      enum "restore-not-needed-for-current" {
        description
          "Restore not needed now for current LSP";
      }
      enum "restore-not-needed-for-standby" {
        description
          "Restore not needed now for standby LSP";
      }
      enum "restore-dp-down" {
        description
          "Restore down in data plane";
      }
      enum "current-not-needed-dp-down" {
        description
          "Current not needed now as down in data plane";
      }
      enum "bad-protct-obj" {
        description
          "Bad protection object";
      }
      enum "head-flexi-cap-change" {
        description
          "Flexi-capability changed at Head node";
      }
      enum "tail-flexi-cap-change" {
        description
          "Flexi-capability changed at Tail node";
      }
      enum "optical-link-down" {
        description
          "TE optical link down";
      }
      enum "optical-link-lsp-out-of-sync" {
        description
          "TE optical link and LSP out of sync";
      }
      enum "optical-link-owner-out-of-sync" {
        description
          "TE optical link owner type out of sync";
      }
      enum "optical-link-interface-handle-out-of-sync" {
        description
          "TE optical link interface handle out of sync";
      }
      enum "optical-link-hop-out-of-sync" {
        description
          "TE optical link next/prev hop out of sync";
      }
      enum "optical-link-role-out-of-sync" {
        description
          "TE optical link role out of sync";
      }
      enum "optical-link-downstream-router-id-out-of-sync" {
        description
          "TE optical link downstream router-ID out of
           sync";
      }
      enum "optical-link-upstream-router-id-out-of-sync" {
        description
          "TE optical link upstream router-ID out of sync";
      }
      enum "optical-link-encoding-type-out-of-sync" {
        description
          "TE optical link encoding type out of sync";
      }
      enum "optical-link-switching-type-out-of-sync" {
        description
          "TE optical link switching type out of sync";
      }
      enum "optical-link-gpid-out-of-sync" {
        description
          "TE optical link GPID out of sync";
      }
      enum "egress-optical-link-not-found" {
        description
          "Egress optical TE link (head) not found";
      }
      enum "ingress-optical-link-not-found" {
        description
          "Ingress optical TE link (tail) not found";
      }
      enum "switch-cap-change-head" {
        description
          "Local Link Switch cap (head) changed";
      }
      enum "switch-cap-change-tail" {
        description
          "Local Link Switch cap (tail) changed";
      }
      enum "mtu-change-head" {
        description
          "Local Link MTU (head) changed";
      }
      enum "mtu-change-tail" {
        description
          "Local Link MTU (tail) changed";
      }
      enum "sync-dest-state" {
        description
          "Syncing of the destination state change";
      }
      enum "prot-object-err" {
        description
          "Protection Object Error";
      }
      enum "reverse-s2l-deleted" {
        description
          "Reverse Associated S2L Deleted";
      }
      enum "cancel-inprogress-by-slave" {
        description
          "In-progress S2L cancelled by slave";
      }
      enum "invalid-reverse-ero" {
        description
          "Bad Reverse ERO";
      }
      enum "reverse-lsp-not-found" {
        description
          "Switchover Reverse LSP Not Found";
      }
      enum "reverse-lsp-not-present" {
        description
          "Switchover Reverse LSP Not Present";
      }
      enum "associated-vif-down" {
        description
          "Associated VIF moved to Down";
      }
      enum "vif-sync-processing" {
        description
          "Tunnel interface sync processing caused
           deletion";
      }
      enum "incoming-interface-lockout" {
        description
          "Incoming interface locked out";
      }
      enum "sr-egress-path-changed" {
        description
          "SR egress path changed on non-current S2L";
      }
      enum "in-if-fail-imp-null-cfg-ch" {
        description
          "Implicit null config changed";
      }
      enum "reverse-lsp-failure" {
        description
          "Reverse LSP Failure";
      }
      enum "lsp-wrap-label-error" {
        description
          "LSP Wrap Label Error";
      }
      enum "lsp-wrap-rewrite-error" {
        description
          "LSP Wrap Rewrite Error";
      }
      enum "transit-lsp-out-of-resources" {
        description
          "LSP OOR";
      }
      enum "path-protection-configuration-change" {
        description
          "Path protection configuration changed under the
           tunnel I/F";
      }
      enum "better-standby-path" {
        description
          "Better standby path exists";
      }
      enum "path-option-config-change" {
        description
          "Path-option configuration change";
      }
      enum "path-protection-non-revertive-config-changed" {
        description
          "Path protection non-revertive config changed
           under the tunnel I/F";
      }
      enum "manually-triggered-non-revertive-recovery" {
        description
          "Manually triggered non-revertive recovery";
      }
      enum "remote-node-triggered-path-protection-switchover" {
        description
          "Received path protection switchover
           notification from remote node";
      }
      enum "user-request-teardown" {
        description
          "User request tunnel teardown";
      }
      enum "fsm-sc-must-be-last" {
        description
          "Not used, must be last entry";
      }
    }
    description
      "S2L deletion subcause";
  }

  typedef Te-p2mp-s2l-deletion-cause {
    type enumeration {
      enum "no-cause" {
        description
          "No cause recorded";
      }
      enum "hpath-cr-err" {
        description
          "Head Path creation";
      }
      enum "hpath-chg-setup" {
        description
          "Head Path change setup";
      }
      enum "hpath-chg-up-err" {
        description
          "Head Path change while up";
      }
      enum "hresv-cr-err" {
        description
          "Head RESV creation";
      }
      enum "hresv-chg-err" {
        description
          "Head RESV change";
      }
      enum "hresv-chg-err-up" {
        description
          "Head RESV change while up";
      }
      enum "hlbl-avail-err" {
        description
          "Head Label available";
      }
      enum "hup-lbl-avail-err" {
        description
          "Head upstream Label available";
      }
      enum "hfrr-act-err" {
        description
          "Head FRR active";
      }
      enum "hbkup-ch-err" {
        description
          "Head Backup change";
      }
      enum "hpath-ch-frr-err" {
        description
          "Head Path change FRR";
      }
      enum "hcleanup" {
        description
          "Head Cleanup handling";
      }
      enum "hlingering-cleanup" {
        description
          "Head lingering cleanup";
      }
      enum "hpat-err" {
        description
          "Head Path error";
      }
      enum "hresv-err" {
        description
          "Head Resv error";
      }
      enum "hresv-del" {
        description
          "Head Resv delete";
      }
      enum "hrw-fail" {
        description
          "Head rewrite failure";
      }
      enum "hup-rw-fail" {
        description
          "Head upstream rewrite failure";
      }
      enum "ha-failure" {
        description
          "HA failure";
      }
      enum "rw-del" {
        description
          "Rewrite Delete";
      }
      enum "up-rw-del" {
        description
          "Upstream Rewrite Delete";
      }
      enum "mpath-cr" {
        description
          "Mid path creation";
      }
      enum "mpath-chg-setup-err" {
        description
          "Mid Path change setup";
      }
      enum "mpath-chg-up-err" {
        description
          "Mid Path change while up";
      }
      enum "mresv-cr-err" {
        description
          "Mid Resv creation";
      }
      enum "mresv-chg-err" {
        description
          "Mid Resv change";
      }
      enum "mresv-chg-err-up" {
        description
          "Mid Resv change while up";
      }
      enum "mlbl-avail-err" {
        description
          "Mid: cannot get local label";
      }
      enum "mlbl-rel-err" {
        description
          "Mid: cannot release local label";
      }
      enum "mup-lbl-avail-err" {
        description
          "Mid: cannot get upstream label";
      }
      enum "mup-lbl-rel-err" {
        description
          "Mid: cannot release upstream label";
      }
      enum "mfrr-act-err" {
        description
          "Mid FRR active";
      }
      enum "mbkup-ch-err" {
        description
          "Mid Backup change";
      }
      enum "mpath-ch-frr-err" {
        description
          "Mid Path change FRR";
      }
      enum "mresv-del" {
        description
          "Mid Resv Delete handling";
      }
      enum "mresv-err" {
        description
          "Mid Resv Error handling";
      }
      enum "mpreempt" {
        description
          "Mid Premption";
      }
      enum "mcleanup" {
        description
          "Mid Cleanup handling";
      }
      enum "mlingering-cleanup" {
        description
          "Mid lingering cleanup";
      }
      enum "mrw-fail" {
        description
          "mid rewrite failure";
      }
      enum "mup-rw-fail" {
        description
          "mid upstream rewrite failure";
      }
      enum "tpath-cr-err" {
        description
          "Tail Path creation";
      }
      enum "tpath-chg-err" {
        description
          "Tail Path change";
      }
      enum "tresv-cr-err" {
        description
          "Tail RESV creation";
      }
      enum "tlbl-avail-err" {
        description
          "Tail: cannot release local label";
      }
      enum "tcleanup" {
        description
          "Tail Cleanup";
      }
      enum "tlingering-cleanup" {
        description
          "Tail lingering cleanup";
      }
      enum "lbl-err" {
        description
          "Local label related error";
      }
      enum "qfailure" {
        description
          "FSM Queueing failure";
      }
      enum "rsvp-recovery" {
        description
          "RSVP Recovery";
      }
      enum "lsd-recovery" {
        description
          "LSD Recovery";
      }
      enum "lmrib-recovery" {
        description
          "LMRIB Recovery";
      }
      enum "te-restart" {
        description
          "TE Restart";
      }
      enum "switchover" {
        description
          "Switchover";
      }
      enum "master-te-recovery" {
        description
          "Master TE recovery";
      }
      enum "optical-r-mgr-recovery" {
        description
          "Optical Resource Manager Recovery";
      }
      enum "te-exit" {
        description
          "TE Exited";
      }
      enum "bkup-assign-fail" {
        description
          "RSVP Backup Assign Failed";
      }
      enum "bfd-fail" {
        description
          "BFD Session Failure";
      }
      enum "bfd-recovery" {
        description
          "BFD Recovery";
      }
      enum "lsp-wrap-act-err" {
        description
          "Mid LSP Wrap active";
      }
      enum "lsp-wrap-rw-err" {
        description
          "Mid LSP Wrap Rewrite";
      }
      enum "fsm-cause-must-be-last" {
        description
          "Not used, must be last entry";
      }
    }
    description
      "S2L Deletion location";
  }

  typedef Te-pp-diversity {
    type enumeration {
      enum "diversity-none" {
        description
          "Standby LSP not diverse";
      }
      enum "link" {
        description
          "Standby LSP link diverse";
      }
      enum "node" {
        description
          "Standby LSP node diverse";
      }
      enum "node-link" {
        description
          "Standby LSP node and link diverse";
      }
      enum "srlg" {
        description
          "Standby SRLG diverse";
      }
      enum "node-srlg" {
        description
          "Standby LSP node and SRLG diverse";
      }
      enum "node-link-srlg" {
        description
          "Standby LSP node and link and SRLG diverse";
      }
      enum "diversity-sticky" {
        description
          "Standby LSP using sticky explicit path";
      }
      enum "diversity-user" {
        description
          "Standby LSP using user defined explicit path";
      }
      enum "diversity-reverse-ero" {
        description
          "Standby LSP using Reverse ERO";
      }
    }
    description
      "Diversity of Protection or Restoration Path from
       Protected Path";
  }

  typedef Te-srlg-collect-request {
    type enumeration {
      enum "none" {
        description
          "No SRLG-collection request";
      }
      enum "mandatory" {
        description
          "Mandatory SRLG-collection request";
      }
      enum "optional" {
        description
          "Optional SRLG-collection request";
      }
    }
    description
      "SRLG-collection request machansim";
  }

  typedef Te-odu-level {
    type enumeration {
      enum "te-odu-level-not-set" {
        value 0;
        description
          "Not set";
      }
      enum "te-odu-level-one" {
        value 1;
        description
          "ODU 1";
      }
      enum "te-odu-level-two" {
        value 2;
        description
          "ODU 2";
      }
      enum "te-odu-level-three" {
        value 3;
        description
          "ODU 3";
      }
      enum "te-odu-level-four" {
        value 4;
        description
          "ODU 4";
      }
      enum "te-odu-zero" {
        value 10;
        description
          "ODU 0";
      }
      enum "te-odu-level-two-e" {
        value 11;
        description
          "ODU 2E";
      }
      enum "te-odu-level-flex-cbr" {
        value 20;
        description
          "ODU Flex CBR";
      }
      enum "te-odu-level-flex-gfpf-resizeable" {
        value 21;
        description
          "ODU Flex GFP-F resizable";
      }
      enum "te-odu-level-flex-gfpf-non-resizable" {
        value 22;
        description
          "ODU Flex GFP-F non resizable";
      }
      enum "te-odu-level-one-e" {
        value 23;
        description
          "ODU 1E";
      }
      enum "te-odu-level-one-f" {
        value 24;
        description
          "ODU 1F";
      }
      enum "te-odu-level-two-f" {
        value 25;
        description
          "ODU 2F";
      }
      enum "te-odu-level-three-e-one" {
        value 26;
        description
          "ODU 3E1";
      }
      enum "te-odu-level-three-e-two" {
        value 27;
        description
          "ODU 3E2";
      }
      enum "te-odu-level-c-two" {
        value 38;
        description
          "ODU C2";
      }
      enum "te-odu-level-c-three" {
        value 39;
        description
          "ODU C3";
      }
      enum "te-odu-level-c-four" {
        value 40;
        description
          "ODU C4";
      }
    }
    description
      "G.709 OTN ODU levels";
  }

  typedef Te-addr {
    type enumeration {
      enum "not-set" {
        description
          "Address not set";
      }
      enum "ipv4" {
        description
          "IPv4";
      }
      enum "ipv4-unnumbered" {
        description
          "IPv4 Unnumbered";
      }
    }
    description
      "TE Address Types";
  }

  typedef Mpls-te-lsp-mode {
    type enumeration {
      enum "mpls-te-lsp-mode-not-set" {
        description
          "LSP mode not set";
      }
      enum "mpls-te-lsp-mode-current" {
        description
          "Current LSP";
      }
      enum "mpls-te-lsp-mode-reopt" {
        description
          "Reoptimized LSP";
      }
      enum "mpls-te-lsp-mode-clean" {
        description
          "Cleaned LSP";
      }
      enum "mpls-te-lsp-mode-standby" {
        description
          "Standby LSP";
      }
      enum "mpls-te-lsp-mode-pp-clean" {
        description
          "Delay PP Clean LSP";
      }
      enum "mpls-te-lsp-mode-restore" {
        description
          "Restore LSP";
      }
      enum "mpls-te-lsp-mode-reopt-standby" {
        description
          "Reopt Standby LSP";
      }
    }
    description
      "Mpls te lsp mode";
  }

  typedef Te-protection {
    type enumeration {
      enum "protection-type-unprotected" {
        value 0;
        description
          "Uni protection unprotected";
      }
      enum "protection-type-reroute" {
        value 1;
        description
          "Uni protection full reroute";
      }
      enum "protection-reroute-no-et" {
        value 2;
        description
          "Uni protection reroute with no extra traffic";
      }
      enum "one-n-protection-extra-traffic" {
        value 4;
        description
          "Uni 1:N protection with extra traffic";
      }
      enum "one-plus-one-unidirectional-protection" {
        value 8;
        description
          "Uni 1+1 unidirectional protection";
      }
      enum "one-plus-one-bidirectional-protection" {
        value 16;
        description
          "Uni 1+1 bidirectional protection";
      }
    }
    description
      "UNI Protection type";
  }

  typedef Te-attribute-set-sr-prepend {
    type enumeration {
      enum "te-attribute-set-sr-prepend-not-set" {
        value 0;
        description
          "Not set";
      }
      enum "te-attribute-set-sr-prepend-next-label" {
        value 1;
        description
          "Next label";
      }
      enum "te-attribute-set-sr-prepend-bgp-nhop" {
        value 2;
        description
          "BGP NHOP";
      }
    }
    description
      "Attribute Set SR prepend type";
  }

  typedef Te-restoration-style {
    type enumeration {
      enum "restoration-style-not-set" {
        value 0;
        description
          "TE Restoration Style Not Set";
      }
      enum "restoration-style-keep-failed-lsp" {
        value 1;
        description
          "TE Restoration Style is to Keep Failed Lsp";
      }
      enum "restoration-style-delete-failed-lsp" {
        value 2;
        description
          "TE Restoration Style is to Delete Failed Lsp";
      }
    }
    description
      "PNR Options";
  }

  typedef Te-path-prot-profile {
    type enumeration {
      enum "path-prot-profile-type1-plus0" {
        value 0;
        description
          "TE Path Option 1PLUS0";
      }
      enum "path-prot-profile-type1-plus-r" {
        value 1;
        description
          "TE Path Option 1PLUSR";
      }
      enum "path-prot-profile-type1-plus1" {
        value 16;
        description
          "TE Path Option 1PLUS1";
      }
      enum "path-prot-profile-type1-plus1-plus-r" {
        value 32;
        description
          "TE Path Option 1PLUS1PLUSR";
      }
      enum "path-prot-profile-type-invalid" {
        value 255;
        description
          "TE Path Option Invalid";
      }
    }
    description
      "Path Protection Profile Type";
  }

  typedef Te-sch-freq {
    type enumeration {
      enum "sch-freq-not-set" {
        value 0;
        description
          "Schedule reversion frequency not set";
      }
      enum "sch-freq-set-once" {
        value 1;
        description
          "Schedule reversion frequency set only once";
      }
      enum "sch-freq-set-daily" {
        value 2;
        description
          "Schedule reversion frequency set daily";
      }
      enum "sch-freq-set-weekly" {
        value 3;
        description
          "Schedule reversion frequency set weekly";
      }
    }
    description
      "Te sch freq";
  }

  typedef Te-pnr-revert-options {
    type enumeration {
      enum "pnr-optionnot-set" {
        value 0;
        description
          "TE Protection Restore Option Not Set";
      }
      enum "pnr-option-revertive" {
        value 1;
        description
          "TE Protection Restore Option Revertive";
      }
      enum "pnr-option-non-revertive" {
        value 2;
        description
          "TE Protection Restore Option Non-revertive";
      }
    }
    description
      "PNR Options";
  }

  typedef Te-protect {
    type enumeration {
      enum "protect-type1-plus1-unidir-no-aps" {
        value 4;
        description
          "Protection Type Uni-directional No APS";
      }
      enum "protect-type1-plus1-unidir-aps" {
        value 8;
        description
          "Protection Type Uni-directional APS";
      }
      enum "protect-type1-plus1-bidir-aps" {
        value 16;
        description
          "Protection Type Bi-directional APS";
      }
      enum "protect-type-not-set" {
        value 255;
        description
          "Protection Type Not Set";
      }
    }
    description
      "Protection Types";
  }

  typedef Te-aps-snc-mode {
    type enumeration {
      enum "snc-mode-not-set" {
        value 0;
        description
          "TE OTN Subnetwork Connection Mode Not Set";
      }
      enum "snc-mode-n" {
        value 1;
        description
          "TE OTN Subnetwork Connection Mode N";
      }
      enum "snc-mode-i" {
        value 2;
        description
          "TE OTN Subnetwork Connection Mode I";
      }
      enum "snc-mode-s" {
        value 3;
        description
          "TE OTN Subnetwork Connection Mode S";
      }
    }
    description
      "APS ANC Modes";
  }

  typedef Te-xro-exclusion {
    type enumeration {
      enum "mandatory" {
        value 0;
        description
          "Mandatory exclusion";
      }
      enum "best-effort" {
        value 1;
        description
          "Best-effort exclusion";
      }
    }
    description
      "XRO exclusion type";
  }

  typedef Te-xro-attribute {
    type enumeration {
      enum "interface" {
        value 0;
        description
          "Exclude the interface specified";
      }
      enum "node" {
        value 1;
        description
          "Exclude the node specified";
      }
      enum "srl-gs" {
        value 2;
        description
          "Exclude all SRLGs related to the data specified";
      }
    }
    description
      "XRO exclusion type";
  }

  typedef Te-xro-subobj {
    type enumeration {
      enum "ipv4" {
        value 1;
        description
          "IPv4 prefix";
      }
      enum "ipv6" {
        value 2;
        description
          "IPv6 prefix";
      }
      enum "unnumbered" {
        value 6;
        description
          "Unnumbered";
      }
      enum "as" {
        value 32;
        description
          "Autonomous System";
      }
      enum "srlg" {
        value 34;
        description
          "SRLG";
      }
      enum "p2p-lsp" {
        value 36;
        description
          "P2P LSP";
      }
    }
    description
      "XRO sub-object type";
  }

  typedef Te-sig-name-append {
    type enumeration {
      enum "none" {
        value 0;
        description
          "Option is Not Set for appending to
           signalled-name";
      }
      enum "address" {
        value 1;
        description
          "Option is to append Address to signalled-name";
      }
      enum "name" {
        value 2;
        description
          "Option is to append Name to signalled-name";
      }
    }
    description
      "Te sig name append";
  }

  typedef Mpls-te-lsp {
    type enumeration {
      enum "mpls-te-lsp-type-not-set" {
        value 0;
        description
          "Tunnel type not set";
      }
      enum "mpls-te-lsp-type-p2p" {
        value 1;
        description
          "Point-to-point packet TE tunnel";
      }
      enum "mpls-te-lsp-type-p2mp" {
        value 2;
        description
          "Point-to-multipoint tunnel";
      }
      enum "mpls-te-lsp-type-gmpls-ouni" {
        value 3;
        description
          "Bidirectional GMPLS UNI tunnel";
      }
      enum "mpls-te-lsp-type-gmpls-nni" {
        value 4;
        description
          "Bidirectional GMPLS NNI tunnel";
      }
      enum "mpls-te-lsp-type-p2p-bidir" {
        value 5;
        description
          "Bidirectional packet point-to-point tunnel";
      }
      enum "mpls-te-lsp-type-gmpls-tp" {
        value 6;
        description
          "Bidirectional GMPLS TP tunnel";
      }
      enum "mpls-te-lsp-type-gmpls-nni-otn" {
        value 7;
        description
          "Bidirectional GMPLS OTN NNI tunnel";
      }
      enum "mpls-te-lsp-type-segment-routing-p2p" {
        value 8;
        description
          "Point-to-point segment-routing packet TE tunnel";
      }
    }
    description
      "LSP Types";
  }

  typedef Mpls-te-tunnel-role {
    type enumeration {
      enum "tunnel-unknown" {
        value 0;
        description
          "Undefined tunnel role";
      }
      enum "tunnel-head" {
        value 1;
        description
          "Tunnel role is head";
      }
      enum "tunnel-mid" {
        value 2;
        description
          "Tunnel role is midpoint";
      }
      enum "tunnel-tail" {
        value 3;
        description
          "Tunnel role is tail";
      }
    }
    description
      "Mpls te tunnel role";
  }

  typedef Mpls-lib-c {
    type enumeration {
      enum "mpls-lib-c-type-null" {
        value 0;
        description
          "NULL Ctype";
      }
      enum "mpls-lib-c-type-ipv4" {
        value 1;
        description
          "IPv4 UDP";
      }
      enum "mpls-lib-c-type-ipv4-p2p-tunnel" {
        value 7;
        description
          "IPv4 point-to-point TE tunnel";
      }
      enum "mpls-lib-c-type-ipv6-p2p-tunnel" {
        value 8;
        description
          "IPv6 point-to-point TE tunnel";
      }
      enum "mpls-lib-c-type-ipv4-uni" {
        value 9;
        description
          "IPv4 unicast";
      }
      enum "mpls-lib-c-type-ipv4-p2mp-tunnel" {
        value 13;
        description
          "IPv4 point-to-point TE tunnel";
      }
      enum "mpls-lib-c-type-ipv6-p2mp-tunnel" {
        value 14;
        description
          "IPv6 point-to-point TE tunnel";
      }
      enum "mpls-lib-c-type-ipv4-tp-tunnel" {
        value 15;
        description
          "IPv4 transport protocol tunnel";
      }
      enum "mpls-lib-c-type-ipv6-tp-tunnel" {
        value 16;
        description
          "IPv6 transport protocol tunnel";
      }
      enum "mpls-lib-c-type-p2p-binding-label" {
        value 17;
        description
          "P2P transport tunnel binding label";
      }
    }
    description
      "Mpls lib c";
  }

  grouping MPLS-TE-AFFINITY-MAP-INFO {
    description
      "Affinity Map";
    leaf affinity-name {
      type string;
      description
        "Affinity name";
    }
    leaf affinity-value {
      type uint32;
      description
        "Affinity value";
    }
    leaf affinity-bit-position {
      type uint8;
      description
        "Affinity bit position";
    }
    leaf affinity-table-id {
      type Te-affinity-table;
      description
        "Affinity table id";
    }
    list affinity-extended-value {
      description
        "EAG value";
      leaf entry {
        type uint32;
        description
          "EAG value";
      }
    }
  }

  grouping MPLS-LM-BFD-NBR-INFO {
    description
      "BFD Neighbor information";
    leaf neighbor-address {
      type inet:ipv4-address;
      description
        "The neighbor's IP address";
    }
    leaf is-bfd-up {
      type boolean;
      description
        "TRUE if the BFD session is Up on this link";
    }
  }

  grouping MPLS-LM-BFD-NBRS-LINK-INFO {
    description
      "BFD Neighbor information based on the link";
    list neighbor {
      description
        "Neighbors of the specified link id";
      uses MPLS-LM-BFD-NBR-INFO;
    }
  }

  grouping ODU-CAPABILITY-FLEX {
    description
      "odu capability for flex  ODUs";
    leaf max-bandwidth {
      type uint32;
      units "kbit/s";
      description
        "Max kbps Bandwidth of this level possible on
         this link";
    }
    leaf unreserved-bandwidth {
      type uint32;
      units "kbit/s";
      description
        "Unreserved kbps Bandwidth of this level possible
         on this link";
    }
    leaf max-lsp-bandwidth {
      type uint32;
      units "kbit/s";
      description
        "Per LSP Max kbps Bandwidth of this level
         possible on this link";
    }
  }

  grouping ODU-CAPABILITY-FIXED {
    description
      "odu capability for fixed ODUs ";
    leaf maximum-od-us {
      type uint8;
      description
        "Maximum Number of ODUs of this level possible on
         this link";
    }
    leaf unreserved-od-us {
      type uint8;
      description
        "Maximum Number of ODUs of this level possible on
         this link";
    }
  }

  grouping ODU-CAP-BW {
    description
      "ODU capability Union for bandwidth";
    container fixed {
      when "../type = 'fixed'" {
        description
          "../type = 'Fixed'";
      }
      description
        "ODU capability for Fixed ODUs";
      uses ODU-CAPABILITY-FIXED;
    }
    container flex {
      when "../type = 'flex'" {
        description
          "../type = 'Flex'";
      }
      description
        "ODU capability for Flex ODUs";
      uses ODU-CAPABILITY-FLEX;
    }
    leaf type {
      type Te-odu-capability;
      description
        "type";
    }
  }

  grouping ODU-CAPABILITY {
    description
      "Odu capability at a level of multiplex tree for
       an ODU type";
    container bandwidth-info {
      description
        "Bandwidth related info for this ODU level";
      uses ODU-CAP-BW;
    }
    leaf signal-type {
      type Te-odu-level;
      description
        "Signal Type";
    }
    leaf stage1 {
      type Te-odu-level;
      description
        "ODU Type at stage 1, Not Set for HO ODU";
    }
    leaf stage2 {
      type Te-odu-level;
      description
        "ODU Type at stage 2, Not Set for single stage
         mulitplexing";
    }
    leaf stage3 {
      type Te-odu-level;
      description
        "ODU Type at stage 3, Not set up to two levels of
         multiplexing";
    }
    leaf stage4 {
      type Te-odu-level;
      description
        "ODU Type at stage 4, Not set up to three levels
         of multiplexing";
    }
    leaf terminable {
      type boolean;
      description
        "True if link is terminable for this ODU level";
    }
    leaf switchable {
      type boolean;
      description
        "True if link is switchable for this ODU level";
    }
    leaf tsg1p25 {
      type boolean;
      description
        "True if link supports 1.25G TSG for this ODU
         level";
    }
    leaf tsg2p5 {
      type boolean;
      description
        "True if link supports 2.5G TSG for this ODU
         level";
    }
    leaf vcat-capable {
      type boolean;
      description
        "True if link VCAT capable for this ODU level";
    }
    leaf lcas-capable {
      type boolean;
      description
        "True if link LCAS capable for this ODU level";
    }
  }

  grouping ODU-LINK-CAPABILITIES {
    description
      "Link ODU Capabilities";
    list max-lsp-bandwidth {
      description
        "Max LSP Bandwidth per priority in kbit/s";
      leaf entry {
        type uint32;
        description
          "Max LSP Bandwidth per priority in kbit/s";
      }
    }
    list odu-capability {
      description
        "ODU Capabilities of Link";
      uses ODU-CAPABILITY;
    }
  }

  grouping MPLS-TE-BFD-LSP-COUNTERS {
    description
      "TE BFDOverLSP Counters";
    leaf session-create-events {
      type uint32;
      description
        "The number of BFDOverLSP session create events";
    }
    leaf session-up-events {
      type uint32;
      description
        "The number of BFDOverLSP session up events";
    }
    leaf session-creation-failed-events {
      type uint32;
      description
        "The number of BFDOverLSP session creation failed
         events";
    }
    leaf session-down-events {
      type uint32;
      description
        "The number of BFDOverLSP session down events";
    }
    leaf session-admin-down-events {
      type uint32;
      description
        "The number of BFDOverLSP session admin down
         events";
    }
    leaf session-gracefully-delete-events {
      type uint32;
      description
        "The number of BFDOverLSP session gracefully
         delete events";
    }
    leaf session-non-gracefully-delete-events {
      type uint32;
      description
        "The number of BFDOverLSP session non gracefully
         delete events";
    }
    leaf session-create-timeout-events {
      type uint32;
      description
        "The number of BFDOverLSP session create timeout
         events";
    }
    leaf session-replay-events {
      type uint32;
      description
        "The number of BFDOverLSP session replay events";
    }
  }

  grouping MPLS-TE-TUNNEL-EGRESS-STATIC-UNI-INFO {
    description
      "Egress Static UNI Info";
    container egress-port {
      description
        "Egress Client Port of Tunnel";
      uses TE-ADDR;
    }
    container term-egress-port {
      description
        "Termination Egress Client Port of Tunnel";
      uses TE-ADDR;
    }
    leaf local-termination {
      type Mpls-te-termination;
      description
        "Local Termination Type";
    }
    leaf remote-uni-type {
      type Mpls-te-uni;
      description
        "Remote uni type";
    }
  }

  grouping TE-TERM-INTERFACE-SRLG-CB {
    description
      "Termination SRLG";
    list discovered-srlg {
      description
        "Discovered SRLG";
      leaf entry {
        type uint32;
        description
          "Discovered SRLG";
      }
    }
  }

  grouping TE-ADDR-TYPE-IPV4-UNNUM {
    description
      "TE IPv4 unnumbered address type";
    leaf router-id {
      type inet:ipv4-address;
      description
        "IPv4 router ID";
    }
    leaf interface-index {
      type uint32;
      description
        "Interface index";
    }
  }

  grouping ADDR {
    description
      "ADDR";
    container ipv4-unnumbered-address {
      when "../type = 'ipv4-unnumbered'" {
        description
          "../Type = 'IPv4Unnumbered'";
      }
      description
        "IPv4 unnumbered address";
      uses TE-ADDR-TYPE-IPV4-UNNUM;
    }
    leaf type {
      type Te-addr;
      description
        "Type";
    }
    leaf ipv4-address {
      when "../type = 'ipv4'" {
        description
          "../Type = 'IPv4'";
      }
      type inet:ipv4-address;
      description
        "IPv4 address";
    }
  }

  grouping TE-ADDR {
    description
      "TE address";
    container te-addr {
      description
        "TE Address";
      uses ADDR;
    }
  }

  grouping MPLS-SRLG-INFO {
    description
      "Information about the Shared Risk Link Group";
    leaf shared-risk-group {
      type uint32;
      description
        "SRLG number";
    }
    leaf srlg-name {
      type string;
      description
        "SRLG name";
    }
  }

  grouping TE-REVERT-SCH {
    description
      "Revert Schedule protection attribute set";
    leaf schedulename {
      type string {
        length "0..255";
      }
      description
        "Schedule name identifier";
    }
    leaf schedule-date {
      type uint32;
      description
        "Schedule time for reversion";
    }
    leaf schedule-frequency {
      type Te-sch-freq;
      description
        "Schedule frequency for reversion";
    }
    leaf duration {
      type uint32;
      description
        "Duration for scheduled reversion";
    }
    leaf max-tries {
      type uint32;
      description
        "Max tries for scheduled reversion";
    }
  }

  grouping TE-XRO-SUBOBJ-P2P-LSP {
    description
      "XRO point-to-point LSP sub-object";
    container fec {
      description
        "LSP FEC";
      uses TE-LSP-FEC;
    }
    leaf ignore-lsp-id {
      type boolean;
      description
        "Flag to indicate whether or not the lsp-id in
         the FEC is to be ignored";
    }
    leaf processing-node-exception {
      type boolean;
      description
        "Processing-node exception flag";
    }
    leaf penultimate-node-exception {
      type boolean;
      description
        "Penultimate-node exception flag";
    }
    leaf destination-node-exception {
      type boolean;
      description
        "Destination-node exception flag";
    }
    leaf exclusion-type {
      type Te-xro-exclusion;
      description
        "Exclusion Type";
    }
  }

  grouping TE-XRO-SUBOBJ-SRLG {
    description
      "XRO SRLG sub-object";
    leaf srlg-id {
      type uint32;
      description
        "SRLG ID";
    }
    leaf exclusion-type {
      type Te-xro-exclusion;
      description
        "Exclusion Type";
    }
  }

  grouping TE-XRO-SUBOBJ-AS {
    description
      "XRO AS sub-object";
    leaf as-number {
      type uint16;
      description
        "Autonomous System number";
    }
  }

  grouping TE-XRO-SUBOBJ-UNNUM {
    description
      "XRO unnumbered sub-object";
    leaf te-router-id {
      type inet:ipv4-address;
      description
        "TE router-id";
    }
    leaf interface-id {
      type uint32;
      description
        "Interface ID";
    }
    leaf attribute {
      type Te-xro-attribute;
      description
        "Attribute";
    }
    leaf exclusion-type {
      type Te-xro-exclusion;
      description
        "Exclusion Type";
    }
  }

  grouping TE-XRO-SUBOBJ-IPV6 {
    description
      "XRO IPv6 sub-object";
    leaf address {
      type inet:ipv6-address;
      description
        "IPv6 address";
    }
    leaf prefix-len {
      type uint8;
      description
        "Prefix length";
    }
    leaf attribute {
      type Te-xro-attribute;
      description
        "Attribute";
    }
    leaf exclusion-type {
      type Te-xro-exclusion;
      description
        "Exclusion Type";
    }
  }

  grouping TE-XRO-SUBOBJ-IPV4 {
    description
      "XRO IPv4 sub-object";
    leaf address {
      type inet:ipv4-address;
      description
        "IPv4 address";
    }
    leaf prefix-len {
      type uint8;
      description
        "Prefix length";
    }
    leaf attribute {
      type Te-xro-attribute;
      description
        "Attribute";
    }
    leaf exclusion-type {
      type Te-xro-exclusion;
      description
        "Exclusion Type";
    }
  }

  grouping TE-XRO-SUBOBJ {
    description
      "XRO sub-object union";
    container ipv4-subobject {
      when "../type = 'ipv4'" {
        description
          "../Type = 'IPv4'";
      }
      description
        "IPv4 sub-object";
      uses TE-XRO-SUBOBJ-IPV4;
    }
    container ipv6-subobject {
      when "../type = 'ipv6'" {
        description
          "../Type = 'IPv6'";
      }
      description
        "IPv6 sub-object";
      uses TE-XRO-SUBOBJ-IPV6;
    }
    container unnumbered-subobject {
      when "../type = 'unnumbered'" {
        description
          "../Type = 'Unnumbered'";
      }
      description
        "Unnumbered sub-object";
      uses TE-XRO-SUBOBJ-UNNUM;
    }
    container as-subobject {
      when "../type = 'as'" {
        description
          "../Type = 'AS'";
      }
      description
        "AS sub-object";
      uses TE-XRO-SUBOBJ-AS;
    }
    container srlg-subobject {
      when "../type = 'srlg'" {
        description
          "../Type = 'SRLG'";
      }
      description
        "SRLG sub-object";
      uses TE-XRO-SUBOBJ-SRLG;
    }
    container lsp-subobject {
      when "../type = 'p2p-lsp'" {
        description
          "../Type = 'P2P_LSP'";
      }
      description
        "P2P LSP sub-object";
      uses TE-XRO-SUBOBJ-P2P-LSP;
    }
    leaf type {
      type Te-xro-subobj;
      description
        "Type";
    }
  }

  grouping TE-XRO {
    description
      "XRO object";
    leaf mutual-diversity-flag {
      type boolean;
      description
        "Mutual Diversity Flag";
    }
    list xro-subobject {
      description
        "List of XRO sub-objects";
      uses TE-XRO-SUBOBJ;
    }
  }

  grouping AFFINITY-NAME-BAG {
    description
      "Affinity name constraints";
    leaf constraint-type {
      type uint8;
      description
        "Constraint type";
    }
    leaf constraint-value {
      type uint32;
      description
        "Deprecated";
    }
    leaf forward-ref-value {
      type uint32;
      description
        "Deprecated";
    }
    list constraint-extended-value {
      description
        "Constraint value";
      leaf entry {
        type uint32;
        description
          "Constraint value";
      }
    }
    list extended-forward-ref-value {
      description
        "Reference bits for undefined affinity names";
      leaf entry {
        type uint32;
        description
          "Reference bits for undefined affinity names";
      }
    }
  }

  grouping MPLS-TE-TUNNELS-AFFINITY-INFO {
    description
      "MPLS TE tunnel Affinity information";
    leaf affinity-bits {
      type uint32;
      description
        "The affinity bits (colors)";
    }
    leaf affinity-mask {
      type uint32;
      description
        "The affinity mask (colors)";
    }
    list named-affinity {
      description
        "Array of name based constratints currently
         applied to the tunnel";
      uses AFFINITY-NAME-BAG;
    }
  }

  grouping TE-S2L-FEC {
    description
      "A sub-LSP FEC";
    leaf s2l-fec-subgroup-id {
      type uint16;
      description
        "sub-LSP subgroup ID";
    }
    leaf s2l-fec-lsp-id {
      type uint16;
      description
        "LSP ID";
    }
    leaf s2l-fec-tunnel-id {
      type uint16;
      description
        "Tunnel ID";
    }
    leaf s2l-fec-extended-tunnel-id {
      type inet:ipv4-address;
      description
        "Extended tunnel ID";
    }
    leaf s2l-fec-source {
      type inet:ipv4-address;
      description
        "LSP source address";
    }
    leaf s2l-fec-dest {
      type inet:ipv4-address;
      description
        "sub-LSP destination address";
    }
    leaf s2l-fec-p2mp-id {
      type uint32;
      description
        "P2MP ID";
    }
    leaf s2l-fec-subgroup-originator {
      type inet:ipv4-address;
      description
        "Subgroup Originator";
    }
    leaf s2l-fec-ctype {
      type Mpls-lib-c;
      description
        "Session identifier (ctype)";
    }
    leaf s2l-fec-vrf {
      type string;
      description
        "VRF; currently only for GMPLS tunnels";
    }
  }

  grouping TE-LSP-FEC-CTYPE-DATA {
    description
      "C-type-specific LSP FEC data";
    leaf fec-ctype {
      type Mpls-lib-c;
      description
        "FEC CType";
    }
    leaf p2p-lsp-destination {
      when "../fec-ctype = 'mpls-lib-c-type-ipv4-p2p-tunnel'" {
        description
          "../FEC_CType = 'MPLS_LIB_CTYPE_IPV4_P2P_TUNNEL'";
      }
      type inet:ipv4-address;
      description
        "P2P LSP destination";
    }
    leaf fec-destination-p2mp-id {
      when "../fec-ctype = 'mpls-lib-c-type-ipv4-p2mp-tunnel'" {
        description
          "../FEC_CType =
           'MPLS_LIB_CTYPE_IPV4_P2MP_TUNNEL'";
      }
      type uint32;
      description
        "P2MP ID";
    }
  }

  grouping TE-LSP-FEC {
    description
      "A LSP FEC";
    container fec-destination-info {
      description
        "Destination or P2MP ID";
      uses TE-LSP-FEC-CTYPE-DATA;
    }
    leaf fec-lsp-id {
      type uint16;
      description
        "LSP ID";
    }
    leaf fec-tunnel-id {
      type uint16;
      description
        "Tunnel ID";
    }
    leaf fec-extended-tunnel-id {
      type inet:ipv4-address;
      description
        "Extended tunnel ID";
    }
    leaf fec-source {
      type inet:ipv4-address;
      description
        "Tunnel source address";
    }
    leaf fec-vrf {
      type string;
      description
        "VRF; currently only for GMPLS tunnels";
    }
  }
}
