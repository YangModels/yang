submodule Cisco-IOS-XR-shellutil-oper-sub1 {

  belongs-to Cisco-IOS-XR-shellutil-oper {
    prefix Cisco-IOS-XR-shellutil-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR shellutil package operational data.

     Copyright (c) 2013-2014 by Cisco Systems, Inc.
     All rights reserved.";

  revision "2013-07-22" {
    description
      "Initial revision.";
  }

  typedef Time-source {
    type enumeration {
      enum error {
        value 0;
        description "Error";
      }
      enum none {
        value 1;
        description "Unsynchronized time";
      }
      enum ntp {
        value 2;
        description "Network time protocol";
      }
      enum manual {
        value 3;
        description "User configured";
      }
      enum calendar {
        value 4;
        description "Hardware calendar";
      }
    }
    description "Time source";
  }

  grouping SYSTEM-UPTIME {
    description "System uptime";
    leaf host-name {
      xr:xr-xml-map "shellutil_clock:Hostname";
      type string;
      description "Host name";
    }
    leaf uptime {
      xr:xr-xml-map "shellutil_clock:Uptime";
      type uint32;
      units "second";
      description
        "Amount of time in seconds since this system    
        was last initialized";
    }
  }

  grouping TIME-DATE {
    description "Date and time";
    leaf year {
      xr:xr-xml-map "shellutil_clock:Year";
      type uint16;
      description "Year [0..65535]";
    }
    leaf month {
      xr:xr-xml-map "shellutil_clock:Month";
      type uint8;
      description "Month [1..12]";
    }
    leaf day {
      xr:xr-xml-map "shellutil_clock:Day";
      type uint8;
      description "Day [1..31]";
    }
    leaf hour {
      xr:xr-xml-map "shellutil_clock:Hour";
      type uint8;
      description "Hour [0..23]";
    }
    leaf minute {
      xr:xr-xml-map "shellutil_clock:Minute";
      type uint8;
      description "Minute [0..59]";
    }
    leaf second {
      xr:xr-xml-map "shellutil_clock:Second";
      type uint8;
      description "Second [0..60], use 60 for leap-second";
    }
    leaf millisecond {
      xr:xr-xml-map "shellutil_clock:Millisecond";
      type uint16;
      description "Millisecond [0..999]";
    }
    leaf time-zone {
      xr:xr-xml-map "shellutil_clock:TimeZone";
      type string;
      description "Time zone";
    }
    leaf time-source {
      xr:xr-xml-map "shellutil_clock:TimeSource";
      type Time-source;
      description "Time source";
    }
  }
}
