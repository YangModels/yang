module Cisco-IOS-XR-tty-management-oper {

  /*** NAMESPACE / PREFIX DEFINITION ***/

  namespace "http://cisco.com/ns/yang"+
    "/Cisco-IOS-XR-tty-management-oper";


  prefix "tty-management-oper";

  /*** LINKAGE (IMPORTS / INCLUDES) ***/

  import Cisco-IOS-XR-types { prefix "xr"; }

  import Cisco-IOS-XR-tty-server-oper { prefix "a1"; }

  include Cisco-IOS-XR-tty-management-oper-sub1 {
    revision-date 2013-07-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tty-management package operational data.

     This YANG module augments the
       Cisco-IOS-XR-tty-server-oper
     module with state data.

     Copyright (c) 2013-2014 by Cisco Systems, Inc.
     All rights reserved.";

  revision "2013-07-22" {
    description
      "Initial revision.";
  }


  augment "/a1:tty/a1:vty-lines/a1:vty-line" {

    container sessions {
      xr:xr-xml-map "tty_management_oper:Sessions";
      description "Outgoing sessions";
      uses CONN-OUT-TABLE-BAG;
    }
    description
      "This augment extends the operational data of
      'Cisco-IOS-XR-tty-server-oper'";
  }
}
