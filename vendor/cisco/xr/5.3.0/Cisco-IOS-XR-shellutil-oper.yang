module Cisco-IOS-XR-shellutil-oper {

  /*** NAMESPACE / PREFIX DEFINITION ***/

  namespace "http://cisco.com/ns/yang/Cisco-IOS-XR-shellutil-oper";


  prefix "shellutil-oper";

  /*** LINKAGE (IMPORTS / INCLUDES) ***/

  import Cisco-IOS-XR-types { prefix "xr"; }

  include Cisco-IOS-XR-shellutil-oper-sub1 {
    revision-date 2013-07-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR shellutil package operational data.

     This module contains definitions
     for the following management objects:
       system-time: System time information

     Copyright (c) 2013-2014 by Cisco Systems, Inc.
     All rights reserved.";

  revision "2013-07-22" {
    description
      "Initial revision.";
  }


  container system-time {
    xr:xr-xml-map "shellutil_clock_oper:SystemTime";
    config false;
    description "System time information";

    container clock {
      xr:xr-xml-map "shellutil_clock_oper:Clock";
      description "System clock information";
      uses TIME-DATE;
    }

    container uptime {
      xr:xr-xml-map "shellutil_clock_oper:Uptime";
      description "System uptime information";
      uses SYSTEM-UPTIME;
    }
  }
}
