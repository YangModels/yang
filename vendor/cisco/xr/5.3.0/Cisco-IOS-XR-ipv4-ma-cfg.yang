module Cisco-IOS-XR-ipv4-ma-cfg {

  /*** NAMESPACE / PREFIX DEFINITION ***/

  namespace "http://cisco.com/ns/yang/Cisco-IOS-XR-ipv4-ma-cfg";


  prefix "ipv4-ma-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-ma package configuration.

     This module contains definitions
     for the following management objects:
       ipv4-network-global: IPv4 network global configuration data
       subscriber-pta: subscriber pta

     Copyright (c) 2013-2014 by Cisco Systems, Inc.
     All rights reserved.";

  revision "2013-07-22" {
    description
      "Initial revision.";
  }

  typedef Ipv4-network-rate {
    type uint32 {
      range "1..4294967295";
    }
    description "Ipv4 network rate";
  }
  typedef Ipv4-qppb {
    type enumeration {
      enum none {
        value 0;
        description "No QPPB configuration";
      }
      enum ip-prec {
        value 1;
        description "Enable ip-precedence based QPPB";
      }
      enum qos-grp {
        value 2;
        description "Enable qos-group based QPPB";
      }
      enum both {
        value 3;
        description
          "Enable both ip-precedence and qos-group based
          QPPB";
      }
    }
    description "Ipv4 qppb";
  }

  container ipv4-network-global {
    xr:xr-xml-map "ipv4_cfg:IPV4NetworkGlobal";
    description "IPv4 network global configuration data";

    container icmp {
      xr:xr-xml-map "ipv4_cfg:ICMP";
      description "ICMP options";

      container rate-limit {
        xr:xr-xml-map "ipv4_cfg:RateLimit";
        description "Rate limit generation of ICMP messages";

        container unreachable {
          xr:xr-xml-map "ipv4_cfg:Unreachable";
          description "Destination Unreachable rate limiting";
          leaf rate {
            xr:xr-xml-map "ipv4_cfg:Rate";
            type Ipv4-network-rate;
            units "millisecond";
            description
              "Destination Unreachable packet response rate
              limit value in milliseconds";
          }
          leaf df {
            xr:xr-xml-map "ipv4_cfg:DF";
            type Ipv4-network-rate;
            units "millisecond";
            description
              "Destination Unreachable DF packets requiring
              fragmentation response rate limit value in
              milliseconds";
          }
        }
      }
    }

    container unnumbered {
      xr:xr-xml-map "ipv4_cfg:Unnumbered";
      description
        "Enable IPv4 processing without an explicit
        address";

      container mpls {
        xr:xr-xml-map "ipv4_cfg:MPLS";
        description "Configure MPLS routing protocol parameters";

        container te {
          xr:xr-xml-map "ipv4_cfg:TE";
          description "IPv4 commands for MPLS Traffic Engineering";
          leaf interface {
            xr:xr-xml-map "ipv4_cfg:Interface";
            xr:xr-cli-map "unnumbered mpls traffic-eng <interface> ";
            type string;
            description
              "The interface whose IPv4 addresses are
              adopted";
          }
        }
      }
    }

    container qppb {
      xr:xr-xml-map "ipv4_cfg:QPPB";
      description "QPPB";
      leaf source {
        xr:xr-xml-map "ipv4_cfg:Source";
        type Ipv4-qppb;
        description "QPPB configuration on source";
      }
      leaf destination {
        xr:xr-xml-map "ipv4_cfg:Destination";
        type Ipv4-qppb;
        description "QPPB configuration on destination";
      }
    }
    leaf source-route {
      xr:xr-xml-map "ipv4_cfg:SourceRoute";
      xr:xr-cli-map "source-route ";
      type boolean;
      default "true";
      description "TRUE if enabled, FALSE if disabled";
    }
    leaf reassemble-max-packets {
      xr:xr-xml-map "ipv4_cfg:ReassembleMaxPackets";
      xr:xr-cli-map "assembler max-packets <number> ";
      type uint32 {
        range "1..50";
      }
      units "percentage";
      description
        "Percentage of total packets available in the
        system";
    }
    leaf reassemble-time-out {
      xr:xr-xml-map "ipv4_cfg:ReassembleTimeOut";
      xr:xr-cli-map "assembler timeout <number> ";
      type uint32 {
        range "1..120";
      }
      units "second";
      description
        "Number of seconds a reassembly queue will hold
        before timeout";
    }
  }

  container subscriber-pta {
    xr:xr-xml-map "ipv4_sub_tcp_mss_cfg:SubscriberPTA";
    description "subscriber pta";
    leaf tcp-mss-adjust {
      xr:xr-xml-map "ipv4_sub_tcp_mss_cfg:TCP_MSSAdjust";
      xr:xr-cli-map "pta tcp mss-adjust <number> ";
      type uint32 {
        range "1280..1536";
      }
      units "byte";
      description "TCP MSS Adjust (bytes)";
    }
  }
}
