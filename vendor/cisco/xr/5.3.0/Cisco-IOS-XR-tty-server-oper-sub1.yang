submodule Cisco-IOS-XR-tty-server-oper-sub1 {

  belongs-to Cisco-IOS-XR-tty-server-oper {
    prefix Cisco-IOS-XR-tty-server-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR tty-server package operational data.

     Copyright (c) 2013-2014 by Cisco Systems, Inc.
     All rights reserved.";

  revision "2013-07-22" {
    description
      "Initial revision.";
  }


  grouping TTY-CONNECTION-STATS {
    description "TTY connection statistics";
    leaf incoming-host-address {
      xr:xr-xml-map "tty_connection:IncomingHostAddress";
      type string {
        length "0..46";
      }
      description "Incoming host address(max)";
    }
    leaf host-address-family {
      xr:xr-xml-map "tty_connection:HostAddressFamily";
      type uint32;
      description "Incoming host address family";
    }
    leaf service {
      xr:xr-xml-map "tty_connection:Service";
      type uint32;
      description "Input transport";
    }
  }
}
