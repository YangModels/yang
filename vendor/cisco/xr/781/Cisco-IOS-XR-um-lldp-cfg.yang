module Cisco-IOS-XR-um-lldp-cfg {
  namespace "http://cisco.com/ns/yang/Cisco-IOS-XR-um-lldp-cfg";
  prefix um-lldp-cfg;

  import Cisco-IOS-XR-types {
    prefix xr;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lldp package configuration.
     
     This YANG module augments the
     modules with configuration data.
     
     Copyright (c) 2020-2022 by Cisco Systems, Inc.
     All rights reserved.";

  revision 2022-09-16 {
    description
      "Added chassis-id and system-description nodes
       2022-07-11
         Added missing description statement to nodes";
    semver:module-version "1.1.0";
  }
  revision 2020-03-23 {
    description
      "Initial release";
    semver:module-version "1.0.0";
  }

  grouping IF-BODY {
    description
      "Grouping for interface";
    container lldp {
      presence "Indicates a lldp node is configured.";
      description
        "LLDP interface configuration commands";
      container transmit {
        description
          "Disable LLDP TX on an interface";
        container disable {
          presence "Indicates a disable node is configured.";
          description
            "Disable LLDP TX on an interface";
        }
      }
      container receive {
        description
          "Disable LLDP RX on an interface";
        container disable {
          presence "Indicates a disable node is configured.";
          description
            "Disable LLDP RX on an interface";
        }
      }
      container destination {
        description
          "Configure LLDP Destination MAC on the interface";
        container mac-address {
          presence "Indicates a mac-address node is configured.";
          description
            "Destination MAC address on the interface";
          container ieee-nearest-non-tmpr-bridge {
            must "not(../ieee-nearest-bridge)";
            presence "Indicates a ieee-nearest-non-tmpr-bridge node is configured.";
            description
              "IEEE Non-TMPR Bridge MAC address, 01:80:C2:00:00:03";
          }
          container ieee-nearest-bridge {
            must "not(../ieee-nearest-non-tmpr-bridge)";
            presence "Indicates a ieee-nearest-bridge node is configured.";
            description
              "Default LLDP Destination MAC address, 01:80:C2:00:00:0E";
          }
        }
      }
      container enable {
        presence "Indicates a enable node is configured.";
        description
          "Enable LLDP TX and RX on an interface";
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  container lldp {
    presence "Indicates a lldp node is configured.";
    description
      "Enable LLDP, or configure global LLDP subcommands";
    leaf holdtime {
      type uint32 {
        range "0..65535" {
          description
            "Length of time (in sec) that receiver must keep this packet";
        }
      }
      description
        "Specify the holdtime (in sec) to be sent in packets";
    }
    leaf timer {
      type uint32 {
        range "5..65534" {
          description
            "Rate at which LLDP packets are sent (in sec)";
        }
      }
      description
        "Specify the rate at which LLDP packets are sent (in sec)";
    }
    leaf reinit {
      type uint32 {
        range "2..5" {
          description
            "Delay (in sec) for LLDP initialization on any interface";
        }
      }
      description
        "Delay (in sec) for LLDP initialization on any interface";
    }
    leaf system-name {
      type xr:Cisco-ios-xr-string {
        length "1..256" {
          description
            "LLDP system name string";
        }
        pattern "[a-zA-Z0-9_.-]+";
      }
      description
        "LLDP system name to advertise";
    }
    leaf system-description {
      type xr:Cisco-ios-xr-string {
        length "1..256" {
          description
            "LLDP system description string";
        }
        pattern "[a-zA-Z0-9_.-]+";
      }
      description
        "LLDP system description to advertise";
    }
    leaf chassis-id {
      type xr:Cisco-ios-xr-string {
        length "1..256" {
          description
            "LLDP chassis id string";
        }
        pattern "[a-zA-Z0-9_.-:]+";
      }
      description
        "LLDP chassis ID to advertise";
    }
    container chassis-id-type {
      description
        "LLDP chassis ID type to advertise";
      container port-component {
        must
          "not(../network-address or ../chassis-component
           or ../mac-address or ../interface-name
           or ../local or ../interface-alias)";
        presence "Indicates a port-component node is configured.";
        description
          "Value of entPhysicalAlias object defined in IETF RFC 2737";
      }
      container network-address {
        must
          "not(../port-component or ../chassis-component
           or ../mac-address or ../interface-name
           or ../local or ../interface-alias)";
        presence "Indicates a network-address node is configured.";
        description
          "Network address associated with a particular chassis";
      }
      container chassis-component {
        must
          "not(../port-component or ../network-address
           or ../mac-address or ../interface-name
           or ../local or ../interface-alias)";
        presence "Indicates a chassis-component node is configured.";
        description
          "Value of entPhysicalAlias object defined in IETF RFC 2737";
      }
      container mac-address {
        must
          "not(../port-component or ../network-address
           or ../chassis-component or ../interface-name
           or ../local or ../interface-alias)";
        presence "Indicates a mac-address node is configured.";
        description
          "Value of a unicast source address";
      }
      container interface-name {
        must
          "not(../port-component or ../network-address
           or ../chassis-component or ../mac-address
           or ../local or ../interface-alias)";
        presence "Indicates a interface-name node is configured.";
        description
          "Value of ifName object defined in IETF RFC 2863";
      }
      container local {
        must
          "not(../port-component or ../network-address
           or ../chassis-component or ../mac-address
           or ../interface-name or ../interface-alias)";
        presence "Indicates a local node is configured.";
        description
          "Chassis identifier based on a locally defined value";
      }
      container interface-alias {
        must
          "not(../port-component or ../network-address
           or ../chassis-component or ../mac-address
           or ../interface-name or ../local)";
        presence "Indicates a interface-alias node is configured.";
        description
          "Value of ifAlias object defined in IETF RFC 2863";
      }
    }
    container subinterfaces {
      description
        "Configure LLDP over Sub-interfaces";
      container enable {
        presence "Indicates a enable node is configured.";
        description
          "Enable LLDP over Sub-interfaces as well";
      }
    }
    container management {
      description
        "Configure LLDP over Management interface";
      container enable {
        presence "Indicates a enable node is configured.";
        description
          "Enable LLDP over Management interface as well";
      }
    }
    container priorityaddr {
      description
        "Configure Priority to advertise Management interface address first";
      container enable {
        presence "Indicates a enable node is configured.";
        description
          "Enable LLDP to use Management interface address first(if configured)";
      }
    }
    container extended-show-width {
      description
        "Configure Extended Show LLDP Neighbor Width";
      container enable {
        presence "Indicates a enable node is configured.";
        description
          "Enable Extended Show LLDP Neighbor Width";
      }
    }
    container tlv-select {
      presence "Indicates a tlv-select node is configured.";
      description
        "Selection of LLDP TLVs to disable";
      container management-address {
        description
          "Management Address TLV";
        container disable {
          presence "Indicates a disable node is configured.";
          description
            "disable Management Address TLV";
        }
      }
      container port-description {
        description
          "Port Description TLV";
        container disable {
          presence "Indicates a disable node is configured.";
          description
            "disable Port Description TLV";
        }
      }
      container system-capabilities {
        description
          "System Capabilities TLV";
        container disable {
          presence "Indicates a disable node is configured.";
          description
            "disable System Capabilities TLV";
        }
      }
      container system-description {
        description
          "System Description TLV";
        container disable {
          presence "Indicates a disable node is configured.";
          description
            "disable System Description TLV";
        }
      }
      container system-name {
        description
          "System Name TLV";
        container disable {
          presence "Indicates a disable node is configured.";
          description
            "disable System Name TLV";
        }
      }
    }
  }
}
