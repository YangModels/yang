submodule Cisco-IOS-XR-ofa-npu-pfc-oper-sub1 {
  belongs-to Cisco-IOS-XR-ofa-npu-pfc-oper {
    prefix Cisco-IOS-XR-ofa-npu-pfc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-npu-pfc package operational data.
     
     Copyright (c) 2013-2022 by Cisco Systems, Inc.
     All rights reserved.";

  revision 2022-10-12 {
    description
      "Added ecn and ecn-max unit fields.";
    semver:module-version "1.0.0";
  }
  revision 2021-08-19 {
    description
      "Create the initial priority-flow-control oper yang model.";
  }
  revision 2019-04-05 {
    description
      "Establish semantic version baseline.";
  }
  revision 2015-11-09 {
    description
      "IOS XR 6.0 revision.";
  }

  grouping OFA-PFC-TC-CFG {
    description
      "OFA PFC TC CFG";
    leaf in-use {
      type boolean;
      description
        "Flag to indicate if PFC is configured for the tc";
    }
    leaf tc-pause-threshold {
      type uint32;
      description
        "Pause-threshold configured";
    }
    leaf tc-headroom {
      type uint32;
      description
        "Headroom configured";
    }
    leaf tc-ecn {
      type uint32;
      description
        "ECN configured";
    }
    leaf tc-ecn-max {
      type uint32;
      description
        "ECN Max configured";
    }
    leaf tc-prob-per {
      type uint32;
      description
        "ECN Prob Per configured";
    }
    leaf tc-pause-threshold-unit {
      type string {
        length "0..6";
      }
      description
        "Pause-threshold Unit";
    }
    leaf tc-headroom-unit {
      type string {
        length "0..6";
      }
      description
        "Headroom Unit";
    }
    leaf tc-ecn-unit {
      type string {
        length "0..6";
      }
      description
        "Ecn Unit";
    }
    leaf tc-ecn-max-unit {
      type string {
        length "0..6";
      }
      description
        "Ecn Max Unit";
    }
  }

  grouping OFA-PFC-CFG {
    description
      "OFA PFC CFG";
    leaf in-use {
      type boolean;
      description
        "Flag to indicate if PFC is configured for the
         line-card";
    }
    leaf pfc-mode {
      type string {
        length "0..16";
      }
      description
        "pfc mode configured";
    }
    list tc-cfg {
      max-elements "8";
      description
        "Keeps a record of the PFC configuration for the
         line-card";
      uses OFA-PFC-TC-CFG;
    }
  }
}
