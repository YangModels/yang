module Cisco-IOS-XR-um-dyn-tmpl-opendns-cfg {
  namespace "http://cisco.com/ns/yang/Cisco-IOS-XR-um-dyn-tmpl-opendns-cfg";
  prefix um-dyn-tmpl-opendns-cfg;

  import Cisco-IOS-XR-types {
    prefix xr;
  }
  import ietf-inet-types {
    prefix inet;
  }
  import Cisco-IOS-XR-um-dynamic-template-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dyn-tmpl-opendns package configuration.
     
     This YANG module augments the
     modules with configuration data.
     
     Copyright (c) 2022 by Cisco Systems, Inc.
     All rights reserved.";

  revision 2022-07-11 {
    description
      "Added missing description statement to nodes";
    semver:module-version "1.1.0";
  }
  revision 2021-03-22 {
    description
      "Initial release";
    semver:module-version "1.0.0";
  }

  grouping TEMPLATE-BODY {
    description
      "Grouping for template";
    container framedroute {
      description
        "Specify additional routes to add for this subscriber [Restricted to development use only !!!]";
      leaf ip-address {
        type inet:ipv4-address-no-zone;
        description
          "framed route address";
      }
    }
    container opendns {
      description
        "OpenDNS feature config";
      leaf deviceid {
        type xr:Cisco-ios-xr-string {
          length "16" {
            description
              "Device ID (16 digit hex value without '0x')";
          }
          pattern "0*[1-9a-fA-F][0-9a-fA-F]*";
        }
        description
          "Specify device ID";
      }
    }
  }

  augment "/a1:dynamic-template/a1:type/a1:service/a1:template" {
    description
      "This augment extends dynamic-template service nodes
       configuration";
    uses TEMPLATE-BODY;
  }
}
