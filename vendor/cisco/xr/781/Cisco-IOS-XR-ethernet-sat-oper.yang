module Cisco-IOS-XR-ethernet-sat-oper {
  namespace "http://cisco.com/ns/yang/Cisco-IOS-XR-ethernet-sat-oper";
  prefix ethernet-sat-oper;

  import Cisco-IOS-XR-types {
    prefix xr;
  }
  import cisco-semver {
    prefix semver;
  }
  include Cisco-IOS-XR-ethernet-sat-oper-sub1 {
    revision-date 2021-12-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-sat package operational data.
     
     This module contains definitions
     for the following management objects:
       service-activation-test: SAT operational data
     
     Copyright (c) 2013-2021 by Cisco Systems, Inc.
     All rights reserved.";

  revision 2021-12-10 {
    description
      "Add support for reporting packet-format
       2021-12-10
         Add burst config option";
    semver:module-version "1.2.0";
  }
  revision 2021-03-29 {
    description
      "Add support for reporting frame delay statistics";
    semver:module-version "1.1.0";
  }
  revision 2019-04-05 {
    description
      "Establish semantic version baseline.";
    semver:module-version "1.0.0";
  }
  revision 2015-11-09 {
    description
      "IOS XR 6.0 revision.";
  }

  container service-activation-test {
    config false;
    description
      "SAT operational data";
    container test-statuses {
      description
        "Table for interfaces with SAT permissions";
      list test-status {
        key "interface-name";
        description
          "SAT status on the interface";
        leaf interface-name {
          type xr:Interface-name;
          description
            "Interface name";
        }
        uses SAT-MA-OPER-TEST-STATUS;
      }
    }
  }
}
