//*************  DO-NOT EDIT  **************
//*********** Auto-generated file **********

 module cisco-xr-openconfig-transport-line-common-deviations {

  namespace "http://cisco.com/ns/yang/cisco-xr-openconfig-transport-line-common-deviations";
  prefix  "oc-line-comdevs";

  import openconfig-platform { prefix oc-platform; }
  import openconfig-transport-line-common { prefix oc-line-com; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for

     openconfig-transport-line-common.yang@2018-11-21

     on Cisco IOS-XR devices.

     Copyright (c) 2017, 2025 by Cisco Systems, Inc.
     All rights reserved.";

  revision "2025-01-26" {
    description
      "Upgraded revision 0.6.0 applicable to IOS-XR 25.2.1";
  }
  
  revision "2019-11-26" {
    description
      "Initial revision applicable to IOS-XR 6.4.1";
  }

  deviation /oc-platform:components/oc-platform:component/oc-platform:port/oc-line-com:optical-port/oc-line-com:state/oc-line-com:optical-port-type {
    deviate not-supported;
  }

}
//total deviations:1
