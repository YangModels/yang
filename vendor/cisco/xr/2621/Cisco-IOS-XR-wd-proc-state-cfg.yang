module Cisco-IOS-XR-wd-proc-state-cfg {
  namespace "http://cisco.com/ns/yang/Cisco-IOS-XR-wd-proc-state-cfg";
  prefix wd-proc-state-cfg;

  import Cisco-IOS-XR-types {
    prefix xr;
  }
  import cisco-semver {
    prefix semver;
  }
  import Cisco-IOS-XR-config-mda-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR wd-proc-state package configuration.
     
     This module contains definitions
     for the following management objects:
       process-state-monitor: Watchdog Root
     
     This YANG module augments the
       Cisco-IOS-XR-config-mda-cfg
     module with configuration data.
     
     Copyright (c) 2013-2022 by Cisco Systems, Inc.
     All rights reserved.";

  revision 2022-01-24 {
    description
      "Using common class to link to /cfg/node/act/";
    semver:module-version "2.0.0";
  }
  revision 2019-04-05 {
    description
      "Establish semantic version baseline.";
    semver:module-version "1.0.0";
  }
  revision 2015-11-09 {
    description
      "IOS XR 6.0 revision.";
  }

  augment "/a1:active-nodes/a1:active-node" {
    description
      "This augment extends the configuration data of
       'Cisco-IOS-XR-config-mda-cfg'";
    container process-state-monitor {
      description
        "Monitor process for death notification";
      container process-names {
        description
          "Process Names";
        list process-name {
          key "process-name";
          description
            "Process Name";
          leaf process-name {
            type xr:Cisco-ios-xr-string;
            description
              "Name of the process";
          }
        }
      }
    }
  }
  container process-state-monitor {
    description
      "Watchdog Root";
    container location {
      description
        "Location where the process is monitored";
      container all {
        description
          "Processes configured under all";
        container process-names {
          description
            "Process Names";
          list process-name {
            key "process-name";
            description
              "Process Name";
            leaf process-name {
              type xr:Cisco-ios-xr-string;
              description
                "Name of the process";
            }
          }
        }
      }
    }
  }
}
