module Cisco-IOS-XR-bte-test-oper {
  namespace "http://cisco.com/ns/yang/Cisco-IOS-XR-bte-test-oper";
  prefix bte-test-oper;

  import ietf-inet-types {
    prefix inet;
  }
  import ietf-yang-types {
    prefix yang;
  }
  import Cisco-IOS-XR-types {
    prefix xr;
  }
  import cisco-semver {
    prefix semver;
  }
  include Cisco-IOS-XR-bte-test-oper-sub1 {
    revision-date 2025-12-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR bte-test package operational data.
     
     This module contains definitions
     for the following management objects:
       bte-test: BTE test operational data
     
     Copyright (c) 2013-2025 by Cisco Systems, Inc.
     All rights reserved.";

  revision 2025-12-04 {
    description
      "Initial commit";
    semver:module-version "1.0.0";
  }
  revision 2019-04-05 {
    description
      "Establish semantic version baseline.";
  }
  revision 2015-11-09 {
    description
      "IOS XR 6.0 revision.";
  }

  container bte-test {
    config false;
    description
      "BTE test operational data";
    container list2-entries {
      description
        "Container for testing list 2 structures";
      list list2-entry {
        key "ipv4-address-val ipv6-address-val ip-address-val interface-val interface-forward-val";
        description
          "List 2 entry for testing different key types";
        leaf ipv4-address-val {
          type inet:ipv4-address-no-zone;
          description
            "IPv4 address";
        }
        leaf ipv6-address-val {
          type inet:ipv6-address-no-zone;
          description
            "IPv6 address";
        }
        leaf ip-address-val {
          type inet:ip-address-no-zone;
          description
            "IP address (generic)";
        }
        leaf interface-val {
          type xr:Interface-name;
          description
            "Interface";
        }
        leaf interface-forward-val {
          type xr:Interface-name;
          description
            "Interface forward";
        }
        uses BTE-TEST-SIMPLE;
      }
    }
    container list3-entries {
      description
        "Container for testing list 3 structures";
      list list3-entry {
        key "node-val vrf-id-val encoded-string-val encoded-bounded-string-val enum-val";
        description
          "List 3 entry for testing different key types";
        leaf node-val {
          type xr:Node-id;
          description
            "Node ID";
        }
        leaf vrf-id-val {
          type xr:Cisco-ios-xr-string;
          description
            "VRF ID";
        }
        leaf encoded-string-val {
          type string;
          description
            "Encoded string";
        }
        leaf encoded-bounded-string-val {
          type string {
            length "1..32";
          }
          description
            "Encoded bounded string";
        }
        leaf enum-val {
          type enumeration {
            enum "red" {
              value 1;
              description
                "Red";
            }
            enum "green" {
              value 2;
              description
                "Green";
            }
            enum "blue" {
              value 3;
              description
                "Blue";
            }
          }
          description
            "Enumeration";
        }
        uses BTE-TEST-SIMPLE;
      }
    }
    container list4-entries {
      description
        "Container for testing list 4 structures";
      list list4-entry {
        key "hex-integer-val sys-db-node-val mac-address-val ipv6-address-hex-string-val";
        description
          "List 4 entry for testing different key types";
        leaf hex-integer-val {
          type xr:Hex-integer;
          description
            "Hexadecimal integer";
        }
        leaf sys-db-node-val {
          type xr:Node-id;
          description
            "SysDB Node ID";
        }
        leaf mac-address-val {
          type yang:mac-address;
          description
            "MAC address";
        }
        leaf ipv6-address-hex-string-val {
          type inet:ipv6-address-no-zone;
          description
            "IPv6 address in hex string format";
        }
        uses BTE-TEST-SIMPLE;
      }
    }
    container linked-list-bag {
      description
        "A linked list bag";
      uses BTE-TEST-LINKED-LIST-BAG;
    }
    container bag-with-linked-list-bag {
      description
        "Bag containing a bag with self-references";
      uses BTE-TEST-BAG-WITH-LINKED-LIST-BAG;
    }
    container bag-with-linked-list-struct {
      description
        "Bag containing a struct with self-references";
      uses BTE-TEST-BAG-WITH-LINKED-LIST-STRUCT;
    }
    container list1-entries {
      description
        "Container for testing list 1 structures";
      list list1-entry {
        key "string-val integer-val signed-integer-val dec-integer-val dec-signed-integer-val dec-node-val interface-handle-val";
        description
          "List 1 entry for testing different key types";
        leaf string-val {
          type xr:Cisco-ios-xr-string;
          description
            "String value";
        }
        leaf integer-val {
          type uint32;
          description
            "Integer value";
        }
        leaf signed-integer-val {
          type int32;
          description
            "Signed integer";
        }
        leaf dec-integer-val {
          type uint32;
          description
            "Decimal Integer value";
        }
        leaf dec-signed-integer-val {
          type int32;
          description
            "Decimal Signed integer";
        }
        leaf dec-node-val {
          type xr:Node-id;
          description
            "Decimal Node ID";
        }
        leaf interface-handle-val {
          type xr:Interface-name;
          description
            "Interface handle";
        }
        uses BTE-TEST-SIMPLE;
      }
    }
    container datatype-bag {
      description
        "Bag with a variety of datatypes";
      uses BTE-TEST-DATATYPES;
    }
  }
}
