module Cisco-IOS-XR-ncs1001-passive-oper {
  namespace "http://cisco.com/ns/yang/Cisco-IOS-XR-ncs1001-passive-oper";
  prefix ncs1001-passive-oper;

  import cisco-semver {
    prefix semver;
  }
  include Cisco-IOS-XR-ncs1001-passive-oper-sub1 {
    revision-date 2020-12-12;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-passive package operational data.
     
     This module contains definitions
     for the following management objects:
       hw-module: ncs1001 hw-module command chain
     
     Copyright (c) 2013-2020 by Cisco Systems, Inc.
     All rights reserved.";

  revision 2020-12-12 {
    description
      "XML query for CLI show hw-module ampli-trail-view/channel-trail-view does not return a response";
    semver:module-version "1.0.0";
  }
  revision 2019-04-05 {
    description
      "Establish semantic version baseline.";
  }
  revision 2015-11-09 {
    description
      "IOS XR 6.0 revision.";
  }

  typedef Ots-passive-eeprom-data {
    type enumeration {
      enum "all" {
        value 0;
        description
          "Displays all eeprom data";
      }
      enum "il" {
        value 1;
        description
          "Displays insertion loss data";
      }
      enum "manuf" {
        value 2;
        description
          "Displays manuf data";
      }
    }
    description
      "Ots passive eeprom data";
  }

  container hw-module {
    config false;
    description
      "ncs1001 hw-module command chain";
    container passive-eeproms {
      description
        "Passive eeprom data information";
      list passive-eeprom {
        key "usb-port";
        description
          "Passive Eeprom Info";
        leaf usb-port {
          type uint32 {
            range "0..3";
          }
          description
            "Details associated with a particular port
             number";
        }
        list passive-eeprom-data {
          key "passive-eeprom-data-type";
          description
            "Display data type list";
          leaf passive-eeprom-data-type {
            type Ots-passive-eeprom-data;
            description
              "Details associated with a particular Data
               type";
          }
          uses OTS-HWMOD-PASSIVE-EEPROM-OP;
        }
      }
    }
  }
}
