module openconfig-pfm-hc {
  namespace "http://openconfig.net/yang/pfm-hc";
  prefix oc-pfm-hc;

  import Cisco-IOS-XR-types {
    prefix xr;
  }
  import cisco-semver {
    prefix semver;
  }
  organization
    "Cisco Systems, Inc.";
  contact
    "Cisco Systems, Inc.
     Customer Service

     Postal: 170 West Tasman Drive
     San Jose, CA 95134

     Tel: +1 800 553-NETS

     E-mail: cs-yang@cisco.com";
  description
    "Internal healthcheck model.

     Copyright (c) 2025-2026 by Cisco Systems, Inc., and/or its affiliates.
     All rights reserved.";

  revision 2025-08-20 {
    description
      "Initial commit";
  }
  typedef Im-cmd-stats-enum {
    type enumeration {
      enum full {
        value 1;
        description "full";
      }
      enum basic {
        value 2;
        description "basic";
      }
    }
    description "List of different interface stats structures";
  }
  container pfm-stats-metrics {
    container asic-errors {
        config false;
        description
        "Error summary of all asics";
        container nodes {
            description
                "Asic errors for each available nodes";
            list node {
                key "node-name";
                description
                "Asic error for a particular node";
                leaf node-name {
                    type xr:Node-id;
                    description
                        "Node ID";
                }
                container all-errors {
                    description
                        "All asic errors";
                    leaf num-nodes {
                        type uint32;
                        description
                            "Number of nodes";
                    }
                    list pacerr-count {
                        description
                            "Pac Error Count";
                        leaf name {
                            type string;
                            description
                                "Name of asic error";
                            }
                        leaf count {
                            type uint32;
                            description
                                "Number of occurrence";
                        }
                    }
                }
            }
        }
    }
    container fabric-stats {
        config false;
        description "Fabric Data";
        container fabric-plane-ids {
            description "Fabric Plane data for available planes";

            list fabric-plane-id {
                key "fabric-plane-key";
                description "Filter Fabric Plane data for specific plane";
                leaf fabric-plane-key {
                    type uint32;
                    description "Plane Number";
                }
                leaf planeid {
                    type int32;
                    description "planeid";
                }
                leaf ucast-oper-state {
                    type string;
                    description "ucast oper state";
                }
                leaf rx-ce-cells {
                    type uint64;
                    description "rx ce cells";
                }
                leaf rx-uce-cells {
                    type uint64;
                    description "rx uce cells";
                }
                leaf rx-pe-cells {
                    type uint64;
                    description "rx pe cells";
                }
                leaf ucast-lost-cells {
                    type uint32;
                    description "ucast lost cells";
                }
                leaf mcast-lost-cells {
                    type uint32;
                    description "mcast lost cells";
                }
                leaf asic-internal-drops {
                    type uint32;
                    description "asic internal drops";
                }
            }
        }
    }
    container intf-counters {
      container intf-list {
        description
          "Detailed operational data for interfaces and
          configured features";
        list intf {
          key "interface-name";
          description
            "Detailed operational data for a particular
            interface";
          leaf interface-name {
            type xr:Interface-name;
            description "The name of the interface";
          }
          leaf packets-received {
            type uint64;
            description "Total Packets received";
          }
          leaf packets-sent {
            type uint64;
            description "Total Packets sent";
          }
          leaf output-drops {
            type uint32;
            description "No. of packet dropped before being transmitted";
          }
          leaf output-queue-drops {
            type uint32;
            description
              "Number of packets dropped due to configured
              output policy";
          }
          leaf input-drops {
            type uint32;
            description "Total input drops";
          }
          leaf input-queue-drops {
            type uint32;
            description
              "Placeholder for packets dropped due to configure
              input policy";
          }
          leaf runt-packets-received {
            type uint32;
            description
              "Received packets which are too small to be
              handled";
          }
          leaf giant-packets-received {
            type uint32;
            description
              "Received packets which are too large to be
              handled";
          }
          leaf throttled-packets-received {
            type uint32;
            description
              "No. of times the receiver on the port is was
              disabled";
          }
          leaf parity-packets-received {
            type uint32;
            description "No. of parity errors on the interface";
          }
          leaf unknown-protocol-packets-received {
            type uint32;
            description
              "No. of packets dropped because they were
              destined for higher levelprotocols not configure
              or running on the interface";
          }
          leaf input-errors {
            type uint32;
            description "Total input errors";
          }
          leaf crc-errors {
            type uint32;
            description "Input CRC errors";
          }
          leaf input-overruns {
            type uint32;
            description
              "No. of input packets received with FIFO or DMA
              overrun errors";
          }
          leaf framing-errors-received {
            type uint32;
            description "No. of packets received with framing error";
          }
          leaf input-ignored-packets {
            type uint32;
            description
              "Packets dropped due to internal driver error or
              hardware errors ";
          }
          leaf input-aborts {
            type uint32;
            description "No. of packets whose reciept was aborted";
          }
          leaf output-errors {
            type uint32;
            description
              "Total packets that could not be transmitted due
              to internal driver error";
          }
          leaf output-underruns {
            type uint32;
            description
              "Transmitted packets with FIFO or DMA underrun
              errors";
          }
          leaf output-buffers-failures {
            type uint32;
            description "No. of no resource error received on output";
          }
          leaf output-buffers-swapped-out {
            type uint32;
            description "No. of packets swapped to DRAM or main memory";
          }
          leaf applique {
            type uint32;
            description
              "No. of unrecoverable error which have occured on
              the applique";
          }
          leaf resets {
            type uint32;
            description "Number of hardware resets";
          }
          leaf carrier-transitions {
            type uint32;
            description
              "No. of times the carrier detect signal of
              interface has changed state";
          }
          leaf is-intf-logical {
            type boolean;
            description
              "Flag to check if interface is logical or
              Physical";
          }
          leaf stats-type {
            type Im-cmd-stats-enum;
            description "StatsType";
          }
        }
      }
    }
  }
}
