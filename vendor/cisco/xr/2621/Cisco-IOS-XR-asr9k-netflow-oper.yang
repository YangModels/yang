module Cisco-IOS-XR-asr9k-netflow-oper {
  namespace "http://cisco.com/ns/yang/Cisco-IOS-XR-asr9k-netflow-oper";
  prefix asr9k-netflow-oper;

  import Cisco-IOS-XR-types {
    prefix xr;
  }
  import cisco-semver {
    prefix semver;
  }
  include Cisco-IOS-XR-asr9k-netflow-oper-sub2 {
    revision-date 2022-01-03;
  }
  include Cisco-IOS-XR-asr9k-netflow-oper-sub1 {
    revision-date 2022-01-03;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-netflow package operational data.
     
     This module contains definitions
     for the following management objects:
       net-flow: NetFlow operational data
     
     Copyright (c) 2013-2022 by Cisco Systems, Inc.
     All rights reserved.";

  revision 2022-01-03 {
    description
      "Added new fields for statistics on a stanbdy node exporter";
    semver:module-version "1.2.0";
  }
  revision 2021-08-18 {
    description
      "Added sFlow counters for ingress flows";
    semver:module-version "1.1.0";
  }
  revision 2019-12-16 {
    description
      "Added map-t logging counters for ingress flows.";
    semver:module-version "1.0.0";
  }
  revision 2019-04-05 {
    description
      "Establish semantic version baseline.";
  }
  revision 2015-11-09 {
    description
      "IOS XR 6.0 revision.";
  }

  container net-flow {
    config false;
    description
      "NetFlow operational data";
    container statistics {
      description
        "Node-specific NetFlow statistics information";
      list statistic {
        key "node";
        description
          "NetFlow statistics information for a particular
           node";
        container producer {
          description
            "NetFlow producer statistics";
          container statistics {
            description
              "Statistics information";
            uses NF-PRODUCER-STATS;
          }
        }
        container server {
          description
            "NetFlow server statistics";
          container flow-exporters {
            description
              "Flow exporter information";
            list flow-exporter {
              key "exporter-name";
              description
                "Exporter information";
              container exporter {
                description
                  "Statistics information for the exporter";
                uses NFSVR-SHOW-FLOW-EXPORTER-RESP-ARRAY;
              }
              leaf exporter-name {
                type xr:Cisco-ios-xr-string;
                description
                  "Exporter name";
              }
            }
          }
        }
        leaf node {
          type xr:Node-id;
          description
            "Node location";
        }
      }
    }
  }
}
