module Cisco-IOS-XR-sysadmin-ethsw-esdma-mlap-connectivity-info-iosxrwbd {
  namespace "http://www.cisco.com/ns/yang/Cisco-IOS-XR-sysadmin-ethsw-esdma-mlap-connectivity-info-iosxrwbd.yang";
  prefix esdma_cluster_connectivity;

  import Cisco-IOS-XR-sysadmin-ethsw-esdma-types {
    prefix esdma_types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show cluster connectivity ethernet control' command.
     
     Copyright(c) 2020 by Cisco Systems, Inc.
     All rights reserved.
     
     Copyright (c) 2012-2020 by Cisco Systems, Inc.
     All rights reserved.";

  revision 2021-03-01 {
    description
      "Removed unused imports from this yang file";
    semver:module-version "1.0.0";
  }
  revision 2021-02-05 {
    description
      "Modified ethernet control to control-ethernet for better correalation";
  }
  revision 2020-05-27 {
    description
      "Initial revision for changes to whitebox esdma-cluster connectivity CLI";
  }

  grouping cluster-connectivity-iosxrwbd {
    container connectivity {
      container control-ethernet {
        list location {
          key "rack card";
          leaf rack {
            type esdma_types:esdma-rack-num-enum;
          }
          leaf card {
            type esdma_types:esdma-cpu;
            description
              "Card that owns a switch of interest";
          }
          list port-iter {
            key "port";
            leaf port {
              type esdma_types:esdma-switch-port-type;
              description
                "Switch port";
            }
            leaf port-name {
              type string;
              description
                "Switch port";
            }
            leaf connects-to {
              type string;
              description
                "Indicates what this port connects to";
            }
            leaf expected-endpoint {
              type string;
              description
                "Indicates what this port is expected to connect to";
            }
            leaf mismatch-string {
              type string;
              description
                "Indicates whether there is a mismatch";
            }
          }
        }
      }
    }
  }
}
