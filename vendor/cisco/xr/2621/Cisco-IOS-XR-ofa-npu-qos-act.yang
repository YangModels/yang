module Cisco-IOS-XR-ofa-npu-qos-act {
  namespace "http://cisco.com/ns/yang/Cisco-IOS-XR-ofa-npu-qos-act";
  prefix ofa-npu-qos-act;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ofa-npu-qos package actions.
     
     This module contains definitions
     for the following management objects:
       npu-qos: NPU QOS data
     
     Copyright (c) 2024 by Cisco Systems, Inc.
     All rights reserved.";

  revision 2024-01-19 {
    description
      "Initial npu-qos action yang model with the
       clear-npu-qos-high-water-marks action";
    semver:module-version "1.0.0";
  }

  rpc clear-npu-qos-high-water-marks {
    description
      "Clear QoS traffic class high water marks";
    input {
      leaf type {
        type enumeration {
          enum "monotonic" {
            description
              "Clear monotonically increasing (since clear) high water marks";
          }
          enum "periodic" {
            description
              "Clear high water marks from recent periodic data collection intervals";
          }
        }
        description
          "type of high water marks to clear, default is all types";
      }
      leaf interface-name {
        type xr:Interface-name;
        description
          "Name of interface to be cleared, default is all interfaces";
      }
      leaf traffic-class {
        type uint8 {
          range "0..7";
        }
        description
          "Traffic class to be cleared, default is all traffic classes";
      }
      leaf node-name {
        type xr:Node-id;
        description
          "Location of interfaces to be cleared, default is all locations";
      }
    }
  }
}
