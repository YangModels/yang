module Cisco-IOS-XR-um-cont-optics-speed-cfg {
  namespace "http://cisco.com/ns/yang/Cisco-IOS-XR-um-cont-optics-speed-cfg";
  prefix um-cont-optics-speed-cfg;

  import Cisco-IOS-XR-types {
    prefix xr;
  }
  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-optics-speed package configuration.
     
     This YANG module augments the
     modules with configuration data.
     
     Copyright (c) 2022-2025 by Cisco Systems, Inc., and/or its affiliates.
     All rights reserved.";

  revision 2025-07-05 {
    description
      "Additon of host-lanes field. And also fix the speed-breakout options";
    semver:module-version "1.0.0";
  }
  revision 2022-07-11 {
    description
      "Added missing description statement to nodes";
  }
  revision 2022-06-01 {
    description
      "Adjusted controller augmentation hierarchy";
  }
  revision 2022-02-03 {
    description
      "Initial release";
  }

  feature optics {
    description
      "optics";
  }

  grouping CONT-BODY {
    description
      "Grouping for controller";
    container speed {
      when "../a1:controller-name[starts-with(text(),'Optics')]" {
        tailf:dependency "../a1:controller-name";
      }
      if-feature "optics";
      presence "Indicates a speed node is configured.";
      description
        "Configure port speed";
      leaf speed {
        type xr:Cisco-ios-xr-string {
          length "1..800" {
            description
              "1g | 10g | 25g | 40g | 50g | 100g | 200g | 300g | 400g | none";
          }
        }
        mandatory true;
        description
          "Configure port speed";
      }
      leaf host-lanes {
        type uint32 {
          range "1..16" {
            description
              "Number of host lanes used on the module";
          }
        }
        must "../speed";
        description
          "Specify the host lanes count for the module";
      }
    }
    container speed-breakout {
      when "../a1:controller-name[starts-with(text(),'Optics')]" {
        tailf:dependency "../a1:controller-name";
      }
      if-feature "optics";
      presence "Indicates a breakout node is configured.";
      description
        "Configure port speed breakout";
      leaf speed {
        type xr:Cisco-ios-xr-string {
          length "1..800" {
            description
              "4x10 | 4x25 | 8x25 | 1x40 | 2x50 | 8x50 | 1x100 | 2x100 | 3x100 | 4x100";
          }
        }
        mandatory true;
        description
          "Configure port breakout";
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
