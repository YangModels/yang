//*************  DO-NOT EDIT  **************
//*********** Auto-generated file ********** 

 module cisco-xr-openconfig-bgp-policy-deviations {

  prefix  "oc-bgp-poldevs";

  namespace "http://cisco.com/ns/yang/cisco-xr-openconfig-bgp-policy-deviations";

  import openconfig-bgp-policy { prefix oc-bgp-pol; }
  import openconfig-routing-policy { prefix oc-rpol; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-bgp-policy.yang@2024-01-31 

     on Cisco IOS-XR devices.

     Copyright (c) 2017 by Cisco Systems, Inc.
     All rights reserved.";

  revision "2019-08-31" {
    description
      "Updated revision applicable to IOS-XR 25.1.1 and OC BGP 7.0.0";
  }

  revision "2019-08-31" {
    description
      "Updated revision applicable to IOS-XR 7.1.1";
  }


  deviation /oc-rpol:routing-policy/oc-rpol:policy-definitions/oc-rpol:policy-definition/oc-rpol:statements/oc-rpol:statement/oc-rpol:conditions/oc-bgp-pol:bgp-conditions/oc-bgp-pol:config/oc-bgp-pol:afi-safi-in {
    deviate not-supported;
  }

  deviation /oc-rpol:routing-policy/oc-rpol:policy-definitions/oc-rpol:policy-definition/oc-rpol:statements/oc-rpol:statement/oc-rpol:conditions/oc-bgp-pol:bgp-conditions/oc-bgp-pol:state/oc-bgp-pol:afi-safi-in {
    deviate not-supported;
  }


}
//total deviations:2
