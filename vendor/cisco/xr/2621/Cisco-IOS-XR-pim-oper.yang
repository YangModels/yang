module Cisco-IOS-XR-pim-oper {
  namespace "http://cisco.com/ns/yang/Cisco-IOS-XR-pim-oper";
  prefix pim-oper;

  import ietf-inet-types {
    prefix inet;
  }
  import Cisco-IOS-XR-types {
    prefix xr;
  }
  import cisco-semver {
    prefix semver;
  }
  include Cisco-IOS-XR-pim-oper-sub2 {
    revision-date 2023-08-02;
  }
  include Cisco-IOS-XR-pim-oper-sub1 {
    revision-date 2023-08-02;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pim package operational data.
     
     This module contains definitions
     for the following management objects:
       pim-ma: PIM MA operational data
       pim: PIM operational data
       ipv6-pim: IPv6 PIM operational data
       pim6-ma: PIM6 MA operational data
     
     Copyright (c) 2013-2023 by Cisco Systems, Inc.
     All rights reserved.";

  revision 2023-08-02 {
    description
      "Changes for IR over TE-Tunnels
       2022-12-22
         Path change for Global interface table
       2022-10-31
         New addition made for Event history show command for periodic pim packets
       2022-08-26
         Addition made for Event history for periodic pim packets
       2022-04-20
         Getting rid of default context path
       2022-02-09
         Addition of new field to pim traffic bag Cisco-IOS-XR-pim-oper";
    semver:module-version "2.0.0";
  }
  revision 2021-02-17 {
    description
      "Addition made for Sticky DR neighbor tracking";
    semver:module-version "1.1.0";
  }
  revision 2019-12-24 {
    description
      "Fixed CSCvr52977.";
    semver:module-version "1.0.0";
  }
  revision 2019-08-27 {
    description
      "Providing PIM information.";
  }
  revision 2019-04-05 {
    description
      "Establish semantic version baseline.";
  }
  revision 2015-11-09 {
    description
      "IOS XR 6.0 revision.";
  }

  typedef Pim-topology-interface-flag {
    type enumeration {
      enum "lh" {
        value 0;
        description
          "LH";
      }
      enum "ld" {
        value 1;
        description
          "LD";
      }
      enum "li" {
        value 2;
        description
          "LI";
      }
      enum "ii" {
        value 3;
        description
          "II";
      }
      enum "id" {
        value 4;
        description
          "ID";
      }
      enum "as" {
        value 5;
        description
          "AS";
      }
      enum "ab" {
        value 6;
        description
          "AB";
      }
      enum "ex" {
        value 7;
        description
          "EX";
      }
    }
    description
      "Pim topology interface flag";
  }

  typedef Pim-safi {
    type enumeration {
      enum "unicast" {
        value 1;
        description
          "SAFI unicast";
      }
      enum "multicast" {
        value 2;
        description
          "SAFI Multicast";
      }
      enum "all" {
        value 3;
        description
          "SAFI all";
      }
      enum "default" {
        value 4;
        description
          "SAFI default";
      }
    }
    description
      "Pim safi";
  }

  typedef Pim-client {
    type enumeration {
      enum "none" {
        value 0;
        description
          "No Client";
      }
      enum "configured-embedded-rp" {
        value 1;
        description
          "Embedded RP from configuration";
      }
      enum "embedded" {
        value 2;
        description
          "Embedded RP learnt from the Group addr";
      }
      enum "permanent" {
        value 3;
        description
          "Permanent";
      }
      enum "auto-rp" {
        value 4;
        description
          "AutoRP";
      }
      enum "bsr" {
        value 5;
        description
          "BSR";
      }
      enum "configured" {
        value 6;
        description
          "Configured";
      }
      enum "static" {
        value 7;
        description
          "Static";
      }
    }
    description
      "Pim client";
  }

  typedef Pim-topology-entry-flag {
    type enumeration {
      enum "kat" {
        value 0;
        description
          "KAT";
      }
      enum "aa" {
        value 1;
        description
          "AA";
      }
      enum "pa" {
        value 2;
        description
          "PA";
      }
      enum "ra" {
        value 3;
        description
          "RA";
      }
      enum "ia" {
        value 4;
        description
          "IA";
      }
      enum "rr" {
        value 5;
        description
          "RR";
      }
      enum "lh" {
        value 6;
        description
          "LH";
      }
      enum "dss" {
        value 7;
        description
          "DSS";
      }
      enum "dcc" {
        value 8;
        description
          "DCC";
      }
      enum "sr" {
        value 9;
        description
          "SR";
      }
      enum "e" {
        value 10;
        description
          "E";
      }
      enum "ex" {
        value 11;
        description
          "EX";
      }
      enum "ma" {
        value 12;
        description
          "MA";
      }
      enum "mt" {
        value 13;
        description
          "MT";
      }
      enum "mfa" {
        value 14;
        description
          "MFA";
      }
      enum "mfp" {
        value 15;
        description
          "MFP";
      }
      enum "mfb" {
        value 16;
        description
          "MFB";
      }
    }
    description
      "Pim topology entry flag";
  }

  typedef Pim-protocol {
    type enumeration {
      enum "non-routable" {
        value 0;
        description
          "Non Routable";
      }
      enum "sparse-mode" {
        value 1;
        description
          "Sparse Mode";
      }
      enum "dense-mode" {
        value 2;
        description
          "Dense Mode";
      }
      enum "bidir" {
        value 3;
        description
          "Bidirectional Mode";
      }
      enum "ssm" {
        value 4;
        description
          "Source Specific Multicast Mode";
      }
      enum "maximum" {
        value 5;
        description
          "Maximum";
      }
      enum "any" {
        value 6;
        description
          "Any";
      }
    }
    description
      "Pim protocol";
  }

  grouping VRF-TABLE {
    description
      "Common node of active, standby";
    container vrfs {
      description
        "VRF Table";
      list vrf {
        key "vrf-name";
        description
          "VRF name";
        container ifrs-interfaces {
          description
            "PIM interfaces in forward reference store
             table";
          list ifrs-interface {
            key "interface-name";
            description
              "PIM IFRS interface information";
            leaf interface-name {
              type xr:Interface-name;
              description
                "Interface name";
            }
            uses PIM-IDB-BAG;
          }
        }
        container interface-statistics {
          description
            "PIM interface statistics";
          list interface-statistic {
            key "interface-name";
            description
              "PIM interface statistics";
            leaf interface-name {
              type xr:Interface-name;
              description
                "Interface name";
            }
            uses PIM-IFSTATS-BAG;
          }
        }
        container topology-route-count {
          description
            "Topology route count information from PIM
             topology table";
          uses PIM-TT-SUMM-BAG;
        }
        container jp-statistics {
          description
            "PIM join prune statistics table";
          list jp-statistic {
            key "interface-name";
            description
              "PIM Join Prune Statistics";
            leaf interface-name {
              type xr:Interface-name;
              description
                "Interface name";
            }
            uses PIM-JPSTATS-BAG;
          }
        }
        container mib-databases {
          description
            "PIM group database for mroute mibs table";
          list mib-database {
            key "source-address group-address source-netmask";
            description
              "PIM multicast static route information";
            leaf source-address {
              type inet:ip-address-no-zone;
              description
                "Multicast static route source address";
            }
            leaf group-address {
              type inet:ip-address-no-zone;
              description
                "Multicast satic route group address";
            }
            leaf source-netmask {
              type uint32;
              description
                "Source mask";
            }
            uses PIM-MROUTE-BAG;
          }
        }
        container ifrs-summary {
          description
            "PIM interfaces in forward reference store
             summary";
          uses PIM-IDB-SUMM-BAG;
        }
        container ranges {
          description
            "PIM range list information";
          list range {
            key "rp-address client";
            description
              "PIM range list information";
            leaf rp-address {
              type inet:ip-address-no-zone;
              description
                "RP address";
            }
            leaf client {
              type Pim-client;
              description
                "Client";
            }
            uses PIM-RL-BAG;
          }
        }
        container bsr {
          description
            "PIM BSR information";
          container rp-caches {
            description
              "PIM BSR RP cache table";
            list rp-cache {
              key "group-prefix prefix-length";
              description
                "PIM BSR RP cache";
              leaf group-prefix {
                type inet:ip-address-no-zone;
                description
                  "Group prefix";
              }
              leaf prefix-length {
                type uint32;
                description
                  "Prefix Length";
              }
              uses PIM-BSR-RP-CACHE-BAG;
            }
          }
          container candidate-rps {
            description
              "PIM candidate-RP";
            list candidate-rp {
              key "rp-address";
              description
                "PIM BSR candidate RP information";
              leaf rp-address {
                type inet:ip-address-no-zone;
                description
                  "Candidate-RP address";
              }
              uses PIM-BSR-CANDIDATE-RP-BAG;
            }
          }
          container bsr-elections {
            description
              "PIM BSR election state";
            list bsr-election {
              key "pim-scope";
              description
                "PIM BSR information";
              leaf pim-scope {
                type uint32;
                description
                  "BSR information";
              }
              uses PIM-BSR-ELECTION-BAG;
            }
          }
        }
        container route-policy {
          description
            "PIM route policy";
          container route-policy-statistics {
            description
              "PIM route policy statistics";
            uses PIM-RPF-POLICY-STATS-BAG;
          }
        }
        container rpf-summary {
          description
            "PIM RPF registration summary";
          uses PIM-RPF-SUMMARY-BAG;
        }
        container interfaces {
          description
            "PIM interfaces";
          list interface {
            key "interface-name";
            description
              "PIM interface name";
            leaf interface-name {
              type xr:Interface-name;
              description
                "Interface name";
            }
            uses PIM-IDB-BAG;
          }
        }
        container net-io-tunnels {
          description
            "Tunnel information that NETIO has ";
          list net-io-tunnel {
            key "tunnel-name";
            description
              "PIM netio tunnel information";
            leaf tunnel-name {
              type xr:Cisco-ios-xr-string {
                length "1..80";
              }
              description
                "Tunnel name";
            }
            uses PIM-TUNNEL-INFO-BAG;
          }
        }
        container bidir-df-states {
          description
            "Bidirectional PIM DF election state table";
          list bidir-df-state {
            key "rp-address interface-name";
            description
              "Bidirectional PIM DF Election Table Entry";
            leaf rp-address {
              type inet:ip-address-no-zone;
              description
                "RP address";
            }
            leaf interface-name {
              type xr:Interface-name;
              description
                "Interface name";
            }
            uses PIM-BIDIR-DF-STATE-BAG;
          }
        }
        container topologies {
          description
            "PIM topology table";
          list topology {
            key "source-address group-address rpt";
            description
              "PIM topology information";
            leaf source-address {
              type inet:ip-address-no-zone;
              description
                "Source address";
            }
            leaf group-address {
              type inet:ip-address-no-zone;
              description
                "Group address";
            }
            leaf rpt {
              type uint32;
              description
                "RPT bit";
            }
            uses PIM-TT-ROUTE-BAG;
          }
        }
        container topology-interface-flag-route-counts {
          description
            "Route count for topology with interface flag
             set";
          list topology-interface-flag-route-count {
            key "interface-flag";
            description
              "Route count for topology with interface flag
               set";
            leaf interface-flag {
              type Pim-topology-interface-flag;
              description
                "Interface flag";
            }
            uses PIM-TT-SUMM-BAG;
          }
        }
        container group-map-sources {
          description
            "PIM group-mapping with source information";
          list group-map-source {
            key "prefix prefix-length client protocol rp-address priority";
            description
              "PIM Group Mapping Entry with source
               information";
            leaf prefix {
              type inet:ip-address-no-zone;
              description
                "Prefix";
            }
            leaf prefix-length {
              type uint32;
              description
                "Prefix length";
            }
            leaf client {
              type Pim-client;
              description
                "Client";
            }
            leaf protocol {
              type Pim-protocol;
              description
                "Protocol";
            }
            leaf rp-address {
              type inet:ip-address-no-zone;
              description
                "RP address";
            }
            leaf priority {
              type uint32;
              description
                "RP Priority";
            }
            uses PIM-GRP-MAP-INFOSRC-BAG;
          }
        }
        container traffic-counters {
          description
            "PIM message traffic counters";
          uses PIM-TRAFFIC-BAG;
        }
        container group-map-rpfs {
          description
            "PIM group mapping information";
          list group-map-rpf {
            key "prefix prefix-length client protocol rp-address rp-priority";
            description
              "PIM group mapping entry";
            leaf prefix {
              type inet:ip-address-no-zone;
              description
                "Prefix";
            }
            leaf prefix-length {
              type uint32;
              description
                "Prefix length";
            }
            leaf client {
              type Pim-client;
              description
                "Client";
            }
            leaf protocol {
              type Pim-protocol;
              description
                "Protocol";
            }
            leaf rp-address {
              type inet:ip-address-no-zone;
              description
                "RP address";
            }
            leaf rp-priority {
              type uint32;
              description
                "RP priority";
            }
            uses PIM-GRP-MAP-INFORPF-BAG;
          }
        }
        container summary {
          description
            "PIM summary";
          uses PIM-SUMMARY-BAG;
        }
        container gre {
          description
            "GRE information";
          container gre-next-hops {
            description
              "GRE destination neighbor table";
            list gre-next-hop {
              key "destination-address";
              description
                "PIM GRE address next-hop information";
              leaf destination-address {
                type inet:ip-address-no-zone;
                description
                  "GRE destination address";
              }
              uses PIM-GRE-INFO-BAG;
            }
          }
        }
        container bidir-df-winners {
          description
            "Bidirectional PIM DF election winner table";
          list bidir-df-winner {
            key "rp-address interface-name";
            description
              "Bidirectional PIM DF election table entry";
            leaf rp-address {
              type inet:ip-address-no-zone;
              description
                "RP address";
            }
            leaf interface-name {
              type xr:Interface-name;
              description
                "Interface name";
            }
            uses PIM-BIDIR-DF-BAG;
          }
        }
        container table-contexts {
          description
            "PIM table context list";
          list table-context {
            key "saf-name topology-name";
            description
              "PIM table context information";
            leaf saf-name {
              type Pim-safi;
              description
                "SAF name";
            }
            leaf topology-name {
              type xr:Cisco-ios-xr-string {
                length "1..32";
              }
              description
                "Topology name";
            }
            uses PIM-TABLE-CTX-BAG;
          }
        }
        container neighbor-summaries {
          description
            "PIM neighbor summary table";
          list neighbor-summary {
            key "interface-name";
            description
              "PIM neighbor summary information";
            leaf interface-name {
              type xr:Interface-name;
              description
                "Interface name";
            }
            uses PIM-NBR-SUMM-BAG;
          }
        }
        container context {
          description
            "PIM context information";
          uses PIM-CONTEXT-BAG;
        }
        container topology-entry-flag-route-counts {
          description
            "Route count for topology with entry flag set";
          list topology-entry-flag-route-count {
            key "entry-flag";
            description
              "Route count for topology with entry flag set";
            leaf entry-flag {
              type Pim-topology-entry-flag;
              description
                "entry flag";
            }
            uses PIM-TT-SUMM-BAG;
          }
        }
        container rpf-redirect {
          description
            "PIM ECMP RPF-redirect bundle";
          container redirect-route-databases {
            description
              "PIM ECMP RPF-redirect route database";
            list redirect-route-database {
              key "source-address group-address";
              description
                "PIM ECMP RPF-redirect route information";
              leaf source-address {
                type inet:ip-address-no-zone;
                description
                  "Source address";
              }
              leaf group-address {
                type inet:ip-address-no-zone;
                description
                  "Group address";
              }
              uses PIM-RPF-RDRCT-ROUTE-BAG;
            }
          }
          container bundle-interfaces {
            description
              "PIM ECMP RPF-redirect bundle information";
            list bundle-interface {
              key "bundle-name interface-name";
              description
                "PIM ECMP RPF-redirect bundle interface
                 information";
              leaf bundle-name {
                type xr:Cisco-ios-xr-string {
                  length "1..32";
                }
                description
                  "Bundle name";
              }
              leaf interface-name {
                type xr:Interface-name;
                description
                  "Bundle interface name";
              }
              uses PIM-RPF-RDRCT-BNDL-BAG;
            }
          }
        }
        container tunnels {
          description
            "Tunnels information that PIM has";
          list tunnel {
            key "tunnel-name";
            description
              "PIM tunnel information";
            leaf tunnel-name {
              type xr:Cisco-ios-xr-string {
                length "1..80";
              }
              description
                "Tunnel name";
            }
            uses PIM-TUNNEL-INFO-BAG;
          }
        }
        container multicast-static-routes {
          description
            "PIM multicast static route table";
          list multicast-static-route {
            key "address prefix-length";
            description
              "PIM multicast static route information";
            leaf address {
              type inet:ip-address-no-zone;
              description
                "Network address";
            }
            leaf prefix-length {
              type uint32;
              description
                "Prefix length";
            }
            uses PIM-MSTATIC-BAG;
          }
        }
        container neighbors {
          description
            "PIM neighbor table";
          list neighbor {
            key "interface-name neighbor-address";
            description
              "PIM neighbor information";
            leaf interface-name {
              type xr:Interface-name;
              description
                "Interface name";
            }
            leaf neighbor-address {
              type inet:ip-address-no-zone;
              description
                "Neighbor address";
            }
            uses PIM-NBR-BAG;
          }
        }
        leaf vrf-name {
          type xr:Cisco-ios-xr-string {
            length "1..32";
          }
          description
            "VRF name ";
        }
      }
    }
  }

  grouping PROCESS {
    description
      "Common node of active, standby";
    container process {
      description
        "Process";
      container missed-packets-table {
        description
          "PIM missed packets information";
        container missed-packets-all-table {
          description
            "PIM missed packets All types information";
          uses PIM-MISSED-PACKETS-LIST-BAG;
        }
        container missed-packets-hello-table {
          description
            "PIM missed packets hello information";
          uses PIM-MISSED-PACKETS-LIST-BAG;
        }
        container missed-packets-candidate-bsr-table {
          description
            "PIM missed packets candidate BSR information";
          uses PIM-MISSED-PACKETS-LIST-BAG;
        }
        container missed-packets-candidate-rp-table {
          description
            "PIM missed packets candidate RP information";
          uses PIM-MISSED-PACKETS-LIST-BAG;
        }
        container missed-packets-join-prune-table {
          description
            "PIM missed packets join-prune information";
          uses PIM-MISSED-PACKETS-LIST-BAG;
        }
      }
      container nsr {
        description
          "NSR Information";
        uses PIM-NSR-BAG;
      }
      container summary {
        description
          "PIM Global Summary";
        uses PIM-SUMMARY-BAG;
      }
      container nsf {
        description
          "PIM NSF information";
        uses PIM-NSF-BAG;
      }
      container issu {
        description
          "ISSU Information";
        uses PIM-ISSU-BAG;
      }
    }
  }

  grouping GLOBAL-INTERFACE-TABLE {
    description
      "Common node of active, standby";
    container global-interfaces {
      description
        "PIM global interface table";
      list global-interface {
        key "interface-name";
        description
          "PIM interface name";
        leaf interface-name {
          type xr:Interface-name;
          description
            "Interface name";
        }
        uses PIM-IDB-BAG;
      }
    }
  }

  grouping PIM-MA-COMMON-OPER-PIM-MA-SUMMARY-MP {
    description
      "Common node of active, standby";
    container pim-ma-summary {
      description
        "PIM MA summary";
      uses PIM-MA-SUMMARY;
    }
  }

  grouping ACTIVE {
    description
      "Common node of pim-ma, pim6-ma";
    container active {
      description
        "Active Process";
      uses INTERFACE-TABLE;
      uses PIM-MA-COMMON-OPER-PIM-MA-SUMMARY-MP;
    }
  }

  grouping IPV4-PIM-ROLE-LVL-OPER-ACTIVE {
    description
      "Common node of pim-ma, pim6-maCommon node of pim,
       ipv6-pim";
    container active {
      description
        "Active Process";
      uses GLOBAL-INTERFACE-TABLE;
      uses PROCESS;
      uses VRF-TABLE;
    }
  }

  grouping INTERFACE-TABLE {
    description
      "Common node of active, standby";
    container interface-table {
      description
        "Interface Table";
      container interface-by-handles {
        description
          "Table of PIM MA interfaces indexed by handle";
        list interface-by-handle {
          key "interface-handle";
          description
            "PIM MA interface referenced by handle";
          leaf interface-handle {
            type uint32;
            description
              "Interface handle";
          }
          uses PIM-MA-IDB;
        }
      }
      container interface-by-names {
        description
          "Table of PIM MA interfaces indexed by name";
        list interface-by-name {
          key "interface-name";
          description
            "PIM MA interface referenced by name";
          leaf interface-name {
            type xr:Interface-name;
            description
              "Interface name";
          }
          uses PIM-MA-IDB;
        }
      }
    }
  }

  grouping STANDBY {
    description
      "Common node of pim-ma, pim6-ma";
    container standby {
      description
        "Standby Process";
      uses INTERFACE-TABLE;
      uses PIM-MA-COMMON-OPER-PIM-MA-SUMMARY-MP;
    }
  }

  grouping IPV4-PIM-ROLE-LVL-OPER-STANDBY {
    description
      "Common node of pim-ma, pim6-maCommon node of pim,
       ipv6-pim";
    container standby {
      description
        "Standby Process";
      uses GLOBAL-INTERFACE-TABLE;
      uses PROCESS;
      uses VRF-TABLE;
    }
  }

  container pim-ma {
    config false;
    description
      "PIM MA operational data";
    uses ACTIVE;
    uses STANDBY;
  }
  container pim {
    config false;
    description
      "PIM operational data";
    uses IPV4-PIM-ROLE-LVL-OPER-STANDBY;
    uses IPV4-PIM-ROLE-LVL-OPER-ACTIVE;
  }
  container ipv6-pim {
    config false;
    description
      "IPv6 PIM operational data";
    uses IPV4-PIM-ROLE-LVL-OPER-STANDBY;
    uses IPV4-PIM-ROLE-LVL-OPER-ACTIVE;
  }
  container pim6-ma {
    config false;
    description
      "PIM6 MA operational data";
    uses ACTIVE;
    uses STANDBY;
  }
}
