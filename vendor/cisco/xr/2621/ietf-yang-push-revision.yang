module ietf-yang-push-revision {
  yang-version 1.1;
  namespace
    "urn:ietf:params:xml:ns:yang:ietf-yang-push-revision";
  prefix ypr;
  import ietf-subscribed-notifications {
    prefix sn;
    reference
      "RFC 8639: Subscription to YANG Notifications";
  }
  import ietf-yang-revisions {
    prefix rev;
    reference
      "RFC YYYY: draft-ietf-netmod-yang-module-versioning-13,
      Updated YANG Module Revision Handling";
  }
  import ietf-yang-types {
    prefix yang;
    rev:recommended-min-date "2013-07-15";
    reference
      "RFC 6991: Common YANG Data Types.";
  }
  import ietf-yang-semver {
    prefix ysver;
    reference
      "RFC ZZZZ: draft-ietf-netmod-yang-semver-23, YANG Semantic
      Versioning";
  }
  import ietf-yang-library {
    prefix yanglib;
    reference
      "RFC 8525: YANG Library";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }

  organization "IETF NETCONF (Network Configuration) Working Group";
  contact
    "WG Web:   <http:/tools.ietf.org/wg/netconf/>
     WG List:  <mailto:netconf@ietf.org>

     Authors:  Thomas Graf
               <mailto:thomas.graf@swisscom.com>
               Benoit Claise
               <mailto:benoit.claise@huawei.com>
               Alex Huang Feng
               <mailto:alex.huang-feng@insa-lyon.fr>";

  description
    "Defines YANG-Push event notification header with the revision
    and the version. Adds the support of the revision and
    version selection in the YANG-Push subscription RPCs.

    Copyright (c) 2025 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    All revisions of IETF and IANA published modules can be found
    at the YANG Parameters registry
    (https://www.iana.org/assignments/yang-parameters).

    This version of this YANG module is part of RFC XXXX; see the RFC
    itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  revision 2025-08-29 {
    description
      "First revision";
    reference
      "RFC XXXX: Support of Versioning in YANG Notifications
      Subscription";
  }

  feature yang-push-revision-supported {
    description
      "This feature indicates the YANG Subscription Notifications
      support specifying the list of modules, revisions and
      versions in the YANG subscription.";
  }

  // Identities
  identity revision-unsupported {
    base sn:establish-subscription-error;
    base sn:modify-subscription-error;
    description
      "Revision not supported.  This failure can be due to
      subscribing to a specific revision not supported by the
      publisher.";
  }

  identity version-unsupported {
    base sn:establish-subscription-error;
    base sn:modify-subscription-error;
    description
      "Version not supported.  This failure can be due to
      subscribing to a specific version not supported by the
      publisher.";
  }

  identity incompatible-revision-and-version {
    base sn:establish-subscription-error;
    base sn:modify-subscription-error;
    description
      "The combination of revision and version are
      incompatible. This failure happens when the revision and the
      version are both specified in the RPC and the YANG
      module supported by the publisher does not support one of them.";
  }

  grouping yang-push-module-version-config {
    description
      "This grouping combines the module name, the revision and
      version leaves. This grouping is to be used for
      configuration and the leaves are not mandatory.";
    leaf name {
      type yang:yang-identifier;
      description
        "This references the YANG module name.";
    }
    leaf revision {
      type rev:revision-date;
      description
        "This references the YANG module revision to be sent in the
        subscription.";
    }
    leaf version {
      type ysver:version;
      description
        "This references the YANG module semantic version to be sent
        in the subscription.";
    }
  }

  grouping yang-push-module-version {
    description
      "This grouping combines the module name, the revision and
      version leaves. This grouping is to be used for
      read-only cases such as the content of YANG-Push Notifications.
      The name and revision are mandatory and MUST be present
      in the data.";
    leaf name {
      type yang:yang-identifier;
      config false;
      mandatory true;
      description
        "This references the YANG module name.";
    }
    leaf revision {
      type rev:revision-date;
      config false;
      mandatory true;
      description
        "This references the YANG module revision of the sent
        notification message.";
    }
    leaf version {
      type ysver:version;
      description
        "This references the YANG module semantic version of the
        sent notification message.";
    }
  }

  grouping yang-push-module-version-list {
    description
      "This grouping defines a list of yang-push-module-version
      grouping.";
    list module-version {
      key "name";
      config false;
      description
        "List of yang-push-module-version grouping. The revision is
        not configurable.";
      uses ypr:yang-push-module-version;
    }
    leaf yang-library-content-id {
      type leafref {
        path "/yanglib:yang-library/yanglib:content-id";
      }
      config false;
      description
        "Contains the YANG library content identifier RFC 8525
        information.";
    }
  }

  grouping yang-push-module-version-config-list {
    description
      "This grouping defines a list of yang-push-module-version-config
      grouping.";
    list module-version-config {
      key "name";
      description
        "List of yang-push-module-version-config grouping. The
        revision is configurable.";
      uses ypr:yang-push-module-version-config;
    }
  }

  // Subscription parameters
  augment "/sn:establish-subscription/sn:input" {
    if-feature "yang-push-revision-supported";
    description
      "Augment the establish-subscription RPC from the
      ietf-subscribed-notifications YANG module with the
      yang-push-module-version-config-list grouping.";
    uses ypr:yang-push-module-version-config-list;
  }
  augment "/sn:modify-subscription/sn:input" {
    if-feature "yang-push-revision-supported";
    description
      "Augment the modify-subscription RPC from the
      ietf-subscribed-notifications YANG module with the
      yang-push-module-version-config-list grouping.";
    uses ypr:yang-push-module-version-config-list;
  }

  // Subscription notifications
  augment "/sn:subscription-started" {
    if-feature "yang-push-revision-supported";
    description
      "Augment the subscription-started notification from the
      ietf-subscribed-notifications YANG module with the
      yang-push-module-version-list grouping.";
    uses ypr:yang-push-module-version-list;
  }
  augment "/sn:subscription-modified" {
    if-feature "yang-push-revision-supported";
    description
      "Augment the subscription-modified notification from the
      ietf-subscribed-notifications YANG module with the
      yang-push-module-version-list grouping.";
    uses ypr:yang-push-module-version-list;
  }

  // Subscription container
  augment "/sn:subscriptions/sn:subscription" {
    if-feature "yang-push-revision-supported";
    description
      "Augment the subscriptions RPC container from the
      ietf-subscribed-notifications YANG module with the
      yang-push-module-version-config-list grouping.";
    uses ypr:yang-push-module-version-config-list;
  }

  // Event capabilities
  augment "/sysc:system-capabilities/notc:subscription-capabilities" {
    description
      "Add system level capabilities";
    leaf yang-push-module-revision-supported {
      type boolean;
      description
        "Specifies whether the publisher supports exporting
        revision and version in YANG-Push subscription state change
        notifications.";
      reference
        "RFC XXXX: Support of Versioning in YANG Notifications
        Subscription";
    }
  }
}
