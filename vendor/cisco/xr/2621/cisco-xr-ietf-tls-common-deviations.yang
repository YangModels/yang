module cisco-xr-ietf-tls-common-deviations {
  namespace "http://cisco.com/ns/yang/cisco-xr-ietf-tls-common-deviations";
  prefix xr-tlscmn-d;

  import ietf-tls-common {
    prefix tlscmn;
  }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations of:

        ietf-tls-common@2024-10-10

     on Cisco IOS-XR devices.

     Copyright (c) 2025 by Cisco Systems, Inc., and/or its affiliates.
     All rights reserved.";


  revision 2025-02-14 {
    description
      "Initial version.";
  }

  /*
   * If in the future this deviations file only contains RPC or notification
   * nodes, it will stop appearing in Yang Library or capabilities/hello
   * output.
   * See CSCwn84289 for more details. This comment can be removed once the
   * issue is resolved.
   */

  // DATA MODEL DEVIATIONS

  deviation /tlscmn:supported-algorithms {
    deviate not-supported;
  }

  // NOTIFICATION DEVIATIONS

  deviation /tlscmn:generate-asymmetric-key-pair {
    deviate not-supported;
  }

}
