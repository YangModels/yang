submodule Cisco-IOS-XR-wd-death-notif-configured-proc-oper-sub1 {
  belongs-to Cisco-IOS-XR-wd-death-notif-configured-proc-oper {
    prefix Cisco-IOS-XR-wd-death-notif-configured-proc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR wd-death-notif-configured-proc package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef String1 {
    type string;
    description
      "String1";
  }

  grouping PROCESS-LIST {
    description
      "list of processes";
    leaf-list process-name {
      type String1;
      description
        "process name";
    }
  }

  grouping CONFIGURED-PROC-INFO-BAG {
    description
      "Count of the processes configured for death
       notification";
    container processes {
      description
        "List of processes";
      uses PROCESS-LIST;
    }
    leaf count {
      type uint32;
      description
        "Configured Process Count";
    }
  }
}
