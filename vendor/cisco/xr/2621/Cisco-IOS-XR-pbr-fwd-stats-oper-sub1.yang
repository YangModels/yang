submodule Cisco-IOS-XR-pbr-fwd-stats-oper-sub1 {
  belongs-to Cisco-IOS-XR-pbr-fwd-stats-oper {
    prefix Cisco-IOS-XR-pbr-fwd-stats-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pbr-fwd-stats package operational data.
     
     Copyright (c) 2013-2025 by Cisco Systems, Inc.
     All rights reserved.";

  revision 2025-01-16 {
    description
      "Stats feature update to support match rules";
    semver:module-version "1.0.0";
  }
  revision 2024-09-11 {
    description
      "Stats feature update";
  }
  revision 2024-05-08 {
    description
      "CSCwj03306 : Meta EBB - PBR Stats feature";
  }
  revision 2019-04-05 {
    description
      "Establish semantic version baseline.";
  }
  revision 2015-11-09 {
    description
      "IOS XR 6.0 revision.";
  }

  typedef Insight-table {
    type enumeration {
      enum "insight-table-type-invalid" {
        description
          "insight table type invalid";
      }
      enum "insight-table-type-aft-pfx-v4" {
        description
          "insight table type aft pfx v4";
      }
      enum "insight-table-type-aft-pfx-v6" {
        description
          "insight table type aft pfx v6";
      }
      enum "insight-table-type-aft-pfx-label" {
        description
          "insight table type aft pfx label";
      }
      enum "insight-table-type-aft-nh-group" {
        description
          "insight table type aft nh group";
      }
      enum "insight-table-type-aft-nh-group-n-hop" {
        description
          "insight table type aft nh group n hop";
      }
      enum "insight-table-type-aft-cond-state" {
        description
          "insight table type aft cond state";
      }
      enum "insight-table-type-aft-next-hop" {
        description
          "insight table type aft next hop";
      }
      enum "insight-table-type-stats-per-label" {
        description
          "insight table type stats per label";
      }
      enum "insight-table-type-stats-per-label-per-path" {
        description
          "insight table type stats per label per path";
      }
      enum "insight-table-type-stats-per-path" {
        description
          "insight table type stats per path";
      }
      enum "insight-table-type-stats-pbr-per-rule" {
        description
          "insight table type stats pbr per rule";
      }
      enum "insight-table-type-xr-cond-group" {
        description
          "insight table type xr cond group";
      }
      enum "insight-table-type-aft-cond-intf" {
        description
          "insight table type aft cond intf";
      }
      enum "insight-table-type-cfg-telemetry" {
        description
          "insight table type cfg telemetry";
      }
      enum "insight-table-type-cfg-class-map" {
        description
          "insight table type cfg class map";
      }
      enum "insight-table-type-cfg-policy-map" {
        description
          "insight table type cfg policy map";
      }
      enum "insight-table-type-cfg-intf" {
        description
          "insight table type cfg intf";
      }
      enum "insight-table-type-cnhg-map" {
        description
          "insight table type cnhg map";
      }
      enum "insight-table-type-asic-ctr" {
        description
          "insight table type asic ctr";
      }
      enum "insight-table-type-ppc-pkt" {
        description
          "insight table type ppc pkt";
      }
      enum "insight-table-type-ppc-drop" {
        description
          "insight table type ppc drop";
      }
      enum "insight-table-type-err-if" {
        description
          "insight table type err if";
      }
      enum "insight-table-type-err-lkup" {
        description
          "insight table type err lkup";
      }
      enum "insight-table-type-err-queue" {
        description
          "insight table type err queue";
      }
      enum "insight-table-type-err-fab" {
        description
          "insight table type err fab";
      }
      enum "insight-table-type-err-host" {
        description
          "insight table type err host";
      }
      enum "insight-table-type-s-flow-oc-if" {
        description
          "insight table type s flow oc if";
      }
      enum "insight-table-type-s-flow-oc-collect-or" {
        description
          "insight table type s flow oc collect or";
      }
      enum "insight-table-type-any-match" {
        description
          "insight table type any match";
      }
      enum "insight-table-type-aft-nh-group-flat" {
        description
          "insight table type aft nh group flat";
      }
      enum "insight-table-type-pbr-str-to-id" {
        description
          "insight table type pbr str to id";
      }
      enum "insight-table-type-pbr-id-to-str" {
        description
          "insight table type pbr id to str";
      }
      enum "insight-table-type-s-flow-collect-or" {
        description
          "insight table type s flow collect or";
      }
      enum "insight-table-type-s-flow-interface" {
        description
          "insight table type s flow interface";
      }
      enum "insight-table-type-res-system" {
        description
          "insight table type res system";
      }
      enum "insight-table-type-res-npu" {
        description
          "insight table type res npu";
      }
      enum "insight-table-type-optics-tcvr" {
        description
          "insight table type optics tcvr";
      }
      enum "insight-table-type-intf-oper-state" {
        description
          "insight table type intf oper state";
      }
      enum "insight-table-type-xrhealth" {
        description
          "insight table type xrhealth";
      }
      enum "insight-table-type-healthz-state" {
        description
          "insight table type healthz state";
      }
      enum "insight-table-type-healthz-component-state" {
        description
          "insight table type healthz component state";
      }
      enum "insight-table-type-healthz-sub-component" {
        description
          "insight table type healthz sub component";
      }
      enum "insight-table-type-ppc-ctrl" {
        description
          "insight table type ppc ctrl";
      }
      enum "insight-table-type-aft-route-sum-v4" {
        description
          "insight table type aft route sum v4";
      }
      enum "insight-table-type-aft-route-sum-v6" {
        description
          "insight table type aft route sum v6";
      }
      enum "insight-table-type-stats-aft-nh" {
        description
          "insight table type stats aft nh";
      }
      enum "insight-table-type-aft-nh-map-ping" {
        description
          "insight table type aft nh map ping";
      }
      enum "insight-table-type-aft-nh-map-ping-rev" {
        description
          "insight table type aft nh map ping rev";
      }
      enum "insight-table-type-stats-aft-pfx-v4" {
        description
          "insight table type stats aft pfx v4";
      }
      enum "insight-table-type-aft-pfx-map-ping-v4" {
        description
          "insight table type aft pfx map ping v4";
      }
      enum "insight-table-type-aft-pfx-map-ping-v4-rev" {
        description
          "insight table type aft pfx map ping v4 rev";
      }
      enum "insight-table-type-stats-aft-pfx-v6" {
        description
          "insight table type stats aft pfx v6";
      }
      enum "insight-table-type-aft-pfx-map-ping-v6" {
        description
          "insight table type aft pfx map ping v6";
      }
      enum "insight-table-type-aft-pfx-map-ping-v6-rev" {
        description
          "insight table type aft pfx map ping v6 rev";
      }
      enum "insight-table-type-oc-tcvr" {
        description
          "insight table type oc tcvr";
      }
      enum "insight-table-type-oc-tcvr-channel" {
        description
          "insight table type oc tcvr channel";
      }
      enum "insight-table-type-oc-optical-channel" {
        description
          "insight table type oc optical channel";
      }
      enum "insight-table-type-oc-tcvr-threshold" {
        description
          "insight table type oc tcvr threshold";
      }
      enum "insight-table-type-oc-if-tcvr-interface" {
        description
          "insight table type oc if tcvr interface";
      }
      enum "insight-table-type-opt-logical-channel" {
        description
          "insight table type opt logical channel";
      }
      enum "insight-table-type-opt-if-name-h" {
        description
          "insight table type opt if name h";
      }
      enum "insight-table-type-opt-logical-asignment" {
        description
          "insight table type opt logical asignment";
      }
      enum "insight-table-type-opt-optical-channel" {
        description
          "insight table type opt optical channel";
      }
      enum "insight-table-type-opt-operational-mode" {
        description
          "insight table type opt operational mode";
      }
      enum "insight-table-type-oc-logical-channel" {
        description
          "insight table type oc logical channel";
      }
      enum "insight-table-type-oc-operational-mode" {
        description
          "insight table type oc operational mode";
      }
      enum "insight-table-type-oc-logical-assignment" {
        description
          "insight table type oc logical assignment";
      }
      enum "insight-table-type-oc-otn" {
        description
          "insight table type oc otn";
      }
      enum "insight-table-type-opt-ifh-name" {
        description
          "insight table type opt ifh name";
      }
      enum "insight-table-type-ppc-q200" {
        description
          "insight table type ppc q200";
      }
      enum "insight-table-type-ppc-p100" {
        description
          "insight table type ppc p100";
      }
      enum "insight-table-type-vdr-q200" {
        description
          "insight table type vdr q200";
      }
      enum "insight-table-type-vdr-p100" {
        description
          "insight table type vdr p100";
      }
      enum "insight-table-type-opt-logical-ingress" {
        description
          "insight table type opt logical ingress";
      }
      enum "insight-table-type-link-mon-snapshot" {
        description
          "insight table type link mon snapshot";
      }
      enum "insight-table-type-cfg-vrf" {
        description
          "insight table type cfg vrf";
      }
      enum "insight-table-type-xrhealth-state" {
        description
          "insight table type xrhealth state";
      }
      enum "insight-table-type-aft-state-synced" {
        description
          "insight table type aft state synced";
      }
      enum "insight-table-type-internal-string" {
        description
          "insight table type internal string";
      }
      enum "insight-table-type-internal-set" {
        description
          "insight table type internal set";
      }
      enum "insight-table-type-internal-list" {
        description
          "insight table type internal list";
      }
      enum "insight-table-type-max" {
        description
          "insight table type max";
      }
    }
    description
      "Insight table";
  }

  grouping FIB-SH-TIMESPEC {
    description
      "FIB SH TIMESPEC";
    leaf seconds {
      type int32;
      description
        "Seconds";
    }
    leaf nano-seconds {
      type int32;
      description
        "NanoSeconds";
    }
  }

  grouping FIB-INSIGHT-FWD-STATS {
    description
      "FIB Insight Generic Forwarding Stats Information";
    container collection-timestamp {
      description
        "Forwarding stats collection timestamp";
      uses FIB-SH-TIMESPEC;
    }
    leaf forwarding-stats-type {
      type Insight-table;
      description
        "Type of stats collection";
    }
    leaf packet-count {
      type uint64;
      description
        "Forwarding stats packet count";
    }
    leaf byte-count {
      type uint64;
      description
        "Forwarding stats byte count";
    }
  }
}
