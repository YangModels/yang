module Cisco-IOS-XR-um-yclt-test-cfg {
  namespace "http://cisco.com/ns/yang/Cisco-IOS-XR-um-yclt-test-cfg";
  prefix um-yclt-test-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR YCLT testing.
     
     Copyright (c) 2025 by Cisco Systems, Inc., and/or its affiliates.
     All rights reserved.";

  revision 2025-07-31 {
    description
      "Initial revision.";
    semver:module-version "1.0.0";
  }

  container yclt-test {
    description
      "YCLT testing";
    container positive {
      description
        "YCLT positive testing";
      leaf yang-cli-accept {
        type string;
        description
          "YANG and CLI both accept input";
      }
    }
    container negative {
      description
        "YCLT negative testing";
      leaf yang-reject-on-re-input {
        type string;
        description
          "YANG rejected when input (leaf in metadata is invalid)";
      }
      container yang-cli-mismatch {
        description
          "YANG re-input succeeds, CLI is changed (by modifying input) and
           accepted";
        leaf one {
          type string;
        }
      }
    }
  }
}
