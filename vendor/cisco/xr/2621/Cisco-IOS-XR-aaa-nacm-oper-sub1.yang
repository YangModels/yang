submodule Cisco-IOS-XR-aaa-nacm-oper-sub1 {
  belongs-to Cisco-IOS-XR-aaa-nacm-oper {
    prefix Cisco-IOS-XR-aaa-nacm-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR aaa-nacm package operational data.
     
     Copyright (c) 2013-2026 by Cisco Systems, Inc.
     All rights reserved.";

  revision 2026-02-26 {
    description
      "Schema corrections and fixing the LDAP oper schema
       2026-02-04
         Added LDAP oper information for servers and timestamps.
       2025-11-07
         Added database source in Nacm Group detail, Group List, User detail, Users List, Rulelist List, Rule Detail, Rule List and Rulelist List.
       2022-04-20
         Added nacm enable-dynamic CLI.";
    semver:module-version "1.1.0";
  }
  revision 2019-04-05 {
    description
      "Establish semantic version baseline.";
    semver:module-version "1.0.1";
  }
  revision 2015-11-09 {
    description
      "IOS XR 6.0 revision.";
  }

  grouping NACM-LDAP-SERVERBAG {
    description
      "LDAP Server Bag";
    leaf addr {
      type uint32;
      description
        "internet address of ldap server";
    }
    leaf port {
      type uint32;
      description
        "per server port to use";
    }
    leaf bytes-in {
      type uint64;
      units "byte";
      description
        "# of bytes read";
    }
    leaf bytes-out {
      type uint64;
      units "byte";
      description
        "# of bytes out";
    }
    leaf closes {
      type uint32;
      description
        "socket closes";
    }
    leaf opens {
      type uint32;
      description
        "socket opens";
    }
    leaf errors {
      type uint32;
      description
        "error count";
    }
    leaf aborts {
      type uint32;
      description
        "abort count";
    }
    leaf paks-in {
      type uint32;
      description
        "# of incoming packets read";
    }
    leaf paks-out {
      type uint32;
      description
        "# of outgoing packets sent";
    }
    leaf replies-expected {
      type uint32;
      description
        "# of replies expected to arrive";
    }
    leaf up {
      type boolean;
      description
        "is the server UP or down ?";
    }
    leaf conn-up {
      type boolean;
      description
        "is the server connected ?";
    }
    leaf is-private {
      type boolean;
      description
        "is this a private server ?";
    }
    leaf connect-timeout {
      type uint32;
      description
        "Connect timeout: configured range 0-1000sec";
    }
    leaf bind-timeout {
      type uint32;
      description
        "Bind timeout: configured range 0-1000sec";
    }
    leaf search-timeout {
      type uint32;
      description
        "Search timeout: configured range 0-1000sec";
    }
    leaf connection-attempted {
      type int64;
      description
        "last attempted contact time";
    }
    leaf vrf-name {
      type string {
        length "0..33";
      }
      description
        "VRF in which server is reachable";
    }
    leaf addr-buf {
      type string {
        length "0..46";
      }
      description
        "IP address buffer";
    }
    leaf family {
      type string {
        length "0..5";
      }
      description
        "IP address Family";
    }
  }

  grouping NACM-LDAP-SERVERS {
    description
      "LDAP Servers";
    list server {
      key "addr port";
      description
        "LDAP Server List";
      uses NACM-LDAP-SERVERBAG;
    }
  }

  grouping NACM-LDAP-POLICYBAG {
    description
      "LDAP Policy Bag";
    leaf policy-name-xr {
      type string {
        length "0..65";
      }
      description
        "Policy Name";
    }
    leaf timestamp {
      type string {
        length "0..64";
      }
      description
        "Policy timestamp string";
    }
  }

  grouping NACM-GROUP-DETAIL {
    description
      "Nacm Group detail";
    leaf group-name {
      type string {
        length "0..256";
      }
      description
        "Group Name";
    }
    leaf database-source {
      type uint32;
      description
        "Database Source";
    }
    list user-name {
      description
        "Users Name List";
      uses LIST-NODE;
    }
    list rule-name {
      description
        "Rules Name List";
      uses LIST-NODE;
    }
  }

  grouping NACM-RULE-DETAIL {
    description
      "Nacm Rule Detail";
    leaf rule-name {
      type string {
        length "0..512";
      }
      description
        "Rule Name";
    }
    leaf rule-index {
      type string {
        length "0..16";
      }
      description
        "Rule Index";
    }
    leaf rulelist-index {
      type string {
        length "0..16";
      }
      description
        "Rulelist Index";
    }
    leaf module-name {
      type string {
        length "0..512";
      }
      description
        "Module Name";
    }
    leaf action {
      type string {
        length "0..256";
      }
      description
        "Action";
    }
    leaf rule-type {
      type string {
        length "0..256";
      }
      description
        "Rule Type";
    }
    leaf comment {
      type string {
        length "0..256";
      }
      description
        "Comment";
    }
    leaf access-operations {
      type string {
        length "0..256";
      }
      description
        "Access Operations";
    }
    leaf rule-value {
      type string {
        length "0..512";
      }
      description
        "Rule Value";
    }
    leaf hit-count {
      type int32;
      description
        "Hit Count";
    }
    leaf database-source {
      type uint32;
      description
        "Database Source";
    }
  }

  grouping NACM-SUMMARY {
    description
      "Nacm Summary";
    leaf groups {
      type int32;
      description
        "Groups";
    }
    leaf users {
      type int32;
      description
        "Users";
    }
    leaf rulelist {
      type int32;
      description
        "Rulelist";
    }
    leaf rules {
      type int32;
      description
        "Rules";
    }
    leaf read-default {
      type string {
        length "0..16";
      }
      description
        "Read Default";
    }
    leaf write-default {
      type string {
        length "0..16";
      }
      description
        "Write Default";
    }
    leaf exec-default {
      type string {
        length "0..16";
      }
      description
        "Exec Default";
    }
    leaf enable-nacm {
      type string {
        length "0..16";
      }
      description
        "Enable Nacm";
    }
    leaf enable-external-groups {
      type string {
        length "0..16";
      }
      description
        "Enable External Groups";
    }
    leaf enable-external-policies {
      type string {
        length "0..16";
      }
      description
        "Enable External Policies";
    }
  }

  grouping LIST-NODE {
    description
      "List Node";
    leaf name {
      type string {
        length "0..256";
      }
      description
        "Name";
    }
  }

  grouping NACM-USER-DETAIL {
    description
      "Nacm User detail";
    leaf user-name {
      type string {
        length "0..256";
      }
      description
        "User Name";
    }
    leaf database-source {
      type uint32;
      description
        "Database Source";
    }
    list group-name {
      description
        "Group Name List";
      uses LIST-NODE;
    }
  }

  grouping NACM-COUNTERS {
    description
      "Nacm Counters";
    leaf denied-operations {
      type int32;
      description
        "Denied Operations";
    }
    leaf denied-data-writes {
      type int32;
      description
        "Denied Data Writes";
    }
    leaf denied-notifications {
      type int32;
      description
        "Denied Notifications";
    }
  }
}
