module Cisco-IOS-XR-ip-icmp-cfg {
  namespace "http://cisco.com/ns/yang/Cisco-IOS-XR-ip-icmp-cfg";
  prefix ip-icmp-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-icmp package configuration.
     
     This module contains definitions
     for the following management objects:
       icmp: IP ICMP configuration data
     
     Copyright (c) 2013-2020 by Cisco Systems, Inc.
     All rights reserved.";

  revision 2020-08-10 {
    description
      "IOS XR 7.3.1 revision.";
    semver:module-version "2.0.0";
  }
  revision 2019-04-05 {
    description
      "Establish semantic version baseline.";
    semver:module-version "1.0.0";
  }
  revision 2017-06-08 {
    description
      "IOS XR 6.3.1 revision.";
  }
  revision 2015-11-09 {
    description
      "IOS XR 6.0 revision.";
  }

  typedef Source-policy {
    type enumeration {
      enum "vrf" {
        value 1;
        description
          "Set Source Selection Policy to vrf";
      }
      enum "rfc" {
        value 2;
        description
          "Set Source Selection Policy to rfc";
      }
    }
    description
      "Source policy";
  }

  grouping SOURCE {
    description
      "Common node of ipv4, ipv6";
    container source {
      description
        "IP ICMP Source Address Selection Policy";
      leaf source-address-policy {
        type Source-policy;
        description
          "Configure Source Address Policy";
      }
    }
  }

  container icmp {
    description
      "IP ICMP configuration data";
    container ipv6 {
      description
        "IP Protocol Type";
      uses SOURCE;
    }
    container ipv4 {
      description
        "IP Protocol Type";
      container rate-limit {
        description
          "Set ratelimit of ICMP packets";
        container unreachable {
          description
            "Set unreachable ICMP packets ratelimit";
          leaf rate {
            type uint32 {
              range "0..4294967295";
            }
            description
              "Rate Limit of Unreachable ICMP packets";
          }
          leaf fragmentation {
            type uint32 {
              range "0..4294967295";
            }
            description
              "Rate Limit of Unreachable DF packets";
          }
        }
      }
      uses SOURCE;
    }
  }
}
