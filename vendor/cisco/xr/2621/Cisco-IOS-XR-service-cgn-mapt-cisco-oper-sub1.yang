submodule Cisco-IOS-XR-service-cgn-mapt-cisco-oper-sub1 {
  belongs-to Cisco-IOS-XR-service-cgn-mapt-cisco-oper {
    prefix Cisco-IOS-XR-service-cgn-mapt-cisco-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR service-cgn-mapt-cisco package operational data.
     
     Copyright (c) 2013-2023 by Cisco Systems, Inc.
     All rights reserved.";

  revision 2023-11-21 {
    description
      "Added mapt-cisco Yang Model.";
    semver:module-version "1.0.0";
  }
  revision 2019-04-05 {
    description
      "Establish semantic version baseline.";
  }
  revision 2015-11-09 {
    description
      "IOS XR 6.0 revision.";
  }

  grouping MAP-T-CISCO-V6-ICMP {
    description
      "IPv6 ICMP counters";
    leaf generated-messages {
      type uint64;
      description
        "ICMP generated messages";
    }
  }

  grouping MAP-T-CISCO-V6 {
    description
      "IPv6 Counters";
    container icmp {
      description
        "IPv6 ICMP counters";
      uses MAP-T-CISCO-V6-ICMP;
    }
  }

  grouping MAP-T-CISCO-V4-ICMP {
    description
      "IPv4 ICMP counters";
    leaf generated-messages {
      type uint64;
      description
        "ICMP generated messages";
    }
  }

  grouping MAP-T-CISCO-V4 {
    description
      "IPv4 Counters";
    container icmp {
      description
        "IPv4 ICMP counters";
      uses MAP-T-CISCO-V4-ICMP;
    }
  }

  grouping MAP-T-CISCO-V6-V4-OPTIONS-PROC {
    description
      "IPv6 to IPv4 options processing counters";
    leaf incoming-packets {
      type uint64;
      description
        "Incoming Count";
    }
    leaf drops {
      type uint64;
      description
        "Drop Count";
    }
    leaf forwards {
      type uint64;
      description
        "Forwarded Count";
    }
    leaf no-db-drops {
      type uint64;
      description
        "No Database Drop Count";
    }
    leaf unsupported-protocols {
      type uint64;
      description
        "Unsupported Protocol Count";
    }
  }

  grouping MAP-T-CISCO-V6-V4-SUB-FRAG {
    description
      "IPv6 to IPv4 Subsequent fragment counters";
    leaf incoming-packets {
      type uint64;
      description
        "Subsequent Fragment Incoming Count";
    }
    leaf non-translatable-drops {
      type uint64;
      description
        "Nontranslatable Drop Count";
    }
    leaf invalid-next-header-drops {
      type uint64;
      description
        "Invalid Next Header Drop Count";
    }
    leaf no-db-drops {
      type uint64;
      description
        "No Database Entry Drop Count";
    }
    leaf translated-packets {
      type uint64;
      description
        "Translated Count";
    }
  }

  grouping MAP-T-CISCO-V6-V4-ICMP {
    description
      "IPv6 to IPv4 ICMP counters";
    leaf incoming-packets {
      type uint64;
      description
        "Incoming count";
    }
    leaf no-db-drops {
      type uint64;
      description
        "No DB drop count";
    }
    leaf fragment-drops {
      type uint64;
      description
        "Fragment Drop count";
    }
    leaf invalid-next-header-drops {
      type uint64;
      description
        "Invalid Next Header Drop Count";
    }
    leaf non-translatable-drops {
      type uint64;
      description
        "Nontranslatable Drop Count";
    }
    leaf non-translatable-forwards {
      type uint64;
      description
        "Nontranslatable Forwarded count";
    }
    leaf unsupported-type-drops {
      type uint64;
      description
        "Unsupported Type Drop Count";
    }
    leaf error-translated-packets {
      type uint64;
      description
        "Error Translated Count";
    }
    leaf query-translated-packets {
      type uint64;
      description
        "Query Translated Count";
    }
    leaf psid-drops {
      type uint64;
      description
        "Psid drop count";
    }
  }

  grouping MAP-T-CISCO-V6-V4-UDP {
    description
      "IPv6 to IPv4 UDP counters";
    leaf incoming-packets {
      type uint64;
      description
        "Incoming packets count";
    }
    leaf non-translatable-drops {
      type uint64;
      description
        "Non Translatable drop count";
    }
    leaf invalid-next-header-drops {
      type uint64;
      description
        "Invalid next header drop count";
    }
    leaf no-db-drops {
      type uint64;
      description
        "No db entry drop count";
    }
    leaf translated-packets {
      type uint64;
      description
        "Translated packets count";
    }
    leaf psid-drops {
      type uint64;
      description
        "Psid entry drop count";
    }
  }

  grouping MAP-T-CISCO-V6-V4-TCP {
    description
      "IPv6 to IPv4 TCP counters";
    leaf incoming-packets {
      type uint64;
      description
        "Incoming packets count";
    }
    leaf non-translatable-drops {
      type uint64;
      description
        "Non Translatable drop count";
    }
    leaf invalid-next-header-drops {
      type uint64;
      description
        "Invalid next header drop count";
    }
    leaf no-db-drops {
      type uint64;
      description
        "No db entry drop count";
    }
    leaf translated-packets {
      type uint64;
      description
        "Translated packets count";
    }
    leaf psid-drops {
      type uint64;
      description
        "PSID drop count";
    }
  }

  grouping MAP-T-CISCO-V6-V4-EX {
    description
      "IPv6 to IPv4 exception counters";
    container tcp {
      description
        "TCP counters";
      uses MAP-T-CISCO-V6-V4-TCP;
    }
    container udp {
      description
        "UDP counters";
      uses MAP-T-CISCO-V6-V4-UDP;
    }
    container icmp {
      description
        "ICMP counters";
      uses MAP-T-CISCO-V6-V4-ICMP;
    }
    container subsequent-fragment {
      description
        "Subsequent fragment counters";
      uses MAP-T-CISCO-V6-V4-SUB-FRAG;
    }
    container options-processing {
      description
        "Options processing counters";
      uses MAP-T-CISCO-V6-V4-OPTIONS-PROC;
    }
  }

  grouping MAP-T-CISCO-V4-V6-OPTS-PROC {
    description
      "IPv4 to IPv6 options processing counters";
    leaf incoming-packets {
      type uint64;
      description
        "Incoming Count";
    }
    leaf drops {
      type uint64;
      description
        "Drop Count";
    }
    leaf forwards {
      type uint64;
      description
        "Forward Count";
    }
    leaf no-db-drops {
      type uint64;
      description
        "No DB Drop Count";
    }
    leaf unsupported-protocols {
      type uint64;
      description
        "Unsupported Protocol Count";
    }
  }

  grouping MAP-T-CISCO-V4-V6-SUB-FRAG {
    description
      "IPv4 to IPv6 Subsequent fragment counters";
    leaf incoming-packets {
      type uint64;
      description
        "Incoming Count";
    }
    leaf no-db-drops {
      type uint64;
      description
        "No DB Entry Drop Count";
    }
    leaf translated-packets {
      type uint64;
      description
        "Translated Count";
    }
    leaf drop-packets {
      type uint64;
      description
        "Drop Count";
    }
    leaf throttled-packets {
      type uint64;
      description
        "Throttled Count";
    }
    leaf timeout-drop-packets {
      type uint64;
      description
        "Timeout Drop Count";
    }
    leaf tcp-input-packets {
      type uint64;
      description
        "TCP Incoming Count";
    }
    leaf udp-input-packets {
      type uint64;
      description
        "UDP Incoming Count";
    }
    leaf icmp-input-packets {
      type uint64;
      description
        "ICMP Incoming Count";
    }
  }

  grouping MAP-T-CISCO-V4-V6-ICMP {
    description
      "IPv4 to IPv6 ICMP counters";
    leaf incoming-packets {
      type uint64;
      description
        "Incoming Count";
    }
    leaf no-db-drops {
      type uint64;
      description
        "No Database Entry Drop Count";
    }
    leaf fragment-drops {
      type uint64;
      description
        "Fragment Drop count";
    }
    leaf unsupported-type-drops {
      type uint64;
      description
        "Unsupported Type Drop Count";
    }
    leaf error-translated-packets {
      type uint64;
      description
        "Error Translated Count";
    }
    leaf query-translated-packets {
      type uint64;
      description
        "Query Translated Count";
    }
    leaf psid-drops {
      type uint64;
      description
        "Psid Entry Drop Count";
    }
  }

  grouping MAP-T-CISCO-V4-V6-UDP {
    description
      "IPv4 to IPv6 UDP counters";
    leaf incoming-packets {
      type uint64;
      description
        "Incoming packet count";
    }
    leaf no-db-drops {
      type uint64;
      description
        "No db entry drop count";
    }
    leaf translated-packets {
      type uint64;
      description
        "Translated packet count";
    }
    leaf fragment-crc-zero-drops {
      type uint64;
      description
        "Fragment CRC Zero Drop Count";
    }
    leaf crc-zero-recycle-sent-packets {
      type uint64;
      description
        "CRC Zero Recycle Sent Count";
    }
    leaf crc-zero-recycle-drops {
      type uint64;
      description
        "CRC Zero Recycle Drop Count";
    }
    leaf psid-drops {
      type uint64;
      description
        "Psid entry drop count";
    }
  }

  grouping MAP-T-CISCO-V4-V6-TCP {
    description
      "IPv4 to IPv6 TCP counters";
    leaf incoming-packets {
      type uint64;
      description
        "Incoming packets count";
    }
    leaf no-db-drops {
      type uint64;
      description
        "No db entry drop count";
    }
    leaf translated-packets {
      type uint64;
      description
        "Translated packets count";
    }
    leaf psid-drops {
      type uint64;
      description
        "Psid entry drop count";
    }
  }

  grouping MAP-T-CISCO-V4-V6-EX {
    description
      "IPv4 to IPv6 Exception counters";
    container tcp {
      description
        "TCP counters";
      uses MAP-T-CISCO-V4-V6-TCP;
    }
    container udp {
      description
        "UDP counters";
      uses MAP-T-CISCO-V4-V6-UDP;
    }
    container icmp {
      description
        "ICMP counters";
      uses MAP-T-CISCO-V4-V6-ICMP;
    }
    container subsequent-fragment {
      description
        "Subsequent fragment counters";
      uses MAP-T-CISCO-V4-V6-SUB-FRAG;
    }
    container options-processing {
      description
        "Options processing counters";
      uses MAP-T-CISCO-V4-V6-OPTS-PROC;
    }
  }

  grouping MAP-T-CISCO-V4-V6 {
    description
      "IPv4 to IPv6 counters";
    leaf udp {
      type uint64;
      description
        "Translated udp packets count";
    }
    leaf tcp {
      type uint64;
      description
        "Translated tcp packets count";
    }
    leaf icmp {
      type uint64;
      description
        "Translated icmp packets count";
    }
    leaf udp-psid {
      type uint64;
      description
        "psid udp packets count";
    }
    leaf tcp-psid {
      type uint64;
      description
        "psid tcp packets count";
    }
    leaf icmp-psid {
      type uint64;
      description
        "psid icmp packets count";
    }
    leaf other-l4 {
      type uint64;
      description
        "Translated other L4 packets count";
    }
    leaf other-l4-drop {
      type uint64;
      description
        "Dropped other L4 packets count";
    }
    leaf other-redirect-frag-needed {
      type uint64;
      description
        "Other redirected packets count that need
         fragmentation";
    }
    leaf other-redirect-frag-needed-drop {
      type uint64;
      description
        "Other dropped packets count that need
         fragmentation but got droped before getting
         redirected ";
    }
    leaf other-redirect-frag-pkt {
      type uint64;
      description
        "Other redirected fragemented packets count";
    }
    leaf other-redirect-frag-pkt-drop {
      type uint64;
      description
        "Other dropped packets count that are fragmented
         but got droped before getting redirected ";
    }
    leaf udp-redirect-frag-needed {
      type uint64;
      description
        "Redirected udp packets count that need
         fragmentation";
    }
    leaf udp-redirect-frag-needed-drop {
      type uint64;
      description
        "Udp dropped packets count that need
         fragmentation but got droped before getting
         redirected ";
    }
    leaf udp-redirect-frag-pkt {
      type uint64;
      description
        "Redirected udp fragemented packets count";
    }
    leaf udp-redirect-frag-pkt-drop {
      type uint64;
      description
        "Udp dropped packets count that are fragmented
         but got droped before getting redirected ";
    }
    leaf tcp-redirect-frag-needed {
      type uint64;
      description
        "Redirected tcp packets count that need
         fragmentation";
    }
    leaf tcp-redirect-frag-needed-drop {
      type uint64;
      description
        "Tcp dropped packets count that need
         fragmentation but got droped before getting
         redirected ";
    }
    leaf tcp-redirect-frag-pkt {
      type uint64;
      description
        "Redirected udp fragemented packets count";
    }
    leaf tcp-redirect-frag-pkt-drop {
      type uint64;
      description
        "Tcp dropped packets count that are fragmented
         but got droped before getting redirected ";
    }
    leaf icmp-redirect-frag-needed {
      type uint64;
      description
        "Redirected icmp packets count that need
         fragmentation";
    }
    leaf icmp-redirect-frag-needed-drop {
      type uint64;
      description
        "Icmp dropped packets count that need
         fragmentation but got droped before getting
         redirected ";
    }
    leaf icmp-redirect-frag-pkt {
      type uint64;
      description
        "Redirected icmp fragemented packets count";
    }
    leaf icmp-redirect-frag-pkt-drop {
      type uint64;
      description
        "Icmp dropped packets count that are fragmented
         but got droped before getting redirected ";
    }
  }

  grouping MAP-T-CISCO-V6-V4 {
    description
      "IPv6 to IPv4 counters";
    leaf udp {
      type uint64;
      description
        "Translated udp packets count";
    }
    leaf tcp {
      type uint64;
      description
        "Translated tcp packets count";
    }
    leaf icmp {
      type uint64;
      description
        "Translated icmp packets count";
    }
    leaf udp-psid {
      type uint64;
      description
        "psid udp packets count";
    }
    leaf tcp-psid {
      type uint64;
      description
        "psid tcp packets count";
    }
    leaf icmp-psid {
      type uint64;
      description
        "psid icmp packets count";
    }
    leaf other-l4 {
      type uint64;
      description
        "Translated other L4 packets count";
    }
    leaf other-l4-drop {
      type uint64;
      description
        "Dropped other L4 packets count";
    }
    leaf other-redirect-frag-needed {
      type uint64;
      description
        "Other redirected packets count that need
         fragmentation";
    }
    leaf other-redirect-frag-needed-drop {
      type uint64;
      description
        "Other dropped packets count that need
         fragmentation but got droped before getting
         redirected ";
    }
    leaf other-redirect-frag-pkt {
      type uint64;
      description
        "Other redirected fragemented packets count";
    }
    leaf other-redirect-frag-pkt-drop {
      type uint64;
      description
        "Other dropped packets count that are fragmented
         but got droped before getting redirected ";
    }
    leaf udp-redirect-frag-needed {
      type uint64;
      description
        "Redirected udp packets count that need
         fragmentation";
    }
    leaf udp-redirect-frag-needed-drop {
      type uint64;
      description
        "Udp dropped packets count that need
         fragmentation but got droped before getting
         redirected ";
    }
    leaf udp-redirect-frag-pkt {
      type uint64;
      description
        "Redirected udp fragemented packets count";
    }
    leaf udp-redirect-frag-pkt-drop {
      type uint64;
      description
        "Udp dropped packets count that are fragmented
         but got droped before getting redirected ";
    }
    leaf tcp-redirect-frag-needed {
      type uint64;
      description
        "Redirected tcp packets count that need
         fragmentation";
    }
    leaf tcp-redirect-frag-needed-drop {
      type uint64;
      description
        "Tcp dropped packets count that need
         fragmentation but got droped before getting
         redirected ";
    }
    leaf tcp-redirect-frag-pkt {
      type uint64;
      description
        "Redirected udp fragemented packets count";
    }
    leaf tcp-redirect-frag-pkt-drop {
      type uint64;
      description
        "Tcp dropped packets count that are fragmented
         but got droped before getting redirected ";
    }
    leaf icmp-redirect-frag-needed {
      type uint64;
      description
        "Redirected icmp packets count that need
         fragmentation";
    }
    leaf icmp-redirect-frag-needed-drop {
      type uint64;
      description
        "Icmp dropped packets count that need
         fragmentation but got droped before getting
         redirected ";
    }
    leaf icmp-redirect-frag-pkt {
      type uint64;
      description
        "Redirected icmp fragemented packets count";
    }
    leaf icmp-redirect-frag-pkt-drop {
      type uint64;
      description
        "Icmp dropped packets count that are fragmented
         but got droped before getting redirected ";
    }
  }

  grouping MAP-T-CISCO-STATS-SUMMARY {
    description
      "CGN Map-t-cisco statstics summary";
    container ipv6-to-ipv4 {
      description
        "IPv6 to IPv4 counters";
      uses MAP-T-CISCO-V6-V4;
    }
    container ipv4-to-ipv6 {
      description
        "IPv4 to IPv6 counters";
      uses MAP-T-CISCO-V4-V6;
    }
    container ipv4to-ipv6exption {
      description
        "IPv4 to IPv6 exception counters";
      uses MAP-T-CISCO-V4-V6-EX;
    }
    container ipv6to-ipv4exption {
      description
        "IPv6 to IPv4 exception counters";
      uses MAP-T-CISCO-V6-V4-EX;
    }
    container ipv4 {
      description
        "IPv4 counters";
      uses MAP-T-CISCO-V4;
    }
    container ipv6 {
      description
        "IPv6 counters";
      uses MAP-T-CISCO-V6;
    }
  }
}
