module Cisco-IOS-XR-openconfig-mpls-te-ext {
  yang-version 1;
  namespace "http://cisco.com/ns/yang/Cisco-IOS-XR-openconfig-mpls-te-ext";
  prefix oc-mpls-te-cisco-xr-ext;

  import openconfig-network-instance {
    prefix oc-ni;
  }
  import openconfig-extensions {
    prefix oc-ext;
  }
  import cisco-semver {
    prefix semver;
  }
  import Cisco-IOS-XR-openconfig-qos-ext {
    prefix oc-qos-cisco-xr-ext;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module adds Cisco-define extensions to the public OpenConfig MPLS-TE
     model to enable Cisco-specific features without modifying the official
     OpenConfig files";

  revision 2022-07-25 {
    description
      "Initial version";
    reference "0.1.0";
  }

  augment "/oc-ni:network-instances/oc-ni:network-instance/oc-ni:mpls/oc-ni:lsps/oc-ni:constrained-path/oc-ni:tunnels/oc-ni:tunnel/oc-ni:p2p-tunnel-attributes/oc-ni:config" {
    description
      "Configuration parameters for MPLS-TE tunnel forward class.";
    uses oc-qos-cisco-xr-ext:qos-ext-classifier-term-action-config;
  }
  augment "/oc-ni:network-instances/oc-ni:network-instance/oc-ni:mpls/oc-ni:lsps/oc-ni:constrained-path/oc-ni:tunnels/oc-ni:tunnel/oc-ni:p2p-tunnel-attributes/oc-ni:state" {
    description
      "State parameters for MPLS-TE tunnel forward class.";
    uses oc-qos-cisco-xr-ext:qos-ext-classifier-term-action-config;
  }
  oc-ext:openconfig-version "0.1.0";
}
