//*************  DO-NOT EDIT  **************
//*********** Auto-generated file ********** 

 module cisco-xr-openconfig-isis-policy-deviations {

  prefix  "oc-isis-poldevs";

  namespace "http://cisco.com/ns/yang/cisco-xr-openconfig-isis-policy-deviations";

  import openconfig-isis-policy { prefix oc-isis-pol; }
  import openconfig-routing-policy { prefix rpol; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-isis-policy.yang@2023-11-02 

     on Cisco IOS-XR devices.

     Copyright (c) 2017 by Cisco Systems, Inc.
     All rights reserved.";

  revision "2024-09-05" {
    description
      "Updated revision applicable to IOS-XR 25.1.1";
  }

  revision "2019-06-10" {
    description
      "Updated revision applicable to IOS-XR 7.1.1";
  }

  deviation /rpol:routing-policy/rpol:policy-definitions/rpol:policy-definition/rpol:statements/rpol:statement/rpol:actions/oc-isis-pol:isis-actions/oc-isis-pol:config/oc-isis-pol:set-metric-type {
    deviate not-supported;
  }

  deviation /rpol:routing-policy/rpol:policy-definitions/rpol:policy-definition/rpol:statements/rpol:statement/rpol:actions/oc-isis-pol:isis-actions/oc-isis-pol:config/oc-isis-pol:set-metric-style-type {
    deviate not-supported;
  }

  deviation /rpol:routing-policy/rpol:policy-definitions/rpol:policy-definition/rpol:statements/rpol:statement/rpol:actions/oc-isis-pol:isis-actions/oc-isis-pol:state/oc-isis-pol:set-metric-type {
    deviate not-supported;
  }

  deviation /rpol:routing-policy/rpol:policy-definitions/rpol:policy-definition/rpol:statements/rpol:statement/rpol:actions/oc-isis-pol:isis-actions/oc-isis-pol:state/oc-isis-pol:set-metric-style-type {
    deviate not-supported;
  }

  deviation /rpol:routing-policy/rpol:policy-definitions/rpol:policy-definition/rpol:statements/rpol:statement/rpol:conditions/oc-isis-pol:isis-conditions/oc-isis-pol:config/oc-isis-pol:level-eq {
    deviate not-supported;
  }

  deviation /rpol:routing-policy/rpol:policy-definitions/rpol:policy-definition/rpol:statements/rpol:statement/rpol:conditions/oc-isis-pol:isis-conditions/oc-isis-pol:config/oc-isis-pol:match-metric-type {
    deviate not-supported;
  }

  deviation /rpol:routing-policy/rpol:policy-definitions/rpol:policy-definition/rpol:statements/rpol:statement/rpol:conditions/oc-isis-pol:isis-conditions/oc-isis-pol:state/oc-isis-pol:level-eq {
    deviate not-supported;
  }

  deviation /rpol:routing-policy/rpol:policy-definitions/rpol:policy-definition/rpol:statements/rpol:statement/rpol:conditions/oc-isis-pol:isis-conditions/oc-isis-pol:state/oc-isis-pol:match-metric-type {
    deviate not-supported;
  }


}
//total deviations:8
