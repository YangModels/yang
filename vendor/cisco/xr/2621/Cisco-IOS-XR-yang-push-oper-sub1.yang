submodule Cisco-IOS-XR-yang-push-oper-sub1 {
  belongs-to Cisco-IOS-XR-yang-push-oper {
    prefix Cisco-IOS-XR-yang-push-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR yang-push package operational data.
     
     Copyright (c) 2013-2025 by Cisco Systems, Inc.
     All rights reserved.";

  revision 2025-11-25 {
    description
      "Initial commit";
    semver:module-version "1.0.0";
  }
  revision 2019-04-05 {
    description
      "Establish semantic version baseline.";
  }
  revision 2015-11-09 {
    description
      "IOS XR 6.0 revision.";
  }

  typedef Yang-push-receiver-transport {
    type enumeration {
      enum "not-set" {
        value 0;
        description
          "Not set";
      }
      enum "tcp" {
        value 1;
        description
          "TCP";
      }
      enum "udp-notif" {
        value 2;
        description
          "UDP Notif";
      }
    }
    description
      "YANG-Push transport";
  }

  typedef Yang-push-sub-error {
    type enumeration {
      enum "config-missing" {
        value 0;
        description
          "This subscription is not fully configured. No
           data will be sent until all missing fields are
           configured.";
      }
      enum "invalid-filter-x-path" {
        value 1;
        description
          "The configured filter XPath does not match a
           node in the currently installed YANG schema.";
      }
      enum "src-intf-not-up" {
        value 2;
        description
          "The source interface either does not exist, is
           not up, or does not have an IP address
           configured.";
      }
      enum "invalid-module-revision" {
        value 3;
        description
          "One or more installed YANG modules are not
           present in the configured filter XPath or have
           revisions that do not match the configured
           revisions. No data will be sent until the
           configured modules/revisions are updated.";
      }
    }
    description
      "YANG-Push subscription error";
  }

  typedef Yang-push-sub-status {
    type enumeration {
      enum "valid" {
        value 0;
        description
          "Valid";
      }
      enum "invalid" {
        value 1;
        description
          "Invalid";
      }
    }
    description
      "YANG-Push subscription status";
  }

  typedef Yang-push-sub-update-policy {
    type enumeration {
      enum "not-set" {
        value 0;
        description
          "Not set";
      }
      enum "on-change" {
        value 1;
        description
          "On change";
      }
      enum "on-change-sync-on-start" {
        value 2;
        description
          "On-change with sync-on-start";
      }
      enum "periodic" {
        value 3;
        description
          "Periodic";
      }
    }
    description
      "YANG-Push update policy";
  }

  typedef Yang-push-sub-encoding {
    type enumeration {
      enum "not-set" {
        value 0;
        description
          "Not set";
      }
      enum "json" {
        value 1;
        description
          "JSON";
      }
    }
    description
      "YANG-Push encoding";
  }

  typedef Yang-push-receiver-status {
    type enumeration {
      enum "active" {
        value 0;
        description
          "Active";
      }
      enum "connecting" {
        value 1;
        description
          "Connecting";
      }
      enum "disconnected" {
        value 2;
        description
          "Disconnected";
      }
    }
    description
      "YANG-Push receiver status";
  }

  grouping YANG-PUSH-DIAGS-RECEIVER {
    description
      "Receiver information";
    leaf transport {
      type Yang-push-receiver-transport;
      description
        "Transport";
    }
    leaf max-segment-size {
      type uint16;
      units "byte";
      description
        "Maximum segment size for UDP transport in bytes";
    }
    leaf address {
      type string;
      description
        "Receiver address";
    }
    leaf port {
      type uint16;
      description
        "Receiver port";
    }
  }

  grouping YANG-PUSH-DIAGS-MODULE {
    description
      "Module information";
    leaf name {
      type string;
      description
        "Module name";
    }
    leaf revision {
      type string;
      description
        "Module revision (formatted as YYYY-MM-DD)";
    }
    leaf module-in-xpath {
      type boolean;
      description
        "Whether the specified module name is part of the
         configured filter xpath";
    }
    leaf revision-match {
      type boolean;
      description
        "Whether the specified revision matches the
         installed revision";
    }
    leaf installed-revision {
      type string;
      description
        "The installed revision of the given module
         (formatted as YYYY-MM-DD)";
    }
  }

  grouping YANG-PUSH-DIAGS-SUB-RECEIVER {
    description
      "Receiver information";
    leaf name {
      type string;
      description
        "Receiver name";
    }
    leaf status {
      type Yang-push-receiver-status;
      description
        "Current status of the receiver";
    }
    leaf status-details {
      type string;
      description
        "Status details of the receiver";
    }
  }

  grouping YANG-PUSH-DIAGS-SUBSCRIPTION {
    description
      "Subscription information";
    leaf filter-x-path {
      type string;
      description
        "XPath expression for the subscription";
    }
    leaf encoding {
      type Yang-push-sub-encoding;
      description
        "Encoding format used for the subscription";
    }
    leaf update-policy {
      type Yang-push-sub-update-policy;
      description
        "Update policy for the subscription";
    }
    leaf period {
      type uint32;
      units "centisecond";
      description
        "The interval between updates for periodic
         subscriptions in centiseconds";
    }
    leaf anchor-time {
      type string;
      description
        "Anchor time for the periodic subscription in
         ISO8601 format";
    }
    leaf purpose {
      type string;
      description
        "Purpose of the subscription";
    }
    leaf dscp {
      type uint8;
      description
        "DSCP value for the subscription";
    }
    leaf source-interface {
      type string;
      description
        "Source interface for the subscription";
    }
    leaf status {
      type Yang-push-sub-status;
      description
        "Current status of the subscription";
    }
    leaf error {
      type Yang-push-sub-error;
      description
        "Error of the subscription";
    }
    leaf error-details {
      type string;
      description
        "Error details of the subscription";
    }
    leaf datastore {
      type string;
      description
        "Datastore for the subscription";
    }
    leaf yang-lib-content-id {
      type string;
      description
        "YANG library Content-ID used for the
         subscription";
    }
    list receiver {
      description
        "List of receivers for the subscription";
      uses YANG-PUSH-DIAGS-SUB-RECEIVER;
    }
    list module {
      description
        "Modules for the subscription";
      uses YANG-PUSH-DIAGS-MODULE;
    }
  }
}
