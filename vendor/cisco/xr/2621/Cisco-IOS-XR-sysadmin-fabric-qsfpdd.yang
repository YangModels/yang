module Cisco-IOS-XR-sysadmin-fabric-qsfpdd {
  namespace "http://www.cisco.com/ns/yang/Cisco-IOS-XR-sysadmin-fabric-qsfpdd";
  prefix fabric_qsfpdd;

  import tailf-xsd-types {
    prefix xs;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for accessing the port's info of each rack.
     
     Copyright (c) 2012-2020, 2022 by Cisco Systems, Inc.
     All rights reserved.";

  revision 2024-07-04 {
    description
      "Remove 'Cisco Supported' info from optics data, correct Transceiver spelling";
    semver:module-version "2.0.0";
  }
  revision 2021-04-21 {
    description
      "Removed unused imports";
    semver:module-version "1.0.0";
  }

  grouping dom_output {
    description
      "dom_output";
    list qsfpdd_port {
      key "qsfpdd_port_num";
      description
        "QSFPDD port";
      leaf show_port {
        type boolean;
        default "false";
        description
          "Front Port Num";
      }
      leaf error_msg {
        type string;
        description
          "Error MSG";
      }
      leaf qsfpdd_port_num {
        type uint32;
        description
          "QSFPDD Port Num";
      }
      leaf optics_description {
        type string;
        description
          "Optics Description";
      }
      leaf vendorname {
        type string;
        description
          "Vendor Name";
      }
      leaf vendor_rev_num {
        type string;
        description
          "Vendor Rev Num";
      }
      leaf vid {
        type string;
        description
          "Vendor Id";
      }
      leaf pid {
        type string;
        description
          "PID";
      }
      leaf qsfp_type {
        type uint32;
        description
          "QSFP Type";
      }
      leaf vendor_pn {
        type string;
        description
          "Vendor PN";
      }
      leaf vendor_sn {
        type string;
        description
          "vendor_sn";
      }
      leaf ven_date_code {
        type string;
        description
          "ven_date_code";
      }
      leaf vendor_oui {
        type string;
        description
          "vendor_oui";
      }
      leaf temp_rd {
        type xs:double;
        description
          "temp_rd";
      }
      leaf volt_rd {
        type xs:double;
        description
          "volt_rd";
      }
      leaf wavelength {
        type xs:double;
        description
          "wavelength";
      }
      leaf temp_hi_alarm_sts {
        type string;
        description
          "temp_hi_alarm_sts";
      }
      leaf temp_lo_alarm_sts {
        type string;
        description
          "temp_lo_alarm_sts";
      }
      leaf volt_hi_alarm_sts {
        type string;
        description
          "volt_hi_alarm_sts";
      }
      leaf volt_lo_alarm_sts {
        type string;
        description
          "volt_lo_alarm_sts";
      }
      leaf rx_power_dbm_0 {
        type xs:double;
        description
          "rx_power_dbm_0";
      }
      leaf rx_power_dbm_1 {
        type xs:double;
        description
          "rx_power_dbm_1";
      }
      leaf rx_power_dbm_2 {
        type xs:double;
        description
          "rx_power_dbm_2";
      }
      leaf rx_power_dbm_3 {
        type xs:double;
        description
          "rx_power_dbm_3";
      }
      leaf rx_power_dbm_4 {
        type xs:double;
        description
          "rx_power_dbm_4";
      }
      leaf rx_power_dbm_5 {
        type xs:double;
        description
          "rx_power_dbm_5";
      }
      leaf rx_power_dbm_6 {
        type xs:double;
        description
          "rx_power_dbm_6";
      }
      leaf rx_power_dbm_7 {
        type xs:double;
        description
          "rx_power_dbm_7";
      }
      leaf rx_los_0 {
        type string;
        description
          "rx_los_0";
      }
      leaf rx_los_1 {
        type string;
        description
          "rx_los_1";
      }
      leaf rx_los_2 {
        type string;
        description
          "rx_los_2";
      }
      leaf rx_los_3 {
        type string;
        description
          "rx_los_3";
      }
      leaf rx_los_4 {
        type string;
        description
          "rx_los_4";
      }
      leaf rx_los_5 {
        type string;
        description
          "rx_los_5";
      }
      leaf rx_los_6 {
        type string;
        description
          "rx_los_6";
      }
      leaf rx_los_7 {
        type string;
        description
          "rx_los_7";
      }
      leaf rx_cdr_lol_0 {
        type string;
        description
          "rx_cdr_lol_0";
      }
      leaf rx_cdr_lol_1 {
        type string;
        description
          "rx_cdr_lol_1";
      }
      leaf rx_cdr_lol_2 {
        type string;
        description
          "rx_cdr_lol_2";
      }
      leaf rx_cdr_lol_3 {
        type string;
        description
          "rx_cdr_lol_3";
      }
      leaf rx_cdr_lol_4 {
        type string;
        description
          "rx_cdr_lol_4";
      }
      leaf rx_cdr_lol_5 {
        type string;
        description
          "rx_cdr_lol_5";
      }
      leaf rx_cdr_lol_6 {
        type string;
        description
          "rx_cdr_lol_6";
      }
      leaf rx_cdr_lol_7 {
        type string;
        description
          "rx_cdr_lol_7";
      }
      leaf rx_hi_alarm_0 {
        type string;
        description
          "rx_hi_alarm_0";
      }
      leaf rx_hi_alarm_1 {
        type string;
        description
          "rx_hi_alarm_1";
      }
      leaf rx_hi_alarm_2 {
        type string;
        description
          "rx_hi_alarm_2";
      }
      leaf rx_hi_alarm_3 {
        type string;
        description
          "rx_hi_alarm_3";
      }
      leaf rx_hi_alarm_4 {
        type string;
        description
          "rx_hi_alarm_4";
      }
      leaf rx_hi_alarm_5 {
        type string;
        description
          "rx_hi_alarm_4";
      }
      leaf rx_hi_alarm_6 {
        type string;
        description
          "rx_hi_alarm_6";
      }
      leaf rx_hi_alarm_7 {
        type string;
        description
          "rx_hi_alarm_7";
      }
      leaf rx_lo_alarm_0 {
        type string;
        description
          "rx_lo_alarm_0";
      }
      leaf rx_lo_alarm_1 {
        type string;
        description
          "rx_lo_alarm_1";
      }
      leaf rx_lo_alarm_2 {
        type string;
        description
          "rx_lo_alarm_2";
      }
      leaf rx_lo_alarm_3 {
        type string;
        description
          "rx_lo_alarm_3";
      }
      leaf rx_lo_alarm_4 {
        type string;
        description
          "rx_lo_alarm_4";
      }
      leaf rx_lo_alarm_5 {
        type string;
        description
          "rx_lo_alarm_5";
      }
      leaf rx_lo_alarm_6 {
        type string;
        description
          "rx_lo_alarm_6";
      }
      leaf rx_lo_alarm_7 {
        type string;
        description
          "rx_lo_alarm_7";
      }
      leaf tx_power_dbm_0 {
        type xs:double;
        description
          "tx_power_dbm_0";
      }
      leaf tx_power_dbm_1 {
        type xs:double;
        description
          "tx_power_dbm_1";
      }
      leaf tx_power_dbm_2 {
        type xs:double;
        description
          "tx_power_dbm_2";
      }
      leaf tx_power_dbm_3 {
        type xs:double;
        description
          "tx_power_dbm_3";
      }
      leaf tx_power_dbm_4 {
        type xs:double;
        description
          "tx_power_dbm_4";
      }
      leaf tx_power_dbm_5 {
        type xs:double;
        description
          "tx_power_dbm_5";
      }
      leaf tx_power_dbm_6 {
        type xs:double;
        description
          "tx_power_dbm_6";
      }
      leaf tx_power_dbm_7 {
        type xs:double;
        description
          "tx_power_dbm_7";
      }
      leaf tx_bias_current_0 {
        type xs:double;
        description
          "tx_bias_current_0";
      }
      leaf tx_bias_current_1 {
        type xs:double;
        description
          "tx_bias_current_1";
      }
      leaf tx_bias_current_2 {
        type xs:double;
        description
          "tx_bias_current_2";
      }
      leaf tx_bias_current_3 {
        type xs:double;
        description
          "tx_bias_current_3";
      }
      leaf tx_bias_current_4 {
        type xs:double;
        description
          "tx_bias_current_4";
      }
      leaf tx_bias_current_5 {
        type xs:double;
        description
          "tx_bias_current_5";
      }
      leaf tx_bias_current_6 {
        type xs:double;
        description
          "tx_bias_current_6";
      }
      leaf tx_bias_current_7 {
        type xs:double;
        description
          "tx_bias_current_7";
      }
      leaf tx_laser_status_0 {
        type string;
        description
          "tx_laser_status_0";
      }
      leaf tx_laser_status_1 {
        type string;
        description
          "tx_laser_status_1";
      }
      leaf tx_laser_status_2 {
        type string;
        description
          "tx_laser_status_2";
      }
      leaf tx_laser_status_3 {
        type string;
        description
          "tx_laser_status_3";
      }
      leaf tx_laser_status_4 {
        type string;
        description
          "tx_laser_status_4";
      }
      leaf tx_laser_status_5 {
        type string;
        description
          "tx_laser_status_5";
      }
      leaf tx_laser_status_6 {
        type string;
        description
          "tx_laser_status_6";
      }
      leaf tx_laser_status_7 {
        type string;
        description
          "tx_laser_status_7";
      }
      leaf tx_los_status_0 {
        type string;
        description
          "tx_los_status_0";
      }
      leaf tx_los_status_1 {
        type string;
        description
          "tx_los_status_1";
      }
      leaf tx_los_status_2 {
        type string;
        description
          "tx_los_status_2";
      }
      leaf tx_los_status_3 {
        type string;
        description
          "tx_los_status_3";
      }
      leaf tx_los_status_4 {
        type string;
        description
          "tx_los_status_4";
      }
      leaf tx_los_status_5 {
        type string;
        description
          "tx_los_status_5";
      }
      leaf tx_los_status_6 {
        type string;
        description
          "tx_los_status_6";
      }
      leaf tx_los_status_7 {
        type string;
        description
          "tx_los_status_7";
      }
      leaf tx_fault_status_0 {
        type string;
        description
          "tx_fault_status_0";
      }
      leaf tx_fault_status_1 {
        type string;
        description
          "tx_fault_status_1";
      }
      leaf tx_fault_status_2 {
        type string;
        description
          "tx_fault_status_2";
      }
      leaf tx_fault_status_3 {
        type string;
        description
          "tx_fault_status_3";
      }
      leaf tx_fault_status_4 {
        type string;
        description
          "tx_fault_status_4";
      }
      leaf tx_fault_status_5 {
        type string;
        description
          "tx_fault_status_5";
      }
      leaf tx_fault_status_6 {
        type string;
        description
          "tx_fault_status_6";
      }
      leaf tx_fault_status_7 {
        type string;
        description
          "tx_fault_status_7";
      }
      leaf tx_cdr_lol_status_0 {
        type string;
        description
          "tx_cdr_lol_status_0";
      }
      leaf tx_cdr_lol_status_1 {
        type string;
        description
          "tx_cdr_lol_status_1";
      }
      leaf tx_cdr_lol_status_2 {
        type string;
        description
          "tx_cdr_lol_status_2";
      }
      leaf tx_cdr_lol_status_3 {
        type string;
        description
          "tx_cdr_lol_status_3";
      }
      leaf tx_cdr_lol_status_4 {
        type string;
        description
          "tx_cdr_lol_status_4";
      }
      leaf tx_cdr_lol_status_5 {
        type string;
        description
          "tx_cdr_lol_status_5";
      }
      leaf tx_cdr_lol_status_6 {
        type string;
        description
          "tx_cdr_lol_status_6";
      }
      leaf tx_cdr_lol_status_7 {
        type string;
        description
          "tx_cdr_lol_status_7";
      }
      leaf tx_power_high_alarm_status_0 {
        type string;
        description
          "tx_power_high_alarm_status_0";
      }
      leaf tx_power_high_alarm_status_1 {
        type string;
        description
          "tx_power_high_alarm_status_1";
      }
      leaf tx_power_high_alarm_status_2 {
        type string;
        description
          "tx_power_high_alarm_status_2";
      }
      leaf tx_power_high_alarm_status_3 {
        type string;
        description
          "tx_power_high_alarm_status_3";
      }
      leaf tx_power_high_alarm_status_4 {
        type string;
        description
          "tx_power_high_alarm_status_4";
      }
      leaf tx_power_high_alarm_status_5 {
        type string;
        description
          "tx_power_high_alarm_status_5";
      }
      leaf tx_power_high_alarm_status_6 {
        type string;
        description
          "tx_power_high_alarm_status_6";
      }
      leaf tx_power_high_alarm_status_7 {
        type string;
        description
          "tx_power_high_alarm_status_7";
      }
      leaf tx_power_low_alarm_status_0 {
        type string;
        description
          "tx_power_low_alarm_status_0";
      }
      leaf tx_power_low_alarm_status_1 {
        type string;
        description
          "tx_power_low_alarm_status_1";
      }
      leaf tx_power_low_alarm_status_2 {
        type string;
        description
          "tx_power_low_alarm_status_2";
      }
      leaf tx_power_low_alarm_status_3 {
        type string;
        description
          "tx_power_low_alarm_status_3";
      }
      leaf tx_power_low_alarm_status_4 {
        type string;
        description
          "tx_power_low_alarm_status_4";
      }
      leaf tx_power_low_alarm_status_5 {
        type string;
        description
          "tx_power_low_alarm_status_5";
      }
      leaf tx_power_low_alarm_status_6 {
        type string;
        description
          "tx_power_low_alarm_status_6";
      }
      leaf tx_power_low_alarm_status_7 {
        type string;
        description
          "tx_power_low_alarm_status_7";
      }
      leaf tx_laser_bias_high_alarm_status_0 {
        type string;
        description
          "tx_laser_bias_high_alarm_status_0";
      }
      leaf tx_laser_bias_high_alarm_status_1 {
        type string;
        description
          "tx_laser_bias_high_alarm_status_1";
      }
      leaf tx_laser_bias_high_alarm_status_2 {
        type string;
        description
          "tx_laser_bias_high_alarm_status_2";
      }
      leaf tx_laser_bias_high_alarm_status_3 {
        type string;
        description
          "tx_laser_bias_high_alarm_status_3";
      }
      leaf tx_laser_bias_high_alarm_status_4 {
        type string;
        description
          "tx_laser_bias_high_alarm_status_4";
      }
      leaf tx_laser_bias_high_alarm_status_5 {
        type string;
        description
          "tx_laser_bias_high_alarm_status_5";
      }
      leaf tx_laser_bias_high_alarm_status_6 {
        type string;
        description
          "tx_laser_bias_high_alarm_status_6";
      }
      leaf tx_laser_bias_high_alarm_status_7 {
        type string;
        description
          "tx_laser_bias_high_alarm_status_7";
      }
      leaf tx_laser_bias_low_alarm_status_0 {
        type string;
        description
          "tx_laser_bias_low_alarm_status_0";
      }
      leaf tx_laser_bias_low_alarm_status_1 {
        type string;
        description
          "tx_laser_bias_low_alarm_status_1";
      }
      leaf tx_laser_bias_low_alarm_status_2 {
        type string;
        description
          "tx_laser_bias_low_alarm_status_2";
      }
      leaf tx_laser_bias_low_alarm_status_3 {
        type string;
        description
          "tx_laser_bias_low_alarm_status_3";
      }
      leaf tx_laser_bias_low_alarm_status_4 {
        type string;
        description
          "tx_laser_bias_low_alarm_status_4";
      }
      leaf tx_laser_bias_low_alarm_status_5 {
        type string;
        description
          "tx_laser_bias_low_alarm_status_5";
      }
      leaf tx_laser_bias_low_alarm_status_6 {
        type string;
        description
          "tx_laser_bias_low_alarm_status_5";
      }
      leaf tx_laser_bias_low_alarm_status_7 {
        type string;
        description
          "tx_laser_bias_low_alarm_status_7";
      }
      leaf temp_high_alarm {
        type xs:double;
        description
          "temp_high_alarm";
      }
      leaf temp_high_warn_alarm {
        type xs:double;
        description
          "temp_high_warn_alarm";
      }
      leaf temp_low_warn_alarm {
        type xs:double;
        description
          "temp_low_warn_alarm";
      }
      leaf temp_low_alarm {
        type xs:double;
        description
          "temp_low_alarm";
      }
      leaf volt_high_alarm {
        type xs:double;
        description
          "volt_high_alarm";
      }
      leaf volt_high_warn_alarm {
        type xs:double;
        description
          "volt_high_warn_alarm";
      }
      leaf volt_low_warn_alarm {
        type xs:double;
        description
          "volt_low_warn_alarm";
      }
      leaf volt_low_alarm {
        type xs:double;
        description
          "volt_low_alarm";
      }
      leaf tx_cur_high_alarm {
        type xs:double;
        description
          "tx_cur_high_alarm";
      }
      leaf tx_cur_high_warn_alarm {
        type xs:double;
        description
          "tx_cur_high_warn_alarm";
      }
      leaf tx_cur_low_warn_alarm {
        type xs:double;
        description
          "tx_cur_low_warn_alarm";
      }
      leaf tx_cur_low_alarm {
        type xs:double;
        description
          "tx_cur_low_alarm";
      }
      leaf tx_pwr_high_alarm {
        type xs:double;
        description
          "tx_pwr_high_alarm";
      }
      leaf tx_pwr_high_warn_alarm {
        type xs:double;
        description
          "tx_pwr_high_warn_alarm";
      }
      leaf tx_pwr_low_warn_alarm {
        type xs:double;
        description
          "tx_pwr_low_warn_alarm";
      }
      leaf tx_pwr_low_alarm {
        type xs:double;
        description
          "tx_pwr_low_alarm";
      }
      leaf rx_pwr_high_alarm {
        type xs:double;
        description
          "rx_pwr_high_alarm";
      }
      leaf rx_pwr_high_warn_alarm {
        type xs:double;
        description
          "rx_pwr_high_warn_alarm";
      }
      leaf rx_pwr_low_warn_alarm {
        type xs:double;
        description
          "rx_pwr_low_warn_alarm";
      }
      leaf rx_pwr_low_alarm {
        type xs:double;
        description
          "rx_pwr_low_alarm";
      }
    }
  }

  grouping fc_qsfpdd {
    description
      "Fabric card QSFPDD";
    container qsfpdd {
      description
        "Fabric card QSFPDD optics information";
      container dom {
        description
          "qsfpdd optic DOM data";
        list location {
          key "loc_str";
          description
            "location";
          leaf loc_str {
            type string;
            description
              "loc_str";
          }
          leaf description {
            type string;
            default "location (R/S)";
            description
              "description location (R/S)";
          }
          uses dom_output;
        }
      }
      container summary {
        description
          "QSFPDD Port Status Summary";
        list rack {
          key "rack_str";
          config false;
          description
            "Rack Num";
          leaf rack_str {
            type string;
            description
              "rack_str";
          }
          leaf description {
            type string;
            default "Rack No.";
            description
              "Rack No.";
          }
          list qsfpdd_rack_summary_data {
            description
              "qsfpdd_rack_summary_data";
            leaf qsfpdd_rack_data {
              type string;
              description
                "qsfpdd_rack_data";
            }
          }
        }
      }
    }
  }
}
