module Cisco-IOS-XR-sysadmin-aaa-disaster-recovery {
  namespace "http://www.cisco.com/ns/yang/Cisco-IOS-XR-sysadmin-aaa-disaster-recovery";
  prefix disaster-recovery;

  import tailf-common {
    prefix tailf;
  }
  import tailf-aaa {
    prefix aaa;
  }
  import cisco-semver {
    prefix semver;
  }

  organization
    "Cisco Systems Inc.";
  contact
    "clos-mgbl@cisco.com";
  description
    "This module defines the system users authentication
     credentials and virtual IP that can be modified in
     runtime.
     
     Copyright (c) 2012-2020 by Cisco Systems, Inc.
     All rights reserved.";

  revision 2019-04-15 {
    description
      "Establish semantic version baseline.";
    semver:module-version "1.0.0";
  }
  revision 2017-05-10 {
    description
      "Namespace changed from disaster-recovery to Cisco-IOS-XR-sysadmin-aaa-disaster-recovery";
  }
  revision 2011-06-20 {
    description
      "Initial revision";
  }

  augment "/aaa:aaa" {
    container disaster-recovery {
      leaf username {
        type leafref {
          path "/aaa:aaa/aaa:authentication/aaa:users/aaa:user/aaa:name";
        }
      }
      leaf password {
        type tailf:md5-digest-string;
      }
    }
  }
}
