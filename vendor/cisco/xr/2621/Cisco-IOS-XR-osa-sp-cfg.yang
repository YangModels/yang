module Cisco-IOS-XR-osa-sp-cfg {
  namespace "http://cisco.com/ns/yang/Cisco-IOS-XR-osa-sp-cfg";
  prefix osa-sp-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa-sp package configuration.
     
     This module contains definitions
     for the following management objects:
       ains: AINS Soak Interval Value
     
     Copyright (c) 2013-2020 by Cisco Systems, Inc.
     All rights reserved.";

  revision 2020-03-09 {
    description
      "Initial Revision.";
    semver:module-version "1.0.0";
  }
  revision 2019-04-05 {
    description
      "Establish semantic version baseline.";
  }
  revision 2015-11-09 {
    description
      "IOS XR 6.0 revision.";
  }

  typedef Ains-soak-hrs-range {
    type uint32 {
      range "0..48";
    }
    description
      "Ains soak hrs range";
  }

  typedef Ains-soak-mins-range {
    type uint32 {
      range "0..59";
    }
    description
      "Ains soak mins range";
  }

  container ains {
    description
      "AINS Soak Interval Value";
    leaf hours {
      type Ains-soak-hrs-range;
      units "hour";
      description
        "Hours";
    }
    leaf minutes {
      type Ains-soak-mins-range;
      units "minute";
      description
        "Minutes";
    }
  }
}
