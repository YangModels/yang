submodule Cisco-IOS-XR-mediasvr-linux-oper-sub2 {
  belongs-to Cisco-IOS-XR-mediasvr-linux-oper {
    prefix Cisco-IOS-XR-mediasvr-linux-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR mediasvr-linux package operational data.
     
     Copyright (c) 2013-2020 by Cisco Systems, Inc.
     All rights reserved.";

  revision 2020-07-11 {
    description
      "Breaking show media result string into fields";
    semver:module-version "2.1.0";
  }
  revision 2019-04-05 {
    description
      "Establish semantic version baseline.";
  }
  revision 2015-11-09 {
    description
      "IOS XR 6.0 revision.";
  }

  grouping SHOW-SMART-MONITOR-EDM-DISK {
    description
      "SHOW SMART MONITOR EDM DISK";
    leaf name-xr {
      type string {
        length "0..32";
      }
      description
        "Disk name";
    }
    leaf model {
      type string {
        length "0..64";
      }
      description
        "Device model";
    }
    leaf serial {
      type string {
        length "0..32";
      }
      description
        "Serial number";
    }
    leaf health-status {
      type string {
        length "0..16";
      }
      description
        "SMART health status";
    }
    leaf soft-read-error-rate {
      type uint64;
      description
        "Soft read error rate";
    }
    leaf reallocated-sectors {
      type uint64;
      description
        "Reallocated sectors count";
    }
    leaf end-to-end-error {
      type uint64;
      description
        "End-to-end error count";
    }
    leaf offline-uncorrectable-sectors-count {
      type uint64;
      description
        "Offline uncorrectable sectors";
    }
    leaf life-left {
      type uint8;
      units "percentage";
      description
        "Percentage of life remaining";
    }
    leaf percentage-used {
      type uint8;
      units "percentage";
      description
        "Percentage of life used";
    }
    leaf raw-data {
      type string {
        length "0..7168";
      }
      description
        "Complete SMART raw output";
    }
  }
}
