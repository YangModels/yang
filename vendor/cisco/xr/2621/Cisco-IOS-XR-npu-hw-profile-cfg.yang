module Cisco-IOS-XR-npu-hw-profile-cfg {
  namespace "http://cisco.com/ns/yang/Cisco-IOS-XR-npu-hw-profile-cfg";
  prefix npu-hw-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR npu-hw-profile package configuration.
     
     This module contains definitions
     for the following management objects:
       npu-hw-module-profile-runtime-config: none
       macsec-hw-module: Macsec Related HW Module configs, Reload
         Card after config
       npu-hw-module-profile-config: none
     
     Copyright (c) 2013-2026 by Cisco Systems, Inc.
     All rights reserved.";

  revision 2026-03-15 {
    description
      "Yang Schema added for max-packets-hbm-buffer in hw-module config.
       2026-02-15
         Yang Schema added for encap-default catch-all in hw-module config.
       2026-02-10
         Yang Schema added for voq-cgm-prefit disable in hw-module config.
       2026-02-05
         Yang Schema removed for og-compr-id-extension in hw-module config.
       2026-01-09
         Yang Schema added for ogacl egress large-scale in hw-module config.
       2025-12-11
         Yang Schema added for TCP MSS adjust in hw-module config.
       2025-12-10
         Yang Schema added for highscale-stage1 in hw-module config.
       2025-11-28
         Yang Schema added for hash ip-field-duplication in hw-module config.
       2025-09-30
         Added large-label-stack in cef-forwarding
       2025-08-27
         Yang Schema added for BGP per connected nh protection
       2025-07-24
         Yang Schema added for acl-oc in hw-module config.
       2025-07-20
         Removed fib leaf in hw-module profile tcam config.
       2025-07-09
         Yang Schema removed for mplsoudp scale profile in hw-module config.
       2025-06-26
         Yang Schema updated for new npu-compatibility mode.
       2025-05-29
         Yang Schema added for l3vpn short pipe mode in hw-module config.
       2025-05-16
         Yang Schema removed the udp-dest-port leaf in hw-module config.
       2025-04-10
         Yang Schema added for iptunnel scale profile in hw-module config.
       2025-03-28
         Yang Schema added for SRv6 Per-path stats full-scale in hw-module config.
       2025-02-09
         Yang Schema added for og-compr-id-extension in hw-module config.
       2025-02-01
         Yang Schema added for host-route scale in hw-module config.
       2024-10-10
         Yang Schema added for LPM Full-scale in hw-module config.
       2024-09-20
         Yang Schema updated for forward-class-lists in hw-module config.
       2024-09-19
         Yang Schema fixed for pifib entry counters hw-module config.
       2024-08-27
         Yang Schema added for evpn-aging hw-module config.
       2024-06-26
         Yang Schema added for encap-exact in hw-module config.
       2024-05-05
         Yang Schema added for intra-npu-over-fabric in hw-module config.
       2024-05-01
         Yang Schema added for PBR pathgroup profile in hw-module config.
       2024-04-12
         Yang Schema added for IRB profile in hw-module config.
       2024-03-06
         Yang Schema added for source-rtbh hw-module config.
       2024-02-20
         Yang Schema added for low-latency profile in hw-module config.
       2023-11-15
         Yang Schema added for mplsoudp scale profile in hw-module config.
       2023-11-13
         Enum added for npu-pktlosswin leaf
       2023-11-07
         Yang Schema added for route scale lpm cem
       2023-10-11
         Yang Schema added for qos high-water-marks
       2023-02-10
         Yang Schema added for IPv6 Shortening in hw-module config.
       2023-01-26
         Yang Schema added for gue underlay hash profile in hw-module config.
       2022-11-22
         Yang Schema updated for route scale lpm tcam-banks
       2022-11-14
         Yang Schema added for bgplu-over-rsvpte
       2022-09-30
         Yang Schema updated to add LDPoTE scale/label knobs
       2022-09-27
         Yang Schema added for pbr vrfredirect in hw-module config.
       2022-09-08
         Yang Schema updated for route scale lpm tcam-banks
       2022-09-01
         Yang Schema added for flowspec ipv6 packet length in hw-module config.
       2022-08-25
         Yang Schema added for vxlan ipv6 tunnel scale
       2022-07-07
         Yang Schema added for route scale lpm high
       2022-04-28
         Yang Schema added for l2 high scale
       2022-04-25
         Yang Schema added for npu compatibility
       2022-04-06
         Yang Schema added for vxlan-dc-leaf
       2022-02-11
         Yang Schema added for configuring CBF forward-class-list
       2021-12-11
         Yang Schema added for route scale high for IPV6 connected-prefix";
    semver:module-version "2.0.0";
  }
  revision 2021-08-15 {
    description
      "Yang Schema updated to make fair-4/fair-8 options visible
       2021-06-28
          Yang Schema updated to accept a range of values for lpts entry counters
       2021-04-30
          Yang Schema added for bd flush convergence
       2021-03-04
          Yang Schema added for pifib entry counters
       2021-02-16
          Yang Schema added for cbf";
    semver:module-version "1.1.0";
  }
  revision 2021-01-26 {
    description
      "Added CEF profile for punting ip-redirect";
    semver:module-version "1.0.0";
  }
  revision 2021-01-11 {
    description
      "Added profile CEF IPv6 hop-limit punt";
  }
  revision 2020-11-13 {
    description
      "Yang Schema removed block for NPU power profile in hw-module config.";
  }
  revision 2020-11-09 {
    description
      "Yang Schema fixed for npu config hw module cli - power profile model.";
  }
  revision 2020-09-29 {
    description
      "Yang Schema added for l2-qos-mode";
  }
  revision 2020-09-01 {
    description
      "Yang Schema added new VoQ modes.";
  }
  revision 2020-07-30 {
    description
      "Yang Schema added for npu-power-optimize";
  }
  revision 2020-06-04 {
    description
      "Yang Schema added for ttl mode of ip tunnel";
  }
  revision 2020-05-27 {
    description
      "Yang Schema added Macsec Related Yang Config Model.";
  }
  revision 2020-04-03 {
    description
      "Yang Schema added for label stats";
  }
  revision 2020-02-05 {
    description
      "Yang Schema updated for reorganized cli knobs.";
  }
  revision 2020-01-22 {
    description
      "Yang Schema added for bw-threshold.";
  }
  revision 2019-12-23 {
    description
      "Yang Schema adde for VoQ and Counter Sharing modes.";
  }
  revision 2019-10-14 {
    description
      "Yang Schema fixed for npu config hw module cli.";
  }
  revision 2019-04-05 {
    description
      "Establish semantic version baseline.";
  }
  revision 2015-11-09 {
    description
      "IOS XR 6.0 revision.";
  }

  typedef Npu-compatibility-mode {
    type enumeration {
      enum "q100" {
        value 1;
        description
          "Q100 asic";
      }
      enum "q200" {
        value 2;
        description
          "Q200 asic";
      }
      enum "p100" {
        value 3;
        description
          "P100 asic";
      }
      enum "p200" {
        value 8;
        description
          "P200 asic";
      }
    }
    description
      "Npu compatibility mode";
  }

  typedef Voq-cgm-prefit-cfg {
    type enumeration {
      enum "disable" {
        value 1;
        description
          "disable voq cgm prefit";
      }
    }
    description
      "Voq cgm prefit cfg";
  }

  typedef Intra-npu-fabric-cfg {
    type enumeration {
      enum "disable" {
        value 1;
        description
          "disable intra npu over fabric";
      }
    }
    description
      "Intra npu fabric cfg";
  }

  typedef Ipv6-hop-limit-action {
    type enumeration {
      enum "punt" {
        value 1;
        description
          "IPv6 hop-limit punt";
      }
    }
    description
      "Ipv6 hop limit action";
  }

  typedef Npu-pkt-loss-win-mode {
    type enumeration {
      enum "3min" {
        value 1;
        description
          "3Min mode";
      }
      enum "5min" {
        value 2;
        description
          "5Min mode";
      }
    }
    description
      "Npu pkt loss win mode";
  }

  typedef Low-latency-mode {
    type enumeration {
      enum "1" {
        value 1;
        description
          "level 1";
      }
    }
    description
      "Low latency mode";
  }

  typedef Qos-voq-mode {
    type enumeration {
      enum "fair-4" {
        value 2;
        description
          "fair-4 VoQ Mode";
      }
      enum "fair-8" {
        value 3;
        description
          "fair-8 VoQ Mode";
      }
      enum "4" {
        value 4;
        description
          "4 VoQ Mode";
      }
      enum "8" {
        value 8;
        description
          "8 VoQ Mode";
      }
    }
    description
      "Qos voq mode";
  }

  container npu-hw-module-profile-runtime-config {
    description
      "none";
    container runtime-profile {
      description
        "Configure profile.";
      container qos-mode {
        description
          "Configure Qos Modes";
        leaf l3vpn-short-pipe {
          type empty;
          description
            "Configure Short Pipe mode for L3VPN";
        }
      }
      container runtime-stats {
        description
          "Configure statistics profile";
        leaf acloc {
          type empty;
          description
            "Enable ACL stats reporting for OC counters
             support";
        }
      }
      leaf npu-pktlosswin {
        type Npu-pkt-loss-win-mode;
        description
          "Configure packet loss duration for raising
           syslog";
      }
    }
  }
  container macsec-hw-module {
    description
      "Macsec Related HW Module configs, Reload Card
       after config";
    container fips-post-location-tables {
      description
        "Enable macsec-fips-post";
      list fips-post-location-table {
        key "location-string";
        description
          "none";
        leaf fips-post-location {
          type string;
          description
            "Macsec FIPS";
        }
        leaf location-string {
          type xr:Cisco-ios-xr-string;
          description
            "Location of MacsecFipsPost config or all";
        }
      }
    }
    container macsec-mode-location-tables {
      description
        "Enable macsec-mode";
      list macsec-mode-location-table {
        key "location-string";
        description
          "none";
        leaf macsec-mode-location {
          type string;
          description
            "Macsec Mode";
        }
        leaf location-string {
          type xr:Cisco-ios-xr-string;
          description
            "Location of MacSecMode config or all";
        }
      }
    }
  }
  container npu-hw-module-profile-config {
    description
      "none";
    container src-cgm-watchdog {
      description
        "src cgm watchdog";
      leaf src-cgm-watchdog-disable {
        type empty;
        description
          "Disable src cgm watchdog";
      }
    }
    container fabricfecmonitor {
      description
        "fabric fec monitor";
      leaf fabricfecmonitordisable {
        type empty;
        description
          "Disable fec monitoring on fabric links";
      }
    }
    container profile {
      description
        "Configure profile.";
      container qos {
        description
          "Configure qos profile";
        leaf intra-npu-over-fabric {
          type Intra-npu-fabric-cfg;
          description
            "Configure Qos intra npu over fabric";
        }
        leaf voq-cgm-prefit {
          type Voq-cgm-prefit-cfg;
          description
            "Configure Qos VOQ CGM prefit";
        }
        leaf low-latency {
          type Low-latency-mode;
          description
            "Configure QoS low latency mode";
        }
        leaf high-water-marks {
          type empty;
          description
            "Enable traffic class high water marks
             monitoring";
        }
        leaf hbm-average-pkt-size {
          type uint32 {
            range "64..10000";
          }
          description
            "Configure Qos hbm average packet size";
        }
        leaf l2-mode {
          type uint32 {
            range "2..3";
          }
          description
            "value either 2 or 3 (for L2 or L3 mode)";
        }
        leaf voq-mode {
          type Qos-voq-mode;
          description
            "voq mode to configure";
        }
      }
      container flowspec {
        description
          "Configure flowspec parameters";
        leaf ipv6-packet-len {
          type empty;
          description
            "Enable flowspec for ipv6 packet length
             classification";
        }
      }
      container gue {
        description
          "Configure gue tunnel features";
        leaf underlay-hash {
          type empty;
          description
            "Enable GUE underlay hash feature";
        }
      }
      container bvi {
        description
          "Configure IRB/BVI profiles";
        leaf throughput-optimized {
          type uint32;
          description
            "If enabled, set value to 1";
        }
      }
      container tcam-table {
        description
          "Configure profile for TCAM LC cards";
        container ogacl {
          description
            "OG ACL configuration";
          container egress {
            description
              "Egress direction";
            container large-scale {
              description
                "Large Scale OG ACL Egress profile";
              leaf dst-prefix {
                type empty;
                description
                  "Config dst prefix large-scale mode";
              }
              leaf src-prefix {
                type empty;
                description
                  "Config src prefix large-scale mode";
              }
            }
          }
        }
        container key-format {
          description
            "Configure key format related feature";
          container compr-id-wide {
            description
              "Configure wide compression result of OG ACL
               feature";
            leaf ingress {
              type empty;
              description
                "Enable wide compression result of Ingress OG
                 ACL ";
            }
            leaf egress {
              type empty;
              description
                "Enable wide compression result of Egress OG
                 ACL ";
            }
          }
        }
        container acl-table {
          description
            "ACL table for TCAM LC cards";
          leaf acl-percent {
            type uint32 {
              range "0..100";
            }
            units "percentage";
            description
              "curve out percentage of TCAM table entries";
          }
        }
      }
      container netflow {
        description
          "Configure Netflow profile.";
        container ipfix-netflow-locations {
          description
            "none";
          list ipfix-netflow-location {
            key "location-string";
            description
              "none";
            leaf location-string {
              type xr:Cisco-ios-xr-string;
              description
                "Location of NETFLOW config";
            }
            list ipfix-netflow-location-leaf {
              key "location-id";
              description
                "none";
              leaf location-id {
                type uint32;
                description
                  "Location ID";
              }
              leaf enable-val {
                type uint32;
                mandatory true;
                description
                  "If Enabled set value to 65535";
              }
            }
          }
        }
        container ipfix-location-all {
          description
            "IPFIX315 Location All";
          leaf ipfix-location-all-leaf {
            type uint32;
            description
              "If Enabled set value to 65535";
          }
        }
      }
      container route {
        description
          "route";
        container scale {
          description
            "scale";
          container lpm {
            description
              "lpm";
            container wide-entries {
              description
                "IPv6 wide entries";
              leaf shortened {
                type empty;
                description
                  "Change shortening";
              }
            }
            leaf medium-cem-medium {
              type empty;
              description
                "Change medium-cem-medium";
            }
            leaf low-cem-high {
              type empty;
              description
                "Change low-cem-high";
            }
            leaf tcam-banks {
              type empty;
              description
                "Enable profile scale lpm tcam-banks";
            }
            leaf full-scale {
              type empty;
              description
                "Enable LPM full scale mode";
            }
            leaf high-cem-low {
              type empty;
              description
                "Change high-cem-low";
            }
          }
          container ipv6-unicast {
            description
              "ipv6 unicast";
            container connected-prefix {
              description
                "connected prefix";
              leaf high {
                type empty;
                description
                  "Enable profile ipv6-unicast
                   connected-prefix high";
              }
            }
          }
          container hbm-algo {
            description
              "hbm algo";
            leaf hbm-hi-hbm {
              type empty;
              description
                "Change hbm-hit-hbm";
            }
            leaf hbm-chronograph {
              type empty;
              description
                "Change hbm-chronograph";
            }
            leaf hbm-hi-sram {
              type empty;
              description
                "Change hbm-hit-sram";
            }
          }
          leaf host-route {
            type empty;
            description
              "Enable host-route scale mode";
          }
        }
      }
      container npu {
        description
          "Configure npu ";
        container buffer-extended-locs {
          description
            "Configure buffer-extended ";
          list buffer-extended-loc {
            key "location-string";
            description
              "none";
            leaf bandwidth-congestion-protect {
              type empty;
              description
                "Disable device congestion protect";
            }
            leaf buffer-extended-congestion-detection {
              type empty;
              description
                "Enable buffer-extended-congestion-detection";
            }
            leaf location-string {
              type xr:Cisco-ios-xr-string;
              description
                "Location of buffer-extended config or all";
            }
          }
        }
        leaf highscale-stage1 {
          type empty;
          description
            "Enable highscale-stage1 feature";
        }
      }
      container stats {
        description
          "Configure statistics profile";
        leaf voq-sharing-counters {
          type uint32 {
            range "1..4";
          }
          description
            "Configure number of voqs (1, 2, 4) sharing
             counters";
        }
      }
      container l2fib {
        description
          "Configure l2fib profiles";
        leaf data-center {
          type empty;
          description
            "Data center mode";
        }
        leaf evpn-aging {
          type empty;
          description
            "EVPN reduced mac aging mode";
        }
        leaf pw-stats {
          type uint32;
          description
            "If enabled, set value to 1";
        }
        leaf bd-flush-conv {
          type empty;
          description
            "BD flush convergence mode";
        }
        leaf high-scale {
          type boolean;
          description
            "TRUE if enabled, FALSE if disabled";
        }
      }
      container encap-exact {
        description
          "enable encap exact";
        container interfaces {
          description
            "enable encap exact on an interface";
          list interface {
            key "interface-name";
            description
              "enable encap exact on an interface";
            leaf interface-mode {
              type empty;
              description
                "enable encap exact mode on an interface";
            }
            leaf interface-name {
              type xr:Cisco-ios-xr-string;
              description
                "Interface name";
            }
          }
        }
        container locations {
          description
            "enable encap exact on a location";
          list location {
            key "location-string";
            description
              "enable encap exact on a location";
            leaf location-mode {
              type empty;
              description
                "enable encap exact mode on a location";
            }
            leaf location-string {
              type xr:Cisco-ios-xr-string;
              description
                "all, all-virtual, or LC/MPA";
            }
          }
        }
      }
      container cef-forwarding {
        description
          "Configure cef profiles";
        container te-tunnel {
          description
            "Configure te-tunnel profile";
          leaf label-over-te-counter {
            type uint32;
            description
              "Configure label counters instead of TE
               counters";
          }
          leaf high-scale-ldpote {
            type uint32;
            description
              "Configure te-tunnel highscale with ldp over
               te feature and disable sr over srte";
          }
          leaf high-scale {
            type uint32;
            description
              "Configure te-tunnel highscale and disable ldp
               over te feature";
          }
        }
        container cef-stats {
          description
            "Configure feature level stats";
          container label {
            description
              "Configure label stats";
            container app-default {
              description
                "Applies to - LDP and SR";
              leaf dynamic {
                type uint32;
                description
                  "If enabled, set value to 1";
              }
            }
          }
        }
        container ttl {
          description
            "Configure ttl profile";
          container tunnel-ip {
            description
              "Configure tunnel-ip ttl mode";
            leaf decrement {
              type uint32;
              description
                "Configure tunnel-ip ttl decrement attribute";
            }
          }
        }
        container cef-accounting {
          description
            "Configure feature level accounting";
          container srv6 {
            description
              "Configure srv6 stats";
            container mode {
              description
                "Configure stats mode";
              container per-prefix-per-nexthop {
                description
                  "Applies to - per-prefix-per-nexthop";
                leaf maximize {
                  type empty;
                  description
                    "if enabled, set value to true";
                }
              }
            }
          }
        }
        container forward-classes {
          description
            "forward class list";
          leaf-list forward-class {
            type uint32 {
              range "0..7";
            }
            max-elements "8";
            description
              "forward class id";
          }
        }
        container ipv6 {
          description
            "Configure IPv6 hw profile";
          leaf hop-limit {
            type Ipv6-hop-limit-action;
            description
              "IPv6 hop-limit 0 packets";
          }
        }
        container vxlan {
          description
            "Configure VXLAN tunnel scale feature";
          leaf ipv6-tnl-scale {
            type empty;
            description
              "Enable profile CEF VXLAN IPV6-TNL-SCALE";
          }
        }
        container hash {
          description
            "Configure ASIC hash profile";
          leaf ip-field-duplication {
            type empty;
            description
              "Enable IP field duplication in hash
               calculation. Applicable to Q200 only.";
          }
        }
        container ip-tunnel {
          description
            "Configure IP tunnel scale feature";
          leaf scale {
            type empty;
            description
              "Enable profile CEF IP tunnel SCALE";
          }
        }
        container lpts {
          description
            "Configure LPTS feature";
          leaf pifib-entry-counters {
            type uint32 {
              range "256..512";
            }
            description
              "Configure number of counters";
          }
          leaf acl {
            type empty;
            description
              "Enable profile CEF LPTS ACL";
          }
        }
        leaf mpls-vpn-scale {
          type uint32;
          default "0";
          description
            "If Enabled set value to 1";
        }
        leaf bgplu-over-rsvpte {
          type uint32;
          description
            "Enable BGPLU over RSVPTE feature";
        }
        leaf sropt {
          type uint32 {
            range "0..1";
          }
          description
            "Configure SROPT feature";
        }
        leaf cbf {
          type empty;
          description
            "Enable class based forwarding feature";
        }
        leaf flex-lsp {
          type uint32;
          description
            "If Enabled set value to 1";
        }
        leaf unipath-surpf {
          type empty;
          description
            "Configure unipath surpf feature";
        }
        leaf bgplu {
          type uint32;
          description
            "If Enabled set value to 1";
        }
        leaf dark-bandwidth {
          type uint32 {
            range "0..1";
          }
          description
            "Configure dark-bandwidth feature";
        }
        leaf source-rtbh {
          type empty;
          description
            "Configure source-based RTBH feature";
        }
        leaf large-label-stack {
          type uint32;
          default "0";
          description
            "If Enabled set value to 1";
        }
        leaf ip-redirect {
          type uint32 {
            range "0..1";
          }
          description
            "value either 0 or 1";
        }
        leaf bgp-per-connected-nh-protection {
          type empty;
          description
            "Enable BGP per connected nh protection feature";
        }
        leaf mplsdecapstats {
          type uint32;
          description
            "Configure mpls decap stats feature";
        }
      }
      container pbr {
        description
          "Configure pbr parameters";
        leaf pathgroup-match {
          type empty;
          description
            "Enable pathgroup-match";
        }
        leaf vrf-redirect {
          type empty;
          description
            "Enable vrf-redirect";
        }
      }
      leaf edge-mode {
        type uint32;
        description
          "If Enabled set value to 1";
      }
      leaf bw-threshold {
        type string;
        units "percentage";
        description
          "Configure fabric BW";
      }
      leaf npu-compatibility {
        type Npu-compatibility-mode;
        description
          "Configure npu compatibility mode for chassis";
      }
    }
    container locationtcps {
      description
        "Adjust tcp mss value on a location";
      list locationtcp {
        key "location-string";
        description
          "Adjust tcp mss on this location";
        container tcp-mss-adjust {
          description
            "tcp mss adjust";
          container tcp-mss-nps {
            description
              "np to set tcp mss adjust";
            list tcp-mss-np {
              key "np-number";
              description
                "set tcp mss value on this np";
              leaf tcp-mss-adjust-value {
                type uint32 {
                  range "1280..9136";
                }
                default "1436";
                description
                  "Adjust tcp mss on a location";
              }
              leaf np-number {
                type uint32;
                description
                  "NP number";
              }
            }
          }
        }
        leaf location-string {
          type xr:Cisco-ios-xr-string;
          description
            "all, or LC/MPA";
        }
      }
    }
    container voqwatchdog {
      description
        "voq watchdog";
      container voqwatchdogfeature {
        description
          "voq watchdog feature";
        leaf voqwatchdogfeatureenable {
          type empty;
          description
            "Enable voq watchdog feature";
        }
      }
      container voqwatchdogcardshut {
        description
          "voq watchdog cardshut";
        leaf voqwatchdogcardshutdisable {
          type empty;
          description
            "Disable voq watchdog cardshut";
        }
      }
    }
    container globaleccthreshold {
      description
        "global mem threshold";
      container globaleccthresholdmbe {
        description
          "global mem mbe threshold";
        leaf globaleccthresholdmbevalue {
          type string;
          description
            "value in multiples of 50, range <0-500>";
        }
      }
    }
  }
}
