module Cisco-IOS-XR-sysadmin-show-inv {
  namespace "http://www.cisco.com/ns/yang/Cisco-IOS-XR-sysadmin-show-inv";
  prefix inv;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Calvados Inventory Service maintain entity database
     
     Copyright (c) 2011-2020 by Cisco Systems, Inc.
     All rights reserved.";

  revision 2021-02-24 {
    description
      "Add container locationinfo";
    semver:module-version "3.0.0";
  }
  revision 2019-04-15 {
    description
      "Establish semantic version baseline.";
    semver:module-version "2.0.0";
  }
  revision 2017-04-12 {
    description
      "Changed the namespace and module name";
  }
  revision 2013-07-20 {
    description
      "MC revision of show inventory commands";
  }

  grouping target_str {
    leaf name {
      type string;
      description
        "Name of the entity";
    }
    leaf Description {
      type string;
      description
        "Description of the entity";
    }
    leaf PID {
      type string;
      description
        "Product ID of the entity";
    }
    leaf VID {
      type string;
      description
        "Version ID of the entity";
    }
    leaf SN {
      type string;
      description
        "Serial Numbe of the entity";
    }
  }

  grouping inv-loc {
    list location {
      key "loc";
      leaf loc {
        type string;
        description
          "Node id of the entity";
      }
      list locationinfo {
        key "name";
        uses target_str;
      }
      leaf name {
        type string;
        status deprecated;
        description
          "Name of the entity";
      }
      leaf Description {
        type string;
        status deprecated;
        description
          "Description of the entity";
      }
      leaf PID {
        type string;
        status deprecated;
        description
          "Product ID of the entity";
      }
      leaf VID {
        type string;
        status deprecated;
        description
          "Version ID of the entity";
      }
      leaf SN {
        type string;
        status deprecated;
        description
          "Serial Numbe of the entity";
      }
    }
  }

  grouping inv-all {
    list all {
      key "index";
      leaf index {
        type uint32;
        description
          "Index for the entity";
      }
      uses target_str;
    }
  }

  grouping inv-chassis {
    list chassis {
      key "index";
      leaf index {
        type uint32;
        description
          "Index for the entity";
      }
      uses target_str;
    }
  }

  grouping inv-power {
    list power {
      key "index";
      leaf index {
        type uint32;
        description
          "Index for the entity";
      }
      uses target_str;
    }
  }

  grouping inv-fan {
    list fan {
      key "index";
      leaf index {
        type uint32;
        description
          "Index for the entity";
      }
      uses target_str;
    }
  }

  grouping inv-raw {
    list raw {
      key "index";
      leaf index {
        type uint32;
        description
          "Index for the entity";
      }
      uses target_str;
    }
  }

  container inventory {
    config false;
    description
      "show inventory";
    uses inv-loc;
    uses inv-all;
    uses inv-chassis;
    uses inv-power;
    uses inv-fan;
    uses inv-raw;
  }
}
