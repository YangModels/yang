module openconfig-hc {
  namespace "http://openconfig.net/yang/hc";
  prefix oc-hc;

  import Cisco-IOS-XR-types {
    prefix xr;
  }
  import cisco-semver {
    prefix semver;
  }
  organization
    "Cisco Systems, Inc.";
  contact
    "Cisco Systems, Inc.
     Customer Service

     Postal: 170 West Tasman Drive
     San Jose, CA 95134

     Tel: +1 800 553-NETS

     E-mail: cs-yang@cisco.com";
  description
    "Internal healthcheck model.

     Copyright (c) 2025-2026 by Cisco Systems, Inc., and/or its affiliates.
     All rights reserved.";

  revision 2025-08-20 {
    description
      "Initial commit";
  }
  typedef Card-redundancy-state {
    type enumeration {
      enum red-state-none {
        value 0;
        description "Not Applicable";
      }
      enum active {
        value 1;
        description "Active";
      }
      enum standby {
        value 2;
        description "Standby";
      }
    }
    description "Redundancy state detail";
  }
  grouping PLATFORM-INFO {
    description "Platform information";
    leaf card-type {
      type string;
      description "Card type";
    }
    leaf card-redundancy-state {
      type Card-redundancy-state;
      description "Redundancy state";
    }
    leaf admin-state {
      type string;
      description "Admin state";
    }
    leaf node-name {
      type string;
      description "Node name";
    }
    leaf oper-state {
      type string;
      description "Operational state";
    }
  }
  grouping SLOT-TABLE {
    description "Common node of rack, rack";

    container slots {
      description "Table of slots";

      list slot {
        key "slot-name";
        description "Slot name";

        container instances {
          description "Table of Instances";

          list instance {
            key "instance-name";
            description "Instance name";
            leaf instance-name {
              type string;
              description "Instance name";
            }
            uses PLATFORM-INFO;
          }
        }

        leaf slot-name {
          type xr:Cisco-ios-xr-string;
          description "Slot name";
        }
        uses PLATFORM-INFO;
      }
    }
  }
  grouping FABRIC-HEALTH {
    description "FSDBAGG EDM FABRIC HEALTH";
    leaf aggr-status {
      type string;
      description "aggr status";
    }
    leaf rack-total {
      type int32;
      description "rack total";
    }
    leaf rack-lcc {
      type int32;
      description "rack lcc";
    }
    leaf rack-fcc {
      type int32;
      description "rack fcc";
    }
    leaf plane-up {
      type int32;
      description "plane up";
    }
    leaf plane-dn {
      type int32;
      description "plane dn";
    }
    leaf plane-mcast-dn {
      type int32;
      description "plane mcast dn";
    }
    leaf plane-admin-dn {
      type int32;
      description "plane admin dn";
    }
    leaf sfe-asics-total {
      type int32;
      description "sfe asics total";
    }
    leaf sfe-asics-up {
      type int32;
      description "sfe asics up";
    }
    leaf sfe-asics-dn {
      type int32;
      description "sfe asics dn";
    }
    leaf fia-asics-total {
      type int32;
      description "fia asics total";
    }
    leaf fia-asics-up {
      type int32;
      description "fia asics up";
    }
    leaf fia-asics-dn {
      type int32;
      description "fia asics dn";
    }
    leaf show-sys-plane-detail {
      type boolean;
      description "show sys plane detail";
    }

    list sys-plane-info {
      max-elements "8";
      description "sys plane info";
      uses FABRIC-HEALTH-SYS-PLANE-INFO;
    }

    list rack-info {
      description "rack health bag";
      uses FABRIC-HEALTH-RACK-INFO;
    }
  }
  grouping FABRIC-HEALTH-RACK-INFO {
    description "FABRIC HEALTH RACK INFO";

    container rack-plane-info {
      description "rack plane info";
      leaf asics-total {
        type uint32;
        description "total asics";
      }
      leaf asics-up {
        type uint32;
        description "up asics";
      }
      leaf asics-dn {
        type uint32;
        description "dn asics";
      }
    leaf plane-state {
      type string {
        length "0..32";
      }
      description "plane state";
    }
    }
    leaf is-rack-valid {
      type boolean;
      description "is valid";
    }
    leaf fsdb-status {
      type string {
        length "0..32";
      }
      description "fsdb status";
    }
    leaf npu-fe-status {
      type string {
        length "0..32";
      }
      description "npu fe status";
    }
    leaf rack-num {
      type string {
        length "0..32";
      }
      description "rack num";
    }
    leaf rack-type {
      type string {
        length "0..32";
      }
      description "rack type";
    }
    leaf sfe-asics-total {
      type int32;
      description "sfe asics total";
    }
    leaf sfe-asics-up {
      type int32;
      description "sfe asics up";
    }
    leaf sfe-asics-dn {
      type int32;
      description "sfe asics dn";
    }
    leaf fia-asics-total {
      type int32;
      description "fia asics total";
    }
    leaf fia-asics-up {
      type int32;
      description "fia asics up";
    }
    leaf fia-asics-dn {
      type int32;
      description "fia asics dn";
    }
    leaf num-valid-fabids {
      type int32;
      description "num valid fabids";
    }
    leaf show-rack-plane-detail {
      type boolean;
      description "show rack plane detail";
    }
  }
  grouping FABRIC-HEALTH-SYS-PLANE-INFO {
    description "FSDBAGG EDM SYS PLANE INFO";
    leaf plane-id {
      type uint32;
      description "plane id";
    }
    leaf admin-state {
      type string;
      description "admin state";
    }
    leaf plane-state {
      type string;
      description "plane state";
    }
    leaf racks-w-plane-fault {
      type int32;
      description "racks w plane fault";
    }
    leaf is-data-drop {
      type boolean;
      description "is data drop";
    }
  }
  container metrics {
    description
      "Healthcheck metrics";
    container cpu {
      description
        "CPU metrics";
      container nodes {
        description
          "CPU metrics for each nodes";
        list node {
          key "node-name";
          description "Processes CPU utilization information";
          leaf node-name {
            type xr:Node-id;
            description "Node name";
          }
          leaf cpu-1min-usage {
            type uint32;
            description "Total CPU utilization in past 1 minute";
          }
          leaf cpu-5min-usage {
            type uint32;
            description "Total CPU utilization in past 5 minute";
          }
          leaf cpu-15min-usage {
            type uint32;
            description "Total CPU utilization in past 15 minute";
          }
        }
      }
    }
    container fpd {
      description
        "FPD info";
      container fpds {
        description
          "FPD info";
        leaf location {
          type string;
          description "fpd location";
        }
        leaf card-name {
          type string;
          description "Name of card on which fpd is located";
        }
        leaf fpd-name {
          type string;
          description "fpd name";
        }
        leaf hw-version {
          type string;
          description "hadware version";
        }
        leaf secure-boot-attr {
          type string;
          description "secure boot attribur";
        }
        leaf status {
          type string;
          description "status of the fpd";
        }
        leaf running-version {
          type string;
          description "image running version ";
        }
        leaf programd-version {
          type string;
          description "image programd version";
        }
      }
    }
    container free-mem {
      config false;
      description "Memory summary information";

      container nodes {
        description "List of nodes";

        list node {
          key "node-name";
          description "Name of nodes";
          leaf node-name {
            type xr:Node-id;
            description "Node name";
          }
          leaf free-physical-memory {
            type uint64;
            units "byte";
            description "Physical memory available in bytes";
          }
          leaf ram-memory {
            type uint64;
            units "byte";
            description "Physical memory size in bytes";
          }
        }
      }
    }
    container file-system {
      config false;
      description "List of filesystems";

      list node {
        key "node-name";
        description "Node ID";
        leaf node-name {
          type xr:Node-id;
          description "Node name";
        }
        container partition {
          description
            "Partition info";
          leaf size {
            type string;
            units "byte";
            description "Size of the file system in bytes";
          }
          leaf free {
            type string;
            units "byte";
            description "Free space in the file system in bytes";
          }
          leaf type {
            type string;
            description "Type of file system";
          }
          leaf flags {
            type string;
            description "Flags of file system";
          }
          leaf prefixes {
            type string;
            description "Prefixes of file system";
          }
        }
      }
    }
    container intf-oor {
      description
        "Out of resource data";
      container interfaces {
        description
          "OOR data for interfaces";
        container interface {
          description
            "OOR interface data";
          leaf interface-name {
            type xr:Cisco-ios-xr-string;
            description
              "The name of the interface";
          }
          leaf interface-status {
            type string;
            description
              "The current state of the interface";
          }
        }
      }
      container summary {
        description
          "Lists interfaces in each of the three states";
        leaf red {
          type uint32;
          description
            "interfaces in red state";
        }
        leaf green {
          type uint32;
          description
            "interfaces in green state";
        }
        leaf yel-low {
          type uint32;
          description
            "interfaces in yellow state";
        }
      }
    }
    container redundancy {
      description
        "Redundancy information";
      leaf active {
        type string;
        description "Active node name R/S/I";
      }
      leaf standby {
        type string;
        description "Standby node name R/S/I";
      }
      leaf ha-state {
        type string;
        description "High Availability state Ready/Not Ready";
      }
      leaf nsr-state {
        type string;
        description "NSR state Configured/Not Configured";
      }
    }
    container shared-mem {
      config false;
      description "Memory summary information";

      container nodes {
        description "List of nodes";

        list node {
          key "node-name";
          description "Name of nodes";

          leaf node-name {
            type xr:Node-id;
            description "Node name";
          }
          leaf total-shared-window {
            type uint64;
            description "Total Shared window";
          }
        }
      }
    }
    container sysdb-health {
      description
        "SysDB information";
      leaf conf-space {
        type string;
        description "Sysdb health for configuration space";
      }
      leaf memory {
        type string;
        description "Sysdb health on memory consumption";
      }
      leaf oper-space {
        type string;
        description "Sysdb health for operational space";
      }
      leaf cpu {
        type string;
        description "Sysdb health on cpu consumption";
      }
    }
    container platform {
      config false;
      description "Platform information";

      container racks {
        description "Table of racks";

        list rack {
          key "rack-name";
          description "Rack name";
          leaf rack-name {
            type xr:Cisco-ios-xr-string;
            description "Rack name";
          }
          uses SLOT-TABLE;
        }
      }
    }
    container fabric-health {
      description
        "Fabric health info";
      config false;
      uses FABRIC-HEALTH;
    }
  }
}
