module Cisco-IOS-XR-um-8000-hw-module-profile-cfg {
  namespace "http://cisco.com/ns/yang/Cisco-IOS-XR-um-8000-hw-module-profile-cfg";
  prefix um-8000-hw-module-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-hw-module-profile package configuration.
     
     This YANG module augments the
     modules with configuration data.
     
     Copyright (c) 2021-2026 by Cisco Systems, Inc., and/or its affiliates.
     All rights reserved.";

  revision 2026-03-10 {
    description
      "Yang Schema added for hbm-average-pkt-size in hw-module config.
       2026-02-24
         Added hw-module profile tcam format og-compr-id-extension ingress/egress.
       2026-02-15
         Updated description for tcp location-all
       2026-02-10
         Added hw-module profile npu voq-cgm-prefit disable config
       2026-01-27
         Added container for TCP MSS adjust in hw-module config
       2026-01-09
         Added support for hw-module profile tcam ogacl egress large-scale dst-prefix/src-prefix disable.
       2025-12-04
         Added hw-module profile npu highscale-stage1 config
       2025-11-28
         Added hw-module profile cef hash ip-field-duplication.
       2025-08-22
         update pfc internal headroom values.
       2025-07-24
         Added hw-module profile stats acl-oc
       2025-07-21
         update pfc internal threshold values.
       2025-07-20
         Removed fib leaf in hw-module profile tcam config
       2025-07-09
         Removed hw-module profile cef mplsoudp scale.
       2025-05-29
         Added hw-module profile l3vpn short pipe mode
       2025-05-16
         Removed udp-dest-port leaf in hw-module profile config.
       2025-04-10
         Added hw-module profile cef iptunnel scale
       2025-03-27
         Removed default keyword for max-non-pfc-tcs under non-pfc-tcs
       2025-03-24
         Added hbm-buffers-percentage for non-pfc-tcs
       2025-02-09
         Added hw-module profile tcam format og-compr-id-extension
       2025-02-06
         remove l2-mode must statement clause from qos-stats-push-collection
       2025-02-01
         Added knob to enable host-route scale mode
       2024-11-20
         updated range value for non-pfc-tc
       2024-10-31
         Added knob to enable LPM full-scale mode
       2024-10-25
         Added pfc buffer-extended non-pfc-tc
       2024-08-16
         Added evpn-aging feature
       2024-06-26
         Added encap-exact feature
       2024-05-05
         Added intra-npu-over-fabric disable feature
       2024-05-01
         Added pbr pathgroup
       2024-04-12
         Added IRB container with throughput-optimized leaf
       2024-04-03
         Added Source-based RTBH knob
       2024-02-20
         Added low-latency feature
       2023-12-10
         Added MPLSoUDP scale feature
       2023-11-30
         Added new route scale lpm sram-banks feature
       2023-10-11
         Added qos high-water-marks container for the traffic class high water marks monitoring feature
       2023-05-09
         Added BGPLU over RSVPTE feature
       2023-04-30
         Added new router scale LPM wide-entries shortened scale feature
       2023-04-20
         Added hbm-algo options
       2023-02-07
         Feature xoff mode added
       2023-01-05
         Added unipath rpf hw-mod profile
       2022-12-06
         Added SROPT mode feature
       2022-11-22
         fix tcam-banks in lpm node
       2022-10-11
         Added vxlan ipv6 tunnel scale
       2022-09-28
         Modified lpm high node as lpm tcam-banks in  hw-module profile route scale lpm
       2022-09-27
         Added hw-module profile pbr vrfredirect
       2022-09-02
         Added leafs in hw-module profile cef
       2022-08-04
         Added buffer-extend support
       2022-07-08
         Added  high lpm scale
       2022-07-04
         Added new node multicast under container hw-module
       2022-06-28
         Updated buffer-extended and buffer-internal nodes. Removed location-name list key node
       2022-06-23
         Modified the range of headroom under ms and us nodes
       2022-04-26
         Added leaf high_scale under l2fib
       2022-04-25
         Added new vxlan-dc-leaf hw-module command
       2022-04-24
         Added npu-compatibility support
       2022-04-20
         Updated buffer-extended and buffer-internal nodes
       2022-03-23
         no-bvi-ingress node moved up one hierarchy under stats
       2022-03-18
         Removed presence statement under buffer-extended node
       2022-03-10
         Added missing nodes
       2022-02-10
         Added leaf pause-threshold-bytes
       2021-12-20
         Added new router scale ipv6-unicast connected-prefix scale feature";
    semver:module-version "2.0.0";
  }
  revision 2021-03-19 {
    description
      "Initial release";
    semver:module-version "1.0.0";
  }

  container hw-module {
    description
      "Configure h/w module";
    container multicast {
      description
        "Configure Multicast Route Scale";
      container route-scale {
        presence "Indicates a route-scale node is configured.";
        description
          "Configure Multicast Route Scale";
      }
    }
    container profile {
      description
        "Configure profile.";
      container tcam {
        description
          "Configure profile for TCAM LC cards";
        container ogacl {
          description
            "OG ACL configuration";
          container egress {
            description
              "Egress direction";
            container large-scale {
              description
                "Large Scale OG ACL Egress profile";
              leaf src-prefix {
                type enumeration {
                  enum "disable" {
                    value 1;
                    description
                      "Disable src-prefix large-scale mode";
                  }
                }
                description
                  "Source prefix";
              }
              leaf dst-prefix {
                type enumeration {
                  enum "disable" {
                    value 1;
                    description
                      "Disable dst-prefix large-scale mode";
                  }
                }
                description
                  "Destination prefix";
              }
            }
          }
        }
        container format {
          description
            "format of the tcam entry";
          container og-compr-id-extension {
            description
              "Enable wide compression result of OG ACL";
            container ingress {
              presence "Indicates wide compression result of ingress OG ACL is configured.";
              description
                "Enable wide compression result of ingress OG ACL";
            }
            container egress {
              presence "Indicates wide compression result of egress OG ACL is configured.";
              description
                "Enable wide compression result of egress OG ACL";
            }
          }
          container access-list {
            description
              "Access List format";
            container ipv4 {
              presence "Indicates a ipv4 node is configured.";
              description
                "IPv4";
              container src-addr {
                presence "Indicates a src-addr node is configured.";
                description
                  "ipv4 source address";
              }
              container dst-addr {
                presence "Indicates a dst-addr node is configured.";
                description
                  "ipv4 destination address";
              }
              container src-port {
                presence "Indicates a src-port node is configured.";
                description
                  "source port for TCP/UDP";
              }
              container dst-port {
                presence "Indicates a dst-port node is configured.";
                description
                  "destination port for TCP/UDP";
              }
              container proto {
                presence "Indicates a proto node is configured.";
                description
                  "protocol field in IPV4 header";
              }
              container precedence {
                presence "Indicates a precedence node is configured.";
                description
                  "precedence/dscp field in IPV4 header";
              }
              container ttl-match {
                presence "Indicates a ttl-match node is configured.";
                description
                  "TTL in IPv4 header";
              }
              container tcp-flags {
                presence "Indicates a tcp-flags node is configured.";
                description
                  "tcp flags";
              }
              container frag-bit {
                presence "Indicates a frag-bit node is configured.";
                description
                  "fragment-bit";
              }
              container src-object-group {
                presence "Indicates a src-object-group node is configured.";
                description
                  "source object group";
              }
              container dst-object-group {
                presence "Indicates a dst-object-group node is configured.";
                description
                  "destination object group";
              }
              container packet-len {
                presence "Indicates a packet-len node is configured.";
                description
                  "packet length";
              }
              container fragment-offset {
                presence "Indicates a fragment-offset node is configured.";
                description
                  "fragment-offset";
              }
              leaf udf1 {
                type xr:Cisco-ios-xr-string {
                  length "1..800" {
                    description
                      "UDF name";
                  }
                }
                description
                  "user defined filter";
              }
              leaf udf2 {
                type xr:Cisco-ios-xr-string {
                  length "1..800" {
                    description
                      "UDF name";
                  }
                }
                description
                  "user defined filter";
              }
              leaf udf3 {
                type xr:Cisco-ios-xr-string {
                  length "1..800" {
                    description
                      "UDF name";
                  }
                }
                description
                  "user defined filter";
              }
              leaf udf4 {
                type xr:Cisco-ios-xr-string {
                  length "1..800" {
                    description
                      "UDF name";
                  }
                }
                description
                  "user defined filter";
              }
              leaf udf5 {
                type xr:Cisco-ios-xr-string {
                  length "1..800" {
                    description
                      "UDF name";
                  }
                }
                description
                  "user defined filter";
              }
              leaf udf6 {
                type xr:Cisco-ios-xr-string {
                  length "1..800" {
                    description
                      "UDF name";
                  }
                }
                description
                  "user defined filter";
              }
              leaf udf7 {
                type xr:Cisco-ios-xr-string {
                  length "1..800" {
                    description
                      "UDF name";
                  }
                }
                description
                  "user defined filter";
              }
              leaf udf8 {
                type xr:Cisco-ios-xr-string {
                  length "1..800" {
                    description
                      "UDF name";
                  }
                }
                description
                  "user defined filter";
              }
            }
            container ipv6 {
              presence "Indicates a ipv6 node is configured.";
              description
                "IPv6";
              container src-addr {
                presence "Indicates a src-addr node is configured.";
                description
                  "ipv6 source address";
              }
              container dst-addr {
                presence "Indicates a dst-addr node is configured.";
                description
                  "ipv6 destination address";
              }
              container src-port {
                presence "Indicates a src-port node is configured.";
                description
                  "source port for TCP/UDP (mandatory field)";
              }
              container dst-port {
                presence "Indicates a dst-port node is configured.";
                description
                  "destination port for TCP/UDP";
              }
              container next-hdr {
                presence "Indicates a next-hdr node is configured.";
                description
                  "next header field in IPV6 header (mandatory field)";
              }
              container traffic-class {
                presence "Indicates a traffic-class node is configured.";
                description
                  "traffic class in IPV6 header";
              }
              container frag-bit {
                presence "Indicates a frag-bit node is configured.";
                description
                  "fragment-bit";
              }
              container tcp-flags {
                presence "Indicates a tcp-flags node is configured.";
                description
                  "tcp flags";
              }
              container src-object-group {
                presence "Indicates a src-object-group node is configured.";
                description
                  "source object group";
              }
              container dst-object-group {
                presence "Indicates a dst-object-group node is configured.";
                description
                  "destination object group";
              }
              container packet-len {
                presence "Indicates a packet-len node is configured.";
                description
                  "packet length";
              }
              leaf udf1 {
                type xr:Cisco-ios-xr-string {
                  length "1..800" {
                    description
                      "UDF name";
                  }
                }
                description
                  "user defined filter";
              }
              leaf udf2 {
                type xr:Cisco-ios-xr-string {
                  length "1..800" {
                    description
                      "UDF name";
                  }
                }
                description
                  "user defined filter";
              }
              leaf udf3 {
                type xr:Cisco-ios-xr-string {
                  length "1..800" {
                    description
                      "UDF name";
                  }
                }
                description
                  "user defined filter";
              }
              leaf udf4 {
                type xr:Cisco-ios-xr-string {
                  length "1..800" {
                    description
                      "UDF name";
                  }
                }
                description
                  "user defined filter";
              }
              leaf udf5 {
                type xr:Cisco-ios-xr-string {
                  length "1..800" {
                    description
                      "UDF name";
                  }
                }
                description
                  "user defined filter";
              }
              leaf udf6 {
                type xr:Cisco-ios-xr-string {
                  length "1..800" {
                    description
                      "UDF name";
                  }
                }
                description
                  "user defined filter";
              }
              leaf udf7 {
                type xr:Cisco-ios-xr-string {
                  length "1..800" {
                    description
                      "UDF name";
                  }
                }
                description
                  "user defined filter";
              }
              leaf udf8 {
                type xr:Cisco-ios-xr-string {
                  length "1..800" {
                    description
                      "UDF name";
                  }
                }
                description
                  "user defined filter";
              }
            }
          }
        }
      }
      container pbr {
        description
          "pbr profiles";
        leaf vrf-redirect {
          type empty;
          description
            "pbr vrfredirect";
        }
        leaf pathgroup {
          type empty;
          description
            "pbr pathgroup";
        }
      }
      container qos {
        description
          "Configure qos profile";
        container voq-mode {
          description
            "voq mode to configure";
          container four {
            must
              "not(../eight or ../fair-four
               or ../fair-eight)";
            presence "Indicates a four node is configured.";
            description
              "4 VoQ Mode";
          }
          container eight {
            must
              "not(../four or ../fair-four
               or ../fair-eight)";
            presence "Indicates a eight node is configured.";
            description
              "8 VoQ Mode";
          }
          container fair-four {
            must
              "not(../four or ../eight
               or ../fair-eight)";
            presence "Indicates a fair-4 node is configured.";
            description
              "fair-4 VoQ Mode";
          }
          container fair-eight {
            must
              "not(../four or ../eight
               or ../fair-four)";
            presence "Indicates a fair-8 node is configured.";
            description
              "fair-8 VoQ Mode";
          }
        }
        leaf l2-mode {
          type enumeration {
            enum "L2" {
              value 2;
              description
                "Use L2 headers for QoS on L2 interfaces";
            }
            enum "L3" {
              value 3;
              description
                "Use L3 headers for QoS on L2 interfaces";
            }
          }
          description
            "Configure QOS mode for L2 interfaces";
        }
        leaf hbm-average-pkt-size {
          type uint32 {
            range "64..10000";
          }
          description
            "Configure average packet size in hbm";
        }
        leaf mode {
          type enumeration {
            enum "l3vpn-short-pipe" {
              value 2;
              description
                "Use inner header DSCP value for classifying packets for L3VPN de-aggregation flow";
            }
          }
          description
            "Configure QOS Mode";
        }
        leaf low-latency-mode {
          type enumeration {
            enum "1" {
              value 1;
              description
                "Enable low-latency level 1";
            }
          }
          description
            "Configure QOS low-latency";
        }
        leaf intra-npu-over-fabric {
          type enumeration {
            enum "disable" {
              value 1;
              description
                "Disable traffic on intra npu over fabric";
            }
          }
          description
            "Configure QOS intra-npu-over-fabric";
        }
        leaf voq-cgm-prefit {
          type enumeration {
            enum "disable" {
              value 1;
              description
                "Disable VOQ CGM prefit";
            }
          }
          description
            "Configure QOS voq-cgm-prefit";
        }
        container qos-stats-push-collection {
          presence "Indicates a qos-stats-push-collection node is configured.";
          description
            "Enable QoS stats push collection";
        }
        container high-water-marks {
          presence "Indicates traffic class high water marks monitoring is enabled";
          description
            "Enable traffic class high water marks monitoring";
        }
      }
      container cef {
        description
          "Configure cef profiles";
        leaf dark-bw {
          type enumeration {
            enum "enable" {
              value 1;
              description
                "Enable Dark bandwidth feature";
            }
          }
          description
            "Configure dark-bandwidth";
        }
        leaf sropt {
          type enumeration {
            enum "enable" {
              value 1;
              description
                "Enable SROPT feature";
            }
          }
          description
            "Enable debug message for SROPT";
        }
        leaf bgplu {
          type enumeration {
            enum "enable" {
              value 1;
              description
                "Enable BGPLU feature";
            }
          }
          description
            "Configure bgplu attribute";
        }
        leaf cbf {
          type enumeration {
            enum "enable" {
              value 1;
              description
                "Enable CBF feature";
            }
          }
          description
            "Enable cbf";
        }
        leaf bgplu-over-rsvpte {
          type enumeration {
            enum "enable" {
              value 1;
              description
                "Enable BGPLU over RSVPTE feature";
            }
          }
          description
            "Configure bgplu over rsvpte attribute";
        }
        container forward-class-lists {
          description
            "Configure hardware forward class list";
          leaf-list forward-class-list {
            type uint32 {
              range "0..7" {
                description
                  "forward class id";
              }
            }
            must "../../cbf";
            max-elements "8";
            description
              "Configure hardware forward class list";
          }
        }
        container ipv6 {
          description
            "IPv6";
          leaf hop-limit {
            type enumeration {
              enum "punt" {
                value 1;
                description
                  "Punt hop-limit 0 packets";
              }
            }
            description
              "Hop-limit 0 packets";
          }
        }
        container lpts {
          description
            "LPTS";
          container acl {
            presence "Indicates a acl node is configured.";
            description
              "Enable ACL";
          }
          leaf pifib-entry-counters {
            type uint32 {
              range "256..512" {
                description
                  "number of counters";
              }
            }
            description
              "Configure number of counters";
          }
        }
        container vxlan {
          description
            "VXLAN";
          container ipv6-tnl-scale {
            presence "Indicates a ipv6-tnl-scale node is configured.";
            description
              "Enable vxlan ipv6 tunnel scale";
          }
        }
        container iptunnel {
          description
            "IPTUNNEL";
          container scale {
            presence "Indicates a scale node is configured.";
            description
              "Enable iptunnel scale";
          }
        }
        container stats {
          description
            "Configure feature level stats";
          container label {
            description
              "Configure label stats";
            leaf app-default {
              type enumeration {
                enum "dynamic" {
                  value 1;
                  description
                    "Allocate counters till OOR";
                }
              }
              description
                "Applies to - LDP and SR";
            }
          }
        }
        container ttl {
          description
            "Configure ttl profile";
          container tunnel-ip {
            description
              "Configure tunnel-ip ttl mode";
            leaf decrement {
              type enumeration {
                enum "disable" {
                  value 1;
                  description
                    "Disable tunnl-ip inner ttl decrement";
                }
              }
              description
                "Configure tunnel-ip ttl decrement behaviour";
            }
          }
        }
        container te-tunnel {
          description
            "Configure te tunnel profile";
          container highscale-no-ldp-over-te {
            presence "Indicates a highscale-no-ldp-over-te node is configured.";
            description
              "Enable te tunnels high scale and disable ldp over te";
          }
          container highscale-ldp-over-te-no-sr-over-srte {
            presence "Indicates a highscale-ldp-over-te-no-sr-over-srte node is configured.";
            description
              "Enable high scale of TE tunnels with LDP over TE and disable SR over SRTE";
          }
          container label-over-te-counters {
            presence "Indicates a label-over-te-counters node is configured.";
            description
              "Enable label counters and disable TE counters";
          }
        }
        leaf ip-redirect {
          type enumeration {
            enum "enable" {
              value 1;
              description
                "Enable IP redirect";
            }
          }
          description
            "IP redirect";
        }
        container unipath-surpf {
          description
            "strict urpf check for single reverse path";
          container enable {
            presence "Indicates a enable node is configured.";
            description
              "Enable unipath surpf";
          }
        }
        container source-rtbh {
          description
            "Source-based RTBH(Remote Triggered Black Hole)";
          container enable {
            presence "Indicates a enable node is configured.";
            description
              "Enable Source-based RTBH";
          }
        }
        container hash {
          description
            "Enable IP field duplication for hash";
          container ip-field-duplication {
            presence "Indicates IP field duplication for hash is configured.";
            description
              "Enable IP field duplication for hash";
          }
        }
      }
      container encap-exact {
        description
          "Configure encap-exact profile";
        container interfaces {
          description
            "Interface name";
          list interface {
            key "interface-name";
            description
              "Interface name";
            leaf interface-name {
              type xr:Interface-name;
              description
                "Interface name";
            }
          }
        }
        container locations {
          description
            "Specify a location";
          list location {
            key "location-name";
            description
              "Specify a location";
            leaf location-name {
              type xr:Node-id;
              description
                "Fully qualified location specification";
            }
          }
          container all {
            presence "Indicates an all node is configured.";
            description
              "All Main Phys and Bundle interfaces";
          }
          container all-virtual {
            presence "Indicates an all-virtual node is configured.";
            description
              "All Main Bundle interfaces";
          }
        }
      }
      container stats {
        description
          "Configure qos stats profile";
        leaf voqs-sharing-counters {
          type enumeration {
            enum "1" {
              value 1;
              description
                "Counter for each queue";
            }
            enum "2" {
              value 2;
              description
                "2 Queues share counters";
            }
            enum "4" {
              value 4;
              description
                "4 Queues share counters";
            }
          }
          description
            "Configure number of voqs (1, 2, 4) sharing counters";
        }
        container no-bvi-ingress {
          presence "Indicates a no-bvi-ingress node is configured.";
          description
            "Disable BVI ingress counter stats";
        }
        container acl-permit {
          presence "Indicates a acl-permit node is configured.";
          description
            "Configure ACL permit stats";
        }
        container acl-oc {
          presence "Indicates acl stats reporting to insight-db is configured";
          description
            "Enable ACL stats reporting to insight-db for OC stats";
        }
      }
      leaf bw-threshold {
        type xr:Cisco-ios-xr-string {
          length "1..800" {
            description
              "value in percent: 10-100 in increments of 10";
          }
          pattern "(100|[1-9]0)";
        }
        description
          "% of Total Fabric BW of Asic requires for INTF bring UP";
      }
      container priority-flow-control {
        description
          "Configure priority-flow-control parameters";
        container locations {
          description
            "Location to apply PFC configuration";
          list location {
            key "location-name";
            description
              "Location to apply PFC configuration";
            leaf location-name {
              type xr:Node-id;
              description
                "Location to apply PFC configuration";
            }
            container buffer-extended {
              description
                "Use Extended Packet Memory buffers";
              list traffic-class {
                must "pause-threshold or pause-threshold-bytes";
                key "traffic-class-id";
                description
                  "configure traffic-class";
                leaf traffic-class-id {
                  type uint32 {
                    range "0..7" {
                      description
                        "Traffic-class";
                    }
                  }
                  description
                    "configure traffic-class";
                }
                leaf pause-threshold {
                  type uint32 {
                    range "2..61440" {
                      description
                        "pause-threshold";
                    }
                  }
                  must "../ms or ../us";
                  must "not(../pause-threshold-bytes)";
                  description
                    "configure pause-threshold";
                }
                leaf pause-threshold-bytes {
                  type uint32 {
                    range "2..61440" {
                      description
                        "pause-threshold";
                    }
                  }
                  must "../kbytes or ../mbytes";
                  must "not(../pause-threshold)";
                  description
                    "configure pause-threshold";
                }
                container ms {
                  presence "Indicates a ms node is configured.";
                  description
                    "Milliseconds (2-25 ms)";
                  leaf headroom {
                    type uint32 {
                      range "4..76800" {
                        description
                          "headroom";
                      }
                    }
                    description
                      "configure headroom";
                  }
                }
                container us {
                  presence "Indicates a us node is configured.";
                  description
                    "Microseconds (2000-25000 us)";
                  leaf headroom {
                    type uint32 {
                      range "4..76800" {
                        description
                          "headroom";
                      }
                    }
                    description
                      "configure headroom";
                  }
                }
                container kbytes {
                  presence "Indicates a kbytes node is configured.";
                  description
                    "KBytes (1024-200000 kbytes)";
                  leaf headroom {
                    type uint32 {
                      range "4..76800" {
                        description
                          "headroom";
                      }
                    }
                    description
                      "configure headroom";
                  }
                }
                container mbytes {
                  presence "Indicates a mbytes node is configured.";
                  description
                    "MBytes (1-200 mbytes)";
                  leaf headroom {
                    type uint32 {
                      range "4..76800" {
                        description
                          "headroom";
                      }
                    }
                    description
                      "configure headroom";
                  }
                }
              }
              list traffic-class-default {
                key "traffic-class-id";
                description
                  "configure traffic-class";
                leaf traffic-class-id {
                  type uint32 {
                    range "0..7" {
                      description
                        "Traffic-class";
                    }
                  }
                  description
                    "configure traffic-class";
                }
              }
              container non-pfc-tcs {
                presence "Indicates a non-pfc-tcs node is configured.";
                description
                  "configure to allow lossy TCs to evict.";
                container max-non-pfc-voqs {
                  description
                    "max lossy voqs to evict";
                  leaf number-of-evict-voqs {
                    type uint32 {
                      range "1..3800" {
                        description
                          "number of evict voqs";
                      }
                    }
                    description
                      "number of evict voqs";
                  }
                  leaf hbm-buffers-percentage {
                    type uint32 {
                      range "50..80" {
                        description
                          "hbm-buffers-percentage";
                      }
                    }
                    description
                      "configure hbm-buffers-percentage for non-pfc-tcs";
                  }
                }
              }
            }
            container buffer-internal {
              description
                "Use Internal Packet Memory buffers";
              list traffic-class {
                key "traffic-class-id";
                description
                  "configure traffic-class";
                leaf traffic-class-id {
                  type uint32 {
                    range "0..7" {
                      description
                        "Traffic-class";
                    }
                  }
                  description
                    "configure traffic-class";
                }
                leaf pause-threshold {
                  type uint32 {
                    range "307200..5760000" {
                      description
                        "pause-threshold (bytes)";
                    }
                  }
                  mandatory true;
                  description
                    "configure pause-threshold";
                }
                leaf headroom {
                  type uint32 {
                    range "201600..1651200" {
                      description
                        "headroom (bytes)";
                    }
                  }
                  mandatory true;
                  description
                    "configure headroom";
                }
                leaf ecn {
                  type uint32 {
                    range "153600..5749376" {
                      description
                        "ecn (bytes)";
                    }
                  }
                  description
                    "configure ecn";
                }
                leaf max-threshold {
                  type uint32 {
                    range "153600..5759616" {
                      description
                        "ecn max threshold(bytes)";
                    }
                  }
                  description
                    "ecn max threshold";
                }
                leaf probability-percentage {
                  type uint32 {
                    range "1..100" {
                      description
                        "percentage";
                    }
                  }
                  description
                    "maximum probability percentage";
                }
              }
              list traffic-class-default {
                key "traffic-class-id";
                description
                  "configure traffic-class";
                leaf traffic-class-id {
                  type uint32 {
                    range "0..7" {
                      description
                        "Traffic-class";
                    }
                  }
                  description
                    "configure traffic-class";
                }
              }
            }
          }
        }
      }
      container npu {
        description
          "Configure npu parameters";
        container buffer-extended {
          description
            "Configure buffer-extended parameters";
          container locations {
            description
              "Location to apply buffer-extended configuration";
            list location {
              key "location-name";
              description
                "Location to apply buffer-extended configuration";
              leaf location-name {
                type xr:Node-id;
                description
                  "Location to apply buffer-extended configuration";
              }
              container bandwidth-congestion-detection {
                description
                  "enable bandwidth congestion detection";
                container enable {
                  presence "Indicates a enable node is configured.";
                  description
                    "enable bandwidth congestion detection";
                }
              }
              container bandwidth-congestion-protect {
                description
                  "device global xoff enable";
                container enable {
                  presence "Indicates a enable node is configured.";
                  description
                    "device global xoff enable";
                }
              }
            }
          }
        }
        leaf highscale-stage1 {
          type enumeration {
            enum "enable" {
              value 1;
              description
                "Enable highscale-stage1 feature";
            }
          }
          description
            "Swap Stage0 and Stage1 resources";
        }
      }
      container l2fib {
        description
          "Configure l2fib profiles";
        container pw-stats {
          presence "Indicates a pw-stats node is configured.";
          description
            "Configure PW stats";
        }
        container bridge-flush-convergence {
          presence "Indicates a bridge-flush-convergence node is configured.";
          description
            "Configure BD flush convergence mode";
        }
        container L2-high-scale {
          presence "Indicates L2 high-scale mode is configured.";
          description
            "Configure L2 high-scale mode";
        }
        container vxlan-dc-leaf {
          presence "Configure datacenter profile for l2 vxlan deployments.";
          description
            "Configure vxlan-dc-leaf profile";
        }
        container evpn-aging {
          presence "Configure reduced evpn mac aging profile.";
          description
            "Configure evpn-aging profile";
        }
      }
      leaf npu-compatibility {
        type enumeration {
          enum "Q100" {
            value 1;
            description
              "Use Q100 for Chassis mode";
          }
          enum "Q200" {
            value 2;
            description
              "Use Q200 for Chassis mode";
          }
          enum "P100" {
            value 4;
            description
              "Use P100 for Chassis mode";
          }
        }
        description
          "Configure npu-compatibility mode for chassis type";
      }
      container route {
        description
          "Configure route scale ipv6-unicast connected-prefix profile";
        container scale {
          description
            "Configure scale";
          container ipv6-unicast {
            description
              "ipv6-unicast";
            container connected-prefix {
              description
                "connected-prefix";
              container high {
                presence "Indicates profile ipv6-unicast connected-prefix high is configured";
                description
                  "Enable profile ipv6-unicast connected-prefix high";
              }
            }
          }
          container host-route {
            presence "Indicates profile host route scale is configured";
            description
              "Enable host route scale for ARP/ND";
          }
          container lpm {
            description
              "enable scale lpm profile";
            container tcam-banks {
              presence "Indicates profile lpm  tcam-banks is configured";
              description
                "Enable high scale for LPM using TCAM banks";
            }
            container full-scale {
              presence "Indicates profile lpm full-scale is configured";
              description
                "Enable full scale for LPM";
            }
            container wide-entries {
              description
                "wide-entries";
              container shortened {
                presence "Indicates profile lpm  wide-entries shorten is configured";
                description
                  "Enable shorten of wide-entries";
              }
            }
            container low-cem-high {
              presence "Indicates high lpm low cem set";
              description
                "configure low-cem-high";
            }
            container medium-cem-medium {
              presence "Indicates medium lpm medium cem set";
              description
                "configure medium-cem-medium";
            }
            container high-cem-low {
              presence "Indicates high lpm cem low set";
              description
                "configure high-cem-low";
            }
          }
          container hbm-algo {
            description
              "configure hbm-algo";
            container hbm-chronograph {
              presence "Indicates hbm chronograph set";
              description
                "configure hbm-algo";
            }
            container hbm-hi-hbm {
              presence "Indicates hbm hi hbm set";
              description
                "configure hbm-hi-hbm";
            }
            container hbm-hi-sram {
              presence "Indicates hbm hi sram set";
              description
                "configure hbm-hi-sram";
            }
          }
        }
      }
      container flowspec {
        description
          "flowspec enable ipv6-packet-length configuration";
        container ipv6-packet-len-enable {
          presence "Indicates profile flowspec ipv6-packet-len-enable is configured";
          description
            "flowspec enable ipv6-packet-length configuration";
        }
      }
      container irb {
        description
          "Configure IRB/BVI profiles";
        container throughput-optimized {
          presence "Indicates that BVI throughput-optimized mode is configured.";
          description
            "Configure BVI throughput-optimized mode";
        }
      }
    }
    container tcp-mss-adjust {
      description
        "Adjust TCP MSS Value for egress traffic";
      container locations {
        description
          "Location to apply tcp_mss_adjust";
        list location {
          must "nps/np or nps/all/value";
          key "location-name";
          description
            "Location to apply TCP MSS Adjust configuration";
          leaf location-name {
            type xr:Node-id;
            description
              "Location to apply TCP MSS Adjust configuration";
          }
          container nps {
            description
              "NP Unit to adjust TCP MSS value";
            list np {
              key "np-id";
              description
                "NP Unit to adjust TCP MSS value";
              leaf np-id {
                type uint32 {
                  range "0..7" {
                    description
                      "Number between 0-7";
                  }
                }
                description
                  "NP to configure";
              }
              leaf value {
                type uint32 {
                  range "1280..9136" {
                    description
                      "TCP MSS value in decimal";
                  }
                }
                mandatory true;
                description
                  "TCP MSS value to set range <1280-9136>";
              }
            }
            container all {
              description
                "Adjust TCP MSS value on all NP units";
              leaf value {
                type uint32 {
                  range "1280..9136" {
                    description
                      "TCP MSS value in decimal";
                  }
                }
                description
                  "TCP MSS value to set range <1280-9136>";
              }
            }
          }
        }
        container all {
          description
            "All Locations";
          container nps {
            description
              "NP Unit to adjust TCP MSS value";
            list np {
              key "np-id";
              description
                "NP Unit to adjust TCP MSS value";
              leaf np-id {
                type uint32 {
                  range "0..7" {
                    description
                      "Number between 0-7";
                  }
                }
                description
                  "NP to configure";
              }
              leaf value {
                type uint32 {
                  range "1280..9136" {
                    description
                      "TCP MSS value in decimal";
                  }
                }
                mandatory true;
                description
                  "TCP MSS value to set range <1280-9136>";
              }
            }
            container all {
              description
                "Adjust TCP MSS value on all NP units";
              leaf value {
                type uint32 {
                  range "1280..9136" {
                    description
                      "TCP MSS value in decimal";
                  }
                }
                description
                  "TCP MSS value to set range <1280-9136>";
              }
            }
          }
        }
      }
    }
  }
}
