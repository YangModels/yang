module Cisco-IOS-XR-8000-platforms-npu-pfc-pause-duration-act {
  namespace "http://cisco.com/ns/yang/Cisco-IOS-XR-8000-platforms-npu-pfc-pause-duration-act";
  prefix platforms-npu-pfc-pause-duration-act;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-platforms-npu-pfc-pause-duration package actions.
     
     This module contains definitions
     for the following management objects:
       8000-platforms-npu-pfc-pause-duration : NPU PFC PAUSE Duration data
     
     Copyright (c) 2024 by Cisco Systems, Inc.
     All rights reserved.";

  revision 2024-06-24 {
    description
      "Initial tx/rx pfc pause duration action yang model with the
       npu-pfc-clear-pause-duration action";
    semver:module-version "1.0.0";
  }

  rpc clear-npu-pfc-pause-duration {
    description
      "Clear QoS traffic class for tx/rx pause duration in time";
    input {
      leaf type {
        type enumeration {
          enum "tx-pause-duration" {
            description
              "Clear the Tx pause duration";
          }
          enum "rx-pause-duration" {
            description
              "Clear the Rx pause duration";
          }
        }
        mandatory true;
        description
          "Type of pfc tx/rx pause duration to clear";
      }
      leaf interface-name {
        type xr:Interface-name;
        description
          "Name of interface to be cleared, default is all interfaces";
      }
      leaf traffic-class {
        type uint8 {
          range "0..7";
        }
        description
          "Traffic class to be cleared, default is all traffic classes";
      }
      leaf node-name {
        type xr:Node-id;
        mandatory true;
        description
          "Location of interfaces to be cleared";
      }
    }
  }
}
