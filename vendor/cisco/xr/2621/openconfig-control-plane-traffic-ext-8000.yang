module openconfig-control-plane-traffic-ext-8000 {
  yang-version "1";
  namespace "http://cisco.com/ns/yang/openconfig-control-plane-traffic-ext-8000";
  prefix "oc-cp-8000";
  
  import openconfig-platform { prefix oc-platform; }
  import openconfig-extensions { prefix oc-ext; }
  import openconfig-platform-pipeline-counters { prefix oc-ppc; }

  organization
    "Cisco Systems, Inc";

  contact
    "Cisco Systems
     Customer Service
     Postal: 170 West Tasman Drive
     San Jose, CA 95134

     Tel: +1 800 553-NETS

     E-mail: cs-yang@cisco.com";

  description
    "Adding augments to oc-ppc yang for providing LPTS and TRAP counters.";

  oc-ext:openconfig-version "1.0.0";
  oc-ext:catalog-organization "openconfig";
  oc-ext:origin "openconfig";

  revision 2026-01-22 {
    description
     "Added 3 new LPTS flows for MSDP: msdp-known, msdp-cfg-peer, msdp-default";
    reference "0.1.3";
  }

  revision 2025-11-12 {
    description
     "Added 5 new LPTS flows: ipsec-known, tcp-listen, pcep, radius, ntp-default";
    reference "0.1.2";
  }

  revision 2025-09-05 {
    description
     "sdacp";
    reference "0.1.1";
  }

  revision 2024-05-10 {
    description
     "Initial version";
    reference "0.1.0";
  }

  grouping cisco-8000-control-plane-traffic-counters {
    description
      "Cisco8000 asic-specific control-plane traffic counters grouping";

      container fragment {
        description "IPv4/V6 Fragments";
        uses oc-ppc:control-plane-traffic-vendor-counters;
      }
      container ospf-mc-known {
        description "OSPF multicast packets on configured interfaces";
        uses oc-ppc:control-plane-traffic-vendor-counters;
      }
      container ospf-mc-default {
        description "OSPF multicast packets on unconfigured (or newly-configured) interfaces";
        uses oc-ppc:control-plane-traffic-vendor-counters;
      }
      container ospf-uc-known {
        description "OSPF unicast packets on configured interfaces";
        uses oc-ppc:control-plane-traffic-vendor-counters;
      }
      container ospf-uc-default {
        description "OSPF unicast packets on unconfigured (or newly-configured) interfaces";
        uses oc-ppc:control-plane-traffic-vendor-counters;
      }
      container bfd-default {
        description "BFD packets on unconfigured (or newly-configured) interfaces";
        uses oc-ppc:control-plane-traffic-vendor-counters;
      }
      container bfd-mp-known {
        description "BFD packets on configured interfaces";
        uses oc-ppc:control-plane-traffic-vendor-counters;
      }
      container bgp-known {
        description "Packets from established BGP peering sessions";
        uses oc-ppc:control-plane-traffic-vendor-counters;
      }
      container bgp-cfg-peer {
        description "Packets from a configured BGP peer (SYNs or newly-established flows)";
        uses oc-ppc:control-plane-traffic-vendor-counters;
      }
      container bgp-default {
        description "Packets from unconfigured, newly-configured, or wild-card BGP peers";
        uses oc-ppc:control-plane-traffic-vendor-counters;
      }
      container pim-mcast-default {
        description "PIM multicast packets";
        uses oc-ppc:control-plane-traffic-vendor-counters;
      }
      container pim-mcast-known {
        description "PIM multicast known packets";
        uses oc-ppc:control-plane-traffic-vendor-counters;
      }
      container pim-ucast {
        description "PIM unicast packets";
        uses oc-ppc:control-plane-traffic-vendor-counters;
      }
      container igmp {
        description "IGMP packets";
        uses oc-ppc:control-plane-traffic-vendor-counters;
      }
      container icmp-local {
        description "ICMP or ICMPv6 packets with local interest";
        uses oc-ppc:control-plane-traffic-vendor-counters;
      }  
      container icmp-control {
        description "ICMP control packets";
        uses oc-ppc:control-plane-traffic-vendor-counters;
      }  
      container icmp-default {
        description "All ICMP Types";
        uses oc-ppc:control-plane-traffic-vendor-counters;
      }  
      container ldp-tcp-known {
        description "Packets from an established LDP & LMP peering session";
        uses oc-ppc:control-plane-traffic-vendor-counters;
      }  
      container ldp-tcp-cfg-peer {
        description "Packets from a configured LDP & LMP peer";
        uses oc-ppc:control-plane-traffic-vendor-counters;
      }  
      container ldp-tcp-default {
        description "Packets from an unconfigured, newly-configured or wild-card LDP & LMP peer";
        uses oc-ppc:control-plane-traffic-vendor-counters;
      }  
      container ldp-udp {
        description "Unicast LDP & LMPUDP packets";
        uses oc-ppc:control-plane-traffic-vendor-counters;
      }  
      container all-routers {
        description "All-routers multicast packets";
        uses oc-ppc:control-plane-traffic-vendor-counters;
      }  
      container rsvp-default {
        description "All RSVP Protocol packets";
        uses oc-ppc:control-plane-traffic-vendor-counters;
      }  
      container rsvp-known {
        description "RSVP packets";
        uses oc-ppc:control-plane-traffic-vendor-counters;
      }  
      container ipsec-known {
        description "IPsec packets on configured interfaces";
        uses oc-ppc:control-plane-traffic-vendor-counters;
      }  
      container msdp-known {
        description "Packets from established MSDP peering sessions";
        uses oc-ppc:control-plane-traffic-vendor-counters;
      }  
      container msdp-cfg-peer {
        description "Packets from a configured MSDP peer";
        uses oc-ppc:control-plane-traffic-vendor-counters;
      }  
      container msdp-default {
        description "Packets from unconfigured, newly-configured, or wild-card MSDP peers";
        uses oc-ppc:control-plane-traffic-vendor-counters;
      }  
      container snmp {
        description "SNMP packets";
        uses oc-ppc:control-plane-traffic-vendor-counters;
      }  
      container ssh-known {
        description "SSH packets";
        uses oc-ppc:control-plane-traffic-vendor-counters;
      }  
      container ssh-default {
        description "all SSH protocol packets";
        uses oc-ppc:control-plane-traffic-vendor-counters;
      }    
      container http-known {
        description "HTTP packets";
        uses oc-ppc:control-plane-traffic-vendor-counters;
      }  
      container shttp-known {
        description "SHTTP packets";
        uses oc-ppc:control-plane-traffic-vendor-counters;
      }  
      container telnet-known {
        description "TELNET packets";
        uses oc-ppc:control-plane-traffic-vendor-counters;
      }  
      container telnet-default {
        description "all TELNET protocol packets";
        uses oc-ppc:control-plane-traffic-vendor-counters;
      }  
      container udp-known {
        description "Packets for other established UDP services";
        uses oc-ppc:control-plane-traffic-vendor-counters;
      }  
      container udp-listen {
        description "Packets for other configured UDP services";
        uses oc-ppc:control-plane-traffic-vendor-counters;
      }  
      container udp-default {
        description "Packets for other unconfigured or newly-configured UDP services";
        uses oc-ppc:control-plane-traffic-vendor-counters;
      }  
      container tcp-known {
        description "Packets for other established TCP sessions";
        uses oc-ppc:control-plane-traffic-vendor-counters;
      }  
      container tcp-listen {
        description "TCP packets on listening ports";
        uses oc-ppc:control-plane-traffic-vendor-counters;
      }  
      container tcp-default {
        description "Packets for other unconfigured or newly-configured TCP services";
        uses oc-ppc:control-plane-traffic-vendor-counters;
      }  
      container raw-default {
        description "Packets for other unconfigured or newly-configured IPv4 or IPv6 protocols";
        uses oc-ppc:control-plane-traffic-vendor-counters;
      }  
      container ip-sla {
        description "Packets for ip-sla";
        uses oc-ppc:control-plane-traffic-vendor-counters;
      }  
      container pcep {
        description "PCEP (Path Computation Element Protocol) packets";
        uses oc-ppc:control-plane-traffic-vendor-counters;
      }  
      container gre {
        description "GRE packets";
        uses oc-ppc:control-plane-traffic-vendor-counters;
      } 
      container vrrp {
        description "VRRP packets";
        uses oc-ppc:control-plane-traffic-vendor-counters;
      } 
      container hsrp {
        description "HSRP packets";
        uses oc-ppc:control-plane-traffic-vendor-counters;
      } 
      container mpls-oam {
        description "MPLS Oam packets";
        uses oc-ppc:control-plane-traffic-vendor-counters;
      } 
      container dns {
        description "DNS packets";
        uses oc-ppc:control-plane-traffic-vendor-counters;
      } 
      container radius {
        description "RADIUS packets";
        uses oc-ppc:control-plane-traffic-vendor-counters;
      } 
      container ntp-known {
        description "NTP-known packets";
        uses oc-ppc:control-plane-traffic-vendor-counters;
      } 
      container ntp-default {
        description "NTP packets on unconfigured or newly-configured interfaces";
        uses oc-ppc:control-plane-traffic-vendor-counters;
      } 
      container dhcpv4 {
        description "DHCPv4 packets";
        uses oc-ppc:control-plane-traffic-vendor-counters;
      } 
      container dhcpv6 {
        description "DHCPv6 packets";
        uses oc-ppc:control-plane-traffic-vendor-counters;
      } 
      container tpa {
        description "TPA packets";
        uses oc-ppc:control-plane-traffic-vendor-counters;
      } 
      container pm-twamp {
        description "PM TWAMP packets";
        uses oc-ppc:control-plane-traffic-vendor-counters;
      }  
      container tpa-appmgr-high {
        description "TPA-APPMGR-HIGH packets";
        uses oc-ppc:control-plane-traffic-vendor-counters;
      } 
      container tpa-appmgr-med {
        description "TPA-APPMGR-MED packets";
        uses oc-ppc:control-plane-traffic-vendor-counters;
      } 
      container tpa-appmgr-low {
        description "TPA-APPMGR-LOW packets";
        uses oc-ppc:control-plane-traffic-vendor-counters;
      }
      
      container arp {
        description "Incoming packet identified as an ARP (Address Resolution Protocol) packet";
        uses oc-ppc:control-plane-traffic-vendor-counters;
      } 
      container arp-bcast-bvi {
        description "Incoming packet identified as BCAST ARP (Address Resolution Protocol) packet on BVI interface";
        uses oc-ppc:control-plane-traffic-vendor-counters;
      } 
      container slow-proto-lacp-synce-eoam {
        description "Incoming Link Aggregation Control Protocol (LACP) packet";
        uses oc-ppc:control-plane-traffic-vendor-counters;
      } 
      container cisco-protocols-cdp-vtp-dtp-pagp-udld {
        description "Cisco protocols (CDP, VTP, DTP, PAGP, UDLD) control traffic counters";
        uses oc-ppc:control-plane-traffic-vendor-counters;
      } 
      container l3-isis-drain {
        description "ISIS packet drop on L2 domain(switch)";
        uses oc-ppc:control-plane-traffic-vendor-counters; 
      } 
      container isis-l3 {
        description "ISIS over L3 control traffic counters";
        uses oc-ppc:control-plane-traffic-vendor-counters;
      } 
      container ptp-over-ethernet {
        description "PTP over ethernet control traffic counters";
        uses oc-ppc:control-plane-traffic-vendor-counters;
      } 
      container l2-dhcp-server-snoop {
        description "L2 DHCP server control traffic counters";
        uses oc-ppc:control-plane-traffic-vendor-counters;
      } 
      container l2-dhcp-client-snoop {
        description "L2 DHCP client control traffic counters";
        uses oc-ppc:control-plane-traffic-vendor-counters;
      } 
      container dhcpv4-server {
        description "DHCP IPV4 control traffic counters";
        uses oc-ppc:control-plane-traffic-vendor-counters;
      } 
      container dhcpv4-client {
        description "DHCP IPV4 control traffic counters";
        uses oc-ppc:control-plane-traffic-vendor-counters;
      } 
      container l3-ip-multicast-rpf {
        description "Filter routed IP multicast packet if RPF check in ingress failed";
        uses oc-ppc:control-plane-traffic-vendor-counters;
      } 
      container l3-ip-mc-egress-punt {
        description "IP multicast packet is egress punt member";
        uses oc-ppc:control-plane-traffic-vendor-counters;
      } 
      container l3-ip-mc-punt-rpf-fail {
        description "IP multicast simple multicast RPF check failed, punt packet to host";
        uses oc-ppc:control-plane-traffic-vendor-counters;
      } 
      container l3-ip-mc-s-g-punt-member {
        description "IP multicast packet forwarding lookup action on (Unicast Source (S), Multicast Group (G)) indicates punt and forward";
        uses oc-ppc:control-plane-traffic-vendor-counters;
      } 
      container l3-ip-mc-g-punt-member {
        description "IP multicast packet forwarding lookup action on on (All Sources, Multicast Group (G)) indicates punt and forward";
        uses oc-ppc:control-plane-traffic-vendor-counters;
      } 
      container macsec {
        description "MACSEC protocol control traffic counters";
        uses oc-ppc:control-plane-traffic-vendor-counters;
      } 
      container cfm-l2-ac {
        description "CFM L2/L3 traffic(CCM/SLA/LBM/LTM) counters, level 1-7";
        uses oc-ppc:control-plane-traffic-vendor-counters;
      } 
      container cfm-down-mep {
        description "CFM CCM Down MEP packets";
        uses oc-ppc:control-plane-traffic-vendor-counters;
      } 
      container cfm-up-mep {
        description "CFM CCM Up MEP packets";
        uses oc-ppc:control-plane-traffic-vendor-counters;
      }
      container cfm-meg-id-no-match {
        description "CFM HW offload packets with unknown MEG ID";
        uses oc-ppc:control-plane-traffic-vendor-counters;
      } 
      container l2mc-igmp-punt {
        description "IGMP control traffic counters";
        uses oc-ppc:control-plane-traffic-vendor-counters;
      } 
      container l2mc-mld-punt {
        description "MLD control traffic counters";
        uses oc-ppc:control-plane-traffic-vendor-counters;
      } 
      container l2mc-mirror-trap {
        description "Local Packet Transport Service (LPTS) mirror packets";
        uses oc-ppc:control-plane-traffic-vendor-counters;
      }
      container mcast-control-packet-l2-evi-drop {
        description "EVPN L2 multicast IGMP PIM MLD control packet counters";
        uses oc-ppc:control-plane-traffic-vendor-counters;
      } 
      container lldp {
        description "LLDP control traffic counters";
        uses oc-ppc:control-plane-traffic-vendor-counters;
      } 
      container lldp-snoop {
        description "LLDP snoop control traffic counters";
        uses oc-ppc:control-plane-traffic-vendor-counters;
      } 
      container pfc {
        description "PFC control traffic counters";
        uses oc-ppc:control-plane-traffic-vendor-counters;
      } 
      container mstp {
        description "MSTP control traffic counters";
        uses oc-ppc:control-plane-traffic-vendor-counters;
      } 
      container macsec-fips-post {
        description "Post bring up interface MACSEC test";
        uses oc-ppc:control-plane-traffic-vendor-counters;
      } 
      container gdp {
        description "GDP control traffic counters";
        uses oc-ppc:control-plane-traffic-vendor-counters;
      } 
      container online-diag {
        description "Loopback/Slice/Fabric health monitoring packets";
        uses oc-ppc:control-plane-traffic-vendor-counters;
      } 
      container mldp-ingress-punt {
        description "Incoming packet identified as Multicast Label Distribution Protocol (MLDP) headend peek mode, punt copy of packet to host";
        uses oc-ppc:control-plane-traffic-vendor-counters;
      }
      container icmp-redirect {
        description "L3 destination interface matched the source interface, indicates the control plane to send ICMP redirect (usually snoop action)";
        uses oc-ppc:control-plane-traffic-vendor-counters;
      }
      container l2-sdacp-discovery {
        description "SDACP Discovery Protocol";
        uses oc-ppc:control-plane-traffic-vendor-counters;
      }
  }
  

  augment "/oc-platform:components/oc-platform:component/oc-platform:integrated-circuit/oc-ppc:pipeline-counters/oc-ppc:control-plane-traffic/oc-ppc:vendor" {
    description
      "Cisco augmentation of the vendor container";
    container cisco {
      description
      "Cisco specific vendor container";
      container c8000 { 
        description
          "Cisco 8000 one asic container";
        container state {
          description
            "control-plane traffic vendor specific counter";
          uses cisco-8000-control-plane-traffic-counters; 
        }
      }
    }
  }
}
