submodule Cisco-IOS-XR-bte-test-oper-sub1 {
  belongs-to Cisco-IOS-XR-bte-test-oper {
    prefix Cisco-IOS-XR-bte-test-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR bte-test package operational data.
     
     Copyright (c) 2013-2025 by Cisco Systems, Inc.
     All rights reserved.";

  revision 2025-12-04 {
    description
      "Initial commit";
    semver:module-version "1.0.0";
  }
  revision 2019-04-05 {
    description
      "Establish semantic version baseline.";
  }
  revision 2015-11-09 {
    description
      "IOS XR 6.0 revision.";
  }

  typedef Test-enum {
    type enumeration {
      enum "one" {
        value 1;
        description
          "one";
      }
      enum "two" {
        value 2;
        description
          "two";
      }
      enum "three" {
        value 3;
        description
          "three";
      }
    }
    description
      "Enum for testing";
  }

  grouping DOUBLE-ARRAY-TYPE {
    description
      "Double Array";
    list double-array-type {
      description
        "double array type";
      uses INTEGER-ARRAY-TYPE;
    }
  }

  grouping INTEGER-ARRAY-TYPE {
    description
      "Integer Array";
    leaf-list int-array-type {
      type uint32;
      description
        "int array type";
    }
  }

  grouping BTE-TEST-UNION-ENUM {
    description
      "Union with enum discriminator";
    leaf enum-discriminator {
      type Test-enum;
      description
        "EnumDiscriminator";
    }
    leaf one-case {
      when "../enum-discriminator = 'one'" {
        description
          "../EnumDiscriminator = 'One'";
      }
      type int32;
      description
        "One case";
    }
    leaf two-case {
      when "../enum-discriminator = 'two'" {
        description
          "../EnumDiscriminator = 'Two'";
      }
      type string;
      description
        "Two case";
    }
  }

  grouping BTE-TEST-DATATYPES {
    description
      "Bag with a variety of datatypes";
    container enum-union {
      description
        "Enum Union";
      uses BTE-TEST-UNION-ENUM;
    }
    leaf int8 {
      type int8;
      description
        "8-bit signed integer";
    }
    leaf uint8 {
      type uint8;
      description
        "8-bit unsigned integer";
    }
    leaf int16 {
      type int16;
      description
        "16-bit signed integer";
    }
    leaf uint16 {
      type uint16;
      description
        "16-bit unsigned integer";
    }
    leaf int32 {
      type int32;
      description
        "32-bit signed integer";
    }
    leaf uint32 {
      type uint32;
      description
        "32-bit unsigned integer";
    }
    leaf int64 {
      type int64;
      description
        "64-bit signed integer";
    }
    leaf uint64 {
      type uint64;
      description
        "64-bit unsigned integer";
    }
    leaf boolean {
      type boolean;
      description
        "Boolean element";
    }
    leaf string {
      type string;
      description
        "String element";
    }
    leaf opaque {
      type yang:hex-string;
      description
        "Opaque element";
    }
    leaf ipv4-address {
      type inet:ipv4-address;
      description
        "IPv4 Address";
    }
    leaf ipv6-address {
      type inet:ipv6-address;
      description
        "IPv6 Address";
    }
    leaf mac-address {
      type yang:mac-address;
      description
        "MAC Address";
    }
    leaf hex-integer {
      type xr:Hex-integer;
      description
        "Hex Integer";
    }
    leaf node-id {
      type xr:Node-id;
      description
        "Node ID";
    }
    leaf interface-handle {
      type xr:Interface-name;
      description
        "Interface Handle";
    }
    leaf hex-binary {
      type yang:hex-string;
      description
        "Hex Binary";
    }
    leaf capsulation {
      type string;
      description
        "Capsulation Type";
    }
    leaf protocol {
      type string;
      description
        "Protocol Type";
    }
    leaf interface-type {
      type string;
      description
        "Interface Type";
    }
    leaf route-distinguisher {
      type xr:Route-dist;
      description
        "Route Distinguisher";
    }
    leaf vrfid {
      type string;
      description
        "VRF ID";
    }
    leaf enumeration {
      type Test-enum;
      description
        "Enumeration element";
    }
    leaf-list simple-array {
      type uint32;
      description
        "Simple Array";
    }
    list double-array {
      description
        "Double Array";
      uses INTEGER-ARRAY-TYPE;
    }
    list triple-array {
      description
        "Triple Array";
      uses DOUBLE-ARRAY-TYPE;
    }
  }

  grouping BTE-TEST-LINKED-LIST-STRUCT {
    description
      "BTE TEST LINKED LIST STRUCT";
    list bte-test-linked-list-struct {
      description
        "bte test linked list struct";
      leaf integer-element {
        type int32;
        description
          "IntegerElement";
      }
    }
  }

  grouping BTE-TEST-BAG-WITH-LINKED-LIST-STRUCT {
    description
      "BTE TEST BAG WITH LINKED LIST STRUCT";
    container list-head {
      description
        "list head";
      uses BTE-TEST-LINKED-LIST-STRUCT;
    }
    leaf outer-item {
      type int32;
      description
        "OuterItem";
    }
  }

  grouping BTE-TEST-BAG-WITH-LINKED-LIST-BAG {
    description
      "BTE TEST BAG WITH LINKED LIST BAG";
    container list-head {
      description
        "list head";
      uses BTE-TEST-LINKED-LIST-BAG;
    }
    leaf outer-item {
      type int32;
      description
        "OuterItem";
    }
  }

  grouping BTE-TEST-LINKED-LIST-BAG {
    description
      "BTE TEST LINKED LIST BAG";
    list bte-test-linked-list-bag {
      description
        "bte test linked list bag";
      leaf integer-element {
        type int32;
        description
          "IntegerElement";
      }
    }
  }

  grouping BTE-TEST-SIMPLE {
    description
      "Simple bag containing a single string";
    leaf name {
      type string;
      description
        "Name element";
    }
  }
}
