module Cisco-IOS-XR-openconfig-wavelength-router-ext {
  namespace "http://cisco.com/ns/yang/Cisco-IOS-XR-openconfig-wavelength-router-ext";
  prefix oc-wave-ext;

  import openconfig-wavelength-router {
    prefix oc-wave-router;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of optical wavelength router model
     and contains the definition of extended parameters for media
     channels in order to optimize the AC1200 settings to get the highest
     performance and spectral efficiency.
     
     This module contains definitions for the following management objects:
     General Parameters
     Submarine Parameters
     
     Copyright (c) 2024 by Cisco Systems, Inc.
     All rights reserved.";

  revision 2026-01-08 {
    description
      "Added support for regulation config and oper parameters";
    reference "26.2.1";
  }
  revision 2024-11-30 {
    description
      "IOS XR 6.0 revision";
    reference "7.3.1";
  }

  grouping regulation-info-config {
    description
      "Configuration data for a regulation-info";
    leaf target-psd {
      type decimal64 {
        fraction-digits 2;
      }
      units "dBm";
      description
        "Target-psd value";
    }
  }

  grouping regulation-info-state {
    description
      "State data for a regulation-info";
    leaf internal-status {
      type string;
      description
        "Internal status";
    }
    leaf block-reasons {
      type string;
      description
        "Block reasons";
    }
    leaf input-gain {
      type decimal64 {
        fraction-digits 2;
      }
      units "dB";
      description
        "Input gain value";
    }
    leaf input-gain-range {
      type string;
      description
        "Input gain range status";
    }
    leaf input-gain-range-min-max {
      type string;
      units "dB";
      description
        "Input gain range minimum and maximum value";
    }
    leaf last-correction-timestamp {
      type string;
      description
        "Last correction timestamp";
    }
    leaf psd-correction-tolerance {
      type decimal64 {
        fraction-digits 2;
      }
      units "dB";
      description
        "PSD Correction tolerance value";
    }
    leaf is-expected-total-input-power {
      type boolean;
      description
        "Is Expected total input power enabled";
    }
    leaf is-channel-min-input-psd {
      type boolean;
      description
        "Is Channel minimum input PSD enabled";
    }
  }

  grouping regulation-config {
    description
      "Config data for regulation";
    leaf regulation-enable {
      type boolean;
      description
        "Regulation config value";
    }
    leaf regulation-pause {
      type boolean;
      description
        "Pause Regulation config";
    }
  }

  grouping regulation-state {
    description
      "State data for regulation";
  }

  grouping oc-wave-extended-regulation {
    description
      "Extended wavelength router parameters";
    container cisco {
      description
        "Extended wavelength router parameters";
      container config {
        description
          "Extended wavelength router config parameters";
        uses regulation-config;
      }
      container state {
        config false;
        description
          "Regulation state container";
        uses regulation-config;
        uses regulation-state;
      }
      container regulation-info {
        description
          "Enclosing container for regulation-info.";
        container config {
          description
            "Extended regulation-info Configuration parameters";
          uses regulation-info-config;
        }
        container state {
          config false;
          description
            "Extended regulation-info Operational parameters";
          uses regulation-info-config;
          uses regulation-info-state;
        }
      }
    }
  }

  grouping media-channel-regulation-info-config {
    description
      "Configuration data for a regulation-info";
  }

  grouping media-channel-regulation-info-state {
    description
      "State data for a regulation-info";
    leaf status {
      type string;
      description
        "Status";
    }
    leaf spectrum-slices-range {
      type string;
      description
        "Spectrum slices start and end range";
    }
    leaf input-psd {
      type decimal64 {
        fraction-digits 2;
      }
      units "dBm";
      description
        "Input psd value in units of dBm";
    }
    leaf output-psd {
      type decimal64 {
        fraction-digits 2;
      }
      units "dBm";
      description
        "Output psd value in units of dBm";
    }
    leaf input-power {
      type decimal64 {
        fraction-digits 2;
      }
      units "dBm";
      description
        "Input power value in units of dBm";
    }
    leaf output-power {
      type decimal64 {
        fraction-digits 2;
      }
      units "dBm";
      description
        "Output power value in units of dBm";
    }
    leaf exp-channel-input-power {
      type decimal64 {
        fraction-digits 2;
      }
      units "dBm";
      description
        "Expected Channel input power value in units of dBm";
    }
    leaf min-channel-input-power {
      type decimal64 {
        fraction-digits 2;
      }
      units "dB";
      description
        "Minimum channel input power value in units of dB";
    }
    leaf psd-discrepancy {
      type decimal64 {
        fraction-digits 2;
      }
      units "dB";
      description
        "PSD discrepancy value in units of dB";
    }
    leaf attenuation {
      type decimal64 {
        fraction-digits 2;
      }
      units "dBm";
      description
        "Attenuation value in unit of dBm";
    }
  }

  grouping oc-wave-extended-media-channel-regulation {
    description
      "Extended wavelength router parameters";
    container cisco {
      description
        "Extended wavelength router parameters";
      container regulation-info {
        description
          "Enclosing container for regulation-info.";
        container config {
          description
            "Extended regulation-info Configuration parameters";
          uses media-channel-regulation-info-config;
        }
        container state {
          config false;
          description
            "Extended regulation-info Operational parameters";
          uses media-channel-regulation-info-config;
          uses media-channel-regulation-info-state;
        }
      }
    }
  }

  augment "/oc-wave-router:wavelength-router/oc-wave-router:port-spectrum-power-profiles/oc-wave-router:port" {
    description
      "This augment extends the configuration data of
       'oc-wave-router'";
    uses oc-wave-extended-regulation;
  }
  augment "/oc-wave-router:wavelength-router/oc-wave-router:media-channels/oc-wave-router:channel" {
    description
      "This augment extends the configuration data of
       'oc-wave-router'";
    uses oc-wave-extended-media-channel-regulation;
  }
}
