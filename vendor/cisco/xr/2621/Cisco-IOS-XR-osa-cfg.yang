module Cisco-IOS-XR-osa-cfg {
  namespace "http://cisco.com/ns/yang/Cisco-IOS-XR-osa-cfg";
  prefix osa-cfg;

  import Cisco-IOS-XR-config-mda-cfg {
    prefix node;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa package configuration.
     
     This YANG module augments the
       Cisco-IOS-XR-config-mda-cfg
     module with configuration data.
     
     Copyright (c) 2013-2025 by Cisco Systems, Inc.
     All rights reserved.";

  revision 2025-11-16 {
    description
      "Added new client rate CLI for SKBO under regen-slice
       2025-10-24
         Increased Slice limit to 16 and lane limit to 8
       2025-04-16
         Added new client rate 800GE for Pulsar, Dione LC in NCS1014
       2025-01-22
         Added new CLI-ols-port for Siachen in Skinny BO
       2023-10-27
         Increased the client port range from 12 to 15
       2022-11-20
         Added new CLI-trunk-rates till 1200g
       2022-10-10
         Added new CLI-trunk-mode for Openroadm in Skinny BO
       2022-09-08
         Fixing the Attention LED in Netconf
       2022-06-01
         Updated Attention LED CLI Port Range for supporting Skinny BO Ports
       2022-05-11
         Updated set of client rates supported in breakout configurations
       2022-03-16
         Enhancement to support hw-module operation for selecting the protection graph with available trunk-rate.
       2021-10-17
         Add New faceplate mapping support.
       2021-10-04
         Incremented MxponderSlice count from 2 to 8
       2021-02-21
         Add Attention LED Support for NCS1004 Linecards.";
    semver:module-version "3.0.0";
  }
  revision 2020-10-09 {
    description
      "Initial Revision.";
    semver:module-version "2.1.0";
  }
  revision 2019-10-11 {
    description
      "Enhancement in CLI for 50G trunk-rate";
    semver:module-version "1.2.0";
  }
  revision 2019-08-13 {
    description
      "Aligning modifications to 7.1.1.";
    semver:module-version "1.1.0";
  }
  revision 2019-04-05 {
    description
      "Establish semantic version baseline.";
    semver:module-version "1.0.0";
  }
  revision 2018-09-26 {
    description
      "Ains DTHO caveats fix.";
  }
  revision 2018-08-30 {
    description
      "Add Ains support.";
  }
  revision 2018-05-23 {
    description
      "Initial Revision.";
  }
  revision 2015-11-09 {
    description
      "IOS XR 6.0 revision.";
  }

  typedef Trunk-data-rate {
    type enumeration {
      enum "fifty-gig" {
        value 1;
        description
          "FiftyGig";
      }
      enum "hundred-gig" {
        value 2;
        description
          "HundredGig";
      }
      enum "one-hundred-fifty-gig" {
        value 3;
        description
          "OneHundredFiftyGig";
      }
      enum "two-hundred-gig" {
        value 4;
        description
          "TwoHundredGig";
      }
      enum "two-hundred-fifty-gig" {
        value 5;
        description
          "TwoHundredFifty";
      }
      enum "three-hundred-gig" {
        value 6;
        description
          "ThreeHundredGig";
      }
      enum "three-hundred-fifty-gig" {
        value 7;
        description
          "ThreeHundredFiftyGig";
      }
      enum "four-hundred-gig" {
        value 8;
        description
          "FourHundredGig";
      }
      enum "four-hundred-fifty-gig" {
        value 9;
        description
          "FourHundredFiftyGig";
      }
      enum "five-hundred-gig" {
        value 10;
        description
          "FiveHundredGig";
      }
      enum "five-hundred-fifty-gig" {
        value 11;
        description
          "FiveHundredFiftyGig";
      }
      enum "six-hundred-gig" {
        value 12;
        description
          "SixHundredGig";
      }
      enum "seven-hundred-gig" {
        value 13;
        description
          "SevenHundredGig";
      }
      enum "eight-hundred-gig" {
        value 14;
        description
          "EightHundredGig";
      }
      enum "nine-hundred-gig" {
        value 15;
        description
          "NineHundredGig";
      }
      enum "ten-hundred-gig" {
        value 16;
        description
          "TenHundredGig";
      }
      enum "eleven-hundred-gig" {
        value 17;
        description
          "ElevenHundredGig";
      }
      enum "twelve-hundred-gig" {
        value 18;
        description
          "TwelveHundredGig";
      }
    }
    description
      "Trunk data rate";
  }

  typedef Trunk-mode {
    type enumeration {
      enum "open-roadm" {
        value 1;
        description
          "OpenRoadm";
      }
      enum "zr" {
        value 2;
        description
          "ZR";
      }
    }
    description
      "Trunk mode";
  }

  typedef Lane-client-data-rate {
    type enumeration {
      enum "ten-gig-e" {
        value 1;
        description
          "TenGigE";
      }
      enum "hundred-gig-e" {
        value 2;
        description
          "HundredGigE";
      }
      enum "otu2" {
        value 4;
        description
          "OTU2";
      }
      enum "otu2e" {
        value 5;
        description
          "OTU2E";
      }
      enum "four-hundred-gig-e" {
        value 8;
        description
          "FourHundredGigE";
      }
      enum "fc16" {
        value 9;
        description
          "FC16";
      }
      enum "fc32" {
        value 10;
        description
          "FC32";
      }
      enum "oc192" {
        value 11;
        description
          "OC192";
      }
      enum "stm64" {
        value 12;
        description
          "STM64";
      }
    }
    description
      "Lane client data rate";
  }

  typedef Ains-soak-hours-range {
    type uint32 {
      range "0..48";
    }
    description
      "Ains soak hours range";
  }

  typedef Client-data-rate {
    type enumeration {
      enum "ten-gig-e" {
        value 1;
        description
          "TenGigE";
      }
      enum "hundred-gig-e" {
        value 2;
        description
          "HundredGigE";
      }
      enum "otu4" {
        value 3;
        description
          "OTU4";
      }
      enum "otu2" {
        value 4;
        description
          "OTU2";
      }
      enum "otu2e" {
        value 5;
        description
          "OTU2E";
      }
      enum "otu3" {
        value 6;
        description
          "OTU3";
      }
      enum "forty-gig-e" {
        value 7;
        description
          "FortyGigE";
      }
      enum "four-hundred-gig-e" {
        value 8;
        description
          "FourHundredGigE";
      }
      enum "fc16" {
        value 9;
        description
          "FC16";
      }
      enum "fc32" {
        value 10;
        description
          "FC32";
      }
      enum "oc192" {
        value 11;
        description
          "OC192";
      }
      enum "stm64" {
        value 12;
        description
          "STM64";
      }
      enum "eight-hundred-gig-e" {
        value 14;
        description
          "EightHundredGigE";
      }
    }
    description
      "Client data rate";
  }

  typedef Ains-soak-minutes-range {
    type uint32 {
      range "0..59";
    }
    description
      "Ains soak minutes range";
  }

  typedef Ols-mode {
    type enumeration {
      enum "edfa" {
        value 1;
        description
          "EDFA";
      }
    }
    description
      "Ols mode";
  }

  grouping NODE-CFG {
    description
      "active/preconfigured nodes configuration";
    container ols-ports {
      description
        "OLS Port configuration";
      list ols-port {
        key "port-id";
        description
          "Port configuration";
        leaf mode {
          type Ols-mode;
          description
            "mode for port";
        }
        leaf port-id {
          type uint32 {
            range "0..15";
          }
          description
            "Set Port";
        }
      }
    }
    container regen-slices {
      description
        "Regenerator Slice configuration";
      list regen-slice {
        key "slice-id";
        description
          "Slice configuration";
        leaf trunk-rates {
          type Trunk-data-rate;
          description
            "Trunk  data rates";
        }
        leaf client-rates {
          type Client-data-rate;
          description
            "Regen Client rate for graph";
        }
        leaf slice-id {
          type uint32 {
            range "0..15";
          }
          description
            "Set Slice";
        }
      }
    }
    container regen {
      description
        "Regenerator Module configuration";
      leaf trunk-rates {
        type Trunk-data-rate;
        description
          "Trunk  data rates";
      }
    }
    container attention-led {
      description
        "Attention LED configuration";
      container att-led-ports {
        description
          "Attention LED configuration";
        list att-led-port {
          key "port-num";
          description
            "Attention LED configuration on given Port
             Number";
          leaf port-list {
            type boolean;
            description
              "Enable Attention LED on given Port Number of
               Line Card";
          }
          leaf port-num {
            type uint32 {
              range "0..15";
            }
            description
              "Enable Attention LED on given Port Number of
               Line Card";
          }
        }
      }
      leaf all-port {
        type boolean;
        description
          "Enable Attention LED on all the Ports of Line
           Card";
      }
    }
    container mxponder-slices {
      description
        "Mxponder slice configuration";
      list mxponder-slice {
        key "slice-id";
        description
          "Slice configuration";
        container client-ains {
          description
            "AINS Soak Interval Value";
          leaf hours {
            type Ains-soak-hours-range;
            units "hour";
            description
              "Hours";
          }
          leaf minutes {
            type Ains-soak-minutes-range;
            units "minute";
            description
              "Minutes";
          }
        }
        container mxp-slice-client-ports {
          description
            "Client Mode";
          list mxp-slice-client-port {
            key "mxp-slice-port-id";
            description
              "client port number";
            container mxp-slice-client-port-mode {
              description
                "Client Port Mode";
              leaf client-type {
                type Client-data-rate;
                description
                  "client traffic type";
              }
            }
            container mxp-slice-client-optics-lanes {
              description
                "Client Port";
              list mxp-slice-client-optics-lane {
                key "optics-lane-id";
                description
                  "client lane number";
                leaf client-type {
                  type Lane-client-data-rate;
                  description
                    "client traffic type";
                }
                leaf optics-lane-id {
                  type uint32 {
                    range "1..8";
                  }
                  description
                    "Set client optics lane";
                }
              }
            }
            leaf mxp-slice-port-id {
              type uint32 {
                range "0..31";
              }
              description
                "Set client port number";
            }
          }
        }
        leaf trunk-rates {
          type Trunk-data-rate;
          description
            "Trunk  data rates";
        }
        leaf lldp {
          type boolean;
          description
            "Drop LLDP Packets";
        }
        leaf trunk-mode {
          type Trunk-mode;
          description
            "Trunk  mode for graph";
        }
        leaf arp-snoop {
          type boolean;
          description
            "Enable ARP Snooping";
        }
        leaf client-rates {
          type Client-data-rate;
          description
            "Client  data rates";
        }
        leaf slice-id {
          type uint32 {
            range "0..15";
          }
          description
            "Set Slice";
        }
      }
    }
    container mxponder {
      description
        "Mxponder module configuration";
      container client-ports {
        description
          "Client Mode";
        list client-port {
          key "port-id";
          description
            "client port number";
          container client-port-mode {
            description
              "Client Port Mode";
            leaf client-type {
              type Client-data-rate;
              description
                "client traffic type";
            }
          }
          container client-optics-lanes {
            description
              "Client Port";
            list client-optics-lane {
              key "lane-id";
              description
                "client lane number";
              leaf client-type {
                type Lane-client-data-rate;
                description
                  "client traffic type";
              }
              leaf lane-id {
                type uint32 {
                  range "1..8";
                }
                description
                  "Set client optics lane";
              }
            }
          }
          leaf port-id {
            type uint32 {
              range "0..15";
            }
            description
              "Set client port number";
          }
        }
      }
      container client-ains {
        description
          "AINS Soak Interval Value";
        leaf hours {
          type Ains-soak-hours-range;
          units "hour";
          description
            "Hours";
        }
        leaf minutes {
          type Ains-soak-minutes-range;
          units "minute";
          description
            "Minutes";
        }
      }
      leaf trunk-rates {
        type Trunk-data-rate;
        description
          "Trunk  data rates";
      }
      leaf lldp {
        type boolean;
        description
          "Drop LLDP Packets";
      }
      leaf arp-snoop {
        type boolean;
        description
          "Enable ARP Snoop";
      }
      leaf protected {
        type boolean;
        description
          "Enable Protected";
      }
      leaf split-client-port-map {
        type boolean;
        description
          "New split client port mapping config";
      }
      leaf client-rates {
        type Client-data-rate;
        description
          "Client  data rates";
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
