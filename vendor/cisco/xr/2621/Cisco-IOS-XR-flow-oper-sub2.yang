submodule Cisco-IOS-XR-flow-oper-sub2 {
  belongs-to Cisco-IOS-XR-flow-oper {
    prefix Cisco-IOS-XR-flow-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR flow package operational data.
     
     Copyright (c) 2013-2025 by Cisco Systems, Inc.
     All rights reserved.";

  revision 2025-12-24 {
    description
      "Added counters for software sampling multiplier
       2025-06-23
         Added gnpsi related operational nodes
       2022-11-25
         Added router-id related field in the exporter configuration information
       2022-09-25
         Added source-port related field in the exporter information
       2022-05-16
         Added more fields in the data template information
       2021-12-16
         Added new fields in collector node to indicate standby mode information.
       2021-08-16
         Added a new field for cache flow record size in cache information";
    semver:module-version "2.0.0";
  }
  revision 2021-06-16 {
    description
      "Added tunnel egress related options for sflow
       2021-04-23
          Added new node for data-template info";
    semver:module-version "1.1.0";
  }
  revision 2019-04-05 {
    description
      "Establish semantic version baseline.";
    semver:module-version "1.0.0";
  }
  revision 2015-11-09 {
    description
      "IOS XR 6.0 revision.";
  }

  typedef Nfsvr-fem-edm-export-method-enum {
    type enumeration {
      enum "normal" {
        description
          "Normal export directly from netflow process";
      }
      enum "gnpsi" {
        description
          "Telemetry based export using gNPSI";
      }
    }
    description
      "Netflow nfsvr export method enum";
  }

  typedef Flow-monitor-name {
    type string;
    description
      "Flow monitor name";
  }

  grouping NFSVR-EXPORTER-PRE-ROUTE-PATH-CONTEXT-INFO {
    description
      "Flow exporter pre-route single context
       information";
    leaf nexthop-interface-handle {
      type uint32;
      description
        "Next hop Interface Handle";
    }
    leaf nexthop-address {
      type string;
      description
        "Nexthop address";
    }
    leaf packets-sent-count {
      type uint32;
      description
        "Packets Sent count";
    }
    leaf last-sequence-number {
      type uint64;
      description
        "Sequence Number of the last packet";
    }
  }

  grouping NFSVR-EXPORTER-PRE-ROUTE-INFO {
    description
      "Pre-route information";
    leaf pre-route-enabled {
      type boolean;
      description
        "Flag indicating pre-routing is enabled";
    }
    leaf pre-route-enabled-default {
      type boolean;
      description
        "Flag indicating pre-routing is enabled as
         default";
    }
    leaf pre-route-enabled-config {
      type boolean;
      description
        "Flag indicating pre-routing is enabled through
         configuration";
    }
    leaf pre-route-platform-capability {
      type boolean;
      description
        "Flag indicating pre-routing has platform level
         capability";
    }
    leaf all-ecmp-paths {
      type boolean;
      description
        "Flag indicating that pre-route will use all ecmp
         paths";
    }
    leaf pre-route-info-reset-time {
      type string;
      description
        "Time at which pre-route info was reset last time";
    }
    leaf packets-handled {
      type uint32;
      description
        "Packets handled via pre-route while pre-route is
         enabled";
    }
    leaf packets-not-handled {
      type uint32;
      description
        "Packets not handled via pre-route while
         pre-route is enabled";
    }
    list context-data-array {
      description
        "Array of context data info ";
      uses NFSVR-EXPORTER-PRE-ROUTE-PATH-CONTEXT-INFO;
    }
  }

  grouping NFSVR-COLLECTOR-INFO {
    description
      "Per collector information";
    leaf exporter-state {
      type string;
      description
        "Exporter state";
    }
    leaf destination-address {
      type string;
      description
        "Destination IPv4 address in AAA.BBB.CCC.DDD
         format";
    }
    leaf source-address {
      type string;
      description
        "Source IPv4 address in AAA.BBB.CCC.DDD format";
    }
    leaf vrf-name {
      type string;
      description
        "VRF Name";
    }
    leaf destination-port {
      type uint16;
      description
        "Destination port number";
    }
    leaf souce-port {
      type uint16;
      description
        "Source port number";
    }
    leaf transport-protocol {
      type string;
      description
        "Transport protocol";
    }
    leaf packets-sent {
      type uint64;
      description
        "Packets sent";
    }
    leaf flows-sent {
      type uint64;
      description
        "Flows sent";
    }
    leaf templates-sent {
      type uint64;
      description
        "Templates sent";
    }
    leaf option-templates-sent {
      type uint64;
      description
        "Option templates sent";
    }
    leaf option-data-sent {
      type uint64;
      description
        "Option data sent";
    }
    leaf bytes-sent {
      type uint64;
      units "byte";
      description
        "Bytes sent";
    }
    leaf flow-bytes-sent {
      type uint64;
      units "byte";
      description
        "Flow bytes sent";
    }
    leaf template-bytes-sent {
      type uint64;
      units "byte";
      description
        "Template bytes sent";
    }
    leaf option-template-bytes-sent {
      type uint64;
      units "byte";
      description
        "Option template bytes sent";
    }
    leaf option-data-bytes-sent {
      type uint64;
      units "byte";
      description
        "Option data bytes sent";
    }
    leaf packets-dropped {
      type uint64;
      description
        "Packets dropped";
    }
    leaf flows-dropped {
      type uint64;
      description
        "Flows dropped";
    }
    leaf templates-dropped {
      type uint64;
      description
        "Templates dropped";
    }
    leaf option-templates-dropped {
      type uint64;
      description
        "Option templates dropped";
    }
    leaf option-data-dropped {
      type uint64;
      description
        "Option data dropped";
    }
    leaf bytes-dropped {
      type uint64;
      units "byte";
      description
        "Bytes dropped";
    }
    leaf flow-bytes-dropped {
      type uint64;
      units "byte";
      description
        "Flow bytes dropped";
    }
    leaf template-bytes-dropped {
      type uint64;
      units "byte";
      description
        "Template bytes dropped";
    }
    leaf option-template-bytes-dropped {
      type uint64;
      units "byte";
      description
        "Option template bytes dropped";
    }
    leaf option-data-bytes-dropped {
      type uint64;
      description
        "Option data dropped";
    }
    leaf last-hour-packest-sent {
      type uint64;
      description
        "Total packets exported over the last one hour";
    }
    leaf last-hour-bytes-sent {
      type uint64;
      units "byte";
      description
        "Total bytes exported over the last one hour";
    }
    leaf last-hour-flows-sent {
      type uint64;
      description
        "Total flows exported over the of last one hour";
    }
    leaf last-minute-packets {
      type uint64;
      description
        "Total packets exported over the last one minute";
    }
    leaf last-minute-bytes-sent {
      type uint64;
      units "byte";
      description
        "Total bytes exported over the last one minute";
    }
    leaf last-minute-flows-sent {
      type uint64;
      description
        "Total flows exported over the last one minute";
    }
    leaf last-second-packets-sent {
      type uint64;
      description
        "Total packets exported over the last one second";
    }
    leaf last-second-bytes-sent {
      type uint64;
      units "byte";
      description
        "Total bytes exported over the last one second";
    }
    leaf last-second-flows-sent {
      type uint64;
      description
        "Total flows exported over the last one second";
    }
    leaf is-standby {
      type boolean;
      description
        "Exporter is in standby mode";
    }
    leaf standby-packets-dropped {
      type uint64;
      description
        "Total export packets dropped while beingin
         standby mode";
    }
  }

  grouping NFSVR-SHOW-FLOW-EXPORTER-RESP-STATS {
    description
      "Flow exporter information";
    container pre-route-info {
      description
        "Pre-route related information";
      uses NFSVR-EXPORTER-PRE-ROUTE-INFO;
    }
    leaf name {
      type string;
      description
        "Exporter name";
    }
    leaf protocol {
      type string;
      description
        "Export Protocol Name";
    }
    leaf memory-usage {
      type uint32;
      description
        "Memory usage";
    }
    leaf export-method {
      type Nfsvr-fem-edm-export-method-enum;
      description
        "Export method enumeration";
    }
    leaf-list used-by-flow-monitor {
      type Flow-monitor-name;
      description
        "List of flow monitors that use the exporter";
    }
    list collector {
      description
        "Statistics of all collectors";
      uses NFSVR-COLLECTOR-INFO;
    }
  }

  grouping NFSVR-EXPORT-SERVER-OPER-CONFIG {
    description
      "Exporter operational config";
    leaf exporter-map-name {
      type string;
      description
        "Exporter-map Name";
    }
    leaf protocol {
      type string;
      description
        "Export Protocol Name";
    }
    leaf destination-address {
      type string;
      description
        "Destination IPv4 address in AAA.BBB.CCC.DDD
         format";
    }
    leaf source-address {
      type string;
      description
        "Source IPv4 address in AAA.BBB.CCC.DDD format";
    }
    leaf vrf-name {
      type string;
      description
        "VRF Name";
    }
    leaf destination-port {
      type uint16;
      description
        "Destination port number";
    }
    leaf source-port {
      type uint16;
      description
        "Source port number";
    }
    leaf transport-protocol {
      type string;
      description
        "Transport protocol";
    }
    leaf df-bit-set {
      type uint8;
      description
        "Do Not Fragment option is set";
    }
    leaf dscp-value {
      type uint8;
      description
        "IPv4 DSCP or IPv6 Traffic class value";
    }
    leaf packet-length {
      type uint32;
      description
        "Maximum length of export packet excluding L2
         header";
    }
    leaf common-template-export-timeout {
      type uint32;
      units "second";
      description
        "Common template export timeout in seconds";
    }
    leaf data-template-export-timeout {
      type uint32;
      units "second";
      description
        "Data template export timeout in seconds";
    }
    leaf options-template-export-timeout {
      type uint32;
      units "second";
      description
        "Options template export timeout in seconds";
    }
    leaf sampler-table-export-timeout {
      type uint32;
      units "second";
      description
        "Sampler table export timeout in seconds";
    }
    leaf interface-table-export-timeout {
      type uint32;
      units "second";
      description
        "Interface table export timeout in seconds";
    }
    leaf vrf-table-export-timeout {
      type uint32;
      units "second";
      description
        "VRF table export timeout in seconds";
    }
  }

  grouping NFSVR-GNPSI-STATISTICS-INFO {
    description
      "Netflow server gnpsi statistics information";
    leaf total-packets {
      type uint64;
      description
        "Total Packets arrived for GNPSI encapsulation";
    }
    leaf packets-sent {
      type uint64;
      description
        "Packets sent successfully for GNPSI
         encapsulation";
    }
    leaf packets-dropped {
      type uint64;
      description
        "Packets those could not be sent successfully for
         GNPSI encapsulation";
    }
    leaf packets-dropped-no-connection {
      type uint64;
      description
        "Packets those could not be sent successfully due
         to lack of connection to GRPC daemon";
    }
    leaf packets-dropped-no-collector {
      type uint64;
      description
        "Packets those could not be sent successfully due
         to lack of at least one GRPC collector";
    }
    leaf packets-dropped-buffer-full {
      type uint64;
      description
        "Packets those could not be sent successfully due
         to buffer full";
    }
    leaf packets-dropped-other-errors {
      type uint64;
      description
        "Packets those could not be sent successfully due
         to other errors";
    }
  }

  grouping NFSVR-GNPSI-SESSION-INFO {
    description
      "Netflow server gnpsi session information";
    leaf destination-address {
      type string;
      description
        "Destination address";
    }
    leaf destination-port {
      type uint16;
      description
        "Destination port number";
    }
    leaf emsd-session-state {
      type string;
      description
        "Emsd session state";
    }
  }
}
