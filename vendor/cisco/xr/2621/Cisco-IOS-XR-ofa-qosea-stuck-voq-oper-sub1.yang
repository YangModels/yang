submodule Cisco-IOS-XR-ofa-qosea-stuck-voq-oper-sub1 {
  belongs-to Cisco-IOS-XR-ofa-qosea-stuck-voq-oper {
    prefix Cisco-IOS-XR-ofa-qosea-stuck-voq-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-qosea-stuck-voq package operational data.
     
     Copyright (c) 2013-2025 by Cisco Systems, Inc.
     All rights reserved.";

  revision 2025-01-02 {
    description
      "Initial version for Stuck VOQ operational data";
    semver:module-version "1.0.0";
  }
  revision 2019-04-05 {
    description
      "Establish semantic version baseline.";
  }
  revision 2015-11-09 {
    description
      "IOS XR 6.0 revision.";
  }

  grouping STUCK-VOQ-INFO-BG {
    description
      "STUCK VOQ INFO BG";
    leaf if-handle {
      type uint32;
      description
        "Interface handle (CLI resolves name from this)";
    }
    leaf aggregate-if-handle {
      type uint32;
      description
        "Aggregate interface handle";
    }
    leaf voq-base {
      type uint32;
      description
        "VOQ base ID";
    }
    leaf traffic-class {
      type uint32;
      description
        "Traffic Class (0-7)";
    }
    leaf stuck-voq-num {
      type uint32;
      description
        "Stuck VOQ number (voq_base + tc)";
    }
    leaf stuck-vsc-num {
      type uint32;
      description
        "Stuck VSC (VOQ-Scheduler Connection) number";
    }
    leaf egress-slot {
      type uint32;
      description
        "Egress slot ID (destination)";
    }
    leaf egress-npu {
      type uint32;
      description
        "Egress NPU ID (destination)";
    }
    leaf egress-slice {
      type uint32;
      description
        "Egress slice ID (destination)";
    }
    leaf ingress-slot {
      type uint32;
      description
        "Ingress slot ID (detection source)";
    }
    leaf ingress-npu {
      type uint32;
      description
        "Ingress NPU ID (detection source)";
    }
    leaf ingress-slice {
      type uint32;
      description
        "Ingress slice ID (detection source)";
    }
    leaf is-stuck-detected {
      type boolean;
      description
        "Whether stuck VOQ is detected";
    }
    leaf is-local {
      type boolean;
      description
        "Whether this is a local VOQ";
    }
    leaf detection-count-ingress {
      type uint32;
      description
        "Number of times detected on ingress";
    }
    leaf first-timestamp-ingress {
      type uint64;
      description
        "First detection timestamp on ingress";
    }
    leaf last-timestamp-ingress {
      type uint64;
      description
        "Last detection timestamp on ingress";
    }
    leaf detection-count-egress {
      type uint32;
      description
        "Number of times detected on egress";
    }
    leaf first-timestamp-egress {
      type uint64;
      description
        "First detection timestamp on egress";
    }
    leaf last-timestamp-egress {
      type uint64;
      description
        "Last detection timestamp on egress";
    }
    leaf voq-empty-state {
      type boolean;
      description
        "VOQ empty state for this TC";
    }
    leaf credit-deficit {
      type uint32;
      description
        "Credit deficit (for local VOQs only)";
    }
    leaf grant-count {
      type uint32;
      description
        "Grant count (for local VOQs only)";
    }
    leaf ingress-isolation-status {
      type string {
        length "0..32";
      }
      description
        "Ingress isolation status: ISOLATED, FAILED,
         IN_PROGRESS, NOT_STARTED";
    }
    leaf egress-isolation-status {
      type string {
        length "0..32";
      }
      description
        "Egress isolation status: ISOLATED, FAILED,
         IN_PROGRESS, NOT_STARTED";
    }
    leaf status {
      type string {
        length "0..32";
      }
      description
        "Overall status: STUCK, CLEARED, UNKNOWN";
    }
    leaf ingress-traffic-class-bit-mask {
      type uint8;
      description
        "TMPort update TC bit mask (ingress)";
    }
    leaf egress-traffic-class-bit-mask {
      type uint8;
      description
        "Scheduler update TC bit mask (egress)";
    }
    leaf ingress-info-valid {
      type boolean;
      description
        "Ingress info valid for this bag (set by EDM)";
    }
    leaf egress-info-valid {
      type boolean;
      description
        "Egress info valid for this bag (set by EDM)";
    }
    leaf port-type {
      type string {
        length "0..16";
      }
      description
        "Port type (local/remote/etc)";
    }
  }
}
