submodule Cisco-IOS-XR-ownership-oper-sub1 {
  belongs-to Cisco-IOS-XR-ownership-oper {
    prefix Cisco-IOS-XR-ownership-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ownership package operational data.
     
     Copyright (c) 2013-2024 by Cisco Systems, Inc.
     All rights reserved.";

  revision 2024-04-18 {
    description
      "security profile details added";
    semver:module-version "1.1.0";
  }
  revision 2019-04-05 {
    description
      "Establish semantic version baseline.";
  }
  revision 2015-11-09 {
    description
      "IOS XR 6.0 revision.";
  }

  typedef Security-profile-values {
    type enumeration {
      enum "default" {
        value 1;
        description
          "Default value";
      }
      enum "enable" {
        value 2;
        description
          "Enabled";
      }
      enum "disable" {
        value 3;
        description
          "Disabled";
      }
    }
    description
      "security profile values";
  }

  grouping OV-INFO {
    description
      "OV INFO";
    leaf serial-no {
      type int32;
      description
        "serial number of OV";
    }
    leaf pdc {
      type string;
      description
        "PDC of OV";
    }
  }

  grouping OWNERSHIP-INFO {
    description
      "ownership information bag ";
    container ov-summary {
      description
        "ov summary";
      uses OV-INFO;
    }
    leaf oc-info {
      type string;
      description
        "ownership certificate info";
    }
  }

  grouping ANTITHEFT-INFO {
    description
      "ANTITHEFT INFO";
    leaf reimage-status {
      type string;
      description
        "status of reimage flag";
    }
  }

  grouping SECURITY-PROFILE-INFO {
    description
      "security profile bag";
    leaf signed-rpm {
      type Security-profile-values;
      description
        "signed rpm bit";
    }
    leaf signed-rpm-current {
      type Security-profile-values;
      description
        "signed rpm cur stat";
    }
    leaf secure-ztp {
      type Security-profile-values;
      description
        "secure ztp bit";
    }
    leaf secure-ztp-current {
      type Security-profile-values;
      description
        "secure ztp cur stat";
    }
  }
}
