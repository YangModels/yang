module Cisco-IOS-XR-um-test-um2-types {
  namespace "http://cisco.com/ns/yang/Cisco-IOS-XR-um-test-um2-types";
  prefix um2_test_module_prefix;

  import Cisco-IOS-XR-um-types {
    prefix xr-um;
  }

  organization
    "Cisco Systems, Inc.";
  contact
    "Cisco Systems, Inc.
     Customer Service
     Postal: 170 West Tasman Drive
     San Jose, CA 95134
     Tel: +1 800 553-NETS
     E-mail: cs-yang@cisco.com";
  description
    "This module contains a collection of YANG definitions
     for Cisco timestamps package configuration.
     This YANG module augments and other modules configuration data.
     Copyright (c) 2024-2026 by Cisco Systems, Inc., and/or its affiliates.
     All rights reserved.";

  revision 2025-06-28 {
    description
      "localfilesize CLI upper limit reduced from 4Gb to 125Mb";
  }

  container test-container {
    presence "test-container configuration commands";
    description
      "test-container configuration commands";
    leaf test-leaf-bounded-string {
      type xr-um:bounded-string;
    }
    leaf test-leaf-extended-bounded-string {
      type xr-um:extended-bounded-string;
    }
    leaf test-leaf-restricted-string {
      type xr-um:restricted-string;
    }
    leaf test-leaf-extended-restricted-string {
      type xr-um:extended-restricted-string;
    }
    leaf test-leaf-whitespace-string {
      type xr-um:whitespace-string;
    }
    leaf test-leaf-extended-whitespace-string {
      type xr-um:extended-whitespace-string;
    }
    leaf test-leaf-binary-string {
      type binary {
        length "0..20";
      }
      description
        "binary string";
    }
    leaf test-encrypted-leaf {
      type xr-um:encrypted;
      description
        "encrypted leaf";
    }
    leaf test-md5-encrypted-leaf {
      type xr-um:md5-encrypted;
      description
        "md5 encrypted leaf";
    }
    leaf test-type6-encrypted-leaf {
      type xr-um:type6-encrypted;
      description
        "type6 encrypted leaf";
    }
    leaf test-type7-encrypted-leaf {
      type xr-um:type7-encrypted;
      description
        "type7 encrypted leaf";
    }
    leaf test-type8-encrypted-leaf {
      type xr-um:type8-encrypted;
      description
        "type8 encrypted leaf";
    }
    leaf test-type9-encrypted-leaf {
      type xr-um:type9-encrypted;
      description
        "type9 encrypted leaf";
    }
    leaf test-type10-encrypted-leaf {
      type xr-um:type10-encrypted;
      description
        "type10 encrypted leaf";
    }
    leaf test-leaf-percentage {
      type xr-um:percentage;
      description
        "percentage leaf";
    }
    leaf test-leaf-char-num {
      type xr-um:char-num;
      description
        "char num leaf";
    }
    leaf test-leaf-identifier {
      type xr-um:identifier;
      description
        "identifier leaf";
    }
    leaf test-leaf-hex-uint64 {
      type xr-um:hex-uint64;
      description
        "hex-uint64 leaf";
    }
    leaf test-leaf-hex-uint32 {
      type xr-um:hex-uint32;
      description
        "hex-uint32 leaf";
    }
    leaf test-leaf-hex-uint16 {
      type xr-um:hex-uint16;
      description
        "hex-uint16 leaf";
    }
    leaf test-leaf-interface-name {
      type xr-um:interface-name;
      description
        "interface-name leaf";
    }
    leaf test-leaf-controller-name {
      type xr-um:controller-name;
      description
        "controller-name leaf";
    }
    leaf test-leaf-location-name {
      type xr-um:location-name;
      description
        "location-name leaf";
    }
    leaf test-leaf-pq-location-name {
      type xr-um:partially-qualified-location-name;
      description
        "partially-qualified-location-name leaf";
    }
    leaf test-leaf-lowercase-string {
      type xr-um:lowercase-string;
      description
        "lowercase-string leaf";
    }
    leaf test-leaf-uppercase-string {
      type xr-um:uppercase-string;
      description
        "uppercase-string leaf";
    }
    leaf test-leaf-acl-name {
      type xr-um:acl-name;
      description
        "acl-name leaf";
    }
    leaf test-leaf-ipv4-address {
      type xr-um:ipv4-address;
      description
        "ipv4-address leaf";
    }
    leaf test-leaf-ipv6-address {
      type xr-um:ipv6-address;
      description
        "ipv6-address leaf";
    }
    leaf test-leaf-mac-address {
      type xr-um:mac-address;
      description
        "mac-address leaf";
    }
    leaf test-leaf-ipv4-prefix {
      type xr-um:ipv4-prefix;
      description
        "ipv4-prefix leaf";
    }
    leaf test-leaf-ipv6-prefix {
      type xr-um:ipv6-prefix;
      description
        "ipv6-prefix leaf";
    }
    leaf test-leaf-vpn-id {
      type xr-um:vpn-id;
      description
        "vpn-id leaf";
    }
    leaf test-leaf-ip-prefix {
      type xr-um:ip-prefix;
      description
        "ip-prefix leaf";
    }
    leaf test-leaf-ip-address {
      type xr-um:ip-address;
      description
        "ip-address leaf";
    }
    leaf test-leaf-port-number {
      type xr-um:port-number;
      description
        "port-number leaf";
    }
    leaf test-leaf-ospf-area-id {
      type xr-um:ospf-area-id;
      description
        "ospf-area-id leaf";
    }
    leaf test-leaf-as-number {
      type xr-um:as-number;
      description
        "as-number leaf";
    }
  }
}
