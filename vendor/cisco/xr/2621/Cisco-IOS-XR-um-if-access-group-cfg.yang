module Cisco-IOS-XR-um-if-access-group-cfg {
  namespace "http://cisco.com/ns/yang/Cisco-IOS-XR-um-if-access-group-cfg";
  prefix um-if-access-group-cfg;

  import Cisco-IOS-XR-um-interface-cfg {
    prefix interface-cfg;
  }
  import Cisco-IOS-XR-types {
    prefix xr;
  }
  import tailf-common {
    prefix tailf;
  }
  import cisco-semver {
    prefix semver;
  }

  organization
    "Cisco Systems, Inc.";
  contact
    "Cisco Systems, Inc.
     Customer Service
     Postal: 170 West Tasman Drive
     San Jose, CA 95134
     Tel: +1 800 553-NETS
     E-mail: cs-yang@cisco.com";
  description
    "This module contains a collection of YANG definitions
     for Cisco access-group package configuration.
     This YANG module augments and other modules configuration data.
     Copyright (c) 2024 by Cisco Systems, Inc.
     All rights reserved.";

  revision 2024-07-23 {
    description
      "Increase max ACL name length
       2024-06-05
         Initial UM2 release
       2023-11-16
         Change maxixum compression level to 4.
       2022-07-11
         Added missing description statement to nodes";
    semver:module-version "1.1.0";
  }
  revision 2019-06-10 {
    description
      "Establish semantic version baseline.";
    semver:module-version "1.0.0";
  }
  revision 2019-04-02 {
    description
      "Initial version";
  }

  grouping GROUP-INTERFACES-INTERFACE-ETHERNET-SERVICES-BODY {
    description
      "Grouping for ethernet services";
    container ethernet-services {
      when "not(../interface-cfg:interface-name[starts-with(text(),'tunnel-ip')]) or not(../interface-cfg:interface-name[starts-with(text(),'tunnel-te')]) or not(../interface-cfg:interface-name[starts-with(text(),'Loopback')]) or not(../interface-cfg:interface-name[starts-with(text(),'BVI')]) or not(../interface-cfg:interface-name[starts-with(text(),'MgmtEth')])" {
        tailf:dependency "../../interface-cfg:interface-name";
      }
      description
        "Ethernet related services";
      container filters {
        description
          "Filter packets";
        list filter {
          key "filter-packets";
          description
            "Filter packets";
          leaf filter-packets {
            type enumeration {
              enum "ingress" {
                value 0;
                description
                  "Filter incoming packets";
              }
              enum "egress" {
                value 1;
                description
                  "Filter outgoing packets";
              }
            }
            description
              "Filter packets";
          }
          leaf access-group {
            type xr:Cisco-ios-xr-string {
              length "1..128" {
                description
                  "Access-list name";
              }
            }
            mandatory true;
            description
              "Specify access control for packets";
          }
        }
      }
    }
  }

  grouping GROUP-IPV4-INTERFACES-INTERFACE-ACCESS-GROUP-BODY {
    description
      "Grouping for ipv4 access group";
    container access-group {
      when "not(../../interface-cfg:interface-name[starts-with(text(),'tunnel-grp')]) or not(../../interface-cfg:interface-name[starts-with(text(),'tunnel-te')]) or not(../../interface-cfg:interface-name[starts-with(text(),'tunnel')]) or not(../../interface-cfg:interface-name[starts-with(text(),'Loopback')]) or not(../../interface-cfg:interface-name[starts-with(text(),'vasileft')]) or not(../../interface-cfg:interface-name[starts-with(text(),'vasiright')])" {
        tailf:dependency "../../interface-cfg:interface-name";
      }
      description
        "Specify access control for packets";
      container ingress {
        must "access-list-name-1";
        presence "Indicates an ingress node is configured.";
        description
          "IPv4 Packet filter to be applied to inbound packets";
        container access-list-name-1 {
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-2 {
          must "../access-list-name-1";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-3 {
          must "../access-list-name-2";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-4 {
          must "../access-list-name-3";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-5 {
          must "../access-list-name-4";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        leaf hardware-count {
          when "../../../../interface-cfg:interface-name[not(starts-with(text(),'MgmtEth'))]" {
            tailf:dependency "../../../../interface-cfg:interface-name";
          }
          type empty;
          description
            "Count packets in hardware";
        }
        leaf interface-statistics {
          type empty;
          description
            "Per interface statistics in hardware";
        }
        leaf compress {
          type uint32 {
            range "0..4";
          }
          must "not(../access-list-name-2 or ../access-list-name-1/common)";
          description
            "Specify ACL compression in hardware";
        }
      }
      container egress {
        must "access-list-name";
        presence "Indicates an egress node is configured.";
        description
          "IPv4 Packet filter to be applied to outbound packets";
        container access-list-name {
          presence "Indicates this Access-list name is configured";
          description
            "Access-list name";
          leaf name {
            type xr:Cisco-ios-xr-string {
              length "1..128";
            }
            mandatory true;
            description
              "Access-list name";
          }
        }
        leaf hardware-count {
          when "../../../../interface-cfg:interface-name[not(starts-with(text(),'MgmtEth'))]" {
            tailf:dependency "../../../../interface-cfg:interface-name";
          }
          type empty;
          description
            "Count packets in hardware";
        }
        leaf interface-statistics {
          type empty;
          description
            "Per interface statistics in hardware";
        }
        leaf compress {
          type uint32 {
            range "0..4";
          }
          description
            "Specify ACL compression in hardware";
        }
      }
    }
  }

  grouping GROUP-IPV6-INTERFACES-INTERFACE-ACCESS-GROUP-BODY {
    description
      "Grouping for ipv6 access-group";
    container access-group {
      when "not(../../interface-cfg:interface-name[starts-with(text(),'tunnel')])or not(../../interface-cfg:interface-name[starts-with(text(),'tunnel-grp')]) or not(../../interface-cfg:interface-name[starts-with(text(),'tunnel-te')]) or not(../../interface-cfg:interface-name[starts-with(text(),'loopback')]) or not(../../interface-cfg:interface-name[starts-with(text(),'vasileft')]) or not(../../interface-cfg:interface-name[starts-with(text(),'vasiright')])" {
        tailf:dependency "../../interface-cfg:interface-name";
      }
      description
        "Specify access control for packets";
      container ingress {
        must "access-list-name-1";
        presence "Indicates an ingress node is configured.";
        description
          "IPv4 Packet filter to be applied to inbound packets";
        container access-list-name-1 {
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-2 {
          must "../access-list-name-1";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-3 {
          must "../access-list-name-2";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-4 {
          must "../access-list-name-3";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        container access-list-name-5 {
          must "../access-list-name-4";
          presence "Indicates this Access-list name is configured";
          description
            "Access-list name";
          leaf name {
            type xr:Cisco-ios-xr-string {
              length "1..128";
            }
            mandatory true;
            description
              "Access-list name";
          }
          leaf common {
            type empty;
            description
              "common Access-list name";
          }
        }
        leaf interface-statistics {
          type empty;
          description
            "Per interface statistics in hardware";
        }
        leaf compress {
          type uint32 {
            range "0..4";
          }
          must "not(../access-list-name-2 or ../access-list-name-1/common)";
          description
            "Specify ACL compression in hardware";
        }
      }
      container egress {
        must "access-list-name";
        presence "Indicates an egress node is configured.";
        description
          "IPv4 Packet filter to be applied to outbound packets";
        container access-list-name {
          presence "Indicates this Access-list name is configured";
          description
            "Access-list name";
          leaf name {
            type xr:Cisco-ios-xr-string {
              length "1..128";
            }
            mandatory true;
            description
              "Access-list name";
          }
        }
        leaf interface-statistics {
          type empty;
          description
            "Per interface statistics in hardware";
        }
        leaf compress {
          type uint32 {
            range "0..4";
          }
          description
            "Specify ACL compression in hardware";
        }
      }
    }
  }

  augment "/interface-cfg:interfaces/interface-cfg:interface/interface-cfg:ipv4" {
    description
      "This augment extends the configuration data of Cisco-IOS-XR-um-interface-cfg";
    uses GROUP-IPV4-INTERFACES-INTERFACE-ACCESS-GROUP-BODY;
  }
  augment "/interface-cfg:interfaces/interface-cfg:interface-preconfigure/interface-cfg:ipv4" {
    description
      "This augment extends the configuration data of Cisco-IOS-XR-um-interface-cfg";
    uses GROUP-IPV4-INTERFACES-INTERFACE-ACCESS-GROUP-BODY;
  }
  augment "/interface-cfg:interfaces/interface-cfg:interface/interface-cfg:ipv6" {
    description
      "This augment extends the configuration data of Cisco-IOS-XR-um-interface-cfg";
    uses GROUP-IPV6-INTERFACES-INTERFACE-ACCESS-GROUP-BODY;
  }
  augment "/interface-cfg:interfaces/interface-cfg:interface-preconfigure/interface-cfg:ipv6" {
    description
      "This augment extends the configuration data of Cisco-IOS-XR-um-interface-cfg";
    uses GROUP-IPV6-INTERFACES-INTERFACE-ACCESS-GROUP-BODY;
  }
  augment "/interface-cfg:interfaces/interface-cfg:interface" {
    description
      "This augment extends the configuration data of Cisco-IOS-XR-um-interface-cfg";
    uses GROUP-INTERFACES-INTERFACE-ETHERNET-SERVICES-BODY;
  }
  augment "/interface-cfg:interfaces/interface-cfg:interface-preconfigure" {
    description
      "This augment extends the configuration data of Cisco-IOS-XR-um-interface-cfg";
    uses GROUP-INTERFACES-INTERFACE-ETHERNET-SERVICES-BODY;
  }
}
