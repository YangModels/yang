module Cisco-IOS-XR-openconfig-ospfv2-ext {
  yang-version 1;
  namespace "http://cisco.com/ns/yang/Cisco-IOS-XR-openconfig-ospfv2-ext";
  prefix oc-ospfv2-cisco-xr-ext;

  import openconfig-extensions {
    prefix oc-ext;
  }
  import openconfig-network-instance {
    prefix oc-ni;
  }

  organization
    "Cisco Systems, Inc.";
  contact
    "Cisco Systems, Inc.
     Customer Service
     Postal: 170 West Tasman Drive
     San Jose, CA 95134
     Tel: +1 800 553-NETS
     
     E-mail: cs-yang@cisco.com";
  description
    "This module is an extension of OSPFv2 model and contains the definition of
     extended parameters for distribute link-state.
     
     Copyright (c) 2025 by Cisco Systems, Inc.
     All rights reserved.";

  revision 2025-06-22 {
    description
      "Initial version";
    reference "0.1.0";
  }

  grouping distribute-config {
    description
      "Configuration data for distribute";
    leaf enabled {
      type boolean;
      default "false";
      description
        "Enable distribution of link-state database services";
    }
    leaf throttle {
      type uint32 {
        range "1..3600";
      }
      units "second";
      description
        "Seconds";
    }
    leaf instance-id {
      type uint64 {
        range "0..4294967295";
      }
      description
        "Instance ID";
    }
    leaf excl-external {
      type boolean;
      default "false";
      description
        "Filter advertisement of external prefixes";
    }
    leaf route-policy-name {
      type string;
      description
        "Route policy for distribute link-state filtering";
    }
    leaf follow-on {
      type uint32 {
        range "1..3600";
      }
      units "second";
      description
        "Seconds";
    }
  }

  grouping distribute-state {
    description
      "State data for distribute";
  }

  grouping distribute-extended {
    description
      "Extended distribute parameters";
    container cisco {
      description
        "Extended distribute parameters";
      container distribute {
        description
          "Enclosing container for distribute";
        container config {
          description
            "Extended Distribute Configuration parameters";
          uses distribute-config;
        }
        container state {
          config false;
          description
            "Extended Distribute Operational parameters";
          uses distribute-config;
          uses distribute-state;
        }
      }
    }
  }

  augment "/oc-ni:network-instances/oc-ni:network-instance/oc-ni:protocols/oc-ni:protocol/oc-ni:ospfv2/oc-ni:global" {
    description
      "This augment extends the configuration data of OSPFv2";
    uses distribute-extended;
  }
  oc-ext:openconfig-version "0.1.0";
}
