module Cisco-IOS-XR-snmp-entstatemib-cfg {
  namespace "http://cisco.com/ns/yang/Cisco-IOS-XR-snmp-entstatemib-cfg";
  prefix snmp-entstatemib-cfg;

  import cisco-semver {
    prefix semver;
  }
  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR snmp-entstatemib package configuration.
     
     This YANG module augments the
       Cisco-IOS-XR-snmp-agent-cfg
     module with configuration data.
     
     Copyright (c) 2013-2019 by Cisco Systems, Inc.
     All rights reserved.";

  revision 2019-04-05 {
    description
      "Establish semantic version baseline.";
    semver:module-version "1.0.1";
  }
  revision 2015-07-27 {
    description
      "IOS XR 6.0.0 revision.";
  }
  revision 2015-01-07 {
    description
      "IOS XR 5.3.1 revision.";
  }

  augment "/a1:snmp/a1:notification" {
    description
      "This augment extends the configuration data of
       'Cisco-IOS-XR-snmp-agent-cfg'";
    container entity-state {
      description
        "ENTITY-STATE-MIB notification configuration";
      leaf switchover {
        type empty;
        description
          "Enable ceStateExtStandbySwitchover notification";
      }
      leaf oper-status {
        type empty;
        description
          "Enable entStateOperEnable and
           entStateOperDisable notifications";
      }
    }
  }
}
