module Cisco-IOS-XR-install-augmented-oper {
  namespace "http://cisco.com/ns/yang/Cisco-IOS-XR-install-augmented-oper";
  prefix install-augmented-oper;

  import Cisco-IOS-XR-types {
    prefix xr;
  }
  import cisco-semver {
    prefix semver;
  }
  include Cisco-IOS-XR-install-augmented-oper-sub2 {
    revision-date 2019-04-05;
  }
  include Cisco-IOS-XR-install-augmented-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install-augmented package operational data.
     
     This module contains definitions
     for the following management objects:
       install: Install operational data
     
     Copyright (c) 2013-2019 by Cisco Systems, Inc.
     All rights reserved.";

  revision 2019-04-05 {
    description
      "Establish semantic version baseline.";
    semver:module-version "1.0.1m";
  }
  revision 2015-11-09 {
    description
      "IOS XR 6.0 revision.";
  }

  grouping ATOMIC-CHANGE-TABLE {
    description
      "Common node of transaction, latest-transaction";
    container atomic-changes {
      description
        "Table for atomic software change specific
         operational data";
      list atomic-change {
        key "index";
        description
          "Information about a particular atomic change";
        leaf index {
          type uint32;
          description
            "Index";
        }
        uses PACKAGING-OPERATION-TABLE;
        uses ATOMIC-CHANGE-INFO;
        uses ATOMIC-CHANGE-INFO-NODE-TABLE;
      }
    }
  }

  grouping TRANSACTION-INFO-NODE-TABLE {
    description
      "Common node of transaction, latest-transaction";
    container transaction-info-nodes {
      description
        "Table for per-node information when carrying out
         a transaction";
      list transaction-info-node {
        key "node";
        description
          "Node specific information when carrying out a
           transaction";
        leaf node {
          type xr:Node-id;
          description
            "Node name";
        }
        uses INST-TRANS-NODE-BAG;
      }
    }
  }

  grouping TRANSACTION-INFO {
    description
      "Common node of transaction, latest-transaction";
    container transaction-info {
      description
        "Summary information about the transaction";
      uses INST-TRANS-BAG;
    }
  }

  grouping ATOMIC-CHANGE-INFO {
    description
      "Common node of atomic-change,
       latest-atomic-change";
    container atomic-change-info {
      description
        "Summary information about the atomic change";
      uses INST-ATOMIC-CHANGE-BAG;
    }
  }

  grouping PACKAGING-OPERATION-INFO-NODE-TABLE {
    description
      "Common node of latest-packaging-operation,
       packaging-operation";
    container packaging-operation-info-nodes {
      description
        "Table for per-node information when carrying out
         a packaging operation";
      list packaging-operation-info-node {
        key "node";
        description
          "Node specific information when carrying out a
           packaging operation";
        leaf node {
          type xr:Node-id;
          description
            "Node name";
        }
        uses INST-PKG-OP-NODE-BAG;
      }
    }
  }

  grouping PACKAGING-OPERATION-TABLE {
    description
      "Common node of atomic-change,
       latest-atomic-change";
    container packaging-operations {
      description
        "Table for packaging operation specific
         operational data";
      list packaging-operation {
        key "index";
        description
          "Data about a particular packaging operation";
        leaf index {
          type uint32;
          description
            "Index";
        }
        uses PACKAGING-OPERATION-ERRORS-NODE-TABLE;
        uses PACKAGING-OPERATION-INFO-NODE-TABLE;
        uses PACKAGING-OPERATION-INFO;
      }
    }
  }

  grouping PACKAGING-OPERATION-ERRORS-NODE-TABLE {
    description
      "Common node of latest-packaging-operation,
       packaging-operation";
    container packaging-operation-errors-nodes {
      description
        "Table for per-node DNF errors when carrying out
         a packaging operation";
      list packaging-operation-errors-node {
        key "node";
        description
          "Node specific DNF errors when carrying out a
           packaging operation";
        leaf node {
          type xr:Node-id;
          description
            "Node name";
        }
        uses INST-PKG-OP-ERRORS-BAG;
      }
    }
  }

  grouping PACKAGING-OPERATION-INFO {
    description
      "Common node of latest-packaging-operation,
       packaging-operation";
    container packaging-operation-info {
      description
        "Information about a packaging operation";
      uses INST-PKG-OP-BAG;
    }
  }

  grouping ATOMIC-CHANGE-INFO-NODE-TABLE {
    description
      "Common node of atomic-change,
       latest-atomic-change";
    container atomic-change-info-nodes {
      description
        "Table for per-node information when carrying out
         an atomic change";
      list atomic-change-info-node {
        key "node";
        description
          "Node specific information when carrying out an
           atomic change";
        leaf node {
          type xr:Node-id;
          description
            "Node name";
        }
        uses INST-ATOMIC-CHANGE-NODE-BAG;
      }
    }
  }

  container install {
    config false;
    description
      "Install operational data";
    container history {
      description
        "Operation history";
      container latest-transaction {
        description
          "Latest transaction data";
        uses TRANSACTION-INFO-NODE-TABLE;
        uses TRANSACTION-INFO;
        uses ATOMIC-CHANGE-TABLE;
      }
      container latest-packaging-operation {
        description
          "Information about the latest packaging
           operation";
        uses PACKAGING-OPERATION-ERRORS-NODE-TABLE;
        uses PACKAGING-OPERATION-INFO-NODE-TABLE;
        uses PACKAGING-OPERATION-INFO;
      }
      container latest-atomic-change {
        description
          "Latest atomic software change";
        uses PACKAGING-OPERATION-TABLE;
        uses ATOMIC-CHANGE-INFO;
        uses ATOMIC-CHANGE-INFO-NODE-TABLE;
      }
      container transactions {
        description
          "Table for transaction-specific operational data";
        list transaction {
          key "transaction-id";
          description
            "Information about a particular transaction";
          leaf transaction-id {
            type uint32;
            description
              "Install Transaction ID";
          }
          uses TRANSACTION-INFO-NODE-TABLE;
          uses TRANSACTION-INFO;
          uses ATOMIC-CHANGE-TABLE;
        }
      }
    }
    container packages {
      description
        "Package information";
      container cached {
        description
          "Information about cached packages";
        container summary {
          description
            "Summary packages";
          uses INST-PACKAGES-BAG;
        }
        container all {
          description
            "All packages including card-specific
             dependencies";
          uses INST-PACKAGES-BAG;
        }
      }
      container available {
        description
          "Information about available packages";
        container internal {
          description
            "All packages including card-specific
             dependencies";
          uses INST-AVAILABLE-PACKAGES-BAG;
        }
        container all {
          description
            "All user-installable packages";
          uses INST-AVAILABLE-PACKAGES-BAG;
        }
      }
    }
    container internal {
      description
        "Internal debug information";
      container packages {
        description
          "Package information";
        container pkgmgr {
          description
            "Information about package-manager installed
             packages. During an atomic change, this is the
             full set of packages that will be active after
             the atomic change is applied";
          container nodes {
            description
              "Table for node level data";
            list node {
              key "node";
              description
                "Per-node packages";
              leaf node {
                type xr:Node-id;
                description
                  "Node name";
              }
              uses INST-PACKAGES-BAG;
            }
          }
          container summary {
            description
              "Summary packages";
            uses INST-PACKAGES-BAG;
          }
        }
      }
    }
    container request {
      description
        "Information about the latest user request";
      container verbose {
        description
          "Verbose information about the status of current
           install operation";
        uses INST-REQUEST-VERBOSE-BAG;
      }
    }
    container version {
      description
        "Install version information";
      container detail {
        description
          "Install version detailed information";
        uses INST-VERSION-BAG;
      }
      container brief {
        description
          "Install version brief information";
        uses INST-VERSION-BAG;
      }
    }
    container rollback {
      description
        "Information about software rollback options";
      container rollback-points {
        description
          "Table for rollback points";
        list rollback-point {
          key "id";
          description
            "Rollback point information";
          container installed-packages {
            description
              "Installed packages";
            container user-installable {
              description
                "User-installable packages associated with
                 rollback point";
              uses INST-PACKAGES-BAG;
            }
            container changes {
              description
                "Changes in packages if rolling back";
              uses INST-CHANGES-BAG;
            }
          }
          leaf id {
            type uint32;
            description
              "Rollback point ID";
          }
        }
      }
    }
    container fixes {
      description
        "Information about DDTS fixes";
      container available {
        description
          "Information about fixes that are available";
        uses INST-AVAILABLE-FIXES-BAG;
      }
    }
  }
}
