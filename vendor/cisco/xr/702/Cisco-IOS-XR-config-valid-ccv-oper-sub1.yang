submodule Cisco-IOS-XR-config-valid-ccv-oper-sub1 {
  belongs-to Cisco-IOS-XR-config-valid-ccv-oper {
    prefix Cisco-IOS-XR-config-valid-ccv-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR config-valid-ccv package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Ccv-bag-optional-string {
    type string;
    description
      "String which may be optionally present.";
  }

  grouping CCV-YVE-VALIDATION-FAILURE {
    description
      "Validation failure";
    leaf error-app-tag {
      type string;
      description
        "A unique string that identifies the error;
         equivalent to error-app-tag in RFC 6241";
    }
    leaf error-message {
      type string;
      description
        "The error message; equivalent to error-message
         in RFC 6241";
    }
    leaf error-severity {
      type string;
      description
        "The severity of the error; equivalent to
         error-severity in RFC 6241";
    }
  }

  grouping CCV-YVE-VALIDATION-FAILURE-ITEM-BAG {
    description
      "CCV YVE VALIDATION FAILURE ITEM BAG";
    leaf group-name {
      type Ccv-bag-optional-string;
      description
        "The configuration group that this item is
         inherited from, if any";
    }
    list failure {
      description
        "Validation failures for this configuration item";
      uses CCV-YVE-VALIDATION-FAILURE;
    }
  }
}
