module Cisco-IOS-XR-ipv6-new-dhcpv6d-oper {
  namespace "http://cisco.com/ns/yang/Cisco-IOS-XR-ipv6-new-dhcpv6d-oper";
  prefix ipv6-new-dhcpv6d-oper;

  import Cisco-IOS-XR-types {
    prefix xr;
  }
  import cisco-semver {
    prefix semver;
  }
  include Cisco-IOS-XR-ipv6-new-dhcpv6d-oper-sub1 {
    revision-date 2019-12-18;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-new-dhcpv6d package operational data.
     
     This module contains definitions
     for the following management objects:
       dhcpv6: IPV6 DHCPD operational data
     
     Copyright (c) 2013-2019 by Cisco Systems, Inc.
     All rights reserved.";

  revision 2019-12-18 {
    description
      "Added IPv6 ND support";
    semver:module-version "1.0.1M";
  }
  revision 2019-04-05 {
    description
      "Establish semantic version baseline.";
    semver:module-version "1.0.0";
  }
  revision 2018-10-09 {
    description
      "Added dhcpv6 server disconnect-history class";
  }
  revision 2018-09-17 {
    description
      "Added dhcpv6 proxy disconnect-history class";
  }
  revision 2017-12-06 {
    description
      "Added proxy class and server class oper for class and server profile";
  }
  revision 2015-11-09 {
    description
      "IOS XR 6.0 revision.";
  }

  container dhcpv6 {
    config false;
    description
      "IPV6 DHCPD operational data";
    container issu-status {
      description
        "DHCP IssuStatus";
      uses IPV6-DHCPD-ISSU-STATUS;
    }
    container nodes {
      description
        "IPv6 DHCP list of nodes";
      list node {
        key "node-name";
        description
          "IPv6 DHCP particular node name";
        container proxy {
          description
            "IPv6 DHCP proxy operational data";
          container vrfs {
            description
              "DHCPV6 proxy list of VRF names";
            list vrf {
              key "vrf-name";
              description
                "IPv6 DHCP proxy VRF name";
              container statistics {
                description
                  "IPv6 DHCP proxy statistics";
                uses IPV6-DHCPV6D-TYPE;
              }
              leaf vrf-name {
                type xr:Cisco-ios-xr-string;
                description
                  "VRF name";
              }
            }
          }
          container profiles {
            description
              "IPv6 DHCP proxy profile";
            list profile {
              key "profile-name";
              description
                "IPv6 DHCP proxy profile";
              container throttle-infos {
                description
                  "DHCPV6 throttle table";
                list throttle-info {
                  key "mac-address";
                  description
                    "IPv6 DHCP proxy profile Throttle Info";
                  leaf mac-address {
                    type xr:Cisco-ios-xr-string;
                    description
                      "MAC address";
                  }
                  uses IPV6-DHCPV6D-MAC-THROTTLE;
                }
              }
              container proxy-classes {
                description
                  "IPv6 DHCP proxy class table";
                list proxy-class {
                  key "class-name";
                  description
                    "IPv6 DHCP proxy class profile";
                  leaf class-name {
                    type xr:Cisco-ios-xr-string;
                    description
                      "Class name";
                  }
                  uses IPV6-DHCPV6D-PROXY-PROFILE-CLASS;
                }
              }
              container info {
                description
                  "IPv6 DHCP proxy profile Info";
                uses IPV6-DHCPV6D-PROXY-PROFILE;
              }
              leaf profile-name {
                type xr:Cisco-ios-xr-string;
                description
                  "Profile name";
              }
            }
          }
          container disconnect-histories {
            description
              "DHCPv6 proxy disconnect history";
            list disconnect-history {
              key "index";
              description
                "Single DHCPv6 proxy disconnect history";
              leaf index {
                type xr:Cisco-ios-xr-string;
                description
                  "Index";
              }
              uses IPV6-DHCPV6D-DISC-HISTORY;
            }
          }
          container interfaces {
            description
              "DHCPV6 proxy interface";
            list interface {
              key "interface-name";
              description
                "IPv6 DHCP proxy interface";
              leaf interface-name {
                type xr:Cisco-ios-xr-string;
                description
                  "Interface Name";
              }
              uses IPV6-DHCPV6D-PROXY-INTERFACE;
            }
          }
          container statistics {
            description
              "DHCPv6 proxy statistics";
            uses IPV6-DHCPV6D-PROXY-STATS;
          }
          container binding {
            description
              "DHCPV6 proxy bindings";
            container clients {
              description
                "DHCPV6 proxy client bindings";
              list client {
                key "client-id";
                description
                  "Single DHCPV6 proxy binding";
                leaf client-id {
                  type xr:Cisco-ios-xr-string;
                  description
                    "Client ID";
                }
                uses IPV6-DHCPV6D-PROXY-BINDING;
              }
            }
            container summary {
              description
                "DHCPV6 proxy binding summary";
              uses IPV6-DHCPV6D-PROXY-BINDINGS-SUMMARY;
            }
          }
        }
        container base {
          description
            "IPv6 DHCP Base";
          container database {
            description
              "DHCP database";
            uses IPV6-DHCPD-DATABASE;
          }
          container addr-bindings {
            description
              "IPv6 DHCP Base Binding";
            list addr-binding {
              key "addr-string";
              description
                "DHCPv6 base stats debug";
              leaf addr-string {
                type xr:Cisco-ios-xr-string;
                description
                  "Address String";
              }
              uses IPV6-DHCPV6D-BASE-BINDING;
            }
          }
        }
        container server {
          description
            "IPv6 DHCP server operational data";
          container disconnect-histories {
            description
              "DHCPv6 server disconnect history";
            list disconnect-history {
              key "index";
              description
                "Single DHCPv6 server disconnect history";
              leaf index {
                type xr:Cisco-ios-xr-string;
                description
                  "Index";
              }
              uses IPV6-DHCPV6D-DISC-HISTORY;
            }
          }
          container binding {
            description
              "DHCPV6 server bindings";
            container summary {
              description
                "DHCPV6 server binding summary";
              uses IPV6-DHCPV6D-SERVER-BINDINGS-SUMMARY;
            }
            container clients {
              description
                "DHCPV6 server client bindings";
              list client {
                key "client-id";
                description
                  "Single DHCPV6 server binding";
                leaf client-id {
                  type xr:Cisco-ios-xr-string;
                  description
                    "Client ID";
                }
                uses IPV6-DHCPV6D-SERVER-BINDING;
              }
            }
          }
          container vrfs {
            description
              "DHCPV6 server list of VRF names";
            list vrf {
              key "vrf-name";
              description
                "IPv6 DHCP server VRF name";
              container statistics {
                description
                  "IPv6 DHCP server statistics";
                uses IPV6-DHCPV6D-TYPE;
              }
              leaf vrf-name {
                type xr:Cisco-ios-xr-string;
                description
                  "VRF name";
              }
            }
          }
          container profiles {
            description
              "IPv6 DHCP server profile";
            list profile {
              key "profile-name";
              description
                "IPv6 DHCP server profile";
              container info {
                description
                  "IPv6 DHCP server profile Info";
                uses IPV6-DHCPV6D-SERVER-PROFILE;
              }
              container throttle-infos {
                description
                  "DHCPV6 throttle table";
                list throttle-info {
                  key "mac-address";
                  description
                    "IPv6 DHCP server profile Throttle Info";
                  leaf mac-address {
                    type xr:Cisco-ios-xr-string;
                    description
                      "MAC address";
                  }
                  uses IPV6-DHCPV6D-MAC-THROTTLE;
                }
              }
              container server-classes {
                description
                  "IPv6 DHCP server class table";
                list server-class {
                  key "class-name";
                  description
                    "IPv6 DHCP server class profile";
                  leaf class-name {
                    type xr:Cisco-ios-xr-string;
                    description
                      "Class name";
                  }
                  uses IPV6-DHCPV6D-SERVER-PROFILE-CLASS;
                }
              }
              leaf profile-name {
                type xr:Cisco-ios-xr-string;
                description
                  "Profile name";
              }
            }
          }
          container interfaces {
            description
              "DHCPV6 server interface";
            list interface {
              key "interface-name";
              description
                "IPv6 DHCP server interface";
              leaf interface-name {
                type xr:Cisco-ios-xr-string;
                description
                  "Interface Name";
              }
              uses IPV6-DHCPV6D-SERVER-INTERFACE;
            }
          }
          container statistics {
            description
              "DHCPv6 server statistics";
            uses IPV6-DHCPV6D-SERVER-STATS;
          }
          container binding-options {
            description
              "DHCPv6 server binding with options";
            container mac-bind-options {
              description
                "DHCPv6 server binding from MAC address";
              list mac-bind-option {
                key "mac-address";
                description
                  "DHCPv6 server binding with options";
                leaf mac-address {
                  type xr:Cisco-ios-xr-string;
                  description
                    "MAC address";
                }
                uses IPV6-DHCPV6D-SERVER-BINDING-OPTIONS;
              }
            }
            container duid-bind-options {
              description
                "DHCPv6 server binding from DUID";
              list duid-bind-option {
                key "duid";
                description
                  "DHCPv6 server binding with options";
                leaf duid {
                  type xr:Cisco-ios-xr-string;
                  description
                    "DUID of Binding";
                }
                uses IPV6-DHCPV6D-SERVER-BINDING-OPTIONS;
              }
            }
          }
        }
        container relay {
          description
            "IPv6 DHCP relay operational data";
          container statistics {
            description
              "DHCPv6 relay statistics";
            uses IPV6-DHCPV6D-RELAY-STATS;
          }
          container binding {
            description
              "DHCPV6 relay bindings";
            container summary {
              description
                "DHCPV6 relay binding summary";
              uses IPV6-DHCPV6D-RELAY-BINDINGS-SUMMARY;
            }
            container clients {
              description
                "DHCPV6 relay client bindings";
              list client {
                key "client-id";
                description
                  "Single DHCPV6 relay binding";
                leaf client-id {
                  type xr:Cisco-ios-xr-string;
                  description
                    "Client ID";
                }
                uses IPV6-DHCPV6D-RELAY-ROUTE-BINDING;
              }
            }
          }
          container vrfs {
            description
              "DHCPV6 relay list of VRF names";
            list vrf {
              key "vrf-name";
              description
                "IPv6 DHCP relay VRF name";
              container statistics {
                description
                  "IPv6 DHCP relay statistics";
                uses IPV6-DHCPV6D-TYPE;
              }
              leaf vrf-name {
                type xr:Cisco-ios-xr-string;
                description
                  "VRF name";
              }
            }
          }
        }
        leaf node-name {
          type xr:Node-id;
          description
            "Node name";
        }
      }
    }
  }
}
