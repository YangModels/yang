module Cisco-IOS-XR-optics-port-mode-cfg {
  namespace "http://cisco.com/ns/yang/Cisco-IOS-XR-optics-port-mode-cfg";
  prefix optics-port-mode-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-port-mode package configuration.
     
     This module contains definitions
     for the following management objects:
       node: Hardware Module Portmode configuration
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container node {
    description
      "Hardware Module Portmode configuration";
    container acts {
      description
        "none";
      list act {
        key "node-name";
        description
          "Nodename";
        container port-ranges {
          description
            "port mode configuration";
          list port-range {
            key "first-port sec-port";
            description
              "Hardware Module Portmode configuration";
            container mode {
              description
                "Mode";
              leaf speed {
                type string;
                description
                  "speed 40-100, 400, 2x100";
              }
            }
            leaf first-port {
              type uint32;
              description
                "Specify port number";
            }
            leaf sec-port {
              type uint32;
              description
                "Specify port number";
            }
          }
        }
        leaf node-name {
          type xr:Cisco-ios-xr-string;
          description
            "NodeName";
        }
      }
    }
  }
}
