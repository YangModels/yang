module Cisco-IOS-XR-shellutil-copy-act {
  namespace "http://cisco.com/ns/yang/Cisco-IOS-XR-shellutil-copy-act";
  prefix shellutil-copy-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2016-2019 by Cisco Systems, Inc.
     All rights reserved.";

  revision 2019-10-01 {
    description
      "Made changes to be RFC6087 compliant";
    semver:module-version "1.0.1m";
  }
  revision 2019-04-05 {
    description
      "Establish semantic version baseline.";
    semver:module-version "1.0.0";
  }
  revision 2019-02-07 {
    description
      "Updated the task group for copy *-ext.yang";
  }
  revision 2018-05-20 {
    description
      "Updated the module name as per CISCO format";
  }
  revision 2018-01-20 {
    description
      "IOS XR 7.0.1 revision.";
  }

  rpc copy {
    description
      "Copy";
    input {
      leaf sourcename {
        type string;
        description
          "source file name to copy";
      }
      leaf destinationname {
        type string;
        mandatory true;
        description
          "destination file name";
      }
      leaf sourcefilesystem {
        type string;
        mandatory true;
        description
          "source file system e.g disk0: tftp";
      }
      leaf destinationfilesystem {
        type string;
        mandatory true;
        description
          "destination file system e.g disk0:, tftp:";
      }
      leaf sourcelocation {
        type string;
        description
          "source location";
      }
      leaf destinationlocation {
        type string;
        description
          "destination location";
      }
      leaf vrf {
        type string;
        description
          "vrf name";
      }
      leaf recurse {
        type boolean;
        description
          "recurse files to copy";
      }
    }
    output {
      leaf response {
        type string;
        description
          "Status of copy operation";
      }
    }
  }
}
