submodule Cisco-IOS-XR-subscriber-session-mon-oper-sub1 {
  belongs-to Cisco-IOS-XR-subscriber-session-mon-oper {
    prefix Cisco-IOS-XR-subscriber-session-mon-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR subscriber-session-mon package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping SHOW-SESSIONMON-STAT {
    description
      "show session_mon statistics";
    leaf total {
      type uint32;
      description
        "total";
    }
    leaf pppoe {
      type uint32;
      description
        "pppoe";
    }
    leaf pppoe-ds {
      type uint32;
      description
        "pppoe ds";
    }
    leaf dhcpv4 {
      type uint32;
      description
        "dhcpv4";
    }
    leaf dhcpv6 {
      type uint32;
      description
        "dhcpv6";
    }
    leaf dhcp-ds {
      type uint32;
      description
        "dhcp ds";
    }
    leaf ippkt {
      type uint32;
      description
        "ippkt";
    }
    leaf active-sessions {
      type uint32;
      description
        "active sessions";
    }
    leaf standby-sessions {
      type uint32;
      description
        "standby sessions";
    }
    leaf peak-active-sessions {
      type uint32;
      description
        "peak active sessions";
    }
    leaf peak-standby-sessions {
      type uint32;
      description
        "peak standby sessions";
    }
    leaf peak-start-time {
      type uint32;
      description
        "peak start time";
    }
    leaf timeout-value {
      type uint32;
      description
        "timeout value";
    }
  }
}
