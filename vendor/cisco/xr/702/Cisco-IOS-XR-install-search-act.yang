module Cisco-IOS-XR-install-search-act {
  namespace "http://cisco.com/ns/yang/Cisco-IOS-XR-install-search-act";
  prefix install-search-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install actions related to searching for package
     information.
     
     Copyright (c) 2016-2019 by Cisco Systems, Inc.
     All rights reserved.";

  revision 2019-10-01 {
    description
      "Made changes to be RFC6087 compliant";
    semver:module-version "1.0.1m";
  }
  revision 2019-04-05 {
    description
      "Establish semantic version baseline.";
    semver:module-version "1.0.0";
  }
  revision 2017-12-01 {
    description
      "IOS XR 7.1.1 revision.";
  }

  typedef Inst-provides-match-type {
    type enumeration {
      enum "description" {
        value 0;
        description
          "Description";
      }
      enum "URL" {
        value 1;
        description
          "URL";
      }
      enum "license" {
        value 2;
        description
          "License";
      }
      enum "filename" {
        value 3;
        description
          "Filename";
      }
      enum "other" {
        value 4;
        description
          "Other";
      }
    }
    description
      "Install provides match type";
  }

  grouping INST-PKG-COMMON-TYPE {
    description
      "Package details";
    leaf name {
      type string;
      description
        "Package name";
    }
    leaf architecture {
      type string;
      description
        "Package architecture";
    }
    leaf summary {
      type string;
      description
        "Brief package description";
    }
  }

  grouping INST-PKG-VERSION-TYPE {
    description
      "Package versioning information";
    leaf version {
      type string;
      description
        "Package version";
    }
    leaf epoch {
      type string;
      description
        "Package epoch, if any";
    }
    leaf release {
      type string;
      description
        "Package release";
    }
  }

  grouping INST-PKG-INFO-TYPE {
    description
      "Further package details for 'info' queries";
    leaf size {
      type uint32;
      description
        "Package size, in kB";
    }
    leaf description {
      type string;
      description
        "More detailed description of the package";
    }
    leaf license {
      type string;
      description
        "Package license information";
    }
    leaf repository {
      type string;
      description
        "Repository containing the package";
    }
  }

  grouping INST-PKG-SEARCH-LIST-TYPE {
    description
      "Install package search list type";
    container packages {
      description
        "List of packages";
      list package {
        description
          "List of packages";
        uses INST-PKG-COMMON-TYPE;
      }
    }
  }

  grouping INST-PKG-INFO-LIST-TYPE {
    description
      "Install package info list type";
    container packages {
      description
        "List of packages";
      list package {
        description
          "List of packages";
        uses INST-PKG-COMMON-TYPE;
        uses INST-PKG-VERSION-TYPE;
        uses INST-PKG-INFO-TYPE;
      }
    }
  }

  grouping INST-PKG-PROVIDES-LIST-TYPE {
    description
      "Install package provides list type";
    container packages {
      description
        "List of packages";
      list package {
        description
          "List of packages";
        uses INST-PKG-COMMON-TYPE;
        uses INST-PKG-VERSION-TYPE;
        leaf repository {
          type string;
          description
            "Repository containing the package";
        }
        container provides-matches {
          description
            "Features or dependencies this package provides";
          list provides-match {
            description
              "Provides match";
            leaf match_type {
              type Inst-provides-match-type;
              description
                "Type of object that the item was matched from";
            }
            leaf item {
              type string;
              description
                "Package/feature/filename that is provided";
            }
          }
        }
      }
    }
  }

  rpc info {
    description
      "Search for information about the given packages";
    input {
      leaf search-packages {
        type string {
          length "1..1024";
        }
        description
          "Space separated list of packages to query";
      }
    }
    output {
      uses INST-PKG-INFO-LIST-TYPE;
    }
  }
  rpc provides {
    description
      "Search for packages that provide the given file. Wildcards may
       be used (do not use quotes).";
    input {
      leaf search-files {
        type string {
          length "1..1024";
        }
        description
          "Space separated list of files or wildcard strings to query";
      }
    }
    output {
      uses INST-PKG-PROVIDES-LIST-TYPE;
    }
  }
  rpc search {
    description
      "Search for packages that contain the given string in the name,
       summary, description or url.  Wildcards may be used.";
    input {
      leaf search-strings {
        type string {
          length "1..1024";
        }
        description
          "Space separated list of strings to search for";
      }
    }
    output {
      uses INST-PKG-SEARCH-LIST-TYPE;
    }
  }
}
