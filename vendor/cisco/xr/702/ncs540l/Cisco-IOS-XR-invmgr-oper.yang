module Cisco-IOS-XR-invmgr-oper {
  namespace "http://cisco.com/ns/yang/Cisco-IOS-XR-invmgr-oper";
  prefix invmgr-oper;

  import cisco-semver {
    prefix semver;
  }
  include Cisco-IOS-XR-invmgr-oper-sub3 {
    revision-date 2019-04-05;
  }
  include Cisco-IOS-XR-invmgr-oper-sub2 {
    revision-date 2019-04-05;
  }
  include Cisco-IOS-XR-invmgr-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR invmgr package operational data.
     
     This module contains definitions
     for the following management objects:
       inventory: Inventory Operational data space
     
     Copyright (c) 2013-2019 by Cisco Systems, Inc.
     All rights reserved.";

  revision 2019-04-05 {
    description
      "Establish semantic version baseline.";
    semver:module-version "1.0.1M";
  }
  revision 2019-03-21 {
    description
      "Resolved string constraints issue.";
  }
  revision 2018-08-03 {
    description
      "Added slot-info and parent-info bags.";
  }
  revision 2018-04-19 {
    description
      "Added additional bags";
  }
  revision 2017-09-07 {
    description
      "Fixed type translation error.";
  }
  revision 2017-05-01 {
    description
      "Fixing backward compatibility error in module.";
  }
  revision 2015-11-09 {
    description
      "IOS XR 6.0 revision.";
  }

  grouping THRESH-BAG {
    description
      "Common node of minor-lo, minor-hi, major-lo,
       major-hi, critical-lo, critical-hi";
    container thresh-bag {
      description
        "Environment threshold info";
      uses ENVMON-THRESHOLD-INFO;
    }
  }

  container inventory {
    config false;
    description
      "Inventory Operational data space";
    container entities {
      description
        "Entities";
      list entity {
        key "name";
        description
          "Entity name";
        container subentities {
          description
            "SubEntities Table";
          list subentity {
            key "name";
            description
              "Subentity Bag";
            leaf name {
              type string;
              description
                "Subentity name";
            }
            uses SUBENTITY-INFO;
          }
        }
        container parent-info {
          description
            "Inventory parent name info";
          uses INV-PARENT-INFO;
        }
        container attributes {
          description
            "Attributes";
          container inv-asset-bag {
            description
              "Inventory Asset Bag";
            uses INV-PHY-ENTITY-ASSET-INFO;
          }
          container inv-eeprom-info {
            description
              "Inventory EDM EEPROM info";
            uses INVMGR-EEPROM-OPAQUE-DATA;
          }
          container inv-basic-bag {
            description
              "Inventory Basic Bag";
            uses INV-PHY-ENTITY-BASIC-INFO;
          }
          container env-sensor-info {
            description
              "Environment sensor info";
            uses ENVMON-SENSOR-INFO;
          }
          container threshold {
            description
              "Temperature alarm data for platform
               components";
            container major-hi {
              description
                "Major High";
              uses THRESH-BAG;
            }
            container critical-hi {
              description
                "Critical High";
              uses THRESH-BAG;
            }
            container minor-lo {
              description
                "Minor Low";
              uses THRESH-BAG;
            }
            container major-lo {
              description
                "Major Low";
              uses THRESH-BAG;
            }
            container minor-hi {
              description
                "Minor High";
              uses THRESH-BAG;
            }
            container critical-lo {
              description
                "Critical Low";
              uses THRESH-BAG;
            }
          }
          container fru-info {
            description
              "Inventory Fru Bag";
            uses INV-CARD-FRU-INFO;
          }
          leaf pi-card-type {
            type uint32 {
              range "0..4294967295";
            }
            description
              "PI Card Type";
          }
          leaf node-id {
            type uint32 {
              range "0..4294967295";
            }
            description
              "Node ID Tuple";
          }
          leaf pd-card-type {
            type uint32 {
              range "0..4294967295";
            }
            description
              "PD Card Type";
          }
        }
        leaf name {
          type string;
          description
            "Entity name";
        }
      }
    }
  }
}
