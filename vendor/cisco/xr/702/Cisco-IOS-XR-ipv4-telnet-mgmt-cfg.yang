module Cisco-IOS-XR-ipv4-telnet-mgmt-cfg {
  namespace "http://cisco.com/ns/yang/Cisco-IOS-XR-ipv4-telnet-mgmt-cfg";
  prefix ipv4-telnet-mgmt-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-telnet-mgmt package configuration.
     
     This module contains definitions
     for the following management objects:
       telnet: Global Telnet configuration commands
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }
  revision 2015-10-30 {
    description
      "Descriptions updated.";
  }

  container telnet {
    description
      "Global Telnet configuration commands";
    container vrfs {
      description
        "VRF name for telnet service";
      list vrf {
        key "vrf-name";
        description
          "VRF name for telnet service";
        container ipv4 {
          description
            "IPv4 configuration";
          leaf dscp {
            type uint32 {
              range "0..63";
            }
            description
              "Specify the DSCP value";
          }
        }
        leaf vrf-name {
          type xr:Cisco-ios-xr-string;
          description
            "VRF name";
        }
      }
    }
  }
}
