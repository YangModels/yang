module Cisco-IOS-XR-um-mpls-lsd-cfg {
  namespace "http://cisco.com/ns/yang/Cisco-IOS-XR-um-mpls-lsd-cfg";
  prefix um-mpls-lsd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-lsd package configuration.
     
     This YANG module augments the
     modules with configuration data.
     
     Copyright (c) 2019 by Cisco Systems, Inc.
     All rights reserved.";

  revision 2019-10-10 {
    description
      "Removed unnecessary augments from the model";
    semver:module-version "1.0.1M";
  }
  revision 2019-06-10 {
    description
      "Establish semantic version baseline.";
    semver:module-version "1.0.0";
  }
  revision 2019-03-30 {
    description
      "Initial version";
  }

  container mpls {
    description
      "Global MPLS configuration subcommands";
    container ip-ttl-propagate {
      description
        "Propagate IP TTL into the label stack";
      container disable {
        must "not(local and forwarded)";
        presence "Indicates a disable node is configured.";
        description
          "Disable IP TTL propagation";
        container local {
          presence "Indicates a local node is configured.";
          description
            "Disable IP TTL propagation for only locally generated MPLS packets";
        }
        container forwarded {
          presence "Indicates a forwarded node is configured.";
          description
            "Disable IP TTL propagation for only forwarded MPLS packets";
        }
      }
    }
    container ipv6 {
      description
        "Configure IPv6 parameters";
      leaf ttl-expiration-pop {
        type uint32 {
          range "1..10" {
            description
              "Number of labels to pop on TTL expiry";
          }
        }
        description
          "Number of labels to pop when MPLS TTL expires";
      }
    }
    container ipv4 {
      description
        "Configure IPv4 parameters";
      leaf ttl-expiration-pop {
        type uint32 {
          range "1..10" {
            description
              "Number of labels to pop on TTL expiry";
          }
        }
        description
          "Number of labels to pop when MPLS TTL expires";
      }
    }
    container label {
      description
        "Label properties";
      container range {
        description
          "Label range";
        list table {
          key "table-index";
          description
            "Specify label table";
          leaf table-index {
            type uint32 {
              range "0" {
                description
                  "Label table index";
              }
            }
            description
              "Label table index";
          }
          leaf minimum-label {
            type uint32 {
              range "16000..1048575";
            }
            mandatory true;
            description
              "Manimum label value";
          }
          leaf maximum-label {
            type uint32 {
              range "16000..1048575";
            }
            mandatory true;
            description
              "Maximum label value";
          }
          container static {
            presence "Indicates a static node is configured.";
            description
              "Specify block of labels for static bindings";
            leaf minimum-label {
              type uint32 {
                range "16..1048575" {
                  description
                    "Minimum static label value";
                }
              }
              mandatory true;
              description
                "Specify block of labels for static bindings";
            }
            leaf maximum-label {
              type uint32 {
                range "16..1048575" {
                  description
                    "Maximum static label value";
                }
              }
              mandatory true;
              description
                "Maximum static label value";
            }
          }
        }
      }
    }
    container lsd {
      description
        "MPLS LSD process command";
      container ltrace-buffer {
        description
          "MPLS LSD LTrace buffer files";
        leaf multiplier {
          type uint32 {
            range "2..5" {
              description
                "Multiplier factor";
            }
          }
          description
            "Ltrace buffer file size multiplier";
        }
      }
      container app-reg-delay {
        description
          "Application registration delay";
        container disable {
          presence "Indicates a disable node is configured.";
          description
            "Disable delay for regular applications' registration";
        }
      }
    }
    container entropy-label {
      presence "Indicates a entropy-label node is configured.";
      description
        "Enable MPLS entropy label";
    }
  }
}
