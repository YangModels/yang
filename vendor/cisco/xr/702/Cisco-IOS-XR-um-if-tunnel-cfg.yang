module Cisco-IOS-XR-um-if-tunnel-cfg {
  namespace "http://cisco.com/ns/yang/Cisco-IOS-XR-um-if-tunnel-cfg";
  prefix um-if-tunnel-cfg;

  import cisco-semver {
    prefix semver;
  }
  import Cisco-IOS-XR-types {
    prefix xr;
  }
  import ietf-inet-types {
    prefix inet;
  }
  import Cisco-IOS-XR-um-interface-cfg {
    prefix a1;
  }
  import tailf-common {
    prefix tailf;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-tunnel package configuration.
     
     This YANG module augments the
     modules with configuration data.
     
     Copyright (c) 2019 by Cisco Systems, Inc.
     All rights reserved.";

  revision 2019-06-10 {
    description
      "Initial version";
    semver:module-version "1.0.0";
  }

  grouping GROUP-TUNNEL {
    container tunnel {
      when "../a1:interface-name[starts-with(text(),'tunnel-ip')]" {
        tailf:dependency "../a1:interface-name";
      }
      container source {
        description
          "Configure source of tunnel";
        leaf interface-name {
          type xr:Interface-name;
          must "not(../ipv6-address or ../ipv4-address)";
          description
            "Name of tunnel source interface";
        }
        leaf ipv6-address {
          type inet:ipv6-address-no-zone;
          must "not(../interface-name or ../ipv4-address)";
          description
            "IPV6 address of the tunnel source";
        }
        leaf ipv4-address {
          type inet:ipv4-address-no-zone;
          must "not(../interface-name or ../ipv6-address)";
          description
            "IPV4 address of the tunnel source";
        }
      }
      container destination {
        description
          "Configure destination of tunnel";
        leaf ipv4-address {
          type inet:ipv4-address-no-zone;
          must "not(../ipv6-address)";
          description
            "IPV4 address of the tunnel destination";
        }
        leaf length {
          type inet:ipv4-address-no-zone;
          must "../ipv4-address";
          description
            "IPv4 prefix length of the tunnel destination";
        }
        leaf ipv6-address {
          type inet:ipv6-address-no-zone;
          must "not(../ipv4-address)";
          description
            "IPV6 address of the tunnel destination";
        }
        leaf prefix-list {
          type xr:Cisco-ios-xr-string {
            length "1..64";
          }
          must "../ipv4-address or ../ipv6-address";
          description
            "Prefix-list to validate destination's resolving prefix";
        }
      }
    }
  }

  augment "/a1:interfaces/a1:interface" {
    uses GROUP-TUNNEL;
  }
  augment "/a1:interfaces/a1:interface-preconfigure" {
    uses GROUP-TUNNEL;
  }
}
