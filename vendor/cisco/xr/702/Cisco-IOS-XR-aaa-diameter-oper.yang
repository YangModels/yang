module Cisco-IOS-XR-aaa-diameter-oper {
  namespace "http://cisco.com/ns/yang/Cisco-IOS-XR-aaa-diameter-oper";
  prefix aaa-diameter-oper;

  import cisco-semver {
    prefix semver;
  }
  import Cisco-IOS-XR-aaa-locald-oper {
    prefix a1;
  }
  include Cisco-IOS-XR-aaa-diameter-oper-sub1 {
    revision-date 2019-09-26;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-diameter package operational data.
     
     This YANG module augments the
       Cisco-IOS-XR-aaa-locald-oper
     module with state data.
     
     Copyright (c) 2013-2019 by Cisco Systems, Inc.
     All rights reserved.";

  revision 2019-09-26 {
    description
      "Introduced a peer-closed-reason leaf and transaction related leaves in DIAMETER-SERVERBAG grouping.";
    semver:module-version "1.0.0";
  }
  revision 2019-04-05 {
    description
      "Establish semantic version baseline.";
    semver:module-version "1.0.0";
  }
  revision 2017-09-07 {
    description
      "Fixed type translation error.";
  }
  revision 2015-11-09 {
    description
      "IOS XR 6.0 revision.";
  }

  augment "/a1:aaa" {
    description
      "This augment extends the operational data of
       'Cisco-IOS-XR-aaa-locald-oper'";
    container diameter {
      description
        "Diameter operational data";
      container gy {
        description
          "Diameter global gy data";
        uses DIAMETER-GY;
      }
      container gx-statistics {
        description
          "Diameter Gx Statistics data";
        uses DIAMETER-GX-STATS;
      }
      container gx {
        description
          "Diameter global gx data";
        uses DIAMETER-GX;
      }
      container peers {
        description
          "Diameter peer global data";
        uses DIAMETER-PEERS;
      }
      container nas {
        description
          "Diameter NAS data";
        uses DIAMETER-NAS-LIST;
      }
      container nas-summary {
        description
          "Diameter NAS summary";
        uses DIAMETER-NAS-SUMMARY;
      }
      container gy-session-ids {
        description
          "Diameter Gy Session data list";
        list gy-session-id {
          key "session-id";
          description
            "Diameter Gy Session data";
          leaf session-id {
            type uint32;
            description
              "Session Id";
          }
          uses DIAMETER-GY-SESS;
        }
      }
      container gy-statistics {
        description
          "Diameter Gy Statistics data";
        uses DIAMETER-GY-STATS;
      }
      container gx-session-ids {
        description
          "Diameter Gx Session data list";
        list gx-session-id {
          key "session-id";
          description
            "Diameter Gx Session data";
          leaf session-id {
            type uint32;
            description
              "Session Id";
          }
          uses DIAMETER-GX-SESS;
        }
      }
      container nas-session {
        description
          "Diameter Nas Session data";
        uses DIAMETER-NAS-LIST;
      }
    }
  }
}
