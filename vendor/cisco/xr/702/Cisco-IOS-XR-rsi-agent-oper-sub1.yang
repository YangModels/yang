submodule Cisco-IOS-XR-rsi-agent-oper-sub1 {
  belongs-to Cisco-IOS-XR-rsi-agent-oper {
    prefix Cisco-IOS-XR-rsi-agent-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR rsi-agent package operational data.
     
     Copyright (c) 2013-2019 by Cisco Systems, Inc.
     All rights reserved.";

  revision 2019-08-14 {
    description
      "Fixing yang oper coverage
       2019-07-30
         Fixing yang oper coverage.";
    semver:module-version "1.0.1M";
  }
  revision 2019-04-05 {
    description
      "Establish semantic version baseline.";
    semver:module-version "1.0.0";
  }
  revision 2019-02-13 {
    description
      "Fixing yang oper coverage.";
  }
  revision 2018-11-26 {
    description
      "Fixing yang usability issues.";
  }
  revision 2018-01-24 {
    description
      "Fixed datatype issues";
  }
  revision 2018-01-11 {
    description
      "Add rsip node into schema.";
  }
  revision 2017-09-07 {
    description
      "Fixed type translation error.";
  }
  revision 2015-11-09 {
    description
      "IOS XR 6.0 revision.";
  }

  typedef Ra-edm-tbl-attr {
    type enumeration {
      enum "ra-edm-tbl-attr-flow-spec" {
        value 0;
        description
          "Flowspec";
      }
      enum "ra-edm-tbl-attr-max" {
        value 1;
        description
          "None";
      }
    }
    description
      "Attribute type";
  }

  typedef Rsi-vr-id {
    type uint32;
    description
      "Rsi vr id";
  }

  typedef Rsi-vrf-id {
    type uint32;
    description
      "Rsi vrf id";
  }

  typedef Rsi-safi {
    type enumeration {
      enum "mgmt-rsi-safi-ucast" {
        value 1;
        description
          "Unicast";
      }
      enum "mgmt-rsi-safi-mcast" {
        value 2;
        description
          "Multicast";
      }
      enum "mgmt-rsi-safi-flow-spec" {
        value 133;
        description
          "Flowspec";
      }
    }
    description
      "RSI SAFI type";
  }

  typedef Rsi-afi {
    type enumeration {
      enum "mgmt-rsi-afi-ipv4" {
        value 1;
        description
          "IPv4";
      }
      enum "mgmt-rsi-afi-ipv6" {
        value 2;
        description
          "IPv6";
      }
    }
    description
      "RSI AFI type";
  }

  typedef Rsi-tbl-id {
    type uint32;
    description
      "Rsi tbl id";
  }

  typedef Rsi-role-type-et {
    type enumeration {
      enum "role-type-invalid" {
        value 0;
        description
          "Invalid Role";
      }
      enum "role-type-standard" {
        value 1;
        description
          "Operating in Standard Role";
      }
      enum "role-type-core" {
        value 2;
        description
          "Operating in Core Role";
      }
      enum "role-type-cust" {
        value 3;
        description
          "Operating in Customer Role";
      }
      enum "role-type-no-interest" {
        value 4;
        description
          "Operating in not-interested Role";
      }
      enum "role-type-vpn-only-cust" {
        value 5;
        description
          "Operating in VPN Only Customer Role";
      }
    }
    description
      "Role type";
  }

  grouping RA-NOTIF-REG-BY-INTF {
    description
      "Registrations for RSI agent notification by
       Interface";
    leaf mdb-type {
      type uint32;
      description
        "Type of MDB";
    }
    leaf reg-hd {
      type uint64;
      description
        "HD registered";
    }
    leaf num-notifs-dispatched {
      type uint32;
      description
        "Notifications dispatched";
    }
    leaf ifname {
      type string;
      description
        "Interface name";
    }
    leaf ifhandle {
      type xr:Interface-name;
      description
        "Interface handle";
    }
    leaf address-family-indicator-filter {
      type uint32;
      description
        "AFI filter";
    }
    leaf subsequent-address-family-indicator-filter {
      type uint32;
      description
        "SAFI filter";
    }
    leaf table-name {
      type string;
      description
        "Name of table";
    }
    leaf global {
      type boolean;
      description
        "Global interface";
    }
    leaf reg-flags {
      type uint32;
      description
        "Registration flags";
    }
  }

  grouping RA-NOTIF-REG-BY-TBL {
    description
      "Registrations for RSI agent notification by Table";
    leaf mdb-type {
      type uint32;
      description
        "Type of MDB";
    }
    leaf reg-hd {
      type uint64;
      description
        "HD registered";
    }
    leaf num-notifs-dispatched {
      type uint32;
      description
        "Notifications dispatched";
    }
    leaf table-name {
      type string;
      description
        "Name of table";
    }
    leaf table-id {
      type Rsi-tbl-id;
      description
        "Identification of table";
    }
  }

  grouping RA-NOTIF-REG-BY-VPN {
    description
      "Registrations for RSI agent notification by VPN";
    container vpn-id {
      description
        "Identification of VPN";
      uses RSI-VPNID;
    }
    leaf mdb-type {
      type uint32;
      description
        "Type of MDB";
    }
    leaf reg-hd {
      type uint64;
      description
        "HD registered";
    }
    leaf num-notifs-dispatched {
      type uint32;
      description
        "Notifications dispatched";
    }
  }

  grouping RA-NOTIF-REG-BY-VRF {
    description
      "Registrations for RSI agent notification by VRF";
    leaf mdb-type {
      type uint32;
      description
        "Type of MDB";
    }
    leaf reg-hd {
      type uint64;
      description
        "HD registered";
    }
    leaf num-notifs-dispatched {
      type uint32;
      description
        "Notifications dispatched";
    }
    leaf vrf-name {
      type string;
      description
        "Name of VRF";
    }
    leaf vrf-id {
      type uint32;
      description
        "Identification of VRF";
    }
  }

  grouping RA-NOTIF-REG-BY-VR {
    description
      "Registrations for RSI agent notification by VR";
    leaf mdb-type {
      type uint32;
      description
        "Type of MDB";
    }
    leaf reg-hd {
      type uint64;
      description
        "HD registered";
    }
    leaf num-notifs-dispatched {
      type uint32;
      description
        "Notifications dispatched";
    }
    leaf vr-name {
      type string;
      description
        "Name of VR";
    }
    leaf vr-id {
      type uint32;
      description
        "Identification of VR";
    }
    leaf flags {
      type uint32;
      description
        "VR flags";
    }
  }

  grouping RA-NOTIF-REG-BY-STATE {
    description
      "Registrations for RSI agent notification by state";
    leaf mdb-type {
      type uint32;
      description
        "Type of MDB";
    }
    leaf reg-hd {
      type uint64;
      description
        "HD registered";
    }
    leaf num-notifs-dispatched {
      type uint32;
      description
        "Notifications dispatched";
    }
    leaf state-id {
      type uint64;
      description
        "State Identification";
    }
  }

  grouping RA-NOTIF-REG-ALL {
    description
      "All registrations for RSI agent notification";
    leaf mdb-type {
      type uint32;
      description
        "Type of MDB";
    }
    leaf reg-hd {
      type uint64;
      description
        "HD registered";
    }
    leaf num-notifs-dispatched {
      type uint32;
      description
        "Notifications dispatched";
    }
    leaf flags {
      type uint32;
      description
        "Notification flags";
    }
  }

  grouping RSI-AGENT-CLIENT {
    description
      "Client for RSI agent";
    leaf name {
      type string;
      description
        "Client Name";
    }
    leaf client-ptr {
      type uint64;
      description
        "Pointer to client";
    }
    leaf client-type {
      type uint32;
      description
        "Type of client";
    }
    leaf zombied {
      type boolean;
      description
        "Zombie flag";
    }
    leaf mdbs-processed {
      type uint32;
      description
        "MDBS state";
    }
    leaf msgs-received {
      type uint32;
      description
        "Message count";
    }
    leaf num-lookups-done {
      type uint32;
      description
        "Total lookups";
    }
    leaf num-failed-lookups {
      type uint32;
      description
        "Lookups failed";
    }
    leaf num-failed-regs {
      type uint32;
      description
        "Registrations failed";
    }
    leaf num-auto-purges {
      type uint32;
      description
        "Purge count";
    }
    leaf num-small-reply-buf {
      type uint32;
      description
        "Reply buffer count";
    }
    leaf proc-name {
      type string;
      description
        "";
    }
    leaf pid {
      type uint32;
      description
        "Process ID";
    }
    leaf scoid {
      type int32;
      description
        "Server Connection ID";
    }
    leaf coid {
      type int32;
      description
        "Connection ID";
    }
    leaf up-time-secs {
      type uint32;
      description
        "connected time in sec";
    }
    leaf zombie-secs {
      type uint32;
      description
        "Zombie for sec";
    }
    leaf last-rx-msg-type {
      type uint32;
      description
        "RX message type";
    }
    leaf pulse-count {
      type uint32;
      description
        "Number of pulse";
    }
    leaf async-q-size {
      type uint32;
      description
        "Size of asynchronous queue";
    }
    leaf async-q-size-max {
      type uint32;
      description
        "Max size of asynchronous queue";
    }
    leaf sync-items-returned {
      type uint32;
      description
        "Items returned Synchronously";
    }
    leaf async-items-returned {
      type uint32;
      description
        "Items returned Asynchronously";
    }
    leaf batch-enabled {
      type boolean;
      description
        "Batch enable flag";
    }
    leaf batch-size {
      type uint32;
      description
        "Size of batch";
    }
    leaf num-active-regs {
      type uint32;
      description
        "Active registrations count";
    }
    leaf num-owned-objs-tdl {
      type uint32;
      description
        "TDLs owned by producer client";
    }
    list by-all {
      description
        "Notif registration by all";
      uses RA-NOTIF-REG-ALL;
    }
    list by-state {
      description
        "Notif registration by state";
      uses RA-NOTIF-REG-BY-STATE;
    }
    list by-vr {
      description
        "Notif registration by VR";
      uses RA-NOTIF-REG-BY-VR;
    }
    list by-vrf {
      description
        "Notif registration by VRF";
      uses RA-NOTIF-REG-BY-VRF;
    }
    list by-vpn {
      description
        "Notif registration by VPN";
      uses RA-NOTIF-REG-BY-VPN;
    }
    list by-table {
      description
        "Notif registration by table";
      uses RA-NOTIF-REG-BY-TBL;
    }
    list by-intf {
      description
        "Notif registration by interface";
      uses RA-NOTIF-REG-BY-INTF;
    }
    list local-table-buf {
      description
        "LTBLs owned by producer client";
      leaf entry {
        type Rsi-tbl-id;
        description
          "LTBLs owned by producer client";
      }
    }
  }

  grouping RSI-AGENT-STATE {
    description
      "State for RSI agent";
    leaf state-id {
      type uint32;
      description
        "Agent state ID";
    }
    leaf state-val {
      type uint32;
      description
        "Agent state value";
    }
    leaf svd-is-enabled {
      type uint32;
      description
        "SVD state";
    }
    leaf intf-caps-v4-count {
      type uint32;
      description
        "IPV4 caps count for Interface";
    }
    leaf intf-caps-v6-count {
      type uint32;
      description
        "IPV6 caps count for Interface";
    }
    leaf vrf-intf-caps-v4-count {
      type uint32;
      description
        "IPV4 caps count for Interface VRF";
    }
    leaf vrf-intf-caps-v6-count {
      type uint32;
      description
        "IPV6 caps count for Interface VRF";
    }
    list state-ctx {
      description
        "Context for state";
      leaf entry {
        type uint32;
        description
          "Context for state";
      }
    }
  }

  grouping RSI-AGENT-TBL-REF {
    description
      "Table reference for RSI agent";
    leaf vrf-table-id {
      type uint32;
      description
        "VRF Table Index";
    }
    leaf address-family-indicator {
      type Rsi-afi;
      description
        "AFI";
    }
    leaf subsequent-address-family-indicator {
      type Rsi-safi;
      description
        "SAFI";
    }
    leaf table-name {
      type string;
      description
        "Table Name";
    }
  }

  grouping RSI-VPNID {
    description
      "VPN ID for RSI";
    leaf oui {
      type uint32;
      description
        "VPNID OUI";
    }
    leaf index {
      type uint32;
      description
        "VPNID Index";
    }
  }

  grouping RSI-AGENT-VRF {
    description
      "VRF for RSI agent";
    container vpn-id {
      description
        "VPN ID";
      uses RSI-VPNID;
    }
    leaf vrf-name {
      type string;
      description
        "VRF Name";
    }
    leaf vrf-id {
      type uint32;
      description
        "VRF ID";
    }
    leaf vr-id {
      type uint32;
      description
        "VR ID";
    }
    leaf submode-flag {
      type uint32;
      description
        "Sub_mode Flag";
    }
    leaf fallback-vrf-name {
      type string;
      description
        "Fallback VRF_Name";
    }
    leaf vr-name {
      type string;
      description
        "VR Name";
    }
    leaf refcount {
      type int32;
      description
        "Reference count";
    }
    leaf intf-count-local {
      type int32;
      description
        "Locally significant Intf Count";
    }
    leaf intf-count-global {
      type int32;
      description
        "Total Interfaces";
    }
    leaf num-real-tbls {
      type int32;
      description
        "Tbl Count";
    }
    leaf num-fwd-ref-tbls {
      type int32;
      description
        "Fwd Ref Tbl Count";
    }
    leaf vrf-by-vrf-id-regs {
      type int32;
      description
        "vrf by vrf id registration count";
    }
    leaf vrf-by-vrf-name-regs {
      type int32;
      description
        "vrf by vrf name registration count";
    }
    leaf table-by-vrf-regs {
      type int32;
      description
        "table by vrf registration count";
    }
    leaf table-by-vrf-name-regs {
      type int32;
      description
        "table by vrf name registration count";
    }
    leaf vrf-flags {
      type uint32;
      description
        "VRF Flags";
    }
    leaf intf-cnt-local {
      type uint32;
      description
        "Local Intf Count";
    }
    leaf vrf-groups {
      type uint32;
      description
        "Number of VRF groups";
    }
    leaf parentvrf-cnt {
      type uint32;
      description
        "Number of parent VRF";
    }
    list table-array {
      description
        "Array of tables in VRF";
      uses RSI-AGENT-TBL-REF;
    }
  }

  grouping RSI-AGENT-TBL-ATTR {
    description
      "RSI AGENT TBL ATTR";
    leaf flags {
      type uint32;
      description
        "Attribute flags";
    }
    leaf type {
      type Ra-edm-tbl-attr;
      description
        "Attribute type";
    }
    leaf length {
      type uint32;
      description
        "Attribute data length";
    }
    leaf data {
      type uint64;
      description
        "Attribute data";
    }
  }

  grouping RSI-AGENT-TBL {
    description
      "RSI AGENT TBL";
    leaf tbl-name {
      type string;
      description
        "Table Name";
    }
    leaf tbl-id {
      type Rsi-tbl-id;
      description
        "Table ID";
    }
    leaf vrf-id {
      type uint32;
      description
        "VRF ID";
    }
    leaf vrf-name {
      type string;
      description
        "VRF Name";
    }
    leaf vr-id {
      type uint32;
      description
        "VR ID";
    }
    leaf vr-name {
      type string;
      description
        "VR Name";
    }
    leaf afi {
      type Rsi-afi;
      description
        "AFI";
    }
    leaf safi {
      type Rsi-safi;
      description
        "SAFI";
    }
    leaf refcount {
      type int32;
      description
        "Reference Count";
    }
    leaf flags {
      type uint32;
      description
        "Flags";
    }
    leaf lst-flags {
      type uint32;
      description
        "LST Flags";
    }
    leaf tbl-by-tbl-id-regs {
      type int32;
      description
        "Table Reg by Table ID";
    }
    leaf vrf-tbl-idx {
      type uint32;
      description
        "VRF Table Index";
    }
    leaf tcm-idx {
      type uint32;
      description
        "TCM Index";
    }
    list attr {
      description
        "Table attribute inforamtion";
      uses RSI-AGENT-TBL-ATTR;
    }
  }

  grouping RSI-AGENT-TDL-INFO {
    description
      "RSI AGENT TDL INFO";
    leaf tbl-id {
      type Rsi-tbl-id;
      description
        "Table ID";
    }
    leaf vrf-name {
      type string;
      description
        "VRF Name";
    }
    leaf tdl-type {
      type uint32;
      description
        "TDL Type";
    }
    leaf owner-ctx {
      type uint64;
      description
        "Owner Context";
    }
  }

  grouping RSI-AGENT-TBL-TDL {
    description
      "RSI AGENT TBL TDL";
    container dependant {
      description
        "Dependant Table";
      uses RSI-AGENT-TBL-INFO;
    }
    leaf num-tdl {
      type uint32;
      description
        "Num TDL in Array";
    }
    list tdl-array {
      description
        "TDL Array";
      uses RSI-AGENT-TDL-INFO;
    }
  }

  grouping RSI-AGENT-INTF {
    description
      "RSI agent interface";
    leaf ifhandle {
      type xr:Interface-name;
      description
        "Interface by handle";
    }
    leaf ifname {
      type string;
      description
        "Name of the interface";
    }
    leaf vrf-id {
      type Rsi-vrf-id;
      description
        "VRF ID";
    }
    leaf vrf-name {
      type string;
      description
        "VRF Name";
    }
    leaf vr-id {
      type Rsi-vr-id;
      description
        "VR ID";
    }
    leaf vr-name {
      type string;
      description
        "VR Name";
    }
    leaf is-virtual {
      type boolean;
      description
        "Virtual";
    }
    leaf is-local {
      type boolean;
      description
        "Local";
    }
    leaf is-licensed {
      type boolean;
      description
        "Licensed";
    }
    leaf flags {
      type uint32;
      description
        "Flag value";
    }
    leaf refcount {
      type int32;
      description
        "Reference count";
    }
    leaf intf-by-ifh-regs {
      type int32;
      description
        "Registered Interface by ifhandle";
    }
    leaf interface-table-by-ifh {
      type int32;
      description
        "Registered Table by interface handle";
    }
    list ra-table-set {
      description
        "RSI agent tables";
      leaf entry {
        type uint8;
        description
          "RSI agent tables";
      }
    }
  }

  grouping RSI-AGENT-REQ-DEP-TBL-INFO {
    description
      "RSI AGENT REQ DEP TBL INFO";
    leaf tbl-name {
      type string;
      description
        "Table Name";
    }
    leaf tbl-id {
      type Rsi-tbl-id;
      description
        "Table ID";
    }
    leaf vrf-id {
      type uint32;
      description
        "VRF ID";
    }
    leaf vrf-name {
      type string;
      description
        "VRF Name";
    }
    leaf lst-flags {
      type uint32;
      description
        "LST Flags";
    }
  }

  grouping RSI-AGENT-TBL-INFO {
    description
      "RSI AGENT TBL INFO";
    leaf tbl-name {
      type string;
      description
        "Table Name";
    }
    leaf tbl-id {
      type Rsi-tbl-id;
      description
        "Table ID";
    }
    leaf vrf-id {
      type uint32;
      description
        "VRF ID";
    }
    leaf vrf-name {
      type string;
      description
        "VRF Name";
    }
    leaf vr-id {
      type uint32;
      description
        "VR ID";
    }
    leaf vr-name {
      type string;
      description
        "VR Name";
    }
    leaf afi {
      type Rsi-afi;
      description
        "AFI";
    }
    leaf safi {
      type Rsi-safi;
      description
        "SAFI";
    }
  }

  grouping RSI-AGENT-TBL-REQ-DEP {
    description
      "RSI AGENT TBL REQ DEP";
    container show-tbl {
      description
        "Show Table";
      uses RSI-AGENT-TBL-INFO;
    }
    list tbl-array {
      description
        "Depedent TBL Array";
      uses RSI-AGENT-REQ-DEP-TBL-INFO;
    }
  }

  grouping RSI-AGENT-PROD {
    description
      "RSI agent producer";
    leaf item-id {
      type uint32;
      description
        "Item identification";
    }
    leaf name {
      type string;
      description
        "Producer name";
    }
    leaf flags {
      type uint32;
      description
        "Producer flags";
    }
    leaf num-owned-objs-vr {
      type uint32;
      description
        "Number Owned Objects VR";
    }
    leaf num-owned-objs-vrf {
      type uint32;
      description
        "Number Owned Objects VRF";
    }
    leaf num-owned-objs-table {
      type uint32;
      description
        "Number Owned Object Table";
    }
    leaf num-owned-objs-intf {
      type uint32;
      description
        "Number Owned Objects Interface";
    }
    leaf num-owned-objs-tdl {
      type uint32;
      description
        "Number Owned Objects TDL";
    }
    leaf num-saved-msgs {
      type uint32;
      description
        "Number Saved Messages";
    }
  }

  grouping RA-ROLE {
    description
      "RA ROLE";
    leaf afi-role {
      type Rsi-role-type-et;
      description
        "Address Family Identifier role";
    }
    leaf time {
      type uint64;
      description
        "Time of role change";
    }
    leaf rolecalctype {
      type uint32;
      description
        "Role calculated type";
    }
    leaf eod {
      type boolean;
      description
        "End of download status";
    }
  }

  grouping RSI-AGENT-ROLE {
    description
      "RSI AGENT ROLE";
    container afi-v4-role {
      description
        "AFI v4 role";
      uses RA-ROLE;
    }
    container afi-v6-role {
      description
        "AFI v6 role";
      uses RA-ROLE;
    }
    leaf converged-v4 {
      type uint32;
      description
        "Is v4 role converged";
    }
    leaf converged-v6 {
      type uint32;
      description
        "Is v6 role converged";
    }
    leaf afi-v4-role-change-num {
      type uint32;
      description
        "Num of Role change v4";
    }
    leaf afi-v6-role-change-num {
      type uint32;
      description
        "Num of Role change v6";
    }
    list afi-v4-role-history {
      description
        "Role history v4";
      uses RA-ROLE;
    }
    list afi-v6-role-history {
      description
        "Role history v6";
      uses RA-ROLE;
    }
  }

  grouping RSI-AGENT-VR {
    description
      "VR for RSI agent";
    leaf vr-name-xr {
      type string;
      description
        "VR Name";
    }
    leaf vr-id {
      type uint32;
      description
        "VR ID";
    }
    leaf refcount {
      type int32;
      description
        "Reference count";
    }
    leaf num-real-vrfs {
      type int32;
      description
        "Number of real vrfs";
    }
    leaf num-fwd-ref-vrfs {
      type int32;
      description
        "Fwd ref vrfs";
    }
    leaf vr-by-vr-id-regs {
      type int32;
      description
        "vr by vr id registrations";
    }
    leaf vr-by-vr-name-regs {
      type int32;
      description
        "vr by vr name registrations";
    }
    leaf vrf-by-vr-regs {
      type int32;
      description
        "vrf by vr registrations";
    }
    leaf table-by-vr-regs {
      type int32;
      description
        "table by vr registrations";
    }
    leaf vrf-cnt-local {
      type int32;
      description
        "vrf count";
    }
  }
}
