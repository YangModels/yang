module Cisco-IOS-XR-subscriber-ipsub-cfg {
  namespace "http://cisco.com/ns/yang/Cisco-IOS-XR-subscriber-ipsub-cfg";
  prefix subscriber-ipsub-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-ipsub package configuration.
     
     This YANG module augments the
       Cisco-IOS-XR-ifmgr-cfg
     module with configuration data.
     
     Copyright (c) 2013-2019 by Cisco Systems, Inc.
     All rights reserved.";

  revision 2019-10-31 {
    description
      "Added mandatory nodes.";
    semver:module-version "1.0.1M";
  }
  revision 2019-04-05 {
    description
      "Establish semantic version baseline.";
    semver:module-version "1.0.0";
  }
  revision 2017-09-07 {
    description
      "Fixed type translation error.";
  }
  revision 2015-11-09 {
    description
      "IOS XR 6.0 revision.";
  }

  augment "/a1:interface-configurations/a1:interface-configuration" {
    description
      "This augment extends the configuration data of
       'Cisco-IOS-XR-ifmgr-cfg'";
    container subscriber {
      description
        "Subscribers on interface";
      container ip-subscriber {
        description
          "IP subscribers on interface";
        container ipv4 {
          description
            "IPv4 subscriber";
          container l2-connected {
            description
              "L2 connected IPv4 subscriber";
            container initiator {
              description
                "Configure IP subscriber initiator";
              container unclassified-source-fsol {
                presence "Indicates a unclassified-source-fsol node is configured.";
                description
                  "Configure IP subscriber unclassified source
                   initiator";
                leaf enable {
                  type empty;
                  mandatory true;
                  description
                    "Enable unclassified source";
                }
                leaf address-unique {
                  type boolean;
                  mandatory true;
                  description
                    "Check for subscriber IP uniqueness during
                     first sign of life";
                }
              }
              leaf dhcp {
                type empty;
                description
                  "Configure IP subscriber DHCP initiator";
              }
            }
          }
          container routed {
            description
              "Routed IPv4 subscriber";
            container initiator {
              description
                "Configure IP subscriber initiator";
              leaf unclassified-ip {
                type empty;
                description
                  "Configure IPv4 subscriber unclassified
                   source initiator";
              }
              leaf dhcp {
                type empty;
                description
                  "Configure IPv4 subscriber DHCP initiator";
              }
              leaf dhcp-snoop {
                type empty;
                description
                  "Configure IPv4 subscriber DHCP Snoop
                   initiator";
              }
            }
          }
        }
        container session-limit {
          description
            "IP subscriber session limit";
          container total {
            description
              "Session limit for all sources";
            leaf per-vlan {
              type uint32;
              default "0";
              description
                "Configure per-vlan session limit for all
                 sources";
            }
          }
          container unclassified-source {
            description
              "Session limit for unclassified sources";
            leaf per-vlan {
              type uint32;
              default "0";
              description
                "Configure per-vlan session limit for
                 unclassified sources";
            }
          }
        }
        container ipv6 {
          description
            "IPv6 subscriber";
          container l2-connected {
            description
              "L2 connected IPv6 subscriber";
            container initiator {
              description
                "Configure IPv6 subscriber initiator";
              container unclassified-source-fsol {
                presence "Indicates a unclassified-source-fsol node is configured.";
                description
                  "Configure IP subscriber unclassified source
                   initiator";
                leaf enable {
                  type empty;
                  mandatory true;
                  description
                    "Enable unclassified source";
                }
                leaf address-unique {
                  type boolean;
                  mandatory true;
                  description
                    "Check for subscriber IP uniqueness during
                     first sign of life";
                }
              }
              leaf dhcp {
                type empty;
                description
                  "Configure IPv6 subscriber DHCP initiator";
              }
            }
          }
          container routed {
            description
              "Routed IPv6 subscriber";
            container initiator {
              description
                "Configure IP subscriber initiator";
              leaf unclassified-ip {
                type uint32 {
                  range "1..128";
                }
                default "128";
                description
                  "Configure unclassified packets as
                   first-sign-of-life for IPv6 subscriber";
              }
              leaf dhcp {
                type uint32 {
                  range "1..128";
                }
                default "128";
                description
                  "Configure IPv6 subscriber DHCP initiator";
              }
              leaf dhcp-snoop {
                type uint32 {
                  range "1..128";
                }
                default "128";
                description
                  "Configure IPv6 subscriber DHCP Snoop
                   initiator";
              }
            }
          }
        }
        leaf subscriber-templates {
          type uint32 {
            range "1..10";
          }
          default "10";
          description
            "Enable subscriber templates on this access
             interface";
        }
        leaf interface {
          type empty;
          description
            "Enable IP Static subscriber";
        }
      }
    }
  }
}
