module Cisco-IOS-XR-aaa-locald-admin-cfg {
  namespace "http://cisco.com/ns/yang/Cisco-IOS-XR-aaa-locald-admin-cfg";
  prefix aaa-locald-admin-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-locald package admin-plane configuration.
     
     This module contains definitions
     for the following management objects:
       aaa: Admin plane AAA configuration
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Aaa-admin-password {
    type enumeration {
      enum "type5" {
        value 5;
        description
          "Type 5 password";
      }
      enum "type8" {
        value 8;
        description
          "Type 8 password";
      }
      enum "type9" {
        value 9;
        description
          "Type 9 password";
      }
    }
    description
      "Aaa admin password";
  }

  container aaa {
    description
      "Admin plane AAA configuration";
    container usernames {
      description
        "Configure local username";
      list username {
        key "name";
        description
          "Admin Username";
        container usergroup-under-usernames {
          description
            "Specify the usergroup to which this admin user
             belongs";
          list usergroup-under-username {
            key "name";
            description
              "Name of the usergroup";
            leaf name {
              type xr:Cisco-ios-xr-string;
              description
                "Name of the usergroup";
            }
          }
        }
        container secret {
          description
            "Specify the secret for the admin user";
          leaf type {
            type Aaa-admin-password;
            description
              "Password type";
          }
          leaf secret5 {
            when "../type = 'type5'" {
              description
                "../Type = Type5";
            }
            type xr:Md5-password;
            description
              "The user's secret password";
          }
          leaf secret8 {
            when "../type = 'type8'" {
              description
                "../Type = Type8";
            }
            type xr:Type8-password;
            description
              "Type 8 password";
          }
          leaf secret9 {
            when "../type = 'type9'" {
              description
                "../Type = Type9";
            }
            type xr:Type9-password;
            description
              "Type 9 password";
          }
        }
        leaf name {
          type string;
          description
            "Username";
        }
      }
    }
  }
}
