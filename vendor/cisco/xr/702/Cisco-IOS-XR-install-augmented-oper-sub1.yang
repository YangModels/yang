submodule Cisco-IOS-XR-install-augmented-oper-sub1 {
  belongs-to Cisco-IOS-XR-install-augmented-oper {
    prefix Cisco-IOS-XR-install-augmented-oper;
  }

  import cisco-semver {
    prefix semver;
  }
  include Cisco-IOS-XR-install-augmented-oper-sub2 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR install-augmented package operational data.
     
     Copyright (c) 2013-2019 by Cisco Systems, Inc.
     All rights reserved.";

  revision 2019-04-05 {
    description
      "Establish semantic version baseline.";
    semver:module-version "1.0.1m";
  }
  revision 2015-11-09 {
    description
      "IOS XR 6.0 revision.";
  }

  typedef Inst-action {
    type enumeration {
      enum "install-package-add" {
        value 10;
        description
          "Package add";
      }
      enum "install-package-remove" {
        value 11;
        description
          "Package remove";
      }
      enum "install-package-upgrade" {
        value 12;
        description
          "Package upgrade";
      }
      enum "install-package-downgrade" {
        value 13;
        description
          "Package downgrade";
      }
      enum "install-package-replace" {
        value 14;
        description
          "Package replace";
      }
      enum "install-package-rollback" {
        value 15;
        description
          "Rollback";
      }
      enum "install-package-abort-latest" {
        value 20;
        description
          "Package abort latest";
      }
      enum "install-package-abort-all-since-apply" {
        value 21;
        description
          "Package abort all since apply";
      }
      enum "install-apply-restart" {
        value 30;
        description
          "Apply by process restart";
      }
      enum "install-apply-reload" {
        value 31;
        description
          "Apply by reload";
      }
      enum "install-commit" {
        value 40;
        description
          "Commit";
      }
    }
    description
      "Inst action";
  }

  typedef Inst-notif-phase {
    type enumeration {
      enum "veto" {
        value 0;
        description
          "Veto";
      }
      enum "prepare" {
        value 1;
        description
          "Prepare";
      }
      enum "pre-pre-apply" {
        value 2;
        description
          "Pre pre apply";
      }
      enum "pre-apply" {
        value 3;
        description
          "Pre apply";
      }
      enum "apply" {
        value 4;
        description
          "Apply";
      }
      enum "post-apply" {
        value 5;
        description
          "Post apply";
      }
      enum "post-post-apply" {
        value 6;
        description
          "Post post apply";
      }
    }
    description
      "Install notification phase type";
  }

  typedef Inst-pkg-op-stage {
    type enumeration {
      enum "not-started" {
        value 0;
        description
          "No operation has yet begun";
      }
      enum "preamble" {
        value 1;
        description
          "Preamble, including loading plugins";
      }
      enum "resolving-dependencies" {
        value 2;
        description
          "Resolving dependencies";
      }
      enum "transaction-check" {
        value 3;
        description
          "Package downloads and transaction check";
      }
      enum "package-operations" {
        value 4;
        description
          "Package operations - installations and removals";
      }
      enum "complete" {
        value 5;
        description
          "Operation has finished. This does not imply
           success";
      }
    }
    description
      "Inst pkg op stage";
  }

  typedef Inst-node-req {
    type enumeration {
      enum "veto-check" {
        value 0;
        description
          "Veto check";
      }
      enum "begin-trans" {
        value 1;
        description
          "Begin transaction";
      }
      enum "end-trans" {
        value 2;
        description
          "End transaction";
      }
      enum "abort-trans" {
        value 3;
        description
          "Abort transaction";
      }
      enum "begin-atomic" {
        value 4;
        description
          "Begin atomic operation";
      }
      enum "abort-atomic" {
        value 5;
        description
          "Abort atomic operation";
      }
      enum "pkg-install" {
        value 6;
        description
          "Package install operation";
      }
      enum "pkg-replace" {
        value 7;
        description
          "Package replace operation";
      }
      enum "undo-pkg-install" {
        value 8;
        description
          "Undo package install or undo other package
           operation";
      }
      enum "apply-reload" {
        value 9;
        description
          "Apply by reload";
      }
      enum "pre-pre-apply-restart" {
        value 10;
        description
          "Pre-pre-apply by restarting processes";
      }
      enum "pre-apply-restart" {
        value 11;
        description
          "Pre-apply by restarting processes";
      }
      enum "apply-and-post-apply-restart" {
        value 12;
        description
          "Apply and post-apply by restarting processes";
      }
      enum "post-post-apply-restart" {
        value 13;
        description
          "Post-post-apply by restarting processes";
      }
      enum "restart-infra" {
        value 14;
        description
          "Restart install infra";
      }
      enum "abort-op" {
        value 15;
        description
          "Abort current operation";
      }
      enum "node-idle" {
        value 16;
        description
          "Node is not handling a request";
      }
      enum "status-unknown" {
        value 17;
        description
          "The node did not respond to the operational
           data request";
      }
    }
    description
      "Install node request type";
  }

  typedef Inst-activity {
    type enumeration {
      enum "initiate-op" {
        value 0;
        description
          "Initiate operation";
      }
      enum "begin-trans" {
        value 1;
        description
          "Begin transaction";
      }
      enum "begin-atomic" {
        value 2;
        description
          "Begin atomic operation";
      }
      enum "veto-check" {
        value 3;
        description
          "Veto check";
      }
      enum "pkg-install" {
        value 4;
        description
          "Package add or other package operation";
      }
      enum "apply-reload" {
        value 5;
        description
          "Apply by reload";
      }
      enum "apply-restart" {
        value 6;
        description
          "Apply by restarting processes";
      }
      enum "restart-infra" {
        value 7;
        description
          "Restart install infra";
      }
      enum "commit-trans" {
        value 8;
        description
          "Commit transaction";
      }
      enum "abort-op" {
        value 9;
        description
          "Abort operation";
      }
      enum "abort-trans" {
        value 10;
        description
          "Abort transaction";
      }
      enum "abort-atomic" {
        value 11;
        description
          "Abort atomic operation";
      }
      enum "undo-pkg-inst" {
        value 12;
        description
          "Undo package install";
      }
      enum "await-user-input" {
        value 13;
        description
          "Await user input";
      }
      enum "await-recovery-input" {
        value 14;
        description
          "Failure, await user recovery input";
      }
      enum "trans-complete" {
        value 15;
        description
          "Transaction complete";
      }
      enum "no-op-in-progress" {
        value 16;
        description
          "No install operation in progress";
      }
    }
    description
      "Install activity type";
  }

  typedef Install-opt-string {
    type string;
    description
      "Install opt string";
  }

  typedef Inst-atomic-status {
    type enumeration {
      enum "in-progress" {
        value 0;
        description
          "In progress";
      }
      enum "apply-in-progress" {
        value 1;
        description
          "Apply in progress";
      }
      enum "success" {
        value 2;
        description
          "Success";
      }
      enum "failure" {
        value 3;
        description
          "Failure";
      }
      enum "aborting" {
        value 4;
        description
          "Aborting";
      }
      enum "aborted" {
        value 5;
        description
          "Aborted";
      }
    }
    description
      "Atomic change status type";
  }

  typedef Inst-pkg-op-status {
    type enumeration {
      enum "in-progress" {
        value 0;
        description
          "In progress";
      }
      enum "success" {
        value 1;
        description
          "Success";
      }
      enum "failure" {
        value 2;
        description
          "Failure";
      }
      enum "aborted" {
        value 3;
        description
          "Aborted";
      }
    }
    description
      "Package operation status type";
  }

  typedef Inst-req-reason {
    type enumeration {
      enum "user" {
        value 0;
        description
          "User request";
      }
      enum "undoing-due-to-abort" {
        value 1;
        description
          "Undoing previous package operation due to user
           request";
      }
    }
    description
      "Install request reason type";
  }

  typedef Inst-notif-res {
    type enumeration {
      enum "awaiting-response" {
        value 0;
        description
          "Awaiting response";
      }
      enum "success" {
        value 1;
        description
          "Success";
      }
      enum "veto-req" {
        value 2;
        description
          "Veto requested";
      }
      enum "reload-req" {
        value 3;
        description
          "Reload requested";
      }
      enum "extra-time" {
        value 4;
        description
          "Extra time requested";
      }
      enum "failure" {
        value 5;
        description
          "Client failed to process notification";
      }
    }
    description
      "Install client notification result type";
  }

  typedef Inst-feature-change {
    type enumeration {
      enum "removed" {
        value 0;
        description
          "Removed";
      }
      enum "added" {
        value 1;
        description
          "Added";
      }
    }
    description
      "Inst feature change";
  }

  typedef Inst-proc-change {
    type enumeration {
      enum "removed" {
        value 0;
        description
          "Removed";
      }
      enum "modified" {
        value 1;
        description
          "Modified";
      }
    }
    description
      "Inst proc change";
  }

  typedef Inst-file-change {
    type enumeration {
      enum "removed" {
        value 0;
        description
          "Removed";
      }
      enum "added" {
        value 1;
        description
          "Added";
      }
      enum "modified" {
        value 2;
        description
          "Modified";
      }
    }
    description
      "File change type";
  }

  typedef Inst-client {
    type enumeration {
      enum "default" {
        value 0;
        description
          "Default client";
      }
      enum "legacy" {
        value 1;
        description
          "Legacy client";
      }
    }
    description
      "Install client type";
  }

  typedef Inst-no-action-reason {
    type enumeration {
      enum "already-installed" {
        value 0;
        description
          "Package was already installed";
      }
      enum "nothing-to-remove" {
        value 1;
        description
          "No matching package found to remove";
      }
      enum "no-suitable-version" {
        value 2;
        description
          "No suitable package to upgrade to or downgrade
           to was found";
      }
    }
    description
      "Install no action reason type";
  }

  typedef Inst-pkg-op-act {
    type enumeration {
      enum "add" {
        value 0;
        description
          "Add";
      }
      enum "remove" {
        value 1;
        description
          "Remove";
      }
    }
    description
      "Install package operation action type";
  }

  typedef Inst-trans-status {
    type enumeration {
      enum "in-progress" {
        value 0;
        description
          "In progress";
      }
      enum "commit-in-progress" {
        value 1;
        description
          "Commit in progress";
      }
      enum "success" {
        value 2;
        description
          "Success";
      }
      enum "failure" {
        value 3;
        description
          "Failure";
      }
      enum "aborting" {
        value 4;
        description
          "Aborting";
      }
      enum "aborted" {
        value 5;
        description
          "Aborted";
      }
      enum "post-commit-cleanup" {
        value 6;
        description
          "Committed, cleaning up";
      }
    }
    description
      "Transaction status type";
  }

  typedef Inst-request {
    type enumeration {
      enum "unknown" {
        value 0;
        description
          "Unknown, operation history not available";
      }
      enum "add" {
        value 1;
        description
          "Add";
      }
      enum "remove" {
        value 2;
        description
          "Remove";
      }
      enum "upgrade" {
        value 3;
        description
          "Upgrade";
      }
      enum "downgrade" {
        value 4;
        description
          "Downgrade";
      }
      enum "replace" {
        value 5;
        description
          "Replace";
      }
      enum "rollback" {
        value 6;
        description
          "Rollback";
      }
    }
    description
      "Install request type";
  }

  typedef Inst-node-event {
    type enumeration {
      enum "node-unavailable" {
        value 0;
        description
          "Node became unavailable";
      }
      enum "node-available" {
        value 1;
        description
          "Node became available";
      }
      enum "error" {
        value 2;
        description
          "Per-node error";
      }
      enum "user-requested-reload" {
        value 3;
        description
          "User requested reload of this node to recover
           from a failure.";
      }
    }
    description
      "Install node event type";
  }

  grouping INST-AVAILABLE-FIX-TYPE {
    description
      "INST AVAILABLE FIX TYPE";
    leaf ddts {
      type string;
      description
        "DDTS id";
    }
    list package {
      description
        "Packages";
      uses INST-AVAILABLE-PKG-TYPE;
    }
  }

  grouping INST-AVAILABLE-FIXES-BAG {
    description
      "Install bag containing details of available fixes";
    list fixes {
      description
        "Fixes";
      uses INST-AVAILABLE-FIX-TYPE;
    }
  }

  grouping INST-QUERY-PKG-CHANGE-TYPE {
    description
      "Package changes type";
    container package {
      description
        "Package";
      uses INST-PKG-TYPE;
    }
    leaf action {
      type Inst-pkg-op-act;
      description
        "Action pending on package";
    }
  }

  grouping INST-CHANGES-BAG {
    description
      "Install pending changes bag";
    list package {
      description
        "List of packages and the action pending on each";
      uses INST-QUERY-PKG-CHANGE-TYPE;
    }
  }

  grouping INST-VER-PKG-TYPE {
    description
      "Install package type";
    leaf name {
      type string;
      description
        "Name";
    }
    leaf version {
      type string;
      description
        "Version";
    }
    leaf built-by {
      type string;
      description
        "User built by";
    }
    leaf built-on {
      type string;
      description
        "Time built";
    }
    leaf workspace {
      type string;
      description
        "Workspace built in";
    }
    leaf build-host {
      type string;
      description
        "Build host";
    }
  }

  grouping INST-VERSION-BAG {
    description
      "Install version bag";
    leaf label {
      type string;
      description
        "Label";
    }
    leaf copyright-info {
      type string;
      description
        "Copyright information";
    }
    leaf hardware-info {
      type string;
      description
        "Hardware information";
    }
    leaf uptime {
      type string;
      description
        "System uptime";
    }
    leaf location {
      type Install-opt-string;
      description
        "Prefix for the path where packages will be
         installed";
    }
    leaf processor {
      type Install-opt-string;
      description
        "Processor";
    }
    list package {
      description
        "Packages";
      uses INST-VER-PKG-TYPE;
    }
  }

  grouping INST-AVAILABLE-ACTIONS {
    description
      "INST AVAILABLE ACTIONS";
    leaf-list available-action {
      type Inst-action;
      description
        "Action available to user. If there are no
         available actions, a system reload may be used
         to recover.";
    }
  }

  grouping INST-NOTIF-STATUS {
    description
      "Install client notification status information";
    leaf notification-phase {
      type Inst-notif-phase;
      description
        "Notification phase";
    }
    leaf time-sent {
      type string;
      description
        "Timestamp notifications were sent, in RFC3339
         internet date/time format";
    }
    leaf-list clients-responded {
      type String1;
      description
        "Clients that have responded to notifications";
    }
    leaf-list clients-waiting {
      type String1;
      description
        "Clients that have not yet responded to
         notifications";
    }
  }

  grouping INST-PKG-OP-INFO {
    description
      "Install packaging operation information";
    leaf stage {
      type Inst-pkg-op-stage;
      description
        "Package operation stage";
    }
    leaf percentage-progress {
      type uint32;
      units "percentage";
      description
        "Percentage complete";
    }
    leaf packages-complete {
      type uint32;
      description
        "Count of packages completed";
    }
    leaf packages-total {
      type uint32;
      description
        "Count of total packages";
    }
  }

  grouping INST-STATUS-NODE {
    description
      "Install per-node status data";
    container packaging-operation-status {
      description
        "Further information, if a packaging operation is
         in progress";
      uses INST-PKG-OP-INFO;
    }
    container client-notification-status {
      description
        "Further information, if client notifications are
         in progress";
      uses INST-NOTIF-STATUS;
    }
    leaf node {
      type string;
      description
        "Node name";
    }
    leaf current-request {
      type Inst-node-req;
      description
        "Node request currently being handled";
    }
    leaf time-started {
      type String1;
      description
        "Timestamp this node request was started, in
         RFC3339 internet date/time format";
    }
  }

  grouping INST-REQUEST-VERBOSE-BAG {
    description
      "Status of current install user request";
    container available-actions {
      description
        "Actions that are currently valid to start";
      uses INST-AVAILABLE-ACTIONS;
    }
    leaf current-activity {
      type Inst-activity;
      description
        "Activity in progress";
    }
    leaf time-started {
      type String1;
      description
        "Timestamp this activity was started, in RFC3339
         internet date/time format";
    }
    leaf next-activity {
      type Inst-activity;
      description
        "Activity ";
    }
    leaf node-request {
      type Inst-node-req;
      description
        "Node request in progress, if any";
    }
    leaf node-request-time {
      type String1;
      description
        "Timestamp node request was sent, in RFC3339
         internet date/time format";
    }
    leaf node-request-time-left {
      type uint32;
      units "second";
      description
        "Seconds until the node request will time out";
    }
    leaf nodes-responded {
      type uint32;
      description
        "Count of nodes that have responded";
    }
    leaf nodes-total {
      type uint32;
      description
        "Total count of nodes the request was sent to";
    }
    list nodes-req-status {
      description
        "Status of per-node processing, if a node request
         is in progress";
      uses INST-STATUS-NODE;
    }
  }

  grouping INST-AVAILABLE-PKG-TYPE {
    description
      "Install package type";
    leaf name {
      type string;
      description
        "Package name";
    }
    leaf architecture {
      type string;
      description
        "Architecture";
    }
    leaf version {
      type string;
      description
        "Version";
    }
    leaf repository {
      type string;
      description
        "Repository";
    }
    leaf cached {
      type boolean;
      description
        "Cached in the internal repository";
    }
    leaf release {
      type Install-opt-string;
      description
        "Release";
    }
    leaf epoch {
      type Install-opt-string;
      description
        "Epoch";
    }
    leaf xr-package {
      type boolean;
      description
        "XR Package";
    }
  }

  grouping INST-AVAILABLE-PACKAGES-BAG {
    description
      "Available package result bag";
    leaf-list inaccessible-repository {
      type String1;
      description
        "List of repositories that the package manager
         was unable to access, likely due to
         configuration errors or network connectivity";
    }
    list package {
      description
        "Packages";
      uses INST-AVAILABLE-PKG-TYPE;
    }
  }

  grouping INST-PKG-TYPE {
    description
      "Install package type";
    leaf name {
      type string;
      description
        "Package name";
    }
    leaf architecture {
      type string;
      description
        "Architecture";
    }
    leaf version {
      type string;
      description
        "Version";
    }
    leaf release {
      type string;
      description
        "Release";
    }
    leaf epoch {
      type Install-opt-string;
      description
        "Epoch";
    }
  }

  grouping INST-PACKAGES-BAG {
    description
      "Package result bag";
    list package {
      description
        "Packages";
      uses INST-PKG-TYPE;
    }
  }

  grouping INST-ATOMIC-CHANGE-NODE-BAG {
    description
      "Node specific atomic change information";
    container changeset {
      description
        "Changeset information";
      uses INST-CHANGESET;
    }
    list pre-pre-apply-notification {
      description
        "Notifications sent for 'Pre-pre-apply' phase";
      uses INST-NOTIF;
    }
    list pre-apply-notification {
      description
        "Notifications sent for 'Pre-apply' phase";
      uses INST-NOTIF;
    }
    list apply-notification {
      description
        "Notifications sent for 'Apply' phase";
      uses INST-NOTIF;
    }
    list further-apply-notification {
      description
        "Further notifications sent for 'Apply' phase,
         after allowing for processes to restart";
      uses INST-NOTIF;
    }
    list post-apply-notification {
      description
        "Notifications sent for 'Post-apply' phase";
      uses INST-NOTIF;
    }
    list post-post-apply-notification {
      description
        "Notifications sent for 'Post-post-apply' phase";
      uses INST-NOTIF;
    }
    list event {
      description
        "Per node events";
      uses INST-NODE-EVENT;
    }
  }

  grouping INST-ATOMIC-CHANGE-NODE {
    description
      "Install per-node atomic change data";
    container changeset {
      description
        "Changeset information";
      uses INST-CHANGESET;
    }
    leaf node {
      type string;
      description
        "Node name";
    }
    list pre-pre-apply-notification {
      description
        "Notifications sent for 'Pre-pre-apply' phase";
      uses INST-NOTIF;
    }
    list pre-apply-notification {
      description
        "Notifications sent for 'Pre-apply' phase";
      uses INST-NOTIF;
    }
    list apply-notification {
      description
        "Notifications sent for 'Apply' phase";
      uses INST-NOTIF;
    }
    list further-apply-notification {
      description
        "Further notifications sent for 'Apply' phase,
         after allowing for processes to restart";
      uses INST-NOTIF;
    }
    list post-apply-notification {
      description
        "Notifications sent for 'Post-apply' phase";
      uses INST-NOTIF;
    }
    list post-post-apply-notification {
      description
        "Notifications sent for 'Post-post-apply' phase";
      uses INST-NOTIF;
    }
    list event {
      description
        "Per node events";
      uses INST-NODE-EVENT;
    }
  }

  grouping INST-ATOMIC-STATUS {
    description
      "Atomic change status";
    leaf status {
      type Inst-atomic-status;
      description
        "Status";
    }
    leaf reason {
      type String1;
      description
        "Reason this status was set, which could be an
         error or a recovery action";
    }
    leaf time {
      type string;
      description
        "Timestamp this status was set, in RFC3339
         internet date/time format";
    }
    leaf event-id {
      type uint32;
      description
        "Transaction level identifier for this status
         change";
    }
  }

  grouping INST-ATOMIC-CHANGE-BAG {
    description
      "Install atomic change entry";
    leaf index {
      type uint32;
      description
        "Atomic change index";
    }
    leaf requested-apply-method {
      type Inst-activation;
      description
        "Requested apply method";
    }
    leaf least-impactful-apply-method {
      type Inst-activation;
      description
        "Least impactful apply method required to apply
         packaging operations thus far.";
    }
    leaf install-restart {
      type boolean;
      description
        "Install infra restart during apply";
    }
    list status-history {
      description
        "Status history for this atomic change, in
         reverse chronological order";
      uses INST-ATOMIC-STATUS;
    }
    list nodes {
      status deprecated;
      description
        "Node-specific information";
      uses INST-ATOMIC-CHANGE-NODE;
    }
  }

  grouping INST-PKG-OP-NODE {
    description
      "Install per-node packaging operation data";
    leaf node {
      type string;
      description
        "Node name";
    }
    leaf download-size {
      type uint64;
      units "byte";
      description
        "Download size in bytes";
    }
    leaf installed-size {
      type uint64;
      units "byte";
      description
        "Total installed size of packages in bytes";
    }
    list package {
      description
        "List of packages";
      uses INST-PKG-INFO;
    }
    list packages-no-action {
      description
        "List of input packages on which no action was
         taken, for example because there was no suitable
         version to upgrade or downgrade to";
      uses INST-PKG-NO-ACTION;
    }
    list veto-notification {
      description
        "List of notifications sent in 'Veto' phase";
      uses INST-NOTIF;
    }
    list prepare-veto-notification {
      description
        "List of veto notifications sent in 'Prepare'
         phase";
      uses INST-NOTIF;
    }
    list prepare-notification {
      description
        "List of prepare notifications sent in 'Prepare'
         phase";
      uses INST-NOTIF;
    }
    list event {
      description
        "Per node events";
      uses INST-NODE-EVENT;
    }
  }

  grouping INST-PKG-OP-STATUS {
    description
      "Package operation status";
    leaf status {
      type Inst-pkg-op-status;
      description
        "Status";
    }
    leaf reason {
      type String1;
      description
        "Reason this status was set, which could be an
         error or a recovery action";
    }
    leaf time {
      type string;
      description
        "Timestamp this status was set, in RFC3339
         internet date/time format";
    }
    leaf event-id {
      type uint32;
      description
        "Transaction level identifier for this status
         change";
    }
  }

  grouping INST-UNDO-REQ {
    description
      "Install undo packaging operation request";
    leaf abort-type {
      type Inst-package-abort;
      description
        "Abort Type";
    }
    leaf-list packaging-operation {
      type uint32;
      description
        "Indices of packaging operations being undone";
    }
  }

  grouping INST-REQ {
    description
      "Install request";
    container operation {
      when "../reason = 'user'" {
        description
          "../Reason = 'User'";
      }
      description
        "Details of user request";
      uses INST-USER-REQ;
    }
    container abort-operation {
      when "../reason = 'undoing-due-to-abort'" {
        description
          "../Reason = 'UndoingDueToAbort'";
      }
      description
        "Details of packaging operation(s) being undone";
      uses INST-UNDO-REQ;
    }
    leaf reason {
      type Inst-req-reason;
      description
        "Reason";
    }
  }

  grouping INST-PKG-OP-BAG {
    description
      "Install package operation entry";
    container request {
      description
        "Requested operation";
      uses INST-REQ;
    }
    leaf index {
      type uint32;
      description
        "Packaging operation index";
    }
    leaf error-string {
      type String1;
      description
        "String pointing the user to any packaging
         manager error information";
    }
    list status-history {
      description
        "Status history for the package operation, in
         reverse chronological order";
      uses INST-PKG-OP-STATUS;
    }
    list nodes {
      status deprecated;
      description
        "Node-specific information";
      uses INST-PKG-OP-NODE;
    }
  }

  grouping INST-NOTIF-TIME-REQ {
    description
      "Extra time request information";
    leaf time {
      type string;
      description
        "Timestamp of request, in RFC3339 internet
         date/time format";
    }
    leaf extra-time {
      type uint32;
      units "second";
      description
        "Amount of extra time requested in seconds";
    }
  }

  grouping INST-NOTIF-RELOAD-TYPE {
    description
      "INST NOTIF RELOAD TYPE";
    leaf node {
      type string;
      description
        "Which node is to be reloaded";
    }
    leaf reason {
      type String1;
      description
        "Reason for requested reload";
    }
  }

  grouping INST-CLIENT-RELOAD {
    description
      "Information about client reload reasons";
    leaf name {
      type string;
      description
        "The name of the client";
    }
    leaf jid {
      type string;
      description
        "Job ID of the client";
    }
    leaf reason {
      type string;
      description
        "Reason to request a reload";
    }
  }

  grouping INST-RELOAD-REASON {
    description
      "Information about reload reasons";
    container packages {
      description
        "List of packages which has requested a reload";
      uses PACKAGE-NAMES;
    }
    leaf too-many-processes {
      type boolean;
      description
        "True if too many processes requested a restart";
    }
    list client {
      description
        "List of clients which have requested a reload";
      uses INST-CLIENT-RELOAD;
    }
  }

  grouping INST-FEATURE-CHANGE {
    description
      "Feature change information";
    leaf feature-name {
      type string;
      description
        "Name of feature";
    }
    leaf change {
      type Inst-feature-change;
      description
        "Change type";
    }
  }

  grouping INST-PROCESS-CHANGE {
    description
      "Impacted process information";
    leaf name {
      type string;
      description
        "Process name";
    }
    leaf change {
      type Inst-proc-change;
      description
        "Type of change";
    }
    leaf pid {
      type uint32;
      description
        "Process ID";
    }
  }

  grouping INST-FILE-CHANGE {
    description
      "File change information";
    leaf path {
      type string;
      description
        "File path, relative to /opt/cisco/iosxr";
    }
    leaf change {
      type Inst-file-change;
      description
        "Change type";
    }
  }

  grouping INST-CHANGESET {
    description
      "Changeset";
    container reload-reasons {
      description
        "Reload reasons";
      uses INST-RELOAD-REASON;
    }
    list changed-file {
      description
        "Changed files";
      uses INST-FILE-CHANGE;
    }
    list impacted-process {
      description
        "Impacted processes";
      uses INST-PROCESS-CHANGE;
    }
    list changed-feature {
      description
        "Changed features";
      uses INST-FEATURE-CHANGE;
    }
  }

  grouping NOTIFICATION-TRIGGER {
    description
      "Notification Trigger";
    container trigger-changeset {
      when "../client-type = 'default'" {
        description
          "../ClientType = 'Default'";
      }
      description
        "Trigger Changeset";
      uses INST-CHANGESET;
    }
    leaf client-type {
      type Inst-client;
      description
        "ClientType";
    }
    leaf legacy-client {
      when "../client-type = 'legacy'" {
        description
          "../ClientType = 'Legacy'";
      }
      type boolean;
      description
        "Legacy client - notifications are sent
         regardless of changeset";
    }
  }

  grouping INST-NOTIF {
    description
      "Install notification information";
    container notification-trigger {
      description
        "Notification trigger";
      uses NOTIFICATION-TRIGGER;
    }
    leaf client {
      type string;
      description
        "Client notification was sent to";
    }
    leaf description {
      type string;
      description
        "Description of the client";
    }
    leaf sent-time {
      type string;
      description
        "Time notification was sent, in RFC3339 internet
         date/time format";
    }
    leaf response-status {
      type Inst-notif-res;
      description
        "Status of response from client";
    }
    leaf error {
      type String1;
      description
        "Error, if any";
    }
    leaf response-time {
      type string;
      description
        "Time of clients response, in RFC3339 internet
         date/time format";
    }
    leaf veto-reason {
      type String1;
      description
        "Reason for requested veto";
    }
    list reload-reason {
      description
        "Reasons for reload, if any";
      uses INST-NOTIF-RELOAD-TYPE;
    }
    list extra-time-request {
      description
        "Requests for extra time, if any";
      uses INST-NOTIF-TIME-REQ;
    }
  }

  grouping INST-PKG-NO-ACTION {
    description
      "Information about a package on which no action
       was taken";
    container package {
      description
        "Package or user input on which no action was
         taken";
      uses INST-PKG;
    }
    leaf reason {
      type Inst-no-action-reason;
      description
        "Reason that no action was taken on this package";
    }
  }

  grouping INST-PKG {
    description
      "Package";
    leaf name {
      type string;
      description
        "Package name";
    }
    leaf version {
      type String1;
      description
        "Version";
    }
    leaf architecture {
      type String1;
      description
        "Package architecture";
    }
  }

  grouping INST-PKG-INFO {
    description
      "Install per package information";
    container package {
      description
        "Package";
      uses INST-PKG;
    }
    leaf action {
      type Inst-pkg-op-act;
      description
        "Action taken on this package";
    }
  }

  grouping INST-PKG-OP-NODE-BAG {
    description
      "Node specific packaging operation information";
    leaf download-size {
      type uint64;
      units "byte";
      description
        "Download size in bytes";
    }
    leaf installed-size {
      type uint64;
      units "byte";
      description
        "Total installed size of packages in bytes";
    }
    list package {
      description
        "List of packages";
      uses INST-PKG-INFO;
    }
    list packages-no-action {
      description
        "List of input packages on which no action was
         taken, for example because there was no suitable
         version to upgrade or downgrade to";
      uses INST-PKG-NO-ACTION;
    }
    list veto-notification {
      description
        "List of notifications sent in 'Veto' phase";
      uses INST-NOTIF;
    }
    list prepare-veto-notification {
      description
        "List of veto notifications sent in 'Prepare'
         phase";
      uses INST-NOTIF;
    }
    list prepare-notification {
      description
        "List of prepare notifications sent in 'Prepare'
         phase";
      uses INST-NOTIF;
    }
    list event {
      description
        "Per node events";
      uses INST-NODE-EVENT;
    }
  }

  grouping INST-PKG-OP-ERRORS-BAG {
    description
      "DNF logs for any node where DNF has encountered
       errors in a packaging operation";
    leaf-list lines {
      type String1;
      description
        "Lines of the DNF output";
    }
  }

  grouping INST-TRANS-NODE {
    description
      "Install per-node transaction data";
    leaf node {
      type String1;
      description
        "Node name";
    }
    list event {
      description
        "Per-node events";
      uses INST-NODE-EVENT;
    }
  }

  grouping INST-TRANS-STATUS {
    description
      "Transaction status";
    leaf status {
      type Inst-trans-status;
      description
        "Status";
    }
    leaf reason {
      type String1;
      description
        "Reason this status was set, which could be an
         error or a recovery action";
    }
    leaf time {
      type string;
      description
        "Timestamp this status was set, in RFC3339
         internet date/time format";
    }
    leaf event-id {
      type uint32;
      description
        "Transaction level identifier for this status
         change";
    }
  }

  grouping PACKAGE-NAMES {
    description
      "PACKAGE NAMES";
    leaf-list package-name {
      type String1;
      description
        "package name";
    }
  }

  grouping INST-USER-REQ {
    description
      "Install user packaging operation request";
    container unknown-packages {
      when "../request = 'unknown'" {
        description
          "../Request = 'Unknown'";
      }
      description
        "List of packages";
      uses PACKAGE-NAMES;
    }
    container install-packages {
      when "../request = 'add'" {
        description
          "../Request = 'Add'";
      }
      description
        "List of packages";
      uses PACKAGE-NAMES;
    }
    container remove-packages {
      when "../request = 'remove'" {
        description
          "../Request = 'Remove'";
      }
      description
        "List of packages";
      uses PACKAGE-NAMES;
    }
    container upgrade-packages {
      when "../request = 'upgrade'" {
        description
          "../Request = 'Upgrade'";
      }
      description
        "List of packages";
      uses PACKAGE-NAMES;
    }
    container downgrade-packages {
      when "../request = 'downgrade'" {
        description
          "../Request = 'Downgrade'";
      }
      description
        "List of packages";
      uses PACKAGE-NAMES;
    }
    leaf request {
      type Inst-request;
      description
        "Request";
    }
    leaf replace-iso {
      when "../request = 'replace'" {
        description
          "../Request = 'Replace'";
      }
      type String1;
      description
        "ISO";
    }
    leaf rollback-to-transaction {
      when "../request = 'rollback'" {
        description
          "../Request = 'Rollback'";
      }
      type uint32;
      description
        "Transaction ID";
    }
  }

  grouping INST-TRANS-BAG {
    description
      "Install transaction entry";
    container started-by-user-request {
      description
        "User request that started this transaction";
      uses INST-USER-REQ;
    }
    leaf transaction-id {
      type uint32;
      description
        "Transaction ID";
    }
    list status-history {
      description
        "Status history for this transaction, in reverse
         chronological order";
      uses INST-TRANS-STATUS;
    }
    list nodes {
      status deprecated;
      description
        "Node-specific information";
      uses INST-TRANS-NODE;
    }
  }

  grouping INST-NODE-EVENT {
    description
      "Node events";
    leaf event {
      type Inst-node-event;
      description
        "Event";
    }
    leaf time {
      type string;
      description
        "Timestamp, in RFC3339 internet date/time format";
    }
    leaf reason {
      type String1;
      description
        "Reason for the event, for example an error
         string";
    }
    leaf event-id {
      type uint32;
      description
        "Transaction level identifier for this event";
    }
  }

  grouping INST-TRANS-NODE-BAG {
    description
      "Node specific transaction information";
    list event {
      description
        "Per-node events";
      uses INST-NODE-EVENT;
    }
  }
}
