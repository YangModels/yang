submodule Cisco-IOS-XR-infra-syslog-oper-sub1 {
  belongs-to Cisco-IOS-XR-infra-syslog-oper {
    prefix Cisco-IOS-XR-infra-syslog-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-syslog package operational data.
     
     Copyright (c) 2013-2019 by Cisco Systems, Inc.
     All rights reserved.";

  revision 2019-04-05 {
    description
      "Establish semantic version baseline.";
    semver:module-version "1.0.0";
  }
  revision 2018-02-23 {
    description
      "Added a new rpc statement.";
  }
  revision 2018-02-22 {
    description
      "Fixed syslog message filter.";
  }
  revision 2017-09-07 {
    description
      "Fixed type translation error.";
  }
  revision 2016-06-24 {
    description
      "Schema added for Show logging files CLI";
  }
  revision 2015-01-07 {
    description
      "IOS XR 5.3.1 revision.";
  }

  typedef System-message-severity {
    type enumeration {
      enum "message-severity-unknown" {
        value -1;
        description
          "Unknown";
      }
      enum "message-severity-emergency" {
        value 0;
        description
          "Emergency";
      }
      enum "message-severity-alert" {
        value 1;
        description
          "Alert";
      }
      enum "message-severity-critical" {
        value 2;
        description
          "Critical";
      }
      enum "message-severity-error" {
        value 3;
        description
          "Error";
      }
      enum "message-severity-warning" {
        value 4;
        description
          "Warning";
      }
      enum "message-severity-notice" {
        value 5;
        description
          "Notice";
      }
      enum "message-severity-informational" {
        value 6;
        description
          "Informational";
      }
      enum "message-severity-debug" {
        value 7;
        description
          "Debug";
      }
    }
    description
      "System message severity";
  }

  grouping FILE-LOG-STATS {
    description
      "System log file destination statistics";
    leaf file-name {
      type string;
      description
        "File name for logging messages";
    }
    leaf message-count {
      type uint32;
      description
        "Message count";
    }
  }

  grouping TLS-REMOTE-LOG-STATS {
    description
      "System log tls remote statistics";
    leaf remote-host-name {
      type string;
      description
        "TLS Remote hostname";
    }
    leaf message-count {
      type uint32;
      description
        "Message count";
    }
  }

  grouping REMOTE-LOG-STATS {
    description
      "System log remote statistics";
    leaf remote-host-name {
      type string;
      description
        "Remote hostname";
    }
    leaf message-count {
      type uint32;
      description
        "Message count";
    }
  }

  grouping LOG-DEST-STATS {
    description
      "System log statistics";
    leaf is-log-enabled {
      type boolean;
      description
        "Is log enabled";
    }
    leaf severity {
      type System-message-severity;
      description
        "Configured severity";
    }
    leaf message-count {
      type uint32;
      description
        "Message count";
    }
    leaf buffer-size {
      type uint32;
      units "byte";
      description
        "Buffer size in bytes if logging buffer isenabled";
    }
  }

  grouping LOG-ENABLE-STATS {
    description
      "System log discard statistics";
    leaf is-log-enabled {
      type boolean;
      description
        "Is log enabled";
    }
    leaf drop-count {
      type uint32;
      description
        "Number of messages dropped";
    }
    leaf flush-count {
      type uint32;
      description
        "Number of messages flushed";
    }
    leaf overrun-count {
      type uint32;
      description
        "Number of messages overrun";
    }
  }

  grouping SYSTEM-MESSAGE-STATISTICS {
    description
      "System message statistics";
    container logging-stats {
      description
        "Logging statistics";
      uses LOG-ENABLE-STATS;
    }
    container console-logging-stats {
      description
        "Console logging statistics";
      uses LOG-DEST-STATS;
    }
    container monitor-logging-stats {
      description
        "Monitor loggingstatistics";
      uses LOG-DEST-STATS;
    }
    container trap-logging-stats {
      description
        "Trap logging statistics";
      uses LOG-DEST-STATS;
    }
    container buffer-logging-stats {
      description
        "Buffer logging statistics";
      uses LOG-DEST-STATS;
    }
    list remote-logging-stat {
      description
        "Remote logging statistics";
      uses REMOTE-LOG-STATS;
    }
    list tls-remote-logging-stat {
      description
        "TLS Remote logging statistics";
      uses TLS-REMOTE-LOG-STATS;
    }
    list file-logging-stat {
      description
        "File logging statistics";
      uses FILE-LOG-STATS;
    }
  }

  grouping SYSTEM-MESSAGE {
    description
      "System message";
    leaf card-type {
      type string;
      description
        "Message card location: 'RP', 'DRP', 'LC', 'SC',
         'SP' or 'UNK' ";
    }
    leaf node-name {
      type xr:Node-id;
      description
        "Message source location";
    }
    leaf time-stamp {
      type uint64;
      units "millisecond";
      description
        "Time in milliseconds since 00:00:00 UTC, January
         11970 of when message was generated";
    }
    leaf time-of-day {
      type string;
      description
        "Time of day of event in DDD MMM DD  YYYY HH:MM
         :SS format, e.g Wed Apr 01 2009  15:50:26";
    }
    leaf time-zone {
      type string;
      description
        "Time Zone in UTC+/-HH:MM format,  e.g UTC+5:30,
         UTC-6";
    }
    leaf process-name {
      type string;
      description
        "Process name";
    }
    leaf category {
      type string;
      description
        "Message category";
    }
    leaf group {
      type string;
      description
        "Message group";
    }
    leaf message-name {
      type string;
      description
        "Message name";
    }
    leaf severity {
      type System-message-severity;
      description
        "Message severity";
    }
    leaf text {
      type string;
      description
        "Additional message text";
    }
  }

  grouping AN-REMOTE-LOG-SERVER {
    description
      "A System log AN remote log server structure";
    leaf ip-address {
      type string;
      description
        "IP Address";
    }
    leaf vrf-name {
      type string;
      description
        "VRF Name";
    }
    leaf vrf-severity {
      type string;
      description
        "VRF Severity";
    }
    leaf rh-discriminator {
      type string;
      description
        "Remote-Host Discriminator";
    }
  }

  grouping AN-REMOTE-LOG-SERVERS {
    description
      "System log All AN remote servers";
    list an-remote-log-server {
      description
        "AN Remote Log Servers";
      uses AN-REMOTE-LOG-SERVER;
    }
  }

  grouping FILE-LOG-DETAILS {
    description
      "System log file details";
    leaf file-path {
      type string;
      description
        "File path for logging messages";
    }
    leaf file-name {
      type string;
      description
        "File name for logging messages";
    }
  }

  grouping FILE-LOG-LIST-PATH {
    description
      "System log files list and path";
    list file-log-detail {
      description
        "Logging Files";
      uses FILE-LOG-DETAILS;
    }
  }
}
