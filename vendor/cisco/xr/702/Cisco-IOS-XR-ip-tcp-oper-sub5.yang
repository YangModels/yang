submodule Cisco-IOS-XR-ip-tcp-oper-sub5 {
  belongs-to Cisco-IOS-XR-ip-tcp-oper {
    prefix Cisco-IOS-XR-ip-tcp-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-tcp package operational data.
     
     Copyright (c) 2013-2019 by Cisco Systems, Inc.
     All rights reserved.";

  revision 2019-04-05 {
    description
      "Establish semantic version baseline.";
    semver:module-version "1.0.0";
  }
  revision 2018-11-01 {
    description
      "Added socket async double free prevention count in tcp statistics summary";
  }
  revision 2018-02-14 {
    description
      "PCB_ID argument is passed in string format.";
  }
  revision 2018-02-14 {
    description
      "Added support for TCP-AO feature.";
  }
  revision 2017-05-01 {
    description
      "Fixing backward compatibility error in module.";
  }
  revision 2016-02-26 {
    description
      "Descriptions updated.";
  }
  revision 2015-11-09 {
    description
      "IOS XR 6.0 revision.";
  }

  grouping TRANSP-CLIENT-STATS-BAG {
    description
      "Aggregated statistics of a transport client";
    leaf client-jid {
      type int32;
      description
        "Job ID of the transport client";
    }
    leaf client-name {
      type string {
        length "0..21";
      }
      description
        "Transport client name";
    }
    leaf ipv4-received-packets {
      type uint32;
      description
        "Total IPv4 packets received from client";
    }
    leaf ipv4-sent-packets {
      type uint32;
      description
        "Total IPv4 packets sent to client";
    }
    leaf ipv6-received-packets {
      type uint32;
      description
        "Total IPv6 packets received from app";
    }
    leaf ipv6-sent-packets {
      type uint32;
      description
        "Total IPv6 packets sent to app";
    }
  }
}
