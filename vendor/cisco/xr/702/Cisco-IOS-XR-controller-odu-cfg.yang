module Cisco-IOS-XR-controller-odu-cfg {
  namespace "http://cisco.com/ns/yang/Cisco-IOS-XR-controller-odu-cfg";
  prefix controller-odu-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-odu package configuration.
     
     This YANG module augments the
       Cisco-IOS-XR-ifmgr-cfg
     module with configuration data.
     
     Copyright (c) 2013-2020 by Cisco Systems, Inc.
     All rights reserved.";

  revision 2020-02-02 {
    description
      "Removed PRBS pattern entry PRBS_PATTERN_NONE, PRBS mode entry PRBS_MODE_INVALID.
       2020-02-02
         Changes made to SAPI/DAPI to support 15 char string.";
    semver:module-version "1.0.1M";
  }
  revision 2019-04-05 {
    description
      "Establish semantic version baseline.";
    semver:module-version "1.0.0";
  }
  revision 2015-11-09 {
    description
      "IOS XR 6.0 revision.";
  }

  typedef Otn-child-controller-name {
    type enumeration {
      enum "odu1" {
        value 1;
        description
          "Create lower order odu1 controller";
      }
      enum "odu2" {
        value 2;
        description
          "Create lower order odu2 controller";
      }
      enum "odu3" {
        value 3;
        description
          "Create lower order odu3 controller";
      }
      enum "odu0" {
        value 10;
        description
          "Create lower order odu0 controller";
      }
      enum "odu2e" {
        value 11;
        description
          "Create lower order odu2e controller";
      }
      enum "odu1e" {
        value 23;
        description
          "Create lower order odu1e controller";
      }
      enum "odu2f" {
        value 25;
        description
          "Create lower order odu2f controller";
      }
      enum "odu3e1" {
        value 26;
        description
          "Create lower order odu3e1 controller";
      }
      enum "odu3e2" {
        value 27;
        description
          "Create lower order odu3e2 controller";
      }
    }
    description
      "Otn child controller name";
  }

  typedef Otn-child-flex-controller-name {
    type enumeration {
      enum "odu-flex" {
        value 22;
        description
          "Create lower order odu-flex controller";
      }
    }
    description
      "Otn child flex controller name";
  }

  typedef Otn-flex-mapping {
    type enumeration {
      enum "gfp-f-fixed" {
        value 1;
        description
          "GFP-FIX Mapping";
      }
      enum "gfp-resizable" {
        value 2;
        description
          "GFP-Resizable Mapping";
      }
      enum "cbr" {
        value 3;
        description
          "CBR Mapping";
      }
    }
    description
      "Otn flex mapping";
  }

  typedef Otn-per-mon {
    type enumeration {
      enum "disable" {
        value 0;
        description
          "Performance Monitoring Disabled";
      }
      enum "enable" {
        value 1;
        description
          "Performance Monitoring Enabled";
      }
    }
    description
      "Otn per mon";
  }

  typedef Odu-prbs-mode {
    type enumeration {
      enum "mode-source" {
        value 1;
        description
          "Prbs Mode Source";
      }
      enum "mode-sink" {
        value 2;
        description
          "Prbs Mode Sink";
      }
      enum "mode-source-sink" {
        value 3;
        description
          "Prbs Mode Source_Sink";
      }
    }
    description
      "Odu prbs mode";
  }

  typedef Odu-time-slot-granularity {
    type enumeration {
      enum "1.25g" {
        value 0;
        description
          "1.25G time slot granularity";
      }
      enum "2.5g" {
        value 1;
        description
          "2.5G time slot granularity";
      }
    }
    description
      "Odu time slot granularity";
  }

  typedef Otn-send-tti-type-os {
    type enumeration {
      enum "send-tti-os-ascii/os-ascii" {
        value 10;
        description
          "Send TTI OS ASCII string";
      }
      enum "send-tti-os-hex/os-hex" {
        value 12;
        description
          "Send TTI OS HEX string";
      }
    }
    description
      "Otn send tti type os";
  }

  typedef Otn-exp-tti-type-sapi {
    type enumeration {
      enum "exp-tti-sapi-ascii/sapi-ascii" {
        value 15;
        description
          "Expected TTI SAPI ASCII string";
      }
    }
    description
      "Otn exp tti type sapi";
  }

  typedef Otn-termination {
    type enumeration {
      enum "ether" {
        value 1;
        description
          "Termination to ether";
      }
    }
    description
      "Otn termination";
  }

  typedef Otn-send-tti-type-sapi {
    type enumeration {
      enum "send-tti-sapi-ascii/sapi-ascii" {
        value 14;
        description
          "Send TTI SAPI ASCII string";
      }
    }
    description
      "Otn send tti type sapi";
  }

  typedef Ca-mode {
    type enumeration {
      enum "mode-laser-squelch" {
        value 1;
        description
          "Laser Squelch Mode";
      }
      enum "mode-idle-frame" {
        value 2;
        description
          "Idle Frame Mode";
      }
    }
    description
      "Ca mode";
  }

  typedef Otn-sec-admin-state {
    type enumeration {
      enum "normal" {
        value 0;
        description
          "In normal state";
      }
      enum "maintenance" {
        value 1;
        description
          "Under maintenance";
      }
    }
    description
      "Otn sec admin state";
  }

  typedef Otn-mapping {
    type enumeration {
      enum "gfp-f" {
        value 1;
        description
          "gfp_f for mapping";
      }
      enum "bmp" {
        value 3;
        description
          "bmp for mapping";
      }
      enum "gmp" {
        value 4;
        description
          "gmp for mapping";
      }
      enum "gfp-f-ext" {
        value 6;
        description
          "gfp_f_ext for mapping";
      }
    }
    description
      "Otn mapping";
  }

  typedef Otn-exp-tti-type-os {
    type enumeration {
      enum "exp-tti-os-ascii/os-ascii" {
        value 11;
        description
          "Expected TTI OS ASCII string";
      }
      enum "exp-tti-os-hex/os-hex" {
        value 13;
        description
          "Expected TTI OS HEX string";
      }
    }
    description
      "Otn exp tti type os";
  }

  typedef Odu-delay {
    type enumeration {
      enum "disable" {
        value 0;
        description
          "Delay Disable";
      }
      enum "enable" {
        value 1;
        description
          "Delay Enable";
      }
    }
    description
      "Odu delay";
  }

  typedef Otn-loopback {
    type enumeration {
      enum "line" {
        value 2;
        description
          "Line loopback";
      }
      enum "internal" {
        value 4;
        description
          "Internal loopback";
      }
    }
    description
      "Otn loopback";
  }

  typedef Otn-exp-tti-type-full {
    type enumeration {
      enum "exp-tti-full-ascii/full-ascii" {
        value 5;
        description
          "Expected TTI Full ASCII string";
      }
      enum "exp-tti-hex/hex" {
        value 7;
        description
          "Expected TTI hex string";
      }
    }
    description
      "Otn exp tti type full";
  }

  typedef Otn-send-tti-type-full {
    type enumeration {
      enum "send-tti-full-ascii/full-ascii" {
        value 4;
        description
          "Send TTI Full ASCII string";
      }
      enum "send-tti-hex/hex" {
        value 6;
        description
          "Send TTI hex string";
      }
    }
    description
      "Otn send tti type full";
  }

  typedef Otn-exp-tti-type-dapi {
    type enumeration {
      enum "exp-tti-dapi-ascii/dapi-ascii" {
        value 9;
        description
          "Expected TTI DAPI ASCII string";
      }
    }
    description
      "Otn exp tti type dapi";
  }

  typedef Otngcc-mode {
    type enumeration {
      enum "disable" {
        value 0;
        description
          "GCC Disabled";
      }
      enum "enable" {
        value 1;
        description
          "GCC Enabled";
      }
    }
    description
      "Otngcc mode";
  }

  typedef Otn-send-tti-type-dapi {
    type enumeration {
      enum "send-tti-dapi-ascii/dapi-ascii" {
        value 8;
        description
          "Send TTI DAPI ASCII string";
      }
    }
    description
      "Otn send tti type dapi";
  }

  typedef Gcc-mode {
    type enumeration {
      enum "gcc2-mode" {
        value 1;
        description
          "GCC2";
      }
    }
    description
      "Gcc mode";
  }

  typedef Pattern {
    type enumeration {
      enum "pattern-pn31" {
        value 1;
        description
          "Prbs pattern pn31";
      }
      enum "pattern-pn23" {
        value 2;
        description
          "Prbs pattern pn23";
      }
      enum "pattern-pn11" {
        value 4;
        description
          "Prbs pattern pn11";
      }
      enum "pattern-inverted-pn31" {
        value 8;
        description
          "Prbs pattern inverted pn31";
      }
      enum "pattern-inverted-pn11" {
        value 16;
        description
          "Prbs pattern inverted pn11";
      }
    }
    description
      "Pattern";
  }

  typedef Otnpmtimca {
    type enumeration {
      enum "disable" {
        value 0;
        description
          "Path layer PM TIM Consequent action Disabled";
      }
      enum "enable" {
        value 1;
        description
          "Path layer PM TIM Consequent action  Enabled";
      }
    }
    description
      "Otnpmtimca";
  }

  augment "/a1:interface-configurations/a1:interface-configuration" {
    description
      "This augment extends the configuration data of
       'Cisco-IOS-XR-ifmgr-cfg'";
    container odu {
      description
        "ODU port controller configuration";
      container otn-send-ttitcmdapi {
        description
          "Configure OTN Send TTI value for DAPI configs";
        leaf string-type {
          type Otn-send-tti-type-dapi;
          description
            "TTI string type (FULL ASCII or  DAPI ASCII or
             SAPI ASCII or hex format or OS ASCII or OS
             HEX)";
        }
        leaf dapi-ascii-string {
          when "../string-type = 'send-tti-dapi-ascii/dapi-ascii'" {
            description
              "../StringType =
               SEND_TTI_DAPI_ASCII/DAPI_ASCII";
          }
          type string {
            length "1..15";
          }
          description
            "DAPI ASCII text (Max 15 characters)";
        }
      }
      container gcc-modes {
        description
          "General Communication Channel Type";
        list gcc-mode {
          key "type";
          description
            "Enable General Communication Channel Mode";
          leaf type {
            type Gcc-mode;
            description
              "Type ";
          }
          leaf mode {
            type Otngcc-mode;
            mandatory true;
            description
              "Enable/Disable GCC";
          }
        }
      }
      container otn-expected-ttisapi {
        description
          "Configure OTN Expected TTI value for SAPI
           configs";
        leaf string-type {
          type Otn-exp-tti-type-sapi;
          description
            "TTI string type (FULL ASCII or  DAPI ASCII or
             SAPI ASCII or hex format or OS ASCII or OS
             HEX)";
        }
        leaf sapi-ascii-string {
          when "../string-type = 'exp-tti-sapi-ascii/sapi-ascii'" {
            description
              "../StringType = EXP_TTI_SAPI_ASCII/SAPI_ASCII";
          }
          type string {
            length "1..15";
          }
          description
            "SAPI ASCII text (Max 15 characters)";
        }
      }
      container laser-squelch-timers {
        description
          "Enable laser squelch and configure hold off
           time";
        list laser-squelch-timer {
          key "mode-type";
          description
            "Enable laser squelch and configure hold off
             time";
          leaf mode-type {
            type Ca-mode;
            description
              "Mode Type";
          }
          leaf timer {
            type uint32 {
              range "20..10000";
            }
            mandatory true;
            description
              "Configure hold off timer";
          }
        }
      }
      container network-srlgs {
        description
          "Configure Network srlgs";
        list network-srlg {
          key "set-id";
          description
            "Configure network srlg sets";
          leaf set-id {
            type uint32 {
              range "1..17";
            }
            description
              "Set index";
          }
          leaf srlg1 {
            type uint32 {
              range "0..4294967294";
            }
            description
              "First value for Network SRLG";
          }
          leaf srlg2 {
            type uint32 {
              range "0..4294967294";
            }
            description
              "Second value for Network SRLG";
          }
          leaf srlg3 {
            type uint32 {
              range "0..4294967294";
            }
            description
              "Third value for Network SRLG";
          }
          leaf srlg4 {
            type uint32 {
              range "0..4294967294";
            }
            description
              "Forth value for Network SRLG";
          }
          leaf srlg5 {
            type uint32 {
              range "0..4294967294";
            }
            description
              "Fifth value for Network SRLG";
          }
          leaf srlg6 {
            type uint32 {
              range "0..4294967294";
            }
            description
              "Sixth value for Network SRLG";
          }
        }
      }
      container otn-send-tti {
        description
          "Configure OTN Send TTI value for Full ASCII/HEX";
        leaf string-type {
          type Otn-send-tti-type-full;
          description
            "TTI string type (FULL ASCII or  DAPI ASCII or
             SAPI ASCII or hex format or OS ASCII or OS
             HEX)";
        }
        leaf full-ascii-string {
          when "../string-type = 'send-tti-full-ascii/full-ascii'" {
            description
              "../StringType =
               SEND_TTI_FULL_ASCII/FULL_ASCII";
          }
          type string {
            length "1..64";
          }
          description
            "Full ASCII text (Max 64 characters)";
        }
        leaf hex-string {
          when "../string-type = 'send-tti-hex/hex'" {
            description
              "../StringType = SEND_TTI_HEX/Hex";
          }
          type string {
            length "1..128";
          }
          description
            "Hex nibbles (Max 128 - The string length
             should be an even number)";
        }
      }
      container otn-expected-ttitcmdapi {
        description
          "Configure OTN Expected TTI value for DAPI
           configs";
        leaf string-type {
          type Otn-exp-tti-type-dapi;
          description
            "TTI string type (FULL ASCII or  DAPI ASCII or
             SAPI ASCII or hex format or OS ASCII or OS
             HEX)";
        }
        leaf dapi-ascii-string {
          when "../string-type = 'exp-tti-dapi-ascii/dapi-ascii'" {
            description
              "../StringType = EXP_TTI_DAPI_ASCII/DAPI_ASCII";
          }
          type string {
            length "1..15";
          }
          description
            "DAPI ASCII text (Max 15 characters)";
        }
      }
      container otn-send-ttisapi {
        description
          "Configure OTN Send TTI value for SAPI configs";
        leaf string-type {
          type Otn-send-tti-type-sapi;
          description
            "TTI string type (FULL ASCII or  DAPI ASCII or
             SAPI ASCII or hex format or OS ASCII or OS
             HEX)";
        }
        leaf sapi-ascii-string {
          when "../string-type = 'send-tti-sapi-ascii/sapi-ascii'" {
            description
              "../StringType =
               SEND_TTI_SAPI_ASCII/SAPI_ASCII";
          }
          type string {
            length "1..15";
          }
          description
            "SAPI ASCII text (Max 15 characters)";
        }
      }
      container prbs {
        presence "Indicates a prbs node is configured.";
        description
          "Enable Prbs And configure";
        leaf mode-value {
          type Odu-prbs-mode;
          mandatory true;
          description
            "Mode value";
        }
        leaf patternvalue {
          type Pattern;
          mandatory true;
          description
            "Pattern value";
        }
      }
      container idle-frame-timers {
        description
          "Enable Idle Frame and configure hold off time";
        list idle-frame-timer {
          key "mode-type";
          description
            "Enable Idle Frame and configure hold off time";
          leaf mode-type {
            type Ca-mode;
            description
              "Mode Type";
          }
          leaf timer {
            type uint32 {
              range "20..10000";
            }
            mandatory true;
            description
              "Configure hold off timer";
          }
        }
      }
      container otn-expected-ttitcmos {
        description
          "Configure OTN Expected TTI value for OS config";
        leaf string-type {
          type Otn-exp-tti-type-os;
          description
            "TTI string type (FULL ASCII or  DAPI ASCII or
             SAPI ASCII or hex format or OS ASCII or OS
             HEX)";
        }
        leaf osascii-string {
          when "../string-type = 'exp-tti-os-ascii/os-ascii'" {
            description
              "../StringType = EXP_TTI_OS_ASCII/OS_ASCII";
          }
          type string {
            length "1..32";
          }
          description
            "OS ASCII text (Max 32 characters)";
        }
        leaf oshex-string {
          when "../string-type = 'exp-tti-os-hex/os-hex'" {
            description
              "../StringType = EXP_TTI_OS_HEX/OS_HEX";
          }
          type string {
            length "1..64";
          }
          description
            "OS HEX text (Max 64 characters)";
        }
      }
      container otn-expected-tti {
        description
          "Configure OTN Expected TTI value for Full
           ASCII/HEX";
        leaf string-type {
          type Otn-exp-tti-type-full;
          description
            "TTI string type (FULL ASCII or  DAPI ASCII or
             SAPI ASCII or hex format or OS ASCII or OS
             HEX)";
        }
        leaf full-ascii-string {
          when "../string-type = 'exp-tti-full-ascii/full-ascii'" {
            description
              "../StringType = EXP_TTI_FULL_ASCII/FULL_ASCII";
          }
          type string {
            length "1..64";
          }
          description
            "Full ASCII text (Max 64 characters)";
        }
        leaf hex-string {
          when "../string-type = 'exp-tti-hex/hex'" {
            description
              "../StringType = EXP_TTI_HEX/Hex";
          }
          type string {
            length "1..128";
          }
          description
            "Hex nibbles (Max 128 - The string length
             should be an even number)";
        }
      }
      container controller-flexes {
        description
          "Channelizing to lower order controller";
        list controller-flex {
          key "controller-name tpn";
          description
            "Creation of lower order controllers";
          leaf controller-name {
            type Otn-child-flex-controller-name;
            description
              "Lower order flex controller";
          }
          leaf tpn {
            type uint32 {
              range "1..80";
            }
            description
              "<1 - MAX> Tributary port number as allowed in
               G.709";
          }
          leaf timeslots {
            type string {
              length "1..230";
            }
            description
              "Timeslots requested - string separated by (:)
               or (-) from 1 to 24. (:) indicates individual
               timeslot and (-) represent range";
          }
          leaf bitrate {
            type uint32 {
              range "1..104124241";
            }
            description
              "Bitrate for Odu-flex in kbps";
          }
          leaf mapping {
            type Otn-flex-mapping;
            description
              "Mapping for flexible containers";
          }
        }
      }
      container otn-send-ttitcmos {
        description
          "Configure OTN Send TTI value for OS config";
        leaf string-type {
          type Otn-send-tti-type-os;
          description
            "TTI string type (FULL ASCII or  DAPI ASCII or
             SAPI ASCII or hex format or OS ASCII or OS
             HEX)";
        }
        leaf osascii-string {
          when "../string-type = 'send-tti-os-ascii/os-ascii'" {
            description
              "../StringType = SEND_TTI_OS_ASCII/OS_ASCII";
          }
          type string {
            length "1..32";
          }
          description
            "OS ASCII text (Max 32 characters)";
        }
        leaf oshex-string {
          when "../string-type = 'send-tti-os-hex/os-hex'" {
            description
              "../StringType = SEND_TTI_OS_HEX/OS_HEX";
          }
          type string {
            length "1..64";
          }
          description
            "OS HEX text (Max 64 characters)";
        }
      }
      container termination {
        presence "enable termination";
        description
          "Termination of ODU Controller";
        leaf state {
          type Otn-termination;
          description
            "ODU Termination";
        }
        leaf mapping {
          type Otn-mapping;
          description
            "ODU Mapping";
        }
      }
      container controllers {
        description
          "Channelizing to lower order controller";
        list controller {
          key "controller-name tpn";
          description
            "Creation of lower order controllers";
          leaf controller-name {
            type Otn-child-controller-name;
            description
              "Lower order controller";
          }
          leaf tpn {
            type uint32 {
              range "1..80";
            }
            description
              "<1 - MAX> Tributary port number as allowed in
               G.709";
          }
          leaf timeslots {
            type string;
            mandatory true;
            description
              "Timeslots requested - string separated by (:)
               or (-) from 1 to 24. (:) indicates individual
               timeslot and (-) represent range";
          }
        }
      }
      leaf secondary-admin-state {
        type Otn-sec-admin-state;
        default "normal";
        description
          "Configure secondary admin state ";
      }
      leaf tsg {
        type Odu-time-slot-granularity;
        default "1.25g";
        description
          "Configure Tributary Slot Granularity ";
      }
      leaf sd {
        type uint32 {
          range "5..9";
        }
        description
          "Signal degrade threshold";
      }
      leaf pmtim-state {
        type Otnpmtimca;
        default "disable";
        description
          "Configure Consequent Action for PM TIM";
      }
      leaf performance-monitoring {
        type Otn-per-mon;
        default "disable";
        description
          "Configure performance monitoring";
      }
      leaf loopback {
        type Otn-loopback;
        description
          "Type of Loopback";
      }
      leaf delay-measurement {
        type Odu-delay;
        default "disable";
        description
          "State of Delay Measurement";
      }
      leaf gcc {
        type empty;
        description
          "General Communication Channel configuration";
      }
      leaf sf {
        type uint32 {
          range "5..9";
        }
        description
          "Signal failure threshold";
      }
    }
  }
}
