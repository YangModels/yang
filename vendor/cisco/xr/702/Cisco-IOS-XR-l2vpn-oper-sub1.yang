submodule Cisco-IOS-XR-l2vpn-oper-sub1 {
  belongs-to Cisco-IOS-XR-l2vpn-oper {
    prefix Cisco-IOS-XR-l2vpn-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR l2vpn package operational data.
     
     Copyright (c) 2013-2019 by Cisco Systems, Inc.
     All rights reserved.";

  revision 2019-12-20 {
    description
      "- EVPN-VPWS related changes - SR-TE policy related changes";
    semver:module-version "1.0.1M";
  }
  revision 2019-04-05 {
    description
      "Establish semantic version baseline.";
    semver:module-version "1.0.0";
  }
  revision 2019-03-30 {
    description
      "- Rename l2fib-mac-learning-mac* interface-handle to interface-name - Rename l2fib-pw-group tunnel-if-handle to tunnel-interface-name - Convert several array from leaf-list to list syntax. - Implement range datatypes for all L2FIB integers.";
  }
  revision 2018-08-01 {
    description
      "Removed empty groupings.";
  }
  revision 2017-09-07 {
    description
      "Fixed type translation error.";
  }
  revision 2017-06-26 {
    description
      "Change identifiers to be more readable.";
  }
  revision 2017-05-01 {
    description
      "Fixing backward compatibility error in module.";
  }
  revision 2015-11-09 {
    description
      "IOS XR 6.0 revision.";
  }

  typedef Iflist-rep-status {
    type enumeration {
      enum "invalid" {
        value 0;
        description
          "Invalid";
      }
      enum "pending" {
        value 1;
        description
          "Pending";
      }
      enum "done" {
        value 2;
        description
          "Done";
      }
      enum "not-supported" {
        value 3;
        description
          "Not supported";
      }
      enum "failed" {
        value 4;
        description
          "Failed";
      }
    }
    description
      "Interface list replication status";
  }

  grouping IFLIST-IFL {
    description
      "Generic interface list info";
    leaf interface-list-name {
      type string {
        length "0..33";
      }
      description
        "Interface-list name";
    }
    leaf interface-list-id {
      type uint32;
      description
        "Interface internal ID";
    }
    leaf items {
      type uint32;
      description
        "Number of items on which interface list is
         replicated";
    }
    leaf is-provisioned {
      type boolean;
      description
        "Is Provisioned";
    }
    leaf is-fib-downloaded {
      type boolean;
      description
        "Is Interface list downloaded to FIB";
    }
    list interface {
      description
        "Interfaces";
      uses IFLIST-IF;
    }
  }

  grouping IFLIST-IF {
    description
      "Interface info for Generic interface list";
    leaf interface-name {
      type string;
      description
        "Interface name";
    }
    leaf pending-replications {
      type uint32;
      description
        "Number of pending replications";
    }
    leaf not-supported-replications {
      type uint32;
      description
        "Number of replications failed because
         unsupported";
    }
    leaf is-fib-downloaded {
      type boolean;
      description
        "Is interface downloaded to FIB";
    }
  }

  grouping ITEM-IFLIST-IF {
    description
      "Interface info for Generic interface list";
    leaf interface-name {
      type string;
      description
        "Interface name";
    }
    leaf replicate-status {
      type Iflist-rep-status;
      description
        "Replicate status";
    }
  }

  grouping ITEM-IFLIST-IFL {
    description
      "Generic interface list info";
    leaf interface-list-name {
      type string {
        length "0..33";
      }
      description
        "Interface-list name";
    }
    leaf interface-list-id {
      type uint32;
      description
        "Interface internal ID";
    }
    list interface {
      max-elements "8";
      description
        "Interfaces";
      uses ITEM-IFLIST-IF;
    }
  }
}
