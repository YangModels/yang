module Cisco-IOS-XR-procfind-oper {
  namespace "http://cisco.com/ns/yang/Cisco-IOS-XR-procfind-oper";
  prefix procfind-oper;

  import Cisco-IOS-XR-types {
    prefix xr;
  }
  import cisco-semver {
    prefix semver;
  }
  include Cisco-IOS-XR-procfind-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR procfind package operational data.
     
     This module contains definitions
     for the following management objects:
       proc-distribution: Process distribution information
     
     Copyright (c) 2013-2019 by Cisco Systems, Inc.
     All rights reserved.";

  revision 2019-04-05 {
    description
      "Establish semantic version baseline.";
    semver:module-version "1.0.0";
  }
  revision 2019-02-18 {
    description
      "Added good description for bag fields.";
  }
  revision 2015-11-09 {
    description
      "IOS XR 6.0 revision.";
  }

  container proc-distribution {
    config false;
    description
      "Process distribution information";
    container nodes {
      description
        "List of nodes";
      list node {
        key "node-name";
        description
          "Process distribution information per node";
        leaf node-name {
          type xr:Node-id;
          description
            "The node name";
        }
        list process {
          key "proc-name";
          description
            "Process distribution information";
          leaf proc-name {
            type xr:Cisco-ios-xr-string {
              length "1..256";
            }
            description
              "Process Name";
          }
          list filter-type {
            key "filter-type";
            description
              "Process distribution information";
            leaf filter-type {
              type xr:Cisco-ios-xr-string {
                length "1..4";
              }
              description
                "Filter Type";
            }
            uses PROCFIND-PROC;
          }
        }
      }
    }
  }
}
