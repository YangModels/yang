module Cisco-IOS-XR-pmengine-clear-act {
  namespace "http://cisco.com/ns/yang/Cisco-IOS-XR-pmengine-clear-act";
  prefix pmengine-clear-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clear statistics for pm-engine module.
     
     Copyright (c) 2018-2019 by Cisco Systems, Inc.
     All rights reserved.";

  revision 2019-10-01 {
    description
      "Made changes to be RFC6087 compliant";
    semver:module-version "1.0.0";
  }
  revision 2019-04-05 {
    description
      "Establish semantic version baseline.";
    semver:module-version "1.0.0";
  }
  revision 2018-01-09 {
    description
      "IOS XR 6.5.1 revision.";
  }

  rpc clear-controller-pm {
    description
      "Clear pm-engine statistics";
    input {
      leaf controller {
        type string;
        description
          "Controller name in R/S/I/P format";
      }
      leaf pm {
        type empty;
        description
          "clear pm counters";
      }
      leaf interval {
        type uint8 {
          range "0..3";
        }
        description
          "Clear 30-sec(2)/15-min(1)/24-hour(2)/all(3) pm statistics";
      }
    }
  }
}
