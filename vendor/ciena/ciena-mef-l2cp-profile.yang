module ciena-mef-l2cp-profile {
    namespace "urn:ciena:params:xml:ns:yang:ciena-pn::ciena-mef-l2cp-profile";
    prefix "mef-l2cp";

    organization
        "Ciena Corporation";

    contact
        "Web URL: http://www.ciena.com/
         E-mail:  yang@ciena.com
         Postal:  7035 Ridge Road
                  Hanover, Maryland 21076
                  U.S.A.
         Phone:   +1 800-921-1144
         Fax:     +1 410-694-5750";

    description
        "This YANG module defines Ciena's configuration of
         the L2 Control Protocol Profile.";

    revision 2017-10-26 {
        description
            "Added description in containers, lists, leafs.";
        reference
            "RFC 6020: YANG - A Data Modeling Language for
             the Network Configuration Protocol (NETCONF).
             No specific reference; standard not available.";
    }

    revision 2015-05-13 {
        description "Initial revision";
        reference
            "RFC 6020: YANG - A Data Modeling Language for
             the Network Configuration Protocol (NETCONF).
             No specific reference; standard not available.";
    }

    typedef l2cp-profile-ref {
        type leafref {
            path "/mef-l2cp:l2cp-profiles/mef-l2cp:l2cp-profile/mef-l2cp:name";
        }
        description
            "This type is used by the data models that need to reference
             configured L2 Control Protocol Profiles.";
    }

    typedef DispositionType {
        type enumeration {
            enum discard {
                description
                    "This indicates L2 Control Protocol PDUs are to be dropped.";
            }
            enum peer {
                description
                    "This indicates L2 Control Protocol PDUs are to be peered.";
            }
            enum forward {
                description
                    "This indicates L2 Control Protocol PDUs are to be forwarded.";
            }
        }
        description
            "This type is used to determine disposition of L2 Control Protocol PDUs.";
    }

    container l2cp-profiles {
        description
            "Configuration Data for L2 Control Protocol Profiles.";

        list l2cp-profile {
            key "name";

            description
                "This denotes the list of L2 Control Protocol Profiles.";

            leaf name {
                type string;
                description
                    "An administratively assigned string, which may be used
                     to identify the profile.";
            }

            leaf description {
                type string;
                description
                    "This is a user-defined string used to describe the profile.";
            }

            leaf untagged-cos-policy {
                type enumeration {
                    enum fixed {
                        description 
                            "This policy assigns fixed resolved and frame CoS to
                             forwarded untagged L2 control frames.";
                    }
                    enum ignore {
                        description
                            "This policy doesn't assign explicit CoS to forwarded
                             untagged L2 control frames. Instead it allows the control 
                             frames to pick resolved and frame CoS in datapath just 
                             like untagged data frames.";
                    }
                }
                description
                    "This denotes CoS policy for forwarded untagged L2 control frames.";
            }

            leaf fixed-cos {
                type uint8 {
                    range "0..63";
                }
                description
                    "This denotes fixed resolved CoS and frame CoS for forwarded 
                     untagged L2 control frames.";
            }

            list protocol-disposition {
                key "protocol";

                description
                    "This denotes the list of disposition of L2 Control Protocols.";

                leaf protocol {
                    type enumeration {
                        enum xstp {
                            description "STP/RSTP/MSTP protocols.
                                         MAC DA 01-80-C2-00-00-00.";
                        }
                        enum lacp {
                            description "LACP protocol. Ethertype 0x8809/01.
                                         MAC DA 01-80-C2-00-00-02.";
                        }
                        enum lamp {
                            description "LAMP protocol. Ethertype 0x8809/02.
                                         MAC DA 01-80-C2-00-00-02.";
                        }
                        enum link-oam {
                            description "LINK OAM protocol. Ethertype 0x8809/03.
                                         MAC DA 01-80-C2-00-00-02.";
                        }
                        enum port-auth {
                            description "Port Authentication protocol. Ethertype 0x888E.
                                         MAC DA 01-80-C2-00-00-03.";
                        }
                        enum e-lmi {
                            description "E-LMI protocol. Ethertype 0x88EE.
                                         MAC DA 01-80-C2-00-00-07.";
                        }
                        enum lldp {
                            description "LLDP protocol. Ethertype 0x88CC.
                                         MAC DA 01-80-C2-00-00-0E.";
                        }
                        enum ptp-peer-delay {
                            description "PTP Peer-Delay protocol. Ethertype 0x88F7.
                                         MAC DA 01-80-C2-00-00-0E.";
                        }
                        enum esmc {
                            description "ESMC protocol. Ethertype 0x8809/0A.
                                         MAC DA 01-80-C2-00-00-02.";
                        }
                        enum garp-block {
                            description "GARP/MRP block range.
                                         MAC DA 01-80-C2-00-00-20 to 01-80-C2-00-00-2F.";
                        }
                        enum bridge-rsvd-0b0f {
                            description "Bridge reserved range.
                                         MAC DA 01-80-C2-00-00-0B/0F.";
                        }
                        enum bridge-rsvd-0c0d {
                            description "Bridge reserved range.
                                         MAC DA 01-80-C2-00-00-0C/0D.";
                        }
                        enum bridge-block {
                            description "Bridge block range.
                                         MAC DA 01-80-C2-00-00-00 to 01-80-C2-00-00-0A and
                                         01-80-C2-00-00-0E.";
                        }
                    }
                    description
                        "This denotes the L2 Control Protocol.";
                }

                leaf untagged-disposition {
                    type DispositionType;
                    description
                        "Disposition assigned to untagged form of L2 control protocol PDUs.";
                }

                leaf tagged-disposition {
                    type DispositionType;
                    description
                        "Disposition assigned to tagged form of L2 control protocol PDUs.";
                }
            }
        }
    }
}
