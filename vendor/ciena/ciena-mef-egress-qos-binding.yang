module ciena-mef-egress-qos-binding {
    namespace "urn:ciena:params:xml:ns:yang:ciena-pn::ciena-mef-egress-qos-binding";
    prefix "mef-egress-qos-binding";
    
    import ciena-mef-egress-qos {
       prefix "mef-egress-qos";
    }

    import ciena-mef-logical-port {
       prefix "mef-logical-port";
    }

    organization
        "Ciena Corporation";
    
    contact
        "Web URL: http://www.ciena.com/
        E-mail:  yang@ciena.com
        Postal:  7035 Ridge Road
                 Hanover, Maryland 21076
                     U.S.A.
        Phone:   +1 800-921-1144
        Fax:     +1 410-694-5750";
    
    description
        "This YANG module defines Ciena's management data definition for the
         association of certain interfaces (e.g. mef-logical-port) to a queue-group-instance.";
    
    revision "2017-10-23" {
        description
            "Added missed references and descriptions.";
        reference
            "RFC 6020: YANG - A Data Modeling Language for
             the Network Configuration Protocol (NETCONF).
             No specific reference; standard not available.";
    }

    revision "2017-02-02" {
        description
            "Initial Version.";
        reference
            "RFC 6020: YANG - A Data Modeling Language for
             the Network Configuration Protocol (NETCONF).
             No specific reference; standard not available.";
    }

/*
 * typedefs
 */

/*
 * features
 */

/*
 * Configuration model.
 */
    container interface-qos-binding {
        description
            "This container contains configuration data for interface QOS binding.";
        
        list interface-qos-binding {
            key "name";
            description
                "It denotes list of interface QOS binding configuration data.";
            
            leaf name {
                type string;
                description
                    "This object indicates the identifier and is a 
                     text string that is used to identify an interface-qos-binding. 
                     Unique string values are chosen to uniquely identify
                     interface-qos-binding.
                     This object should only be used for interfaces where it is not possible
                     to import ciena-mef-egress-qos module (e.g. logical-port).";
            }

            leaf queue-group-instance {
                type mef-egress-qos:queue-group-ref;
                description
                    "A reference to a Queue Group Instance specific to the Interface (e.g. logical-port).";
            }

            leaf logical-port {
                type mef-logical-port:logical-port-ref;

                description
                    "Reference to the logical-port that the queue-group-instance is the default
                    Queue Group Instance for the logical-port and all logical-interfaces (e.g. flow-points)
                    which are not specifying a specific Queue Group Instance otherwise.";
            }
        }
    }
}
