module ciena-mef-cos-to-frame-map {
    namespace "urn:ciena:params:xml:ns:yang:ciena-pn:ciena-mef-cos-to-frame-map";
    prefix "ctf";

    organization
        "Ciena Corporation";

    contact
        "Web URL: http://www.ciena.com/
         E-mail:  yang@ciena.com
         Postal:  7035 Ridge Road
                  Hanover, Maryland 21076
                  U.S.A.
         Phone:   +1 800-921-1144
         Fax:     +1 410-694-5750";

    description
        "This YANG module defines the CoS to Frame Map. A combination of 
         cos and color yields a pcp and dei or ip-dscp or mpls-tc.
         Additionally, for some forwarding-plane architectures, this module also
         defines the CoS to Queue Map. CoS yields a Queue Number and also a WRED
         curve number for green or yellow frames.";

    revision 2017-10-26 {
        description
            "Added description in containers, lists, leafs.";
        reference
            "RFC 6020: YANG - A Data Modeling Language for
             the Network Configuration Protocol (NETCONF).
             No specific reference; standard not available.";
    }

    revision 2015-07-16 {
        description "Initial revision.";
        reference
            "RFC 6020: YANG - A Data Modeling Language for
             the Network Configuration Protocol (NETCONF).
             No specific reference; standard not available.";
    }

    /*
     * Typedefs
     */
    typedef cos-to-frame-ref {
        type leafref {
            path "/ctf:cos-to-frame-maps/ctf:cos-to-frame-map/ctf:name";
        }
        description
            "This type is used by data models that need to reference
             configured CoS to frame maps.";
    }

    container cos-to-frame-maps {
        description
            "Configuration data for CoS to Frame Maps.";

        list cos-to-frame-map {
            key "name";

            description
                "A list of profiles that can contain several map entries.";

            leaf name {
                type string;
                description
                    "A string used to uniquely identify a profile entry within
                     the list of maps (profiles).";
            }

            leaf description {
                type string;
                description
                    "A more detailed description of the map.";
            }

            list map-entry {
                key "cos color";

                description
                    "A list of map entries within a CoS to Frame map.";

                leaf cos {
                    type uint8 {
                        range "0..63";
                    }
                    description
                        "Class of Service bits.";
                }

                leaf color {
                    type enumeration {
                        enum green {
                            description
                                "A color of green indicates the frame is conformant with CIR.";
                        }
                        enum yellow {
                            description
                                "A color of yellow indicates the frame is not conformant with
                                 CIR but is conformant with EIR and red means it is not
                                 conformant with EIR or CIR and thus will be dropped.";
                        }
                    }
                    description
                        "The assigned color for the frame.";
                }

                leaf pcp {
                    type uint8 {
                        range "0..7";
                    }
                    description
                        "The frame's VLAN tag priority bits will be set to this 
                         value if the frame's assigned cos and color matches this 
                         map instance.";
                }

                leaf dei {
                    type enumeration {
                        enum enabled {
                            description 
                                "The frame's VLAN tag DEI bit will be set to this if the 
                                 frame's assigned cos and color matches this map instance.";
                        }
                        enum disabled {
                            description 
                                "The frame's VLAN tag DEI bit will be set to this if the 
                                 frame's assigned cos and color matches this map instance.";
                        }
                    }
                    description
                        "Drop Eligibility Indication.";
                }

                leaf ip-dscp {
                    type uint8 {
                        range "0..63";
                    }
                    description
                        "IP DiffServ Code Point value.";
                }

                leaf mpls-tc {
                    type uint8 {
                        range "0..7";
                    }
                    description
                        "MPLS Traffic Class (TC) bits.";
                }     

                leaf queue {
                    type uint32;
                    description
                        "Queue mapped to by internal CoS for E-QoS.";
                }

                leaf green-wred-curve {
                    type uint32;
                    description
                        "WRED curve relative to a Queue to use for traffic whose internal
                         color is Green.";
                }

                leaf yellow-wred-curve {
                    type uint32;
                    description
                        "WRED curve relative to a Queue to use for traffic whose internal
                         color is Yellow.";
                }
            }
        }
    }
}
