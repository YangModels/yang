module ciena-mef-frame-to-cos-map {
    namespace "urn:ciena:params:xml:ns:yang:ciena-pn:ciena-mef-frame-to-cos-map";
    prefix "ftc";

    organization
        "Ciena Corporation";
 
    contact
        "Web URL: http://www.ciena.com/
         E-mail:  yang@ciena.com
         Postal:  7035 Ridge Road
                  Hanover, Maryland 21076
                  U.S.A.
         Phone:   +1 800-921-1144
         Fax:     +1 410-694-5750";

    description
        "This YANG module defines the Frame to Cos Map.";
    
    revision 2017-10-23 {
        description
            "Added missing reference and description for container and list.";
        reference
            "RFC 6020: YANG - A Data Modeling Language for
             the Network Configuration Protocol (NETCONF).
             No specific reference; standard not available.";
    }

    revision 2015-07-16 {
        description 
            "Initial revision.";
        reference
            "RFC 6020: YANG - A Data Modeling Language for
             the Network Configuration Protocol (NETCONF).
             No specific reference; standard not available.";
    }
    
    /*
     * Typedefs
     */
    typedef frame-to-cos-ref {
        type leafref {
            path "/ftc:frame-to-cos-maps/ftc:frame-to-cos-map/ftc:name";
        }
        description
            "This type is used by data models that need to reference
             configured frame to CoS maps.";
    }
    
    container frame-to-cos-maps {
        description
            "Configuration Data for Frame to CoS profiles.";    

        list frame-to-cos-map {
            key "name";
            
            description
                "A list of profiles that can contain several map entries.";

            leaf name {
                type string;             
                description
                    "A string used to uniquely identify a list of profiles.";
            }
            
            leaf description {
                type string;
                description
                    "A more detailed description of the map.";
            }
            
            list map-entry {
                key "name";
                description
                    "A list of map entries within a frame-to-cos map profile.";
                
                leaf name {
                    type string;
                    description
                        "A string used to uniquely identify a particular map 
                         entry within the profile.";
                }
                
                choice frame-type {
                    description
                        "The frame type can be either vlan-tag or IP or MPLS type.";

                    case vlan-tag {
                        leaf pcp {
                            type uint8 {
                                range "0..7";
                            }
                            description
                                "This represents VLAN tag priority bits of frame.";
                        }

                        leaf dei {
                            type enumeration {
                                enum enabled {
                                    description
                                        "Enables VLAN tag DEI bit.";
                                }
                                enum disabled {
                                    description
                                        "Disables VLAN tag DEI bit.";
                                }
                            }
                            description
                                "This represents VLAN tag DEI bits of frame.";
                        }
                        description
                            "For layer 2 frames, the VLAN tag's priority bits and 
                             DEI value are used as key fields to derive an assigned 
                             COS and color for the frame.";
                    }
                    
                    case ip {
                        leaf ip-dscp {
                            type uint8 {
                                range "0..63";
                            }
                            description
                                "This represents IP header DSCP value.";
                        }
                        description
                            "For IP frames, DSCP bits are used to derive an assigned 
                             CoS and color for the frame.";
                    }
                    
                    case mpls {
                        leaf mpls-tc {
                            type uint8 {
                                range "0..7";
                            }
                            description
                                "This represents MPLS label EXP bits.";
                        }
                        description
                            "For frames with MPLS label, EXP bits are used to derive an 
                             assigned CoS and color for the frame.";
                    }
                }
                
                leaf cos {
                    type uint8 {
                        range "0..63";
                    }
                    description
                        "Class of Service bits.";
                }
                
                leaf color {
                    type enumeration {
                        enum green {
                            description
                                "This represents frame color green.";
                        }
                        enum yellow {
                            description
                                "This represents frame color yellow.";
                        }
                        enum red {
                            description
                                "This represents frame color red.";
                        }
                    }
                    description
                        "The assigned color for the frame. A color of green
                         indicates the frame is conformant with CIR,
                         a yellow indicates it is not conformant with CIR but
                         is conformant with EIR and red means it is not 
                         conformant with EIR or CIR and thus will be dropped.";
                }     
            }
        }
    }
}
