module ciena-bw-calculation-mode {
  namespace "http://www.ciena.com/ns/yang/ciena-bw-calculation-mode";
  prefix "ciena-bw-calculation-mode";

  organization
    "Ciena Corporation";

  contact
    "Web URL: http://www.ciena.com/
    E-mail:  yang@ciena.com
    Postal:  7035 Ridge Road
             Hanover, Maryland 21076
             U.S.A.
    Phone:   +1 800-921-1144
    Fax:     +1 410-694-5750";

  description
    "This YANG module defines the nodes for
     BW Calculation Mode.

     Copyright (c) 2017 Ciena Corporation.  All rights
     reserved.

     All information contained herein is, and remains
     the property of Ciena Corporation. Dissemination of this
     information or reproduction of this material is strictly
     forbidden unless prior written permission is obtained from
     Ciena Corporation.";

  revision "2017-10-23" {
      description
          "Added missed references and descriptions";
      reference
          "RFC 6020: YANG - A Data Modeling Language for
           the Network Configuration Protocol (NETCONF).
           No specific reference; standard not available.";
  }

  revision "2016-12-08" {
      description
          "Initial version";
      reference
          "RFC 6020: YANG - A Data Modeling Language for
           the Network Configuration Protocol (NETCONF).
           No specific reference; standard not available.";
  }

  /*
   * Type definitions
   */

   identity bw-calculation-modes {
      description
         "Modes of bandwidth calculation.";
   }

   identity transport {
       base bw-calculation-modes;
       description
          "Bandwidth calculation mode is transport.";
   }

   identity payload {
      base bw-calculation-modes;
      description
         "Bandwidth calculation mode is payload.";
   }

  /*
   * Configuration data nodes
   */
   
   container bw-calculation-mode {
       description
           "Mode configuration for bandwidth calculations."; 

           leaf eqos-bw-calculation-mode {
               type identityref {
                   base bw-calculation-modes;
               }
               default transport;  

               description
                   "Egress QoS Bandwidth calculation mode selection. (Egress Shaping)";
           }
           leaf iqos-bw-calculation-mode {
               type identityref {
                   base bw-calculation-modes;
               }
               default transport;  

               description
                   "Ingress QoS Bandwidth calculation mode selection. (Ingress Metering)";
          }
    }    
}
