module ciena-mef-flood-containment-profile {
    namespace "urn:ciena:params:xml:ns:yang:ciena-pn:ciena-mef-flood-containment-profile";
    prefix "mef-fc";

    organization
        "Ciena Corporation";

    contact
        "Web URL: http://www.ciena.com/
         E-mail:  yang@ciena.com
         Postal:  7035 Ridge Road
                  Hanover, Maryland 21076
                  U.S.A.
         Phone:   +1 800-921-1144
         Fax:     +1 410-694-5750";

    description
        "This YANG module defines Ciena's configuration of
         the Flood Containment Profile.";

    revision 2017-10-26 {
        description
            "Added description in containers, lists, leafs.";
        reference
            "RFC 6020: YANG - A Data Modeling Language for
             the Network Configuration Protocol (NETCONF).
             No specific reference; standard not available.";
    }

    revision 2016-01-13 {
        description "Initial revision";
        reference
            "RFC 6020: YANG - A Data Modeling Language for
             the Network Configuration Protocol (NETCONF).
             No specific reference; standard not available.";
    }

    typedef flood-containment-profile-ref {
        type leafref {
            path "/mef-fc:flood-containment-profiles/mef-fc:flood-containment-profile/mef-fc:name";
        }
        description
            "This type is used by the data models that need to reference
             configured Flood Containment Profiles.";
    }

    container flood-containment-profiles {
        description
            "Configuration data for Flood Containment Profiles.";

        list flood-containment-profile {
            key "name";

            description
                "This denotes list of Flood Containment Profiles.";

            leaf name {
                type string {
                    length "1..1024";
                }
                description
                    "An administratively assigned string, which may be used
                     to identify the profile.";
            }

            leaf description {
                type string;
                description
                    "This is a user-defined string used to describe the profile.";
            }

            list containment {
                key "frame-type";

                description
                    "This denotes list of permissible rate for frame types.";

                leaf frame-type {
                    type bits {
                        bit unknown-unicast {
                            description
                                "Indicates it's a unknown unicast frame.";
                        }
                        bit unknown-l2-multicast {
                            description
                                "Indicates it's a unknown L2 multicast frame.";
                        }
                        bit unknown-ip-multicast {
                            description
                                "Indicates it's a unknown IP multicast frame.";
                        }
                        bit known-multicast {
                            description
                                "Indicates it's a known multicast frame.";
                        }
                        bit broadcast {
                            description
                                "Indicates it's a broadcast frame.";
                        }
                    }
                    description
                        "The frame types to be contained with the given rate.";
                }

                leaf rate {
                    type uint64;
                    description
                        "Data rate in kbps.";
                }
            }
        }
    }
}
