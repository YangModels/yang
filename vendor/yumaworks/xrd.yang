module xrd {
    yang-version 1.1;
    namespace "http://docs.oasis-open.org/ns/xri/xrd-1.0";
    prefix "xrd";

    import yuma-ncx { prefix ncx; }

    organization "YumaWorks, Inc.";

    contact
        "Support <support@yumaworks.com>";

    description
         "XRD template for parsing by yangcli-pro

     Copyright (c) 2016 YumaWorks, Inc. All rights reserved.

     Redistribution and use in source and binary forms, with or
     without modification, is permitted pursuant to, and subject
     to the license terms contained in, the BSD 3-Clause License
     http://opensource.org/licenses/BSD-3-Clause";

    revision 2016-12-15 {
       description
         "Initial version.";
    }

    container XRD {
        ncx:abstract;
        config false;
        leaf-list Link {
            ncx:metadata "string rel";
            ncx:metadata "string href";
            type string;  // really empty
            description "The Link element";
        }
    }
}
