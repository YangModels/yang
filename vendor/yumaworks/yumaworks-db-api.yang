module yumaworks-db-api {

    namespace "http://yumaworks.com/ns/yumaworks-db-api";

    prefix "ydb";

    import ietf-yang-patch { prefix yp; }
    import yumaworks-ycontrol { prefix yctl; }

    organization "YumaWorks, Inc.";

    contact
        "Support <support at yumaworks.com>";

    description 
       "YumaPro Database API Sub-Agent message definitions.

     Copyright (c) 2014 - 2016 YumaWorks, Inc. All rights reserved.

     Redistribution and use in source and binary forms, with or
     without modification, is permitted pursuant to, and subject
     to the license terms contained in, the BSD 3-Clause License
     http://opensource.org/licenses/BSD-3-Clause";

    revision 2016-08-29 {
        description
          "Update yp-ha-mode event";
    }

    revision 2016-07-31 {
        description
          "Add new events to support YP-HA mode changes.";
    }

    revision 2015-03-29 {
        description
          "Add edit-type parameter to edit-request.";
    }

    revision 2014-11-18 {
        description
          "Initial version for datastore access.";
    }

    augment "/yctl:ycontrol/yctl:payload" {
      container db-api {

        choice message-type {
          mandatory true;

          leaf register-request {
            type empty;
            description
             "Message type: subsys-request;
              Purpose: register the DB-API subsystem
              Expected Response Message: ok or error";
          }

          container edit-request {
            description
             "Message type: subsys-request;
              Purpose: Ask the main server to accept an edit request
              to be added to the running configuration, and saved to
              NV-storage unless the :startup capability is supported.

              Expected Response Message: ok or error";

            leaf target {
              type string;  // target-path-string
              mandatory true;
              description
               "Identifies the target resource for the edit
                operation.";
            }

            leaf edit-type {
              type enumeration {
                enum user {
                  description "A user edit with access control";
                }
                enum system {
                  description "A system edit without access control";
                }
              }
              default user;
              description
               "Indicates whether this is a user edit or system edit.
                System edits will bypass all access control enforcement,
                including the ncx:user-write extension.";
            }

            uses yp:yang-patch;

          }  // container edit-request

          container yp-ha-mode {
            description
             "Message type: subsys-event;
              Purpose: send mode change event to the server
              Expected Response Message: none";

            choice action {
              mandatory true;
              leaf go-active {
                type empty;
                description
                  "Become the YP-HA active server.
                   All normal management operations are supported
                   in this mode.";
              }
              container go-standby {
                description
                  "Become a YP-HA standby server, and try to connect
                   to the active server 'new-active'. Only the superuser
                   can use management sesssions in this mode.";

                leaf new-active {
                  type string;
                  mandatory true;
                  description
                    "Server name of the active server to use";
                }
              }
              leaf go-none {
                type empty;
                description
                  "Leave current YP-HA role and wait new role.
                   Only the superuser can use management sesssions
                   in this mode.";
              }

            }
          }  // container yp-ha-mode

        } // choice message-type
      } // container db-api
    } // augment
}
