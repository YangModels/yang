module InterfaceDataType {
  namespace "http://brocade.com/ns/interfacedatatype";
  prefix interfacedatatype;

  import ietf-yang-types {
    prefix yang;
  }
  import ietf-inet-types {
    prefix inet;
  }

  typedef UI32Range {
    type string {
      pattern "[0-9]+(-[0-9]+)?(,[0-9]+(-[0-9]+)?)*";
    }
  }

  typedef MACRange {
    type string {
      pattern "[0-9a-fA-F][0-9a-fA-F][0-9a-fA-F][0-9a-fA-F].[0-9a-fA-F][0-9a-fA-F][0-9a-fA-F][0-9a-fA-F].[0-9a-fA-F][0-9a-fA-F][0-9a-fA-F][0-9a-fA-F](-[0-9a-fA-F][0-9a-fA-F])?(,[0-9a-fA-F][0-9a-fA-F][0-9a-fA-F][0-9a-fA-F].[0-9a-fA-F][0-9a-fA-F][0-9a-fA-F][0-9a-fA-F].[0-9a-fA-F][0-9a-fA-F][0-9a-fA-F][0-9a-fA-F](-[0-9a-fA-F][0-9a-fA-F])?)*";
    }
  }

  container DataType {
    leaf bitmap {
      type bits {
        bit pos0 {
          position 0;
        }
        bit pos3 {
          position 3;
        }
      }
      mandatory true;
    }
    leaf datetime {
      type yang:date-and-time;
      mandatory true;
    }
    leaf decimal64 {
      type decimal64 {
        fraction-digits 2;
      }
      mandatory true;
    }
    leaf utype {
      type union {
        type int32;
        type string;
      }
      mandatory true;
    }
    leaf ipv4prefix {
      type inet:ipv4-prefix;
      mandatory true;
    }
    leaf ipv6prefix {
      type inet:ipv6-prefix;
      mandatory true;
    }
    leaf snmpobjectid {
      type yang:object-identifier;
      mandatory true;
    }
    leaf rangeintegers {
      type UI32Range;
      mandatory true;
    }
    leaf rangeintegers2 {
      type UI32Range;
    }
    leaf rangemac {
      type MACRange;
    }
    leaf ui8default {
      type uint8;
    }
    leaf ui16default {
      type uint16;
    }
    leaf ui64default {
      type uint64;
    }
    leaf stringuc {
      type string;
      default "d-e-f-a-u-l-t";
    }
    leaf ui32uc {
      type uint32;
      default "99";
    }
    leaf booluc {
      type empty;
    }
    leaf enumuc {
      type enumeration {
        enum "WAVE";
        enum "DCM";
        enum "PLATFORM";
        enum "PLUGIN";
      }
    }
    leaf ipv4addressuc {
      type inet:ipv4-address;
    }
    leaf-list stringvectoruc {
      type string;
    }
    leaf-list ui32vectoruc {
      type uint32;
    }
    leaf hostuc {
      type inet:host;
    }
    leaf ui64uc {
      type uint64;
      default "64";
    }
    leaf uuid {
      type string;
    }
  }
}
