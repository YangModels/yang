module DcmInterface {
  namespace "http://brocade.com/ns/dcminterface";
  prefix dcminterface;

  import ietf-inet-types {
    prefix inet;
  }
  import ietf-yang-types {
    prefix yang;
  }

  typedef interfaceType {
    type string;
    description
      "mappedId/slot/port";
  }

  container interface_priority {
    leaf vlanPriority {
      type int32;
      mandatory true;
    }
    leaf ethernetPriority {
      type int32;
      mandatory true;
    }
    container interface_class {
      leaf vlanClass {
        type int32;
        mandatory true;
      }
      leaf ethernetClass {
        type int32;
        mandatory true;
      }
    }
  }
  container dcminterfaces {
    list dcminterface {
      key "name";
      max-elements "1024";
      leaf name {
        type string;
      }
      leaf demostring {
        type string;
      }
      leaf ip {
        type inet:ipv4-address;
        mandatory true;
      }
      leaf ipdef {
        type inet:ipv4-address;
        mandatory true;
      }
      leaf-list ipV4Vector {
        type inet:ipv4-address;
      }
      leaf ip6 {
        type inet:ipv6-address;
        mandatory true;
      }
      leaf-list ipV6Vector {
        type inet:ipv6-address;
      }
      leaf ipVx {
        type inet:ip-address;
        mandatory true;
      }
      leaf mac {
        type yang:mac-address;
        mandatory true;
      }
      leaf mac2 {
        type string {
          pattern "[0-9a-fA-F]{4}((\\.)[0-9a-fA-F]{4}){2}";
        }
        mandatory true;
      }
      leaf wwn {
        type string;
        mandatory true;
      }
      leaf mtu8 {
        type int8;
        mandatory true;
      }
      leaf mtu16 {
        type int16;
        mandatory true;
      }
      leaf mtu32 {
        type int32;
        mandatory true;
      }
      leaf mtu32def {
        type int32;
        mandatory true;
      }
      leaf-list mtu32Vector {
        type int32;
      }
      leaf mtu8u {
        type uint8;
        mandatory true;
      }
      leaf mtu16u {
        type uint16;
        mandatory true;
      }
      leaf mtu32u {
        type uint32;
        mandatory true;
      }
      leaf mtu32udef {
        type uint32;
      }
      leaf mtu64u {
        type uint64;
        mandatory true;
      }
      leaf enumtype {
        type enumeration {
          enum "TCP";
          enum "UDP";
          enum "SMTP";
          enum "IP";
          enum "ETHERNET";
        }
      }
      leaf enumtype2 {
        type enumeration {
          enum "DCM_DEBUG";
          enum "DCM_INFO";
          enum "DCM_WARNING";
          enum "DCM_ERROR";
        }
      }
      leaf isEthernet {
        type boolean;
        mandatory true;
      }
      leaf interfaceTuple {
        type interfaceType;
      }
      leaf operationalsi8 {
        type int8;
        mandatory true;
        config false;
      }
      leaf operationalsi16 {
        type int16;
        mandatory true;
        config false;
      }
      leaf operationalsi32 {
        type int32;
        mandatory true;
        config false;
      }
      leaf-list operationalsi32Vector {
        type int32;
        config false;
      }
      leaf operationalsi64 {
        type int64;
        mandatory true;
        config false;
      }
      leaf operationalui8 {
        type uint8;
        mandatory true;
        config false;
      }
      leaf operationalui16 {
        type uint16;
        mandatory true;
        config false;
      }
      leaf operationalui32 {
        type uint32;
        mandatory true;
        config false;
      }
      leaf-list operationalui32Vector {
        type uint32;
        config false;
      }
      leaf operationalui64 {
        type uint64;
        mandatory true;
        config false;
      }
      leaf operationalIsEthernet {
        type boolean;
        mandatory true;
        config false;
      }
      leaf operationalIp {
        type inet:ipv4-address;
        mandatory true;
        config false;
      }
      leaf operationalIp6 {
        type inet:ipv6-address;
        mandatory true;
        config false;
      }
      leaf operationalMac {
        type yang:mac-address;
        mandatory true;
        config false;
      }
      leaf-list operationalMacVector {
        type yang:mac-address;
        config false;
      }
      leaf operationalWwn {
        type string;
        mandatory true;
        config false;
      }
      leaf shutdown {
        type empty;
      }
    }
  }
}
