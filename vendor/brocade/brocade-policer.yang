module brocade-policer {
  namespace "urn:brocade.com:mgmt:brocade-policer";
  prefix policer;

  import brocade-interface {
    prefix interface;
  }

  organization "Brocade Communications";
  contact
    "SSM-QoS Team";
  description
    "This module describes the data model for Modular Quality of Service
     (Modular QoS)";

  revision 2011-03-04 {
    description
      "Initial Version";
  }

  typedef priority-value {
    type uint32 {
      range "0..7";
    }
  }

  typedef dscp-value {
    type uint32 {
      range "0..63";
    }
  }

  typedef tc-value {
    type uint32 {
      range "0..7";
    }
  }

  typedef precedence-value {
    type uint32 {
      range "0..7";
    }
  }

  typedef map-name-type {
    type string {
      pattern "[a-zA-Z]{1}([-a-zA-Z0-9_]{0,63})";
    }
  }

  typedef mac-ip-acl-name {
    type string {
      pattern "[a-zA-Z0-9]{1}([-a-zA-Z0-9_]{0,62})";
    }
    description
      "The definition for the mac/ip access-list name.";
  }

  typedef shaping-rate-limit {
    type uint64 {
      range "28000 .. 100000000";
    }
  }

  list police-priority-map {
    key "name";
    leaf name {
      type map-name-type;
    }
    container conform {
      leaf map-pri0-conform {
        type priority-value;
      }
      leaf map-pri1-conform {
        type priority-value;
      }
      leaf map-pri2-conform {
        type priority-value;
      }
      leaf map-pri3-conform {
        type priority-value;
      }
      leaf map-pri4-conform {
        type priority-value;
      }
      leaf map-pri5-conform {
        type priority-value;
      }
      leaf map-pri6-conform {
        type priority-value;
      }
      leaf map-pri7-conform {
        type priority-value;
      }
    }
    container exceed {
      leaf map-pri0-exceed {
        type priority-value;
      }
      leaf map-pri1-exceed {
        type priority-value;
      }
      leaf map-pri2-exceed {
        type priority-value;
      }
      leaf map-pri3-exceed {
        type priority-value;
      }
      leaf map-pri4-exceed {
        type priority-value;
      }
      leaf map-pri5-exceed {
        type priority-value;
      }
      leaf map-pri6-exceed {
        type priority-value;
      }
      leaf map-pri7-exceed {
        type priority-value;
      }
    }
  }
  list class-map {
    key "name";
    leaf name {
      type map-name-type;
    }
    container match {
      when "((../name !=\"default\") and (../name !=\"cee\"))";
      container access-group {
        description
          "This provides the grouping of configuration
           elements of MAC/IP access list.";
        leaf access-group-name {
          type mac-ip-acl-name;
          description
            "This specifies the Access list name which is 
             already configured at the global level. This
             access list contains access rules.";
        }
      }
    }
  }
  list policy-map {
    key "po-name";
    leaf po-name {
      type map-name-type;
    }
    list class {
      key "cl-name";
      leaf cl-name {
        type map-name-type;
      }
      container police {
        when "../cl-name != \"cee\"";
        leaf cir {
          type uint64 {
            range "40000..40000000000";
          }
          units "Bits Per Second.";
        }
        leaf cbs {
          type uint64 {
            range "1250..5000000000";
          }
          units "Bytes.";
        }
        leaf eir {
          type uint64 {
            range "0..40000000000";
          }
          units "Bits Per Second.";
        }
        leaf ebs {
          type uint64 {
            range "1250..5000000000";
          }
          units "Bytes.";
        }
        leaf set-priority {
          type string {
            length "1..64";
          }
        }
        leaf conform-set-dscp {
          type dscp-value;
        }
        leaf conform-set-prec {
          type precedence-value;
        }
        leaf conform-set-tc {
          mandatory false;
          type tc-value;
        }
        leaf exceed-set-dscp {
          type dscp-value;
        }
        leaf exceed-set-prec {
          type precedence-value;
        }
        leaf exceed-set-tc {
          type tc-value;
        }
      }
      container set {
        when "((../cl-name !=\"default\") and (../cl-name !=\"cee\"))";
        container set_cos_tc {
          leaf cos {
            type uint8 {
              range "0 .. 7" {
                description
                  "<0-7>;;CoS value";
              }
            }
          }
          leaf traffic-class {
            type uint8 {
              range "0 .. 7" {
                description
                  "<0-7>;;Traffic class value";
              }
            }
          }
        }
        container set_dscp {
          leaf dscp {
            type uint16 {
              range "0 .. 63" {
                description
                  "<0-63>;;dscp value";
              }
            }
          }
        }
      }
      container map {
        when "../cl-name !=\"cee\"";
        leaf cos-mutation {
          when "../../cl-name = \"default\"";
          type map-name-type;
          description
            "This specifies the mapping between CoS 
             to Cos.";
        }
        leaf cos-traffic-class {
          when "../../cl-name = \"default\"";
          type map-name-type;
          description
            "This specifies the mapping between CoS 
             to Traffic class.";
        }
        leaf dscp-cos {
          when "../../cl-name = \"default\"";
          type map-name-type;
          description
            "This specifies the mapping between Dscp
             to Cos.";
        }
        leaf dscp-traffic-class {
          when "../../cl-name = \"default\"";
          type map-name-type;
          description
            "This specifies the mapping between Dscp
             to Traffic class.";
        }
        leaf dscp-mutation {
          when "../../cl-name = \"default\"";
          type map-name-type;
          description
            "This specifies the mapping between Dscp
             to Dscp.";
        }
        leaf sflow {
          when "../../cl-name !=\"default\"";
          type map-name-type;
          description
            "This specifies the sflow action.";
        }
      }
      container shape {
        when "../cl-name = \"default\"";
        leaf shaping_rate {
          type shaping-rate-limit;
        }
      }
      container scheduler {
        when "../cl-name = \"default\"";
        container strict-priority {
          leaf priority-number {
            type uint8 {
              range "0 .. 7";
            }
          }
          leaf scheduler-type {
            type enumeration {
              enum "dwrr" {
                value 1;
              }
            }
          }
          leaf dwrr-traffic-class0 {
            type uint32 {
              range "0 .. 100";
            }
          }
          leaf dwrr-traffic-class1 {
            type uint32 {
              range "0 .. 100";
            }
          }
          leaf dwrr-traffic-class2 {
            type uint32 {
              range "0 .. 100";
            }
          }
          leaf dwrr-traffic-class3 {
            type uint32 {
              range "0 .. 100";
            }
          }
          leaf dwrr-traffic-class4 {
            type uint32 {
              range "0 .. 100";
            }
          }
          leaf dwrr-traffic-class5 {
            type uint32 {
              range "0 .. 100";
            }
          }
          leaf dwrr-traffic-class6 {
            type uint32 {
              range "0 .. 100";
            }
          }
          leaf dwrr-traffic-class-last {
            type uint32 {
              range "0 .. 100";
            }
          }
          leaf TC1 {
            type shaping-rate-limit;
          }
          leaf TC2 {
            type shaping-rate-limit;
          }
          leaf TC3 {
            type shaping-rate-limit;
          }
          leaf TC4 {
            type shaping-rate-limit;
          }
          leaf TC5 {
            type shaping-rate-limit;
          }
          leaf TC6 {
            type shaping-rate-limit;
          }
          leaf TC7 {
            type shaping-rate-limit;
          }
        }
      }
      container priority-mapping-table {
        when "../cl-name = \"cee\"";
        container import {
          leaf cee {
            type map-name-type;
            description
              "This specifies the cee map config to be imported.";
          }
        }
      }
    }
  }

  grouping ser-pol {
    leaf in {
      type map-name-type;
    }
    leaf out {
      type map-name-type;
    }
  }

  augment "/interface:interface/interface:tengigabitethernet" {
    container service-policy {
      uses ser-pol;
    }
  }
  augment "/interface:interface/interface:gigabitethernet" {
    container service-policy {
      uses ser-pol;
    }
  }
  augment "/interface:interface/interface:fortygigabitethernet" {
    container service-policy {
      uses ser-pol;
    }
  }
  augment "/interface:interface/interface:port-channel" {
    container service-policy {
      uses ser-pol;
    }
  }
}
