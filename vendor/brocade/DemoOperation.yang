module DemoOperation {
  namespace "http://brocade.com/demowysereaoperation/";
  prefix brocade-demo-wysereaoperation;

  import ietf-yang-types {
    prefix yang;
  }
  import ietf-inet-types {
    prefix inet;
  }

  organization "Brocade Communications Inc.";
  description
    "Demo action point";

  revision 2011-01-18;

  container demoaction_container;
}
