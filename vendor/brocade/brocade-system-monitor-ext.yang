module brocade-system-monitor-ext {
  namespace "urn:brocade.com:mgmt:brocade-system-monitor-ext";
  prefix system-monitor-extensions;

  import ietf-inet-types {
    prefix inet;
  }
  import ietf-yang-types {
    prefix ietfyang;
  }
  import brocade-common-def {
    prefix common-def;
  }

  organization "Brocade Communications Inc.";
  contact
    "Brocade Communications Systems, Inc.
     Postal: 130 Holger Way
             San Jose, CA 95134
             U.S.A
     Tel: +1-408-333-6061
     E-mail: support@Brocade.com
     web: www.brocade.com.";
  description
    "This sub module defines show system-monitor data model
     Copyright (c) 2011 by Brocade Communications Systems, Inc.
     All rights reserved.";

  revision 2011-05-05 {
    description
      "Initial version of this module.";
  }

  typedef system-monitor-health-state-enum {
    type enumeration {
      enum "state-unknown";
      enum "state-healthy";
      enum "state-marginal";
      enum "state-down";
      enum "state-unmonitored";
    }
  }

  typedef system-monitor-port-state-enum {
    type enumeration {
      enum "port-healthy";
      enum "port-marginal";
      enum "port-faulty";
      enum "port-offline";
    }
  }

  augment "/common-def:show" {
    container system;
  }
  rpc show-system-monitor {
    input {
      leaf rbridge-id {
        mandatory false;
        type common-def:rbridge-id-all-type;
      }
    }
    output {
      list switch-status {
        leaf rbridge-id-out {
          type common-def:rbridge-id-type;
        }
        leaf switch-name {
          type string;
          description
            "name of the switch";
        }
        leaf switch-ip {
          type inet:ip-address;
          description
            "ip address of the switch";
        }
        leaf report-time {
          type ietfyang:date-and-time;
          description
            "switch report timestamp";
        }
        leaf switch-state {
          type system-monitor-health-state-enum;
          description
            "switch status based on components";
        }
        leaf switch-state-reason {
          type string;
          description
            "component reason for switch status";
        }
        list component-status {
          leaf component-name {
            type string;
            description
              "component name";
          }
          leaf component-state {
            type system-monitor-health-state-enum;
            description
              "component status based on thresholds";
          }
        }
        list port-status {
          leaf port-area {
            type uint32;
            description
              "port identifier";
          }
          leaf port-name {
            type string;
          }
          leaf port-state {
            type system-monitor-port-state-enum;
            description
              "port state";
          }
        }
      }
    }
  }
}
