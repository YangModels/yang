module brocade-ntp {
  namespace "urn:brocade.com:mgmt:brocade-ntp";
  prefix ntp-server;

  import ietf-inet-types {
    prefix inet;
  }
  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "Instrument to configure ntp servers and monitoring active server";

  revision 2009-05-01 {
    description
      "Initial version of this module.";
  }

  rpc show-ntp {
    description
      "show active ntp server for cluster or specified switchid";
    input {
      leaf rbridge-id {
        mandatory false;
        type common-def:rbridge-id-all-type;
      }
    }
    output {
      list node-active-server {
        leaf rbridge-id-out {
          type common-def:rbridge-id-type;
        }
        choice ip4-6-or-local {
          case ipv4-6 {
            leaf active-server {
              type inet:ip-address;
            }
          }
          case local {
            leaf LOCL {
              default "true";
              type boolean;
            }
          }
        }
      }
    }
  }
  container ntp {
    list server {
      key "ip";
      max-elements "5";
      leaf ip {
        type inet:ip-address;
      }
      leaf key {
        type uint32 {
          range "0 .. 65535" {
            error-message
              "Key ID must be in the range
               1..65535";
          }
        }
        default "0";
      }
    }
    list authentication-key {
      key "keyid";
      max-elements "5";
      leaf keyid {
        type uint32 {
          range "1 .. 65535" {
            error-message
              "Key ID must be in the range
               1..65535";
          }
        }
      }
      leaf md5 {
        type string {
          length "1 .. 15" {
            error-message
              "MD5 string must be in the range
               1 .. 15 alphanumeric characters";
          }
        }
      }
    }
  }
}
