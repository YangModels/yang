module brocade-pim {
  namespace "urn:brocade.com:mgmt:brocade-pim";
  prefix pim;

  import brocade-rbridge {
    prefix rbridge;
  }
  import brocade-interface {
    prefix interface;
  }
  import brocade-ip-config {
    prefix ip-config;
  }
  import brocade-common-def {
    prefix common-def;
  }
  import ietf-inet-types {
    prefix inet;
  }

  organization "Brocade Communications Systems, Inc.";
  contact
    "Brocade Communications Systems, Inc.
     130 Holger Way,
     San Jose, CA 95134
     U.S.A
     Tel: +1-408-333-8000
     E-mail: info@brocade.com
     Web: www.brocade.com";
  description
    "This file describes the data modeliing of all
     the configuration commands for the multicast 
     protocol, Protocol Independent Multicast (PIM).";

  revision 2011-06-01 {
    description
      "Initial version of PIM module";
  }

  typedef spt-thr-type {
    type union {
      type uint32 {
        range "1..4294967295";
      }
      type enumeration {
        enum "infinity" {
          value 0;
        }
      }
    }
  }

  typedef pim-src-grp-ipv4-addr {
    type inet:ipv4-address;
  }

  typedef pim-grp-prefix-addr {
    type inet:ipv4-address;
  }

  typedef pim-ipv4-addr {
    type string {
      pattern "((0|(1[0-9]{0,2})|(2(([0-4][0-9]?)|(5[0-5]?)|([6-9]?)))|([3-9][0-9]?))\\.){3}(0|(1[0-9]{0,2})|(2(([0-4][0-9]?)|(5[0-5]?)|([6-9]?)))|([3-9][0-9]?))";
    }
  }

  typedef pim-intf-types {
    type enumeration {
      enum "gigabitethernet";
      enum "fortygigabitethernet";
      enum "tengigabitethernet";
      enum "port-channel";
      enum "ve";
    }
  }

  typedef grp-prefix-action {
    type enumeration {
      enum "add" {
        value 1;
      }
      enum "delete" {
        value 2;
      }
    }
  }

  grouping rtr-pim-cfg-cmd {
    leaf max-mcache {
      type uint32 {
        range "1..2048";
      }
      default "2048";
    }
    leaf hello-interval {
      type int16 {
        range "10..3600";
      }
      units "Seconds";
      default "30";
    }
    leaf nbr-timeout {
      type int16 {
        range "35..12600";
      }
      default "105";
    }
    leaf inactivity-timer {
      type int16 {
        range "60..3600";
      }
      default "180";
    }
    leaf message-interval {
      type uint32 {
        range "10..65535";
      }
      units "Seconds";
      default "60";
    }
    leaf spt-threshold {
      type spt-thr-type;
      default "1";
    }
    container bsr-candidate {
      list bsr-cand-interface {
        key "bsr-cand-intf-type bsr-cand-intf-id";
        leaf bsr-cand-intf-type {
          type pim-intf-types;
        }
        leaf bsr-cand-intf-id {
          type string;
        }
        leaf hash-mask-length {
          type uint16 {
            range "1..32";
          }
        }
        leaf bsr-cand-priority {
          type uint32 {
            range "0..255";
          }
          mandatory false;
        }
      }
    }
    container rp-candidate {
      list rp-cand-interface {
        key "rp-cand-intf-type rp-cand-intf-id";
        leaf rp-cand-intf-type {
          type pim-intf-types;
        }
        leaf rp-cand-intf-id {
          type string;
        }
      }
      list rp-cand-grp-prefix {
        key "rp-cand-grp-prefix-action rp-cand-grp-prefix-ip rp-cand-grp-prefix-length";
        leaf rp-cand-grp-prefix-action {
          type grp-prefix-action;
        }
        leaf rp-cand-grp-prefix-ip {
          type pim-grp-prefix-addr;
        }
        leaf rp-cand-grp-prefix-length {
          type uint16 {
            range "1..32";
          }
        }
      }
    }
    list rp-address {
      key "rp-ip-addr";
      leaf rp-ip-addr {
        type inet:ipv4-address;
      }
      leaf prefix-list {
        type string {
          length "1..64";
        }
      }
    }
  }

  grouping pim-intf-cfg-cmd {
    container pim-int-cmd {
      leaf pim-sparse {
        type empty;
      }
      container pim {
        leaf dr-priority {
          type uint32 {
            range "0..65535";
          }
          default "1";
        }
        leaf ttl-threshold {
          type uint32 {
            range "1..64";
          }
          default "1";
        }
      }
      leaf multicast-boundary {
        type empty;
      }
    }
  }

  grouping pim-intf-phy-cfg {
    container pim-intf-phy-cont {
      uses pim-intf-cfg-cmd;
    }
  }

  grouping pim-intf-vlan-cfg {
    container pim-intf-vlan-cont {
      uses pim-intf-cfg-cmd;
    }
  }

  grouping pim-intf-po-cfg {
    container pim-intf-po-cont {
      uses pim-intf-cfg-cmd;
    }
  }

  grouping global-pim-cmds {
    container pim {
      presence "true";
      uses rtr-pim-cfg-cmd;
    }
  }

  augment "/rbridge:rbridge-id/rbridge:router" {
    container hide-pim-holder {
      uses global-pim-cmds;
    }
  }
  augment "/interface:interface/interface:tengigabitethernet/interface:ip" {
    uses pim-intf-phy-cfg;
  }
  augment "/interface:interface/interface:fortygigabitethernet/interface:ip" {
    uses pim-intf-phy-cfg;
  }
  augment "/interface:interface/interface:gigabitethernet/interface:ip" {
    uses pim-intf-phy-cfg;
  }
  augment "/rbridge:rbridge-id/interface:interface/interface:ve/ip-config:ip" {
    uses pim-intf-vlan-cfg;
  }
  augment "/interface:interface-vlan/interface:interface/interface:ve/interface:ip" {
    uses pim-intf-vlan-cfg;
  }
}
