module brocade-vlan {
  namespace "urn:brocade.com:mgmt:brocade-vlan";
  prefix brocade-vlan;

  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "This submodule Manages Vlan classifier related CLI.";

  revision 2009-12-10 {
    description
      "Initial Version of this management module.";
  }

  typedef vlan-classifier-group-type {
    type uint32 {
      range "1..16";
    }
  }

  typedef vlan-classifier-rule-type {
    type uint32 {
      range "1..256";
    }
  }

  typedef vmac-address-type {
    type string {
      pattern "[0-9a-fA-F]{4}(\\.[0-9a-fA-F]{4}){2}";
    }
  }

  typedef ethernet-hexstring {
    type string {
      pattern "[0][x][0-9a-fA-F]{3,4}";
    }
  }

  grouping vlan-classifier-activate {
    container classifier {
      container activate {
        list group {
          key "groupid vlan-name vlan";
          leaf groupid {
            type uint32 {
              range "1..16";
            }
          }
          leaf vlan-name {
            type enumeration {
              enum "vlan" {
                value 0;
              }
            }
          }
          leaf vlan {
            type interface:vlan-type;
          }
        }
      }
    }
  }

  container vlan {
    container classifier {
      list rule {
        key "ruleid";
        leaf ruleid {
          type uint32 {
            range "1..256";
          }
        }
        choice class-type {
          case mac {
            container mac {
              leaf address {
                type vmac-address-type;
              }
            }
          }
          case proto {
            container proto {
              leaf proto-val {
                type union {
                  type enumeration {
                    enum "arp" {
                      value 2054;
                    }
                    enum "ip" {
                      value 2048;
                    }
                    enum "ipv6" {
                      value 34525;
                    }
                  }
                  type ethernet-hexstring;
                }
              }
              leaf encap {
                type enumeration {
                  enum "ethv2" {
                    value 1;
                  }
                  enum "nosnapllc" {
                    value 3;
                  }
                  enum "snapllc" {
                    value 2;
                  }
                }
              }
            }
          }
        }
      }
      list group {
        key "groupid oper rule-name ruleid";
        leaf groupid {
          type uint32 {
            range "1..16";
          }
        }
        leaf oper {
          type rule-opp-type;
        }
        leaf rule-name {
          type rule-name-type;
        }
        leaf ruleid {
          type uint32 {
            range "1..256";
          }
        }
      }
    }

    typedef rule-opp-type {
      type enumeration {
        enum "add" {
          value 1;
        }
        enum "delete" {
          value 2;
        }
      }
      description
        "Add/Delete Rule";
    }

    typedef rule-name-type {
      type enumeration {
        enum "rule" {
          value 0;
        }
      }
    }
    container dot1q {
      container tag {
        leaf native {
          type empty;
        }
      }
    }
  }
  augment "/interface:interface/interface:fortygigabitethernet" {
    container vlan {
      uses vlan-classifier-activate;
    }
  }
  augment "/interface:interface/interface:tengigabitethernet" {
    container vlan {
      uses vlan-classifier-activate;
    }
  }
  augment "/interface:interface/interface:gigabitethernet" {
    container vlan {
      uses vlan-classifier-activate;
    }
  }
  augment "/interface:interface/interface:port-channel" {
    container vlan {
      uses vlan-classifier-activate;
    }
  }
}
