module brocade-sec-services {
  namespace "urn:brocade.com:mgmt:brocade-sec-services";
  prefix brcd-sec-services;

  import brocade-common-def {
    prefix common-def;
  }
  import brocade-rbridge {
    prefix rbridge;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "Instrument to configure Telnet Server and SSH Server";

  revision 2012-07-28 {
    description
      "Initial version of this module.";
  }

  grouping telnet-group {
    container telnet {
      container server {
        leaf shutdown {
          type empty;
        }
      }
    }
  }

  augment "/common-def:show" {
    container telnet {
      container server;
    }
  }
  augment "/rbridge:rbridge-id" {
    uses telnet-group;
  }
  container telnet-sa {
    uses telnet-group;
  }

  typedef key-exchange-type {
    type enumeration {
      enum "dh-group-14" {
        value 2;
      }
    }
  }

  grouping ssh-group {
    container ssh {
      container server {
        leaf shutdown {
          type empty;
        }
        list key-exchange {
          key "protocol";
          leaf protocol {
            type key-exchange-type;
          }
        }
      }
    }
  }

  augment "/rbridge:rbridge-id" {
    uses ssh-group;
  }
  container ssh-sa {
    uses ssh-group;
  }
  augment "/common-def:show" {
    container ssh {
      container server;
    }
  }
}
