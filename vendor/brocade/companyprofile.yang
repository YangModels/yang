module companyprofile {
  namespace "http://brocade.com/ns/companyprofile";
  prefix companyprofile;

  import ietf-inet-types {
    prefix inet;
  }

  list company {
    key "companyname";
    leaf companyname {
      type string;
    }
    list employee {
      key "employeename";
      leaf employeename {
        type string;
      }
      leaf employeegroup {
        type string;
      }
      leaf employeelocation {
        type string;
      }
    }
    list group {
      key "groupname";
      leaf groupname {
        type string;
      }
      leaf-list groupemployee {
        type string;
      }
      leaf grouplocation {
        type string;
      }
      list subgroup {
        key "subgroupname";
        leaf subgroupname {
          type string;
        }
        leaf-list subgroupemployee {
          type string;
        }
        leaf subgrouplocation {
          type string;
        }
      }
    }
    list location {
      key "locationname";
      leaf locationname {
        type string;
      }
      leaf locationcityname {
        type string;
      }
    }
  }
  list city {
    key "cityname";
    leaf cityname {
      type string;
    }
    leaf citycode {
      type uint32;
    }
    leaf population {
      type uint64;
    }
    leaf ismetro {
      type boolean;
    }
    leaf cityIpV4Address {
      type inet:ipv4-address;
    }
    leaf cityIpV4AddressNetworkMask {
      type inet:ipv4-prefix;
    }
    leaf cityIpV6Address {
      type inet:ipv6-address;
    }
    leaf cityIpV6AddressNetworkMask {
      type inet:ipv6-prefix;
    }
    leaf cityIpVxAddress {
      type inet:ip-address;
    }
  }
}
