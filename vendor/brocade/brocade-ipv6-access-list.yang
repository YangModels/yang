module brocade-ipv6-access-list {
  namespace "urn:brocade.com:mgmt:brocade-ipv6-access-list";
  prefix ipv6-access-list;

  import brocade-rbridge {
    prefix rbridge;
  }
  import brocade-interface {
    prefix interface;
  }
  import brocade-common-def {
    prefix common-def;
  }
  import ietf-inet-types {
    prefix inet;
  }
  import brocade-ip-access-list {
    prefix ip-access-list;
  }

  organization "Brocade Communications Systems, Inc.";
  contact
    "Brocade Communications Systems, Inc.
     Postal: 130 Holger Way
            San Jose, CA 95134
            U.S.A
     Tel: +1-408-333-8000
     E-mail: support@Brocade.com
     Web: www.brocade.com";
  description
    "This management sub-module contains the configuration
     and rpc implementaion for IP Access-list.";

  revision 2012-07-01 {
    description
      "Initial version";
  }

  typedef sip {
    type inet:ipv6-address;
  }

  typedef sip-cidr {
    type inet:ipv6-prefix;
  }

  typedef dip {
    type inet:ipv6-address;
  }

  typedef dip-cidr {
    type inet:ipv6-prefix;
  }

  typedef ipv6-l3-acl-policy-name {
    type string {
      pattern "[a-zA-Z0-9]{1}([-a-zA-Z0-9_]{0,62})";
      length "1..63";
    }
  }

  grouping ipv6-ext-access-list-rule {
    leaf action {
      type enumeration {
        enum "permit" {
          value 1;
        }
        enum "deny" {
          value 2;
        }
        enum "hard-drop" {
          value 3;
        }
      }
      mandatory true;
    }
    leaf protocol-type {
      type union {
        type enumeration {
          enum "ipv6-icmp" {
            value 58;
          }
          enum "ip" {
            value 4;
          }
          enum "tcp" {
            value 6;
          }
          enum "udp" {
            value 17;
          }
        }
        type ip-access-list:proto-type;
      }
      mandatory true;
    }
    leaf src-host-any-sip {
      type union {
        type enumeration {
          enum "any" {
            value 1;
          }
          enum "host" {
            value 2;
          }
        }
        type sip-cidr;
      }
      mandatory true;
    }
    leaf src-host-ip {
      when "../src-host-any-sip ='host'";
      type sip;
    }
    leaf sport {
      when
        "((../protocol-type ='tcp') or 
         (../protocol-type ='udp') or 
         (../protocol-type ='6') or 
         (../protocol-type ='17'))";
      type enumeration {
        enum "eq" {
          value 1;
        }
        enum "gt" {
          value 2;
        }
        enum "lt" {
          value 3;
        }
        enum "neq" {
          value 4;
        }
        enum "range" {
          value 5;
        }
      }
    }
    leaf sport-number-eq-neq-tcp {
      when
        "(((../protocol-type ='tcp') or 
         (../protocol-type ='6')) and 
         ((../sport ='eq') or
         (../sport ='neq')))";
      type union {
        type ip-access-list:wellknown-port-tcp;
        type ip-access-list:sport-number-eq-neq-tcp-udp;
      }
    }
    leaf sport-number-lt-tcp {
      when
        "(((../protocol-type ='tcp') or 
         (../protocol-type ='6')) and 
         (../sport ='lt'))";
      type union {
        type ip-access-list:wellknown-port-tcp;
        type ip-access-list:sport-number-lt-tcp-udp;
      }
    }
    leaf sport-number-gt-tcp {
      when
        "(((../protocol-type ='tcp') or
         (../protocol-type ='6')) and 
         (../sport ='gt'))";
      type union {
        type ip-access-list:wellknown-port-tcp;
        type ip-access-list:sport-number-gt-tcp-udp;
      }
    }
    leaf sport-number-eq-neq-udp {
      when
        "(((../protocol-type ='udp')
         or (../protocol-type ='17')) 
         and ((../sport ='eq') or 
         (../sport ='neq')))";
      type union {
        type ip-access-list:wellknown-port-udp;
        type ip-access-list:sport-number-eq-neq-tcp-udp;
      }
    }
    leaf sport-number-lt-udp {
      when
        "(((../protocol-type ='udp') 
         or (../protocol-type ='17')) 
         and (../sport ='lt'))";
      type union {
        type ip-access-list:wellknown-port-udp;
        type ip-access-list:sport-number-lt-tcp-udp;
      }
    }
    leaf sport-number-gt-udp {
      when
        "(((../protocol-type ='udp') 
         or (../protocol-type ='17')) 
         and (../sport ='gt'))";
      type union {
        type ip-access-list:wellknown-port-udp;
        type ip-access-list:sport-number-gt-tcp-udp;
      }
    }
    leaf sport-number-range-lower-tcp {
      when
        "(((../protocol-type ='tcp') 
         or (../protocol-type ='6')) 
         and (../sport ='range'))";
      type union {
        type ip-access-list:wellknown-port-tcp;
        type ip-access-list:sport-range-lower-tcp-udp;
      }
    }
    leaf sport-number-range-lower-udp {
      when
        "(((../protocol-type ='udp') 
         or (../protocol-type ='17')) 
         and (../sport ='range'))";
      type union {
        type ip-access-list:wellknown-port-udp;
        type ip-access-list:sport-range-lower-tcp-udp;
      }
    }
    leaf sport-number-range-higher-tcp {
      when
        "(((../protocol-type ='tcp') 
         or (../protocol-type ='6')) 
         and (../sport ='range') 
         and (../sport-number-range-lower-tcp))";
      type union {
        type ip-access-list:wellknown-port-tcp;
        type ip-access-list:sport-range-higher-tcp-udp;
      }
    }
    leaf sport-number-range-higher-udp {
      when
        "(((../protocol-type ='udp') 
         or (../protocol-type ='17')) 
         and (../sport ='range') 
         and (../sport-number-range-lower-udp))";
      type union {
        type ip-access-list:wellknown-port-udp;
        type ip-access-list:sport-range-higher-tcp-udp;
      }
    }
    leaf dst-host-any-dip {
      type union {
        type enumeration {
          enum "any" {
            value 1;
          }
          enum "host" {
            value 2;
          }
        }
        type dip-cidr;
      }
      mandatory true;
    }
    leaf dst-host-ip {
      when "../dst-host-any-dip ='host'";
      type dip;
    }
    leaf dport {
      when
        "((../protocol-type ='tcp') 
         or (../protocol-type ='17')
         or (../protocol-type ='udp') 
         or (../protocol-type ='6'))";
      type enumeration {
        enum "eq" {
          value 1;
        }
        enum "gt" {
          value 2;
        }
        enum "lt" {
          value 3;
        }
        enum "neq" {
          value 4;
        }
        enum "range" {
          value 5;
        }
      }
    }
    leaf dport-number-eq-neq-tcp {
      when
        "(((../protocol-type ='tcp') 
         or (../protocol-type ='6')) 
         and ((../dport ='eq') 
         or (../dport ='neq')))";
      type union {
        type ip-access-list:wellknown-port-tcp;
        type ip-access-list:dport-number-eq-neq-tcp-udp;
      }
    }
    leaf dport-number-lt-tcp {
      when
        "(((../protocol-type ='tcp') 
         or (../protocol-type ='6')) 
         and (../dport ='lt'))";
      type union {
        type ip-access-list:wellknown-port-tcp;
        type ip-access-list:dport-number-lt-tcp-udp;
      }
    }
    leaf dport-number-gt-tcp {
      when
        "(((../protocol-type ='tcp') 
         or (../protocol-type ='6')) 
         and (../dport ='gt'))";
      type union {
        type ip-access-list:wellknown-port-tcp;
        type ip-access-list:dport-number-gt-tcp-udp;
      }
    }
    leaf dport-number-eq-neq-udp {
      when
        "(((../protocol-type ='udp') 
         or (../protocol-type ='17')) 
         and ((../dport ='eq') 
         or (../dport ='neq')))";
      type union {
        type ip-access-list:wellknown-port-udp;
        type ip-access-list:dport-number-eq-neq-tcp-udp;
      }
    }
    leaf dport-number-lt-udp {
      when
        "(((../protocol-type ='udp') 
         or (../protocol-type ='17')) 
         and (../dport ='lt'))";
      type union {
        type ip-access-list:wellknown-port-udp;
        type ip-access-list:dport-number-lt-tcp-udp;
      }
    }
    leaf dport-number-gt-udp {
      when
        "(((../protocol-type ='udp') 
         or (../protocol-type ='17')) 
         and (../dport ='gt'))";
      type union {
        type ip-access-list:wellknown-port-udp;
        type ip-access-list:dport-number-gt-tcp-udp;
      }
    }
    leaf dport-number-range-lower-tcp {
      when
        "(((../protocol-type ='tcp')
         or (../protocol-type ='17'))
         and ((../dport ='range')))";
      type union {
        type ip-access-list:wellknown-port-tcp;
        type ip-access-list:dport-range-lower-tcp-udp;
      }
    }
    leaf dport-number-range-lower-udp {
      when
        "(((../protocol-type ='udp') 
         or (../protocol-type ='6')) 
         and ((../dport ='range')))";
      type union {
        type ip-access-list:wellknown-port-udp;
        type ip-access-list:dport-range-lower-tcp-udp;
      }
    }
    leaf dport-number-range-higher-tcp {
      when
        "(((../protocol-type ='tcp') or 
         (../protocol-type ='6')) and 
         (../dport ='range') and 
         (../dport-number-range-lower-tcp))";
      type union {
        type ip-access-list:wellknown-port-tcp;
        type ip-access-list:dport-range-higher-tcp-udp;
      }
    }
    leaf dport-number-range-higher-udp {
      when
        "(((../protocol-type ='udp') or 
         (../protocol-type ='17')) and 
         (../dport ='range') and 
         (../dport-number-range-lower-udp))";
      type union {
        type ip-access-list:wellknown-port-udp;
        type ip-access-list:dport-range-lower-tcp-udp;
      }
    }
    leaf dscp {
      type union {
        type ip-access-list:wellknown-dscp;
        type ip-access-list:dscp-uint;
      }
    }
    leaf urg {
      when
        "(../protocol-type ='tcp') or 
         (../protocol-type ='6')";
      type empty;
    }
    leaf ack {
      when
        "(../protocol-type ='tcp') or
         (../protocol-type ='6')";
      type empty;
    }
    leaf push {
      when
        "(../protocol-type ='tcp') or
         (../protocol-type ='6')";
      type empty;
    }
    leaf fin {
      when
        "(../protocol-type ='tcp') or 
         (../protocol-type ='6')";
      type empty;
    }
    leaf rst {
      when
        "(../protocol-type ='tcp') or
         (../protocol-type ='6')";
      type empty;
    }
    leaf sync {
      when
        "(../protocol-type ='tcp') or
         (../protocol-type ='6')";
      type empty;
    }
    leaf count {
      type empty;
    }
    leaf log {
      type empty;
    }
  }

  grouping ipv6-std-access-list-rule {
    leaf action {
      type enumeration {
        enum "permit" {
          value 1;
        }
        enum "deny" {
          value 2;
        }
        enum "hard-drop" {
          value 3;
        }
      }
      mandatory true;
    }
    leaf src-host-any-sip {
      type union {
        type enumeration {
          enum "any" {
            value 1;
          }
          enum "host" {
            value 2;
          }
        }
        type sip-cidr;
      }
      mandatory true;
    }
    leaf src-host-ip {
      when "../src-host-any-sip ='host'";
      type sip;
    }
    leaf count {
      type empty;
    }
    leaf log {
      type empty;
    }
  }

  grouping ipv6_l3_access_list_cmds {
    container access-list {
      list standard {
        key "name";
        leaf name {
          type ipv6-l3-acl-policy-name;
        }
        list seq {
          key "seq-id";
          leaf seq-id {
            type ip-access-list:seq-id-std-ext;
          }
          uses ipv6-std-access-list-rule;
        }
      }
      list extended {
        key "name";
        leaf name {
          type ipv6-l3-acl-policy-name;
        }
        list seq {
          key "seq-id";
          leaf seq-id {
            type ip-access-list:seq-id-std-ext;
          }
          uses ipv6-ext-access-list-rule;
        }
      }
    }
  }

  container ipv6-acl {
    container ipv6 {
      uses ipv6_l3_access_list_cmds;
    }
  }
  augment "/interface:interface/interface:management/interface:ipv6" {
    container access-group {
      leaf mgmt-ipv6-access-list {
        type ipv6-l3-acl-policy-name;
      }
      leaf mgmt-ip-direction {
        type enumeration {
          enum "in" {
            value 1;
          }
        }
      }
    }
  }
}
