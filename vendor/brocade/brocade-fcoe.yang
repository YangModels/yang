module brocade-fcoe {
  namespace "urn:brocade.com:mgmt:brocade-fcoe";
  prefix fcoe;

  import brocade-rbridge {
    prefix rbridge;
  }
  import ietf-yang-types {
    prefix ietfyang;
  }
  import brocade-interface {
    prefix interface;
  }

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an instrumentation to manage fcoe  
     feature.
     
     Fiber Channel over Ethernet (FCoE) is an
     encapsulation of Fiber Channel frames over Ethernet networks. 
     This allows Fiber Channel to use 10 Gigabit Ethernet networks
     (or higher speeds) while preserving the Fiber Channel protocol.
     
     The FCoE interface can be managed using this module.
     
     This module provides a mechanism to configure FCoE maps and
     FCoE interface.
      
     Glossary of the terms used
     --------------------------  
     FIP -      FCoE Initialization Protocol is the standard for
                initialization of FCoE network.   
     VFID -     Virtual Fabric Identifier";
  reference "The FC-BB-5 standard ANSI/INCITS 462-2010.";

  revision 2011-07-22 {
    description
      "Initial version of the management module brocade-fcoe.";
  }

  typedef fcoe-fcmap-type {
    type string {
      pattern "[0][Ee]:[Ff][Cc]:[0-9a-fA-F]{2}";
      length "1..9" {
        description
          "This indicates the minimum and maximum length of
           characters that can be specified for FC map.";
      }
    }
    description
      "The definition for specifying FCoE FC map.";
  }

  typedef fcoe-vlan-type {
    type uint32 {
      range "2..4090" {
        description
          "The indicates the range of values that can be 
           specified for FCoE VLAN.";
      }
    }
    description
      "The definition for specifying FCoE VLAN.";
  }

  typedef fcoe-vfid-type {
    type int32 {
      range "1..4096" {
        description
          "This indicates the range of values that can be
           specified for  Virtual Fabric ID.";
      }
    }
    description
      "The definition for specifying virtual fabric ID.";
  }

  typedef fcoe-fabric-map-name-type {
    type string {
      pattern "default";
      length "1..32" {
        description
          "This indicates the minimum and maximum number of
           characters that can be specified for 
           FCoE Fabric map name.";
      }
    }
    description
      "The definition for specifying FCoE Fabric name.";
  }

  typedef fcoe-enode-fabric-map-name-type {
    type string {
      pattern "default";
      length "1..32" {
        description
          "This indicates the minimum and maximum number of
           characters that can be specified for 
           FCoE Fabric map name.";
      }
    }
    description
      "The definition for specifying FCoE Enodes Fabric name.";
  }

  typedef fcoe-map-name-type {
    type string {
      pattern "default";
      length "1..32" {
        description
          "This indicates the minimum and maximum number of 
           characters that can be specified for FCoE Map 
           name.";
      }
    }
    description
      "The definition for specifying FCoE Map name.";
  }

  typedef fcoe-cee-map-name-type {
    type string {
      length "1..32" {
        description
          "This indicates the minimum and maximum number of 
           characters that can be specified for CEE map
           name.";
      }
    }
    description
      "The definition for specifying CEE map name.";
  }

  typedef fcoe-priority-type {
    type int32 {
      range "0..6" {
        description
          "This indicates the range of values that can be
           specified for FCoE priority.";
      }
    }
    description
      "The definition for specifying the FCoE priority.";
  }

  typedef interface-fcoe-type {
    type string {
      length "3..32" {
        description
          "This indicates the maximum and minimum length of
           characters that can be specified for 
           FCoE interface.";
      }
    }
    description
      "The definition for FCoE interface.The FCoE 
       interface can be specified in the 'VN-Num/Rbridge/port' 
       format.";
  }

  typedef fcoe-max-enodes-type {
    type uint32 {
      range "256..1000" {
        description
          "NUMBER:256-1000;;Enter the max-enodes count";
      }
    }
  }

  typedef fcoe-max-enodes-per-rbridge-type {
    type uint32 {
      range "0..1000" {
        description
          "NUMBER:0-1000;;Enter fcoe max-enodes ";
      }
    }
  }

  typedef fcoe-enodes-cfg-type {
    type string {
      pattern "global|local";
      length "1..6" {
        description
          "This indicates the mode of Enodes configuration.";
      }
    }
    description
      "The definition for specifying FCoE Enodes config mode.";
  }

  grouping fcoe-fip-config-cmd-set {
    container fcoe-fip-advertisement {
      description
        "This provides the grouping of all FIP configuration
         elements.";
      leaf fcoe-fip-advertisement-interval {
        type int32 {
          range "250..90000" {
            description
              "This indicates the range of values that can 
               be specified for FIP advertisement 
               interval.";
          }
        }
        description
          "This specifies the FCoE advertisement interval.";
      }
    }
    container fcoe-fip-keep-alive {
      description
        "This provides the grouping of FCoE keep alive
         configuration elements.";
      leaf fcoe-fip-keep-alive-timeout {
        type empty;
        description
          "This specifies if the keep alive timeout should
           be enabled.
           
           The presence of this leaf specifies that FIP
           keep-alive timeout is enabled.";
      }
    }
  }

  container fcoe-fsb {
    description
      "This CLI will disable/enable fsb mode";
    leaf fcoe-fsb-enable {
      type empty;
      description
        "The presence of this leaf specifies that fsb
         mode is enabled.";
    }
  }
  container fcoe {
    description
      "This provides the grouping of all FCoE map configuration
       elements.";
    list fcoe-fabric-map {
      key "fcoe-fabric-map-name";
      description
        "List of FCoE fabric map parameters.";
      leaf fcoe-fabric-map-name {
        type fcoe-fabric-map-name-type;
        description
          "This specifies the name for the FCoE fabric map.";
      }
      leaf fcoe-fabric-map-vlan {
        type fcoe-vlan-type;
        description
          "This specifies the VLAN for the FCoE Fabric Map.";
      }
      leaf fcoe-fabric-map-priority {
        type fcoe-priority-type;
        description
          "This specifies the priority for the FCoE
           Fabric-map.";
      }
      leaf fcoe-fabric-map-virtual-fabric {
        type fcoe-vfid-type;
        description
          "This specifies the Virtual Fabric ID for the 
           Fabric-map.";
      }
      leaf fcoe-fabric-map-fcmap {
        type fcoe-fcmap-type;
        description
          "This specifies the FCMAP value for a FCoE
           Fabric-map.";
      }
      leaf fcoe-fabric-map-max-enodes {
        description
          "Configure the MAX Enodes for a FCOE Fabric-map";
        type fcoe-max-enodes-type;
      }
      leaf fcoe-fabric-map-enodes-cfg {
        type fcoe-enodes-cfg-type;
        description
          "This specifies the Enodes configuration mode.";
      }
      uses fcoe-fip-config-cmd-set;
    }
    list fcoe-map {
      key "fcoe-map-name";
      description
        "The list of FCoE maps.Each row contains the FCoE map
         name and the list of FCoE fabric maps and CEE maps.";
      leaf fcoe-map-name {
        type fcoe-map-name-type;
        description
          "This specifies the FCoE map name.";
      }
      list fcoe-map-fabric-map {
        key "fcoe-map-fabric-map-name";
        description
          "List of FCoE Fabric map in the FCoE map. Each row 
           represents Fabric Map name.";
        leaf fcoe-map-fabric-map-name {
          type fcoe-fabric-map-name-type;
          description
            "This specifies the FCoE fabric map name.";
        }
      }
      container fcoe-map-cee-map {
        description
          "This provides the grouping for FCoE CEE map
           configuration elements.";
        leaf fcoe-map-cee-map-leaf {
          type fcoe-cee-map-name-type;
          description
            "This specifies the CEE Map in the FCoE map.";
        }
      }
    }
  }
  augment "/interface:interface" {
    list fcoe {
      key "fcoe-interface-name";
      description
        "The list of FCoE interfaces. Each row contains FCoE
         interface name and its status.";
      leaf fcoe-interface-name {
        type interface-fcoe-type;
        description
          "This specifies the FCoE interface name.";
      }
      leaf fcoe-interface-shutdown {
        type empty;
        description
          "This specifies, if the FCoE interface is enabled
           or not. 
           The presence of this leaf indicates the 
           interface is shutdown.";
      }
      container fcoe-interface-bind {
        description
          "Bind the FCoE interface to a Physical Ethernet Port.";
        leaf fcoe-interface-bind-type {
          description
            "Physical Ethernet Port type";
          type enumeration {
            enum "TenGigabitEthernet" {
              value 1;
              description
                "Bind to TenGigabitEthernet port";
            }
            enum "FortyGigabitEthernet" {
              value 2;
              description
                "Bind to FortyGigabitEthernet port";
            }
            enum "Port-channel" {
              value 3;
              description
                "Bind to a Port-channel";
            }
            enum "mac-address" {
              value 4;
              description
                "Bind to an Enode Mac-address";
            }
          }
        }
        leaf fcoe-interface-bind-name {
          description
            "Interface name or Enode mac address";
          type string {
            length "0..32" {
              description
                "This indicates the interface bind value.
                 Bind value can be a Physical or Logical 
                 Ethernet interface or a Mac-Address.";
            }
          }
          default "";
        }
      }
    }
  }

  grouping fcoeport-lag-commands {
    container fcoeport {
      leaf fcoeport-map {
        type fcoe-map-name-type;
      }
    }
  }

  grouping fcoeport-commands {
    container fcoeport {
      description
        "This provides the grouping for FCoE configuration
         elements on a port.";
      leaf fcoeport-map {
        type fcoe-map-name-type;
        description
          "This specifies the name of the FCoE map.";
      }
    }
  }

  augment "/interface:interface/interface:port-channel" {
    uses fcoeport-lag-commands;
  }

  grouping fabric-commands {
    container fabric {
      description
        "Configure the Fabric Protocol parameters";
      container fabric-isl {
        description
          "Configure the Fabric Protocol ISL parameters";
        leaf fabric-isl-enable {
          description
            "Configure the Fabric Protocol ISL status";
          type empty;
        }
      }
      container fabric-trunk {
        description
          "Configure the Fabric Protocol Trunk parameters";
        leaf fabric-trunk-enable {
          description
            "Configure the Fabric Protocol Trunk status";
          type empty;
        }
      }
      container neighbor-discovery {
        description
          "Neighbor discovery at this port";
        leaf disable {
          description
            "Disable neighbor discovery at this port";
          type empty;
        }
      }
    }
  }

  grouping fcoe-rbridge-commands {
    container fcoe-config {
      description
        "This provides the grouping of all FCoE map configuration
         elements.";
      list fcoe-enode-fabric-map {
        key "fcoe-enode-fabric-map-name";
        description
          "List of FCoE fabric map parameters.";
        leaf fcoe-enode-fabric-map-name {
          type fcoe-enode-fabric-map-name-type;
          description
            "This specifies the name for the FCoE fabric map.";
        }
        leaf fcoe-max-enode {
          type fcoe-max-enodes-per-rbridge-type;
          description
            "This specifies the Number of the FCoE Enodes.";
        }
      }
    }
  }

  augment "/interface:interface/interface:fortygigabitethernet" {
    uses fabric-commands {
      refine "fabric/neighbor-discovery";
    }
    uses fcoeport-commands;
  }
  augment "/interface:interface/interface:tengigabitethernet" {
    uses fabric-commands {
      refine "fabric/neighbor-discovery";
    }
    uses fcoeport-commands;
  }
  augment "/interface:interface/interface:gigabitethernet" {
    container fabric {
      container neighbor-discovery {
        description
          "Neighbor discovery at this port";
        leaf disable {
          description
            "Disable neighbor discovery at this port";
          type empty;
        }
      }
    }
  }
  augment "/rbridge:rbridge-id" {
    uses fcoe-rbridge-commands;
  }
}
