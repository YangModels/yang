module interface_with_ndeepcomposition {
  namespace "http://brocade.com/ns/interface_ndeepcomposition";
  prefix interface_ndeepcomposition;

  container interfaces_with_ndeepcomposition {
    list interface {
      key "name";
      max-elements "1024";
      leaf name {
        type string;
      }
      list interface_rule {
        key "rule_id";
        leaf rule_id {
          type int32;
          mandatory true;
        }
        leaf isAllowed {
          type boolean;
          mandatory true;
        }
        list interface_rule_vlan {
          key "vlan_id";
          leaf vlan_id {
            type int32;
            mandatory true;
          }
          leaf x_id {
            type int32;
            mandatory true;
          }
        }
      }
    }
  }
}
