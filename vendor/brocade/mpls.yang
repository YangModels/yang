module brocade-mpls {

  namespace "urn:brocade.com:mgmt:brocade-cdp";

  prefix "mpls";

  import ietf-yang-types {
    prefix "yang";
  }

  import ietf-interfaces {
    prefix "if";
  }

  organization
    "Brocade Communications Systems, Inc.";
  contact
    "Brocade Communications Systems, Inc.
     Postal: 1745 Technology Drive,
             San Jose, CA 95110 
              U.S.A
     Tel: +1-408-392-6061
     E-mail: support@Brocade.com 
     web: www.brocade.com.";

  description
    "This management module is an instrumentation to manage 
     MPLS provisioning.";

  revision 2014-12-17 {
    description
      "Updated version of this management module. 
      (Make this model brocade specific)";

  revision 2014-11-21 {
    description
      "Initial revision.";
    reference
      "RFC XXXX: A YANG Data Model for Routing Management";
  }
  // == LDP SECTION ==

  grouping end-of-lib-params {
    description 
      "Parameters for End of Lib processing."
      leaf notification-timer {
      description
        "Period in seconds after which last label mapping is received from a
       peer without an End Of Lib Notification, an ldp speaker assumes
       the last label mapping has been received."
        type uint32;
      range "1..60";
      default: 5;
    }
    leaf enable {
      description
        "Enable the End of Lib feature.  This means an LDP speaker 
        sends a notification when it has sent the last label mapping
        after session establishment."
        type boolean;
      default "false";
    }
    leaf transmit-notification-timer {
      description
        "Period in seconds after which no Label Mapping 
        has been sent to a peer, an LDP speaker will send 
        an End of Lib notification to the peer."
        type uint32;
      range "1..60";
      default 1;
    }
  }

  grouping advertise-fec {
    description
      "Prefixes for which this LDP speaker acts as tunnel egress"
      leaf prefix-list {
      description
        "";
      type prefix-list-ref; //see bgp
    }
  }
     
  grouping fec-type-for-auto-discovery {
    description
      "";
    type vc-fec-type; //enum for fec 128/129
  }

  grouping in-fec-filter {
    description
      "Prefixes this LDP speaker maintains received Label Mappings within its lib"
      leaf prefix-list {
      description
        "";
      type prefix-list-ref; //see bgp
    }
  }

  grouping out-fec-filter {
    description
      "Prefixes fow whixh this LDP speaker will send Label Mappings"
      leaf prefix-list {
      description
        "";
      type prefix-list-ref; //see bgp
    }
  }

  grouping graceful-restart {
    description 
      "For LDP GR parameters"
      leaf helper-only {
      description 
        "";
      type boolean;
      default false;
    }
    leaf enable {
      description 
        "";
      type boolean;
      default false;
    }
    leaf reconnect-time {
      description 
        "";
      type uint32;
      default 60;
    }
    leaf recovery-time {
      description 
        "";
      type uint32;
      default 60;
    }
    leaf max-reconnect-time {
      description 
        "";
      type uint32;
      default 60;
    }

    leaf max-recovery-time {
      description 
        "";
      type uint32;
      default 60;
    }
  }

  grouping ldp-interval-spec {
    leaf timeout;
    leaf interval;
  }

  grouping basic-adjacency-interval-spec {
    uses interval-spec;
  }

  grouping target-adjacency-interval-spec {
    uses interval-spec;
  }
 
  grouping session-interval-spec {
    uses interval-spec;
  }
   
  grouping ldp-hello-timers
  {
    container target {
      uses interval-spec;
    }
    container basic {
      uses interval-spec;
    }
  }

  grouping ldp-keepalive-timers {
    uses interval-spec;
  }

  grouping load-sharing {
    leaf max-load-share-links {
      type uint32;
      default 8;
    }
  }

  grouping lsr-id {
    leaf lsr-ip-address {
      type inet:ip-address;
    }
  }

  grouping session-list {
    list sessions {
      description 
        "Per session parameters";
      key "session-ip";
      leaf session-ip {
        type inet:ip-address;
      }
      leaf md5-key {
        type string;
      }
    }
  }

  grouping targeted-peer-list {
    list peers {
      description 
        "List of targeted peers";
      key "peer-ip";
      leaf peer-ip {
        type inet:ip-address;
      }
    }
  }

  grouping tunnel-metric {
    leaf tunnel-metric {
      description 
        "Cost of tunnel route in routing calculations."
        type uint32;
      default 0;
    }
  }
  grouping ldp-params {
    uses  end-of-lib-params;
    uses  advertise-fec;
    uses  fec-type-for-auto-discovery;
    uses  in-fec-filter;
    uses  out-fec-filter;
    uses  graceful-restart;
    uses  hello-params;
    uses  keepalive-params;
    uses  load-sharing;
    uses  lsr-id
    uses  session-list;
    uses  targeted-peer-list;
    uses  tunnel-metric;
  }

  // == RSVP SECTION ==

  grouping refresh-interval {
    leaf refresh-interval {
      description 
        "Avg. interval between refresh path and resv msgs";
      type uint32;
      default: 30;
    }
  }
 
  grouping refresh-multiple {
    leaf refresh-multiple {
      description
        "Num of unresponded path or resv before time out";
      type uint32;
      default: 3;
    }
  }

  grouping rsvp-hello {
    leaf rsvp-hello {
      description 
        "Enable RSVP Hello on all mpls-interfaces";
      type uint32;
    }
    leaf acknowledgements {
      description 
        "Acknowledge RSVP Hellos on interfaces supporting RSVP Hello and not having RSVP sessions";
      type boolean;
    }                  
    leaf interval {
      description 
        "Interval between two RSVP Hello requests";
      type uint32;
    }
    leaf tolerance {
      description 
        "Number of unacknowledged RSVP Hello requests before timeout";
      type uint32;
    }
  }

  grouping rsvp-reliable-messaging {
    leaf rsvp-reliable-messaging {
      description 
        "Enable RSVP Reliable messaging Globally";
      type boolean;
    }
    leaf rapid-retrans-decay {
      description 
        "In percentage (0-100). Default: 100";
      type uint32;
      default 100;
    }

    leaf rapid-retrans-interval {
      description 
        "In msec (100-30000). Default: 2000msec";
      type uint32;
      default: 200;
    }
    leaf rapid-retry-limit {
      description 
        "Maximum number of retry(1-16). Default: 5";
      type uint32;
    }
  }

  grouping rsvp-bundle-messages {
    leaf bundle-messages {
      description 
        "Refresh Reduction bundle messaging feature";
      type boolean;
    }
    leaf bundle-messages-send-delay {
      description 
        "Bundle delay for messages";
      type uint32;
    }

  }

  grouping rsvp-refresh-reduction {
    contains rsvp-reliable-messaging;
    contains rsvp-bundle-messages;
    leaf summary-refresh {
      description 
        "Refresh Reduction Summary Refresh feature";
      type boolean;
    }
  }


  grouping retry-parms {
    leaf rapid-retry {
      description 
        "Configure Rapid retry feature for LSPs";
      type boolean;
    }

    leaf retry-limit {
      description 
        "Set lsp connect maximum number of retries";
      type uint32;
    }

    leaf retry-time {
      description 
        "Set lsp connect retry time in seconds";
      type uint32;
    }

    leaf backup-retry-time {
      description 
        "Set backup lsp connect retry time in seconds";
      type uint32;
    }
  }

  grouping traffic-eng-parms {
    list rsvp-flooding-threshold-list {
      description
        "List of rsvp flooding thresholds.";
      key "rsvp-flooding-threshold";
      leaf rsvp-flooding-threshold {
        description 
          "RSVP triggered TE-LSA flooding reduction(use negative for down)";
        type int32;
      }
    }

    leaf rsvp-periodic-flooding-time {
      description 
        "Set the interval for RSVP TE periodic flooding";
      type uint32;
    }

    leaf traffic-engineering {
      description 
        "Select IGP for advertising traffic engineering";
      enum igp-type; //ie. ospf, isis; and level  (TBD)
    }
  }

  grouping rsvp-igp-sync-parms {
    leaf handle-isis-neighbor-down {
      description 
        "Configure MPLS to handle ISIS neighbor down";
      type boolean;
    }
    leaf handle-ospf-neighbor-down {
      description 
        "Configure MPLS to handle OSPF neighbor down";
      type boolean;
    }
  }

  grouping auto-bandwidth {
    description
      "A set of configuration parameters that is applicable to automatic adjustment of LSP bandwidth.";
  
    leaf adjustment-interval {
      description
        "Specifies interval at which LSP may be adjusted";
      type uint32;
    }
    leaf adjustment-threshold {
      description
        "Specifies threshold percentage at which LSP may be adjusted";
      type uint32;
    }
    leaf max-bandwidth {
      description
        "Specifies maximum bandwidth of the LSP";
      type uint32;
    }
    leaf min-bandwidth {
      description
        "Specifies minimum bandwidth of the LSP";
      type uint32;
    }
    leaf mode {
      description
        "Autobw-signaling mode for the LSP.";
      type enumeration {
        enum "monitor-only";
        enum "monitor-and-signal";
      }
      default "monitor-and-signal";
    }
    leaf overflow-limit  {
      description
        "(TBD)";
      type uint32;
    }
    leaf sample-recording  {
      description
        "(TBD)";
      type uint32;
    }
    leaf underflow-limit  {
      description
        "(TBD)";
      type uint32;
    }
  }

  grouping soft-preemption {
    leaf enable {
      type boolean;
    }
    leaf cleanup-timer {
      type uint32;
    }
  }

  grouping rsvp-params {
    uses rsvp-lsp-config;
    uses refresh-interval;
    uses refresh-multiple;
    uses rsvp-hello;
    uses rsvp-refresh-reduction;
    uses retry-parms;
    uses traffic-eng-parms;
    uses rsvp-igp-sync-parms;
    uses auto-bandwidth;
    uses soft-preemption;
    uses backup-retry-time;
    uses dynamic-bypass;
  }

  // For the policy - {MPLS model(uniform, pipe, short pipe; instead of TTL }

  // == RSVP LSP SECTION ==

  grouping adapative {
    leaf adaptive {
      description 
        "enable lsp to be modified on fly";
      type boolean;
      default: false;
    }
  }

  grouping cos {
    leaf cos {
      description 
        "Class of service";
      type uint32;
      default: 0;
    }
  }

  grouping lsp-enable {
    leaf lsp-enable {
      description 
        "Establish the LSP";
      type boolean;
    }
  }

  grouping administration-groups {
    leaf include-all {
      description 
        "Include all of the administrative groups";
      type uint32;
    }

    leaf include-any {
      description 
        "Include any of the administrative groups";
      type uint32;
    }

    leaf exclude-any {
      description 
        "Exclude any of the administrative groups";
      type uint32;
    }
  }

  grouping dest-parms {
    leaf from {
      description 
        "Set ingress router of the LSP";
      type inet:ip-address;
    }
    leaf to {
      description 
        "Set egress router of the LSP";
      type inet:ip-address;
    }
  }

  grouping frr {
    //TBD
  }

  grouping hop-limit {
    leaf hop-limit {
      description 
        "Limit of hops the LSP can traverse";
      type uint32;
    }
  }

  grouping ipmtu {
    leaf ipmtu {
      description 
        "IP Packet Maximum Transmission Unit";
      type uint32;
    }
  }

  grouping ldp-tunneling {
    leaf ldp-tunneling {
      description 
        "Enable LDP over RSVP tunneling";
      type boolean;
    }
  }

  grouping metric {
    leaf metric {
      description 
        "Set the LSP metric";
      type uint32;
    }
  }

  grouping primary-path {
    primary-path                  Set primary explicit path;
  }

  grouping priority {
    leaf setup-priority {
      description 
        "Setup priority";
      type uint32;
    }

    leaf hold-priority {
      description 
        "hold priority";
      type uint32;
      default:0;
    }
  }


  grouping record {
    leaf record {
      description 
        "Enable or disable recording path routes";
      type boolean;
    }
  }

  grouping reoptimize-timer {
    leaf reoptimize-timer {
      description 
        "set reoptimize timer value";
      type uint32;
    }
  }

  grouping revert-timer {
    leaf revert-timer {
      description 
        "set lsp revert timer";
      type uint32;
    }
  }

  grouping cspf {
    leaf cspf {
      description 
        "Enable or disable CSPF";
      type boolean;
      default: false;
    }
  }

  grouping shortcuts {
    leaf shortcuts {
      description 
        "Enable the LSP tunnel for IGP shortcuts";
      type boolean;
    }
  }

  grouping bypass-lsp-params {
    leaf exclude-interface {
      //list of exclude-interfaces
    }
  }

  grouping lsp-traffic-eng-parms {
    leaf max-burst {
      description 
        "In bytes (0-2147483647)";
      type uint32;
    }
    
    leaf max-rate {
      description 
        "In kbits/sec (0-2147483647)";
      type uint32;
    }
    
    leaf mean-rate {
      description 
        "In kbits/sec (0-2147483647)";
      type uint32;
    }
  }

  grouping lsp-params {
    uses  adaptive;
    uses  auto-bandwidth;
    //   uses  bfd;  //tbd
    uses  cos;
    uses  lsp-enable;
    uses  administration-groups;
    uses  dest-parms;
    uses  frr;
    uses  hop-limit;
    uses  ipmtu;
    uses  ldp-tunneling;
    uses  metric;
    uses  primary-path;
    uses  priority;
    uses  record;
    uses  reoptimize-timer;
    uses  revert-timer;
    uses  shortcuts;
    uses  soft-preemption;
    uses  lsp-traffic-eng-parms;
    uses  bypass-lsp-parms;
  }

  grouping rsvp-lsp-config {
    list lsps {
      description
        "List of user configured lsps.";
      key "lsp-name";
      leaf lsp-name {
        type string;
      }
      uses lsp-params;
    }
  }

  // == MPLS Interface SECTION ==
 
  grouping admin-group {
    leaf admin-group {
      description 
        "Administrative group";
      type uint32;
    }
    // Also named option for admin group; tbd
  }

  grouping ldp-interface-params {
    uses basic-adjacency-interval-spec;
    leaf enable {
      type: boolean;
    }
  }

  grouping dynamic-bypass {
    uses adaptive;
    uses cos;
    uses lsp-enable;
    uses administration-groups;
    uses dest-group;
    uses hop-limit;
    leaf max-bypasses-per-mp {
      description 
        "Set maximum dynamic bypass LSP limit per Merge Point";
      type uint32;
    }
    leaf name-prefix {
      description 
        "Set name prefix for the dynamic bypass LSP";
      type uint32;
    }
    uses primary-path;
    uses priority;
    uses record;
    uses reoptimize-timer;
    uses traffic-eng-parms;
  }

  grouping rsvp-interface-params {
    uses   rsvp-refresh-reduction;
    uses   rsvp-hello;
    uses   rsvp-reliable-messaging;
    uses   traffic-eng-parms;
    leaf enable {
      type: boolean;
    }
    leaf reservable-bandwidth {
      description 
        "Max. reservable bandwidth (in kbits/sec)";
      type uint32;
    }

    leaf rsvp-authentication {
      description 
        "Enable RSVP authentication on this interface";
      type uint32;
    }
    leaf te-metric {
      description 
        "Set te-metric for this interface";
      type uint32;
    }
  }

  grouping  mpls-interface {
    uses admin-group;
    uses dynamic-bypass;
    uses rsvp-interface-params;
    uses ldp-interface-params;
  }

  grouping mpls-interface-config {
    list interfaces {
      description
        "List of mpls interfaces.";
      key "interface-id";
      leaf interface-id {
        type uint32;  //tbd - interface type
      }
      uses mpls-interface;
    }
  }
  
  // == Static LSP SECTION ==

  grouping static-lsp {
    leaf in-label {
      description 
        "incoming label";
      type uint32;
    }

    leaf out-label {
      description 
        "outgoing label";
      type uint32;
    }

    leaf nexthop-ip {
      description 
        "next hop ip address";
      type uint32;
    }

    leaf label-operation {
      description 
        "label-op";
      type enum;  //ie. pop / swap / push
    }
  }

  grouping static-lsp-list {
    list {
      uses static-lsp;
    }
  }

  // Overall section

  grouping mpls
  {
    uses ldp-params;
    uses rsvp-params;
    uses mpls-interface-config;
    uses static-lsp-list;
  }
}
