module CompanyService {
  namespace "http://brocade.com/ns/CompanyService";
  prefix companyservice;

  import ietf-inet-types {
    prefix inet;
  }

  list company {
    key "companyname";
    leaf companyname {
      type string;
    }
    list employee {
      key "employeename";
      leaf employeename {
        type string;
      }
      leaf employeegroup {
        type string;
      }
      leaf employeelocation {
        type string;
      }
    }
    list group {
      key "groupname";
      leaf groupname {
        type string;
      }
      uses groupbase;
      list subgroup {
        key "subgroupname";
        leaf subgroupname {
          type string;
        }
        uses groupbase;
        list subgroupmanager {
          key "subgroupmanagername";
          leaf subgroupmanagername {
            type string;
          }
        }
      }
      list groupmanager {
        key "groupmanagername";
        leaf groupmanagername {
          type string;
        }
      }
    }
    leaf location {
      type string;
    }
    container company_region {
      choice region {
        case EMEA {
          leaf EMEA_country {
            type string;
          }
        }
        case AsiaPac {
          leaf AsiaPac_country {
            type string;
          }
        }
        case Americas {
          leaf Americas_country {
            type string;
          }
        }
      }
    }
    list boardOfDirector {
      key "boardOfDirectorname";
      leaf boardOfDirectorname {
        type string;
      }
      leaf boardOfDirectorlocation {
        type string;
      }
    }
  }
  container stockOption {
    presence "true";
    leaf isStockOption {
      type boolean;
    }
    leaf stockshare {
      type uint32;
    }
  }
  list city {
    key "cityname";
    leaf cityname {
      type string;
    }
    leaf citycode {
      type uint32;
    }
    leaf population {
      type uint64;
    }
    leaf ismetro {
      type boolean;
    }
    leaf cityIpV4Address {
      type inet:ipv4-address;
    }
    leaf cityIpV4AddressNetworkMask {
      type inet:ipv4-prefix;
    }
    leaf cityIpV6Address {
      type inet:ipv6-address;
    }
    leaf cityIpV6AddressNetworkMask {
      type inet:ipv6-prefix;
    }
    leaf cityIpVxAddress {
      type inet:ip-address;
    }
  }

  grouping groupbase {
    leaf groupEmployee {
      type string;
    }
    leaf groupLocation {
      type string;
    }
  }
}
