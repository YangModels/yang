module brocade-certutil {
  namespace "urn:brocade.com:mgmt:certutil";
  prefix certutil;

  import ietf-inet-types {
    prefix inet;
  }
  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This module is used to support certificate management operations";

  revision 2011-06-13 {
    description
      "Initial version of this module.";
  }

  grouping import_cert_parameters {
    leaf protocol {
      description
        "Protocol";
      type enumeration {
        enum "SCP";
        enum "FTP";
      }
      mandatory true;
    }
    leaf user {
      description
        "Username";
      type string;
      mandatory true;
    }
    leaf password {
      description
        "Password";
      type string;
    }
    leaf host {
      description
        "Host IPv4 address";
      type string;
      mandatory true;
    }
    leaf directory {
      description
        "Remote Directory";
      type string;
      mandatory true;
    }
    leaf file {
      description
        "Certificate file in PEM format";
      type string;
      mandatory true;
    }
    leaf rbridge-id {
      mandatory false;
      type common-def:rbridge-id-all-type;
    }
  }

  grouping export_cert_parameters {
    leaf protocol {
      description
        "Protocol";
      type enumeration {
        enum "SCP";
        enum "FTP";
      }
      mandatory true;
    }
    leaf user {
      description
        "Username";
      type string;
      mandatory true;
    }
    leaf password {
      description
        "Password";
      type string;
    }
    leaf host {
      description
        "Host ipv4 address";
      type string;
      mandatory true;
    }
    leaf directory {
      description
        "Directory";
      type string;
      mandatory true;
    }
  }

  grouping import_sshkey_parameters {
    leaf user {
      description
        "Username";
      type string;
      mandatory true;
    }
    leaf host {
      description
        "Host IPv4 address";
      type string;
      mandatory true;
    }
    leaf directory {
      description
        "Remote Directory";
      type string;
      mandatory true;
    }
    leaf file {
      description
        "SSH public key with .pub extension";
      type string;
      mandatory true;
    }
    leaf login {
      description
        "Login name in the remote host";
      type string;
      mandatory true;
    }
    leaf password {
      description
        "User password in the remote host";
      type string;
    }
    leaf rbridge-id {
      mandatory false;
      type common-def:rbridge-id-all-type;
    }
  }

  container certutil {
    description
      "Security Certificate Management Operations";
    container import {
      description
        "Certificate import operation";
    }
  }
  augment "/common-def:no" {
    container certutil;
  }
  augment "/common-def:show" {
    container cert-util;
  }
}
