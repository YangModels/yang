module interface_container_in_list {
  namespace "http://brocade.com/ns/interface_container_in_list";
  prefix interface_container_in_list;

  import ietf-inet-types {
    prefix inet;
  }

  container interface_container_in_list {
    list interface {
      key "name";
      max-elements "1024";
      leaf name {
        type string;
      }
      container ip_wwn {
        leaf ip {
          type inet:ipv4-address;
          mandatory true;
        }
        leaf wwn {
          type string;
          mandatory true;
        }
      }
      container mtu {
        leaf mtu32 {
          type int32;
          mandatory true;
        }
      }
      container configtype {
        choice configtype {
          case fibrechannel {
            leaf fabricid {
              type int32;
            }
          }
          case ethernet {
            leaf ipaddress {
              type int32;
            }
          }
        }
      }
    }
  }
}
