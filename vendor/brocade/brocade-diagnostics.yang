module brocade-diagnostics {
  namespace "urn:brocade.com:mgmt:brocade-diagnostics";
  prefix diagnostics;

  import brocade-common-def {
    prefix common-def;
  }
  import brocade-interface {
    prefix interfaces;
  }

  organization "Brocade Communications Systems, Inc.";
  contact
    "sshaik@brocade.com";
  description
    "Modules for entities implementing FOS Diagnostics";

  revision 2010-09-20 {
    description
      "Initial version.";
  }

  feature platform_chassis {
    description
      "chassis-platform";
  }

  feature platform_pizzabox {
    description
      "pizzabox-platform";
  }

  feature portlevel_testing_on {
    description
      "Enables port level testing options";
  }

  feature portlevel_testing_off {
    description
      "Disables port level testing options";
  }

  typedef slotidtype {
    type string {
      length "2";
    }
  }

  container diag {
    container post {
      list rbridge-id {
        key "rbridge-id";
        leaf enable {
          type empty;
        }
        leaf rbridge-id {
          type common-def:rbridge-id-type;
        }
      }
      leaf enable {
        type empty;
      }
    }
  }
  container fos;
}
