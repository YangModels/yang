module brocade-license {
  namespace "urn:brocade.com:mgmt:brocade-license";
  prefix brocade-license;

  import brocade-interface {
    prefix interface;
  }
  import brocade-common-def {
    prefix common-def;
  }

  organization "Brocade Communications Inc.";
  contact
    "Brocade Communications Systems, Inc.
     Postal: 1745 Technology Drive,
     San Jose, CA 95110
     U.S.A
     Tel: +1-408-392-6061
     E-mail: support@Brocade.com
     web: www.brocade.com.";
  description
    "This management sub-module is an instrumentation to manage
     the licenses in the VCS fabric.
     
     Glossary of the terms used:
     ---------------------------
     DPOD        -   Dynamic ports on demand
     licStr      -   License string (i.e., license key)
     POD         -   Ports on demand
     ";

  revision 2011-08-22 {
    description
      "Providing Netconf Support to the existing version.";
  }

  typedef license-dpod-operation-type {
    type enumeration {
      enum "release" {
        value 1;
        description
          "DPOD operation to release a license.";
      }
      enum "reserve" {
        value 2;
        description
          "DPOD operation to reserve a license.";
      }
    }
  }

  augment "/common-def:show" {
    container license;
    container enh-show-license-keys;
  }
  container license {
    description
      "The function for installing or uninstalling the license
       keys of a given RBridge.";
  }
  container dpod {
    list port-id {
      ordered-by user;
      key "port-id";
      leaf port-id {
        type interface:interface-type;
        mandatory true;
        description
          "Port details for identification
           [rbridge-id/slot/port].";
      }
      leaf operation {
        type license-dpod-operation-type;
        default "reserve";
        description
          "Operation to release or reserve a DPOD
           license for this port.";
      }
    }
  }
}
