module brocade-fc-auth {
  namespace "urn:brocade.com:mgmt:brocade-fc-auth";
  prefix brcd-fc-auth;

  import brocade-common-def {
    prefix common-def;
  }
  import brocade-rbridge {
    prefix rbridge;
  }

  organization "Brocade Communications Systems, Inc.";
  contact
    "Brocade Communications Systems, Inc.
     Postal: 130 Holger Way
            San Jose, CA 95134
             U.S.A
     Tel: +1-408-333-8000
     E-mail: support@Brocade.com
     web: www.brocade.com.";
  description
    "Data Model for AAA CLIs";

  revision 2010-10-21 {
    description
      "Removed the max-elements attribute for list";
  }

  typedef authtype {
    type enumeration {
      enum "dh-chap";
    }
    description
      "Authentication types";
  }

  typedef fcsp-authtype {
    type authtype;
    description
      "FCSP authentication types";
  }

  typedef hashtype {
    type enumeration {
      enum "sha1";
      enum "md5";
      enum "all";
    }
    description
      "Hash types";
  }

  typedef fcsp-hashtype {
    type hashtype;
    description
      "FCSP supported hash types";
  }

  typedef switch-policy-state {
    type enumeration {
      enum "on";
      enum "off";
      enum "active";
      enum "passive";
    }
    description
      "Switch authentication policy mode";
  }

  typedef fcsp-switch-policy-state {
    type switch-policy-state;
  }

  typedef secpolicy-option {
    type string {
      pattern "SCC_POLICY";
    }
  }

  typedef secpolicy-type {
    type secpolicy-option;
  }

  typedef secpolicy-action-type {
    type enumeration {
      enum "activate" {
        value 0;
      }
    }
  }

  typedef fc-node-name-type {
    type union {
      type common-def:wwn-type;
      type string;
      type common-def:rbridge-id-type;
    }
  }

  grouping fcsp-group {
    container fcsp {
      container auth {
        container proto {
          leaf auth-type {
            type fcsp-authtype;
            default "dh-chap";
          }
          leaf group {
            type string {
              pattern "[0-4\\*]" {
                error-message
                  "Group value should be
                    in the range 0-4 or *";
              }
            }
            default "*";
          }
          leaf hash {
            type fcsp-hashtype;
            default "all";
          }
        }
        container policy {
          leaf switch {
            type fcsp-switch-policy-state;
            default "passive";
          }
        }
      }
    }
  }

  container fcsp {
    container auth-secret;
  }
  augment "/rbridge:rbridge-id" {
    uses fcsp-group;
  }
  container fcsp-sa {
    uses fcsp-group;
  }
  augment "/common-def:no" {
    container fcsp {
      container auth-secret;
    }
  }
  augment "/common-def:show" {
    container fcsp {
      description
        "Displaying FCSP auth secrets";
      container authsecret;
    }
  }

  grouping secpolicy-group {
    container secpolicy {
      container defined-policy {
        description
          "Set the defined policy";
        list policies {
          key "policy";
          leaf policy {
            type secpolicy-type;
          }
          list member-entry {
            key "member";
            leaf member {
              type string;
              description
                "Indicates the switch WWN";
            }
          }
        }
      }
      container active-policy {
        description
          "Set the Active policy";
        list policies {
          key "policy";
          leaf policy {
            type secpolicy-type;
          }
          list member-entry {
            key "member";
            leaf member {
              type string;
              description
                "Indicates the switch WWN";
            }
          }
        }
      }
    }
  }

  container secpolicy {
    container action;
  }
  augment "/rbridge:rbridge-id" {
    uses secpolicy-group;
  }
  container secpolicy-sa {
    uses secpolicy-group;
  }
}
