module brocade-lag {
  namespace "urn:brocade.com:mgmt:brocade-lag";
  prefix lag;

  import ietf-yang-types {
    prefix yang;
  }
  import brocade-interface {
    prefix interface;
  }

  organization "Brocade Communications Systems, Inc.";
  contact
    "Brocade Communications Systems, Inc.
     Postal: 130 Holger Way
            San Jose, CA 95134
            U.S.A
     Tel: +1-408-333-8000
     E-mail: support@Brocade.com
     Web: www.brocade.com";
  description
    "This management sub-module is an instrumentation to manage Link
     aggregation or IEEE 802.1AX-2008 feature.
     
     Glossary of the terms used:
     --------------------------
     LAG - Link Aggregation.
     LACP - Link Aggregation Control Protocol";

  revision 2011-02-20 {
    description
      "Initial version of this management module";
  }
  revision 2012-02-20 {
    description
      "Added pagination support";
  }

  typedef lacp-key {
    type uint32 {
      range "0..65535";
    }
  }

  typedef lacp-state {
    type bits {
      bit activity {
        position 0;
      }
      bit timeout {
        position 1;
      }
      bit aggregation {
        position 2;
      }
      bit synchronization {
        position 3;
      }
      bit collecting {
        position 4;
      }
      bit distributing {
        position 5;
      }
      bit defaulted {
        position 6;
      }
      bit expired {
        position 7;
      }
    }
  }

  typedef brcd-trunk-states {
    type bits {
      bit marker-generated {
        position 0;
      }
      bit deskew-calculation-completed {
        position 1;
      }
      bit deskew-ok {
        position 2;
      }
      bit deskew-not-ok {
        position 3;
      }
      bit port-attached {
        position 4;
      }
    }
  }

  grouping lacp-common-actor-partner-detail {
    leaf admin-key {
      type lacp-key;
      description
        "The Admin key";
    }
    leaf oper-key {
      type lacp-key;
      description
        "The Opertional key";
    }
    leaf actor-system-id {
      type yang:mac-address;
      description
        "The Actor system id";
    }
    leaf partner-system-id {
      type yang:mac-address;
      description
        "The Partner system id";
    }
    leaf system-priority {
      type uint32 {
        range "1..65535";
      }
      description
        "The System Priority";
    }
    leaf partner-oper-priority {
      type uint32 {
        range "1..65535";
      }
      description
        "The partner operational priority";
    }
  }

  grouping dynamic-lacp-aggr {
    uses lacp-common-actor-partner-detail;
    leaf rx-link-count {
      type uint64;
      description
        "The RX link counter";
    }
    leaf tx-link-count {
      type uint64;
      description
        "The RX link counter";
    }
    leaf individual-agg {
      type uint32;
      description
        "Individual aggregator";
    }
    leaf ready-agg {
      type uint32;
      description
        "Individual aggregator";
    }
    leaf partner-oper-key {
      type lacp-key;
      description
        "The Partner Opertional key";
    }
  }

  rpc get-port-channel-detail {
    description
      "A function that returns Link Aggregation Control
       configuration parameters for all the port channels in
       the system.";
    input {
      leaf last-aggregator-id {
        type interface:portchannel-type;
        description
          "Agreegator-id value should be given only when previous
           response indicates that more records exists. This value
           will be the Id of last aggregator received in previous
           response.";
        mandatory false;
      }
    }
    output {
      list lacp {
        leaf aggregator-id {
          type interface:portchannel-type;
          description
            "Agreegator id";
        }
        leaf aggregator-type {
          type enumeration {
            enum "standard" {
              value 1;
              description
                " Aggregator type is standard.";
            }
            enum "brcd" {
              value 2;
              description
                " Aggregator type is brocade.";
            }
            enum "hybrid" {
              value 3;
              description
                " Aggregator type is hybrid.";
            }
            enum "internal" {
              value 4;
              description
                " Aggregator type is internal.";
            }
          }
        }
        leaf isvlag {
          type boolean;
          description
            " Specifies if Agreegator is vlag.";
        }
        leaf aggregator-mode {
          type enumeration {
            enum "none" {
              value 0;
              description
                " Aggregator mode  is passive.";
            }
            enum "dynamic" {
              value 1;
              description
                " Aggregator mode  is active.";
            }
            enum "static" {
              value 2;
              description
                " Aggregator mode  is on.";
            }
          }
        }
        uses dynamic-lacp-aggr;
        list aggr-member {
          description
            "Describes the aggregator member
             details.";
          leaf rbridge-id {
            type uint32;
            description
              "VCS domiain-id.";
          }
          uses interface:interface-name-info {
            description
              "Aggregated port.";
          }
          leaf actor-port {
            type uint64;
            description
              "The actor port number.
               This is valid only in active mode only.";
          }
          leaf sync {
            type uint64;
            description
              "sync-info.
               This is valid in active mode only.";
          }
        }
      }
      leaf has-more {
        type boolean;
        description
          "This indicates that there are more Aggregators details
           available. New request has to be sent with id of last
           aggregator to get more details.";
      }
    }
  }
  rpc get-portchannel-info-by-intf {
    description
      "A function that returns Link Aggregation Control
       configuration parameters for a given 'Aggregation Port' in
       the system.";
    input {
      uses interface:interface-name-info;
    }
    output {
      container lacp {
        uses interface:interface-name-info;
        leaf actor-port {
          type uint64;
          description
            "The actor port number";
        }
        uses lacp-common-actor-partner-detail;
        leaf actor-priority {
          type uint32 {
            range "1..65535";
          }
          description
            "The Actor Priority";
        }
        leaf receive-machine-state {
          type enumeration {
            enum "unknown" {
              value 1;
            }
            enum "invalid" {
              value 2;
              description
                "Invalid state";
            }
            enum "initialize" {
              value 3;
              description
                "When the physical connectivity of a
                 link changes or a Begin event occurs,
                 the state machine enters the Initialize
                 state";
            }
            enum "port-disabled" {
              value 4;
              description
                "If the port becomes inoperable and a
                 'begin' event has not occurred, the
                 state machine enters the Port Disabled
                 state";
            }
            enum "lacp-disabled" {
              value 5;
              description
                "If the port is operating in half
                 duplex, the operation of LACP is
                 disabled on the port, forcing the state
                 to LACP Disabled. This state is similar
                 to the Defaulted state, except that the
                 port is forced to operate as an
                 individual port";
            }
            enum "expired" {
              value 6;
              description
                "If no LACP PDU is received before the
                 timer for the Current state expires
                 once, the state machine enters the
                 Expired state";
            }
            enum "defaulted" {
              value 7;
              description
                "If no LACP PDU is received before the
                 timer for the Current state expires a
                 second time, the state machine enters
                 the Defaulted state";
            }
            enum "current" {
              value 8;
              description
                "The state machine receives an LACP PDU
                 and enters the Current state";
            }
          }
          description
            "The state of the 'Receive Machine'";
        }
        leaf periodic-transmission-machine-state {
          type enumeration {
            enum "unknown" {
              value 1;
            }
            enum "invalid" {
              value 2;
              description
                "Invalid state";
            }
            enum "no-periodic" {
              value 3;
              description
                "Periodic transmissions are disabled";
            }
            enum "fast-periodic" {
              value 4;
              description
                "Periodic transmissions are enabled at a
                 fast transmission rate";
            }
            enum "slow-periodic" {
              value 5;
              description
                "Periodic transmissions are enabled at a
                 slow transmission rate";
            }
            enum "periodic" {
              value 6;
              description
                "Transitory state entered when the
                 periodic timer expires";
            }
          }
          description
            "The state of the 'Periodic Transmission
             machine'";
        }
        leaf mux-machine-state {
          type enumeration {
            enum "unknown" {
              value 1;
            }
            enum "detached" {
              value 2;
              description
                "Process of detaching the port from the
                 aggregator is in progress";
            }
            enum "waiting" {
              value 3;
              description
                "Mux state machine is in a holding
                 process, awaiting an outcome";
            }
            enum "attached" {
              value 4;
              description
                "Mux machine initiates the process of
                 attaching the port to the selected
                 aggregator";
            }
            enum "collecting" {
              value 5;
              description
                "The receive function of this link is
                 enabled with respect to its
                 participation in an aggregation";
            }
            enum "distributing" {
              value 6;
              description
                "The transmit function of this link is
                 enabled with respect to its
                 participation in an aggregation. Frames
                 may be passed down from the aggregator's
                 distribution function for transmission";
            }
            enum "collecting-distributing" {
              value 7;
              description
                "Collecting and distributing states are
                 merged together to form a combined state
                 (coupled control). Because independent
                 control is not possible, the coupled
                 control state machine does not wait for
                 the partner to signal that collection
                 has started before enabling both
                 collection and distribution";
            }
            enum "generated-mark" {
              value 8;
            }
            enum "calculate-deskew" {
              value 9;
            }
            enum "waiting-remote-deskew" {
              value 10;
            }
            enum "deskew-ok" {
              value 11;
            }
            enum "deskew-not-ok" {
              value 12;
            }
          }
          description
            "The state of the 'Mux machine'";
        }
        leaf admin-state {
          type lacp-state;
          description
            "The Admin state";
        }
        leaf oper-state {
          type lacp-state;
          description
            "The Operational state";
        }
        leaf partner-oper-state {
          type lacp-state;
          description
            "The Partner Operational state";
        }
        leaf partner-oper-port {
          type uint64;
          description
            "The Partner Operational port";
        }
        leaf actor-chip-number {
          type uint32;
          description
            "The actor chip number";
        }
        leaf actor-max-deskew {
          type uint32;
          description
            "The actor maximum deskew";
        }
        leaf partner-chip-number {
          type uint32;
          description
            "The actor chip number";
        }
        leaf partner-max-deskew {
          type uint32;
          description
            "The partner maximum deskew";
        }
        leaf actor-brcd-state {
          type brcd-trunk-states;
          description
            "Actor brcd trunk state";
        }
        leaf partner-brcd-state {
          type brcd-trunk-states;
          description
            "partner brcd trunk state";
        }
      }
    }
  }
}
