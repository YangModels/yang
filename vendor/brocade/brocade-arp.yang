module brocade-arp {
  namespace "urn:brocade.com:mgmt:brocade-arp";
  prefix arp;

  import brocade-mac-access-list {
    prefix mac-access-list;
  }
  import brocade-interface {
    prefix interface;
  }
  import brocade-rbridge {
    prefix rbridge;
  }
  import brocade-vrf {
    prefix vrf;
  }
  import ietf-inet-types {
    prefix inet;
  }

  organization "Brocade Communications Systems, Inc.";
  contact
    "Brocade Communications Systems, Inc.
     Postal: 130 Holger way,
     San Jose, CA 95134,
     U.S.A
     Tel: +1-408-333-8000
     E-mail: support@Brocade.com
     web: www.brocade.com.";
  description
    "This management module is an instrumentation to manage
     ARPD Daemon";

  revision 2011-10-31 {
    description
      "Initial version of this management module.";
  }

  typedef slot-id {
    type uint8 {
      range "1..16" {
        description
          "Slot-ID;;  1..16";
      }
    }
  }

  grouping arp_cmds {
    container system-max {
      status obsolete;
      leaf arp {
        type uint32 {
          range "0..16384";
        }
        default "4096";
      }
      description
        "Configure system-wide maximum values (reload required)'.
                    This support is obsoleted.";
    }
    uses arp-entry-group;
  }

  grouping arp-entry-group {
    list arp-entry {
      key "arp-ip-address";
      leaf arp-ip-address {
        type inet:ipv4-address;
        description
          "IPv4 Address";
      }
      leaf mac-address-value {
        type mac-access-list:mac-address-type;
      }
      leaf interfacename {
        type enumeration {
          enum "interface" {
            description
              "Interface to use";
          }
        }
      }
      choice interfacetype {
        case GigabitEthernet {
          leaf GigabitEthernet {
            description
              "GigabitEthernet";
            type interface:interface-type;
          }
        }
        case TenGigabitEthernet {
          leaf TenGigabitEthernet {
            description
              "TenGigabitEthernet";
            type interface:interface-type;
          }
        }
        case FortyGigabitEthernet {
          leaf FortyGigabitEthernet {
            description
              "FortyGigabitEthernet";
            type interface:interface-type;
          }
        }
        case Ve {
          leaf Ve {
            description
              "Ve";
            type interface:vlan-type;
          }
        }
      }
    }
  }

  augment "/rbridge:rbridge-id" {
    uses arp_cmds;
  }
  container hide-arp-holder {
    uses arp_cmds;
  }
  augment "/rbridge:rbridge-id/vrf:vrf/vrf:address-family/vrf:ipv4" {
    uses arp-entry-group;
  }
  rpc get-arp {
    description
      "This RPC returns ARP entries of the managed entity.
       Depending on the input argument, the ARP entries are
       displayed. When there is no input argument entered, all
       the ARP entries of the managed entity are returned.";
    input {
      choice input-type {
        case interface {
          uses interface:interface-name-info;
        }
        case dynamic {
          leaf dynamic {
            type empty;
            description
              "This input queries for all the dynamic
               arp entries";
          }
        }
        case static {
          leaf static {
            type empty;
            description
              "This input queries for all the static
               arp entries";
          }
        }
        case ip {
          leaf ip-address {
            type inet:ipv4-address;
            description
              "This input queries for all the arp
               entries for this ip address";
          }
        }
      }
    }
    output {
      list arp-entry {
        key "ip-address";
        leaf ip-address {
          type inet:ipv4-address;
          description
            "IP address of the ARP entry";
        }
        leaf mac-address {
          type mac-access-list:mac-address-type;
          description
            "Mac address of the ARP entry";
        }
        uses interface:interface-name-info;
        leaf is-resolved {
          type boolean;
          description
            "This indicates whether the arp entry is
             resolved or not";
        }
        leaf age {
          type string;
          description
            "This indicates the age of the arp entry";
        }
        leaf entry-type {
          type enumeration {
            enum "static" {
              value 1;
            }
            enum "dynamic" {
              value 2;
            }
            enum "unknown" {
              value 3;
            }
          }
          description
            "This indicates the type of the arp entry";
        }
      }
    }
  }
}
