module brocade-intf-loopback {
  namespace "urn:brocade.com:mgmt:brocade-intf-loopback";
  prefix intf-loopback;

  import brocade-rbridge {
    prefix rbridge;
  }
  import brocade-common-def {
    prefix common-def;
  }
  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "Module for implementing Interface Loopback CLIs";

  revision 2011-09-28 {
    description
      "Initial Version";
  }

  typedef intf-loopback-port-type {
    type uint32 {
      range "1..255";
    }
  }

  typedef intf-loopback-ipv4addr-type {
    type string {
      pattern "(([1-9]|[1-9][0-9]|1[0-9][0-9]|2[0-4][0-9]|25[0-5])\\.)(([0-9]|[1-9][0-9]|1[0-9][0-9]|2[0-4][0-9]|25[0-5])\\.){2}([0-9]|[1-9][0-9]|1[0-9][0-9]|2[0-4][0-9]|25[0-5])/32" {
        error-message "Invalid IPv4 Address/32 format";
      }
    }
  }

  container hide-intf-loopback-holder {
    description
      "An intermediary node that separates the loopback related 
       managed objects from rest of the interface types.";
    container interface {
      list loopback {
        key "id";
        leaf id {
          type intf-loopback-port-type;
        }
        uses interface:interface-vrf-config;
        container intf-loopback {
          leaf shutdown {
            type empty;
          }
        }
      }
      description
        "The loopback interface configurations/data of this managed
         device.";
    }
  }
  augment "/rbridge:rbridge-id/interface:interface" {
    list loopback {
      key "id";
      leaf id {
        type intf-loopback-port-type;
      }
      uses interface:interface-vrf-config;
      container intf-loopback {
        leaf shutdown {
          type empty;
        }
      }
    }
  }
}
