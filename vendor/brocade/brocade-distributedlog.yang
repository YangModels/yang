module brocade-distributedlog {
  namespace "urn:brocade.com:mgmt:brocade-distributedlog";
  prefix distributedlog;

  import brocade-common-def {
    prefix common-def;
  }

  organization "Brocade Communications Inc.";
  contact
    "Brocade Communications Systems, Inc.
     Postal: 130 Holger Way,
     San Jose, CA 95134
     U.S.A
     Tel: +1-408-333-8000
     E-mail: support@Brocade.com
     web: www.brocade.com.";
  description
    "Vcs log related information";
  reference "<Author Name>, '<Title>', <RFC XXXX>, <Month> <YEAR>.";

  revision 2010-12-02 {
    description
      "Initial version";
  }

  augment "/common-def:show" {
    container log;
  }
}
