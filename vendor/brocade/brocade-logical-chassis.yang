module brocade-logical-chassis {
  namespace "http://brocade.com/ns/brocade-logical-chassis";
  prefix brocade-logical-chassis;

  import brocade-vcs {
    prefix brocade-vcs;
  }
  import brocade-rbridge {
    prefix rbridge;
  }

  grouping logical-chassis-cmds {
    container logical-chassis {
      leaf principal-priority {
        type uint32 {
          range "1..128";
        }
      }
    }
  }

  augment "/rbridge:rbridge-id" {
    uses logical-chassis-cmds;
  }
}
