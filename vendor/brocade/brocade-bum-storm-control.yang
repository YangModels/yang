module brocade-bum-storm-control {
  namespace "urn:brocade.com:mgmt:brocade-bum-storm-control";
  prefix bum-storm-control;

  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "A traffic storm occurs when packets flood the LAN, 
     creating excessive traffic and degrading network performance.  
     The BUM storm control feature is meant to prevent disruptions 
     on Layer 2 physical ports caused by excessive ingress broadcast, 
     multicast, and unknown unicast. BUM Storm control allows the 
     user to limit the amount of BUM traffic admitted to the system.";

  revision 2011-11-10 {
    description
      "Initial version of this management module.";
  }

  typedef percentage-rate-limit {
    type uint32 {
      range "0 .. 100";
    }
  }

  typedef bps-rate-limit {
    type uint64 {
      range "0 .. 40000000000";
    }
  }

  grouping common-phy-storm-control-cmds {
    container storm-control {
      list ingress {
        key "protocol-type";
        leaf protocol-type {
          type enumeration {
            enum "broadcast" {
              value 1;
            }
            enum "multicast" {
              value 2;
            }
            enum "unknown-unicast" {
              value 3;
            }
          }
        }
        leaf rate-format {
          type enumeration {
            enum "limit-bps" {
              value 1;
            }
            enum "limit-percent" {
              value 2;
            }
          }
        }
        leaf rate-bps {
          type bps-rate-limit;
        }
        leaf rate-percent {
          type percentage-rate-limit;
        }
        leaf bum-action {
          type enumeration {
            enum "monitor" {
              value 2;
            }
            enum "shutdown" {
              value 3;
            }
          }
        }
      }
    }
  }

  augment "/interface:interface/interface:tengigabitethernet" {
    uses common-phy-storm-control-cmds;
  }
  augment "/interface:interface/interface:gigabitethernet" {
    uses common-phy-storm-control-cmds;
  }
  augment "/interface:interface/interface:fortygigabitethernet" {
    uses common-phy-storm-control-cmds;
  }
}
