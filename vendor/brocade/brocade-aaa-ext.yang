module brocade-aaa-ext {
  namespace "urn:brocade.com:mgmt:brocade-aaa-ext";
  prefix aaa-extensions;

  import brocade-common-def {
    prefix common-def;
  }

  revision 2010-09-21 {
    description
      "Added aaa-show-ext.";
  }

  augment "/common-def:show" {
    container aaa-users;
  }
  rpc user-session-info {
    output {
      leaf user-role {
        type string {
          length "4 .. 32";
        }
      }
    }
  }
}
