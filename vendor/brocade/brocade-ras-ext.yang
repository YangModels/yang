module brocade-ras-ext {
  namespace "urn:brocade.com:mgmt:brocade-ras-ext";
  prefix ras-extensions;

  import ietf-yang-types {
    prefix ietfyang;
  }
  import brocade-common-def {
    prefix common-def;
  }

  organization "Brocade Communications Systems, Inc.";
  contact
    "Brocade Communications Systems, Inc.
     Postal: 130 Holger Way
             San Jose, CA 95134
             U.S.A
     Tel: +1-408-333-6061
     E-mail: support@Brocade.com
     web: www.brocade.com.";
  description
    "This module defines RASLOG related information.
     Copyright (c) 2010-11 by Brocade Communications Systems, Inc.
     All rights reserved.";
  reference "brocade-ras.yang";

  revision 2011-01-20 {
    description
      "Added new Action Point for RASLOG for Netconf interface.";
    reference "RAS.yang";
  }

  typedef switchid-type {
    type string {
      length "1..3" {
        error-message "Invalid rbridge-id (must be in the range 1 - 239) or all";
      }
    }
  }

  typedef switchid-type-noall {
    type string {
      length "1..3" {
        error-message "Invalid rbridge-id (must be in the range 1 - 239)";
      }
    }
  }

  typedef rbridge-ids-all-type {
    description
      "The unique identifier for a switch.  The usage of `all'
       refers to `all' rbridge-id's in the cluster.";
    type union {
      type common-def:ui32-range;
      type string {
        pattern "all";
      }
    }
  }

  typedef ha-recovery-type {
    type enumeration {
      enum "unknown" {
        value 0;
      }
      enum "warm-recovery-in-progress" {
        value 1;
      }
      enum "cold-recovery-in-progress" {
        value 2;
      }
      enum "warm-recovered" {
        value 3;
      }
      enum "cold-recovered" {
        value 4;
      }
    }
  }

  typedef fru-type {
    type enumeration {
      enum "other" {
        value 1;
      }
      enum "unknown" {
        value 2;
      }
      enum "chassis" {
        value 3;
      }
      enum "cp" {
        value 4;
      }
      enum "other-cp" {
        value 5;
      }
      enum "switch-blade" {
        value 6;
      }
      enum "wwn" {
        value 7;
      }
      enum "power-suppy" {
        value 8;
      }
      enum "fan" {
        value 9;
      }
      enum "core-blade" {
        value 10;
      }
      enum "application-blade" {
        value 11;
      }
    }
  }

  typedef fru-operational-status {
    type enumeration {
      enum "other" {
        value 1;
      }
      enum "unknown" {
        value 2;
      }
      enum "on" {
        value 3;
      }
      enum "off" {
        value 4;
      }
      enum "faulty" {
        value 5;
      }
      enum "inserted" {
        value 6;
      }
      enum "ready" {
        value 7;
      }
      enum "up" {
        value 8;
      }
    }
  }

  typedef sensor-type {
    type enumeration {
      enum "unknown" {
        value 1;
      }
      enum "other" {
        value 2;
      }
      enum "temperature" {
        value 3;
      }
      enum "pressure" {
        value 4;
      }
      enum "emf" {
        value 5;
      }
      enum "current" {
        value 6;
      }
      enum "airflow" {
        value 7;
      }
      enum "frequency" {
        value 8;
      }
      enum "power" {
        value 9;
      }
      enum "door" {
        value 10;
      }
    }
  }

  typedef sensor-status {
    type enumeration {
      enum "unknown" {
        value 1;
      }
      enum "other" {
        value 2;
      }
      enum "ok" {
        value 3;
      }
      enum "warning" {
        value 4;
      }
      enum "failed" {
        value 5;
      }
    }
  }

  augment "/common-def:show" {
    container support;
    container copy-support;
    container infra {
      description
        "show system info";
      container process;
      container environment;
    }
    container logging;
  }
  container rasman;
  rpc show-raslog {
    description
      "Shows the entries of RASLOG";
    input {
      leaf rbridge-id {
        type switchid-type;
      }
      leaf number-of-latest-events {
        type uint32;
        description
          "This specifies the number of recent events to be fetched
           from RASLOG entries.";
      }
    }
    output {
      list show-all-raslog {
        leaf rbridge-id {
          type switchid-type;
        }
        leaf number-of-entries {
          type uint32;
          description
            "This specifies the number of entries in the  be fetched";
        }
        list raslog-entries {
          leaf index {
            type uint32;
            description
              "Sequence number for the message";
          }
          leaf message-id {
            type string;
            description
              "Message identifier";
          }
          leaf date-and-time-info {
            type string;
            description
              "Date and time of the message.
               The format is: YYYY-MM-DD/HH:MM:SS.SSSS (micro seconds)";
          }
          leaf severity {
            type enumeration {
              enum "critical" {
                value 1;
              }
              enum "error" {
                value 2;
              }
              enum "warning" {
                value 3;
              }
              enum "informational" {
                value 4;
              }
              enum "debug" {
                value 5;
              }
              enum "unknown" {
                value 6;
              }
            }
            reference "swEventLevel defined in SW.mib";
            description
              "Severity of the message. Valid values include
               INFO, WARNING, ERROR, and CRITICAL.";
          }
          leaf repeat-count {
            type uint32;
            description
              "It identifies how many times this particular
               event has occurred.";
          }
          leaf message {
            type string;
            description
              "It contains the textual description of the event.";
          }
          leaf message-flag {
            type enumeration {
              enum "other" {
                value 1;
              }
              enum "unknown" {
                value 2;
              }
              enum "ffdc" {
                value 3;
              }
              enum "vcs" {
                value 4;
              }
            }
            description
              "It specifies the type of the message.";
          }
          leaf log-type {
            type enumeration {
              enum "system" {
                value 0;
              }
              enum "dce" {
                value 1;
              }
            }
            description
              "It specifies if the message is a SYSTEM or DCE log";
          }
          leaf switch-or-chassis-name {
            type string;
            description
              "Switch name for the generator of this message, or chassis";
          }
        }
      }
      leaf cmd-status-error-msg {
        type string;
      }
    }
  }
  rpc show-support-save-status {
    description
      "Information on the status of recent support save request";
    input {
      leaf rbridge-id {
        type switchid-type;
      }
    }
    output {
      list show-support-save-status {
        leaf rbridge-id {
          type switchid-type;
        }
        leaf status {
          type enumeration {
            enum "other" {
              value 1;
            }
            enum "unknown" {
              value 2;
            }
            enum "completed" {
              value 3;
            }
            enum "inProgress" {
              value 4;
            }
            enum "error" {
              value 5;
            }
          }
          description
            "status of recent support save.";
        }
        leaf message {
          type string;
          description
            "Textual description of status of recent support save is
             as follows:
              unknown/other - Support Save is failed for
                              Unknown/undefined reason.  
              completed - The recent support save is completed successfully.
              in-progress - The support save is not yet completed.
                            It may contain the value of % completed.
              error - Specify the error message.";
        }
        leaf percentage-of-completion {
          type uint32;
          description
            "It specifies the value of % of completion.";
        }
      }
    }
  }
  rpc show-system-info {
    description
      "Shows the system information MAC etc.";
    input {
      leaf rbridge-id {
        type switchid-type;
      }
    }
    output {
      list show-system-info {
        leaf rbridge-id {
          type switchid-type;
        }
        leaf stack-mac {
          type ietfyang:mac-address;
          description
            "MAC address of the switch.";
        }
      }
    }
  }
  augment "/common-def:clear" {
    container support;
    container logging;
  }
}
