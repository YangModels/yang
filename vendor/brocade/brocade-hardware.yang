module brocade-hardware {
  namespace "urn:brocade.com:mgmt:brocade-hardware";
  prefix hardware;

  import brocade-vcs {
    prefix brocade-vcs;
  }
  import brocade-rbridge {
    prefix rbridge;
  }
  import brocade-interface {
    prefix interface;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This hardware management module is used to manage connectors.
     It can be used to breakout the connectors and set the type
     of the connectors.";

  revision 2012-12-20 {
    description
      "Initial version of this management module.";
  }

  typedef u-port-type {
    type enumeration {
      enum "ethernet" {
        value 1;
      }
      enum "fibre-channel" {
        value 2;
      }
    }
  }

  container hardware {
    list connector {
      key "name";
      leaf name {
        type interface:interface-type;
        mandatory true;
      }
      container sfp {
        leaf breakout {
          type empty;
        }
      }
    }
  }
}
