module brocade-bprate-limit {
  namespace "urn:brocade.com:mgmt:brocade-bprate-limit";
  prefix bprate-limit;

  import ietf-inet-types {
    prefix inet;
  }

  organization "Brocade Communications Systems, Inc.";
  contact
    "Brocade Communications Systems, Inc.
     Postal: 130 Holger way,
     San Jose, CA 95134,
     U.S.A
     Tel: +1-408-333-8000
     E-mail: support@Brocade.com
     web: www.brocade.com.";
  description
    "This management module is an instrumentation to manage
     Bp Ratelimit module";

  revision 2011-10-31 {
    description
      "Initial version of this management module.";
  }

  typedef slotnumber {
    type uint32 {
      range "0..16" {
        error-message "Invalid slot number.";
      }
    }
  }

  container bp-rate-limit {
    container heavy {
      list bp-rate-limit-slot {
        key "bp-rate-limit-slot-num";
        leaf bp-rate-limit-slot-num {
          type slotnumber;
        }
      }
    }
  }
}
