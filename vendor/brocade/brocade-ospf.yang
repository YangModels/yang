module brocade-ospf {
  namespace "urn:brocade.com:mgmt:brocade-ospf";
  prefix ospf;

  import brocade-rbridge {
    prefix rbridge;
  }
  import brocade-interface {
    prefix interface;
  }
  import brocade-ip-config {
    prefix ip-config;
  }
  import brocade-common-def {
    prefix common-def;
  }
  import brocade-intf-loopback {
    prefix intf-loopback;
  }
  import ietf-inet-types {
    prefix inet;
  }

  organization "Brocade Communications Systems, Inc.";
  contact
    "Brocade Communications Systems, Inc.
     Postal: 130 Holger Way,
             San Jose, CA 95134 
              U.S.A
     Tel: +1-408-333-8000
     E-mail: support@Brocade.com 
     web: www.brocade.com.";
  description
    "This management module is an instrumentation to manage 
     OSPF Version 2 Protocol.";

  revision 2010-11-29 {
    description
      "Initial version of this management module.";
  }

  typedef ospf-area-id {
    type string {
      pattern "((([0-9]|[1-9][0-9]|1[0-9][0-9]|2[0-4][0-9]|25[0-5])\\.)(([0-9]|[1-9][0-9]|1[0-9][0-9]|2[0-4][0-9]|25[0-5])\\.){2}([0-9]|[1-9][0-9]|1[0-9][0-9]|2[0-4][0-9]|25[0-5]))|(([0-9])|([1-9]([0-9]{1,8}))|([1]([0-9]{1,9}))|([2][0]([0-9]{1,8}))|([2][1][0-3]([0-9]{1,7}))|([2][1][4][0-6]([0-9]{1,6}))|([2][1][4][7][0-3]([0-9]{1,5}))|([2][1][4][7][4][0-7]([0-9]{1,4}))|([2][1][4][7][4][8][0-2]([0-9]{1,3}))|([2][1][4][7][4][8][3][0-5]([0-9]{1,2}))|([2][1][4][7][4][8][3][6][0-3][0-9])|([2][1][4][7][4][8][3][6][4][0-7]))";
    }
  }

  typedef ospf-auth-psswd-string {
    type string;
  }

  typedef big-metric {
    type uint32;
  }

  typedef range-metric {
    type uint32;
  }

  typedef band-width {
    type uint32 {
      range "1..4294967";
    }
    units "megabits per second";
  }

  typedef metric-type {
    type enumeration {
      enum "type1" {
        value 1;
      }
      enum "type2" {
        value 2;
      }
    }
  }

  typedef route-option-type {
    type enumeration {
      enum "all" {
        value 1;
      }
      enum "connected" {
        value 2;
      }
      enum "static" {
        value 4;
      }
    }
  }

  typedef route-type-enum {
    type enumeration {
      enum "external" {
        value 1;
      }
      enum "inter-area" {
        value 2;
      }
      enum "intra-area" {
        value 3;
      }
    }
  }

  typedef match-set-metric-option-type {
    type enumeration {
      enum "match-metric" {
        value 1;
      }
      enum "set-metric" {
        value 2;
      }
    }
  }

  typedef key-type {
    type uint32 {
      range "0|2|255";
    }
  }

  typedef ospf-hexstring {
    type string {
      pattern "[0-9a-fA-F]{1,8}";
    }
  }

  typedef ospf-ipv4-address {
    type inet:ipv4-address;
  }

  typedef ospf-ipv4-prefix {
    type inet:ipv4-prefix;
  }

  typedef ospf-link-state-id {
    type inet:ipv4-address;
  }

  typedef ospf-adv-router-id {
    type inet:ipv4-address;
  }

  typedef ospf-router-id {
    type inet:ipv4-address;
  }

  typedef ospf-lsdb-index {
    type uint32;
  }

  typedef ospf-show-area-id-num-range {
    type uint32 {
      range "0..2147483647";
    }
  }

  typedef ospf-show-area-id-ip-range {
    type inet:ipv4-address;
  }

  typedef ospf-show-area-id-range {
    type union {
      type ospf-show-area-id-num-range;
      type ospf-show-area-id-ip-range;
    }
  }

  typedef ospf-neighbor-rid {
    type inet:ipv4-address;
  }

  typedef ospf-entry-index {
    type uint32;
  }

  typedef ospf-interface-ip {
    type inet:ipv4-address;
  }

  typedef ospf-route-dest {
    type inet:ipv4-address;
  }

  typedef ospf-route-prefix {
    type inet:ipv4-address;
  }

  typedef ospf-route-mask {
    type inet:ipv4-address;
  }

  grouping common-link-props {
    container authentication-key {
      container no-encrypt-auth-key-table {
        leaf no-encrypt-auth-key {
          type ospf-auth-psswd-string;
        }
      }
      container auth-key-table {
        leaf encrypttype {
          type key-type;
        }
        leaf auth-key {
          type ospf-auth-psswd-string;
        }
      }
    }
    leaf dead-interval {
      default "40";
      type common-def:time-interval-sec {
        range "3..65535";
      }
    }
    leaf hello-interval {
      default "10";
      type common-def:time-interval-sec {
        range "1..65535";
      }
    }
    leaf retransmit-interval {
      type common-def:time-interval-sec {
        range "0..3600";
      }
    }
    leaf transmit-delay {
      type common-def:time-interval-sec {
        range "0..3600";
      }
    }
    container md5-authentication {
      leaf key-activation-wait-time {
        type common-def:time-interval-sec {
          range "0..14400";
        }
      }
      container no-encrypt-key-table {
        leaf no-encrypt-key-id {
          type uint32 {
            range "1..255";
          }
        }
        leaf no-encrypt-key {
          type ospf-auth-psswd-string;
        }
      }
      container key-table {
        leaf key-id {
          type uint32 {
            range "1..255";
          }
        }
        leaf key {
          type key-type;
          description
            "MD5 Authentication password (key)";
        }
        leaf md5-authentication-key {
          type ospf-auth-psswd-string;
        }
      }
    }
  }

  grouping interface-fo-ospf {
    container interface-fo-ospf-conf {
      uses interface-ospf;
    }
  }

  grouping interface-te-ospf {
    container interface-te-ospf-conf {
      uses interface-ospf;
    }
  }

  grouping interface-gi-ospf {
    container interface-gi-ospf-conf {
      uses interface-ospf;
    }
  }

  grouping interface-PO-ospf {
    container interface-PO-ospf-conf {
      uses interface-ospf;
    }
  }

  grouping interface-vlan-ospf {
    container interface-vlan-ospf-conf {
      uses interface-ospf;
    }
  }

  grouping interface-loopback-ospf {
    container interface-loopback-ospf-conf {
      uses interface-ospf;
    }
  }

  typedef database-filter-options {
    type enumeration {
      enum "allow-default-out" {
        value 1;
      }
      enum "allow-default-and-type4-out" {
        value 2;
      }
      enum "out" {
        value 3;
      }
    }
  }

  grouping interface-ospf {
    container ospf1 {
      leaf area {
        type ospf-area-id;
      }
      leaf auth-change-wait-time {
        type common-def:time-interval-sec {
          range "0..14400";
        }
      }
      uses common-link-props;
      leaf cost {
        default "1";
        type uint32 {
          range "1..65535";
        }
      }
      container database-filter {
        leaf all-out {
          type empty;
        }
        leaf all-external {
          type database-filter-options;
        }
        leaf all-summary-external {
          type database-filter-options;
        }
      }
      leaf mtu-ignore {
        type empty;
      }
      leaf network {
        type enumeration {
          enum "broadcast" {
            value 1;
          }
          enum "non-broadcast" {
            value 2;
          }
          enum "point-to-point" {
            value 3;
          }
        }
      }
      leaf active {
        type empty;
      }
      leaf passive {
        type empty;
      }
      leaf priority {
        type uint32 {
          range "0..255";
        }
      }
    }
  }

  grouping global-ospf {
    leaf database-overflow-interval {
      type common-def:time-interval-sec {
        range "0..86400";
      }
    }
    container default-information-originate {
      presence "true";
      leaf always {
        type empty;
      }
      leaf def-orig-metric {
        type uint32 {
          range "1..65535";
        }
      }
      leaf def-orig-metric-type {
        type metric-type;
      }
      leaf def-orig-route-map {
        default "";
        type string;
      }
    }
    leaf default-passive-interface {
      type empty;
    }
    leaf default-metric {
      type uint32 {
        range "1..65535";
      }
      default "10";
    }
    leaf external-lsdb-limit {
      type uint32 {
        range "1..14913080";
      }
      default "14913080";
    }
    container log {
      container adjacency {
        presence "true";
        leaf dr-only {
          type empty;
        }
      }
      leaf log-all {
        type empty;
      }
      container bad-packet {
        presence "true";
        leaf log-checksum {
          type empty;
        }
      }
      leaf log-database {
        type empty;
      }
      leaf log-retransmit {
        type empty;
      }
    }
    leaf ospf-metric-type {
      type metric-type;
    }
    list neighbor {
      key "neighbor-addr";
      leaf neighbor-addr {
        type ospf-ipv4-address;
      }
    }
    container nssa-translator {
      presence "nssaTranslator";
      description
        "Enable NSSA Type 7 to Type 5 LSA translation";
      leaf nssa-translator-flag {
        type empty;
      }
    }
    container redistribute {
      container connected {
        presence "true";
        leaf connected-route-map {
          type common-def:name-string63;
        }
      }
      container static {
        presence "true";
        leaf static-route-map {
          type common-def:name-string63;
        }
      }
      container bgp {
        presence "true";
        leaf bgp-route-map {
          type common-def:name-string63;
        }
      }
    }
    container rfc1583-compatibility {
      presence "rfc1583";
      leaf rfc1583-compatibility-flag {
        type empty;
      }
    }
    list area {
      key "area-id";
      leaf area-id {
        type ospf-area-id;
      }
      leaf normal {
        type empty;
      }
      container nssa {
        container metric {
          leaf nssa-value {
            type big-metric;
          }
          leaf no-summary1 {
            type empty;
          }
        }
        leaf default-information-originate {
          type empty;
        }
      }
      list range {
        key "range-address range-mask";
        leaf range-address {
          type inet:ipv4-address;
          mandatory true;
        }
        leaf range-mask {
          type inet:ipv4-address;
          mandatory true;
        }
        leaf range-effect {
          type enumeration {
            enum "advertise" {
              value 1;
            }
            enum "not-advertise" {
              value 2;
            }
          }
        }
        leaf range-cost {
          type range-metric;
          default "0";
        }
      }
      container stub {
        container metric {
          leaf stub-value {
            type big-metric;
          }
          leaf no-summary {
            type empty;
          }
        }
      }
      list virtual-link {
        key "virt-link-neighbor";
        leaf virt-link-neighbor {
          type inet:ipv4-address;
        }
        uses common-link-props;
      }
    }
    container auto-cost {
      container reference-bandwidth {
        leaf ref-bandwidth {
          type band-width;
        }
        leaf use-active-ports {
          type empty;
        }
      }
    }
    list distance {
      key "route-type";
      leaf route-type {
        type route-type-enum;
      }
      leaf dist-value {
        type uint32 {
          range "1..255";
        }
      }
    }
    container distribute-list {
      container route-map {
        leaf route-map {
          type common-def:name-string63;
        }
        leaf in {
          type empty;
        }
      }
    }
    container max-metric {
      container router-lsa {
        presence "true";
        leaf all-vrfs {
          type empty;
        }
        leaf all-lsas {
          type empty;
        }
        container external-lsa {
          presence "true";
          leaf external-lsa-val {
            type uint32 {
              range "1..16777214";
            }
            default "16711680";
          }
        }
        container summary-lsa {
          presence "true";
          leaf summary-lsa-val {
            type uint32 {
              range "1..16777214";
            }
            default "16711680";
          }
        }
        container link {
          leaf all {
            type empty;
          }
          leaf ptp {
            type empty;
          }
          leaf stub {
            type empty;
          }
          leaf transit {
            type empty;
          }
        }
        container on-startup {
          leaf time {
            type uint32 {
              range "5 ..86400";
            }
            units "seconds";
          }
          leaf wait-for-bgp {
            type empty;
          }
          leaf all-lsas-onstartup {
            type empty;
          }
          container external-lsa-onstartup {
            presence "true";
            leaf external-lsa-val-onstartup {
              type uint32 {
                range "1..16777214";
              }
              default "16711680";
            }
          }
          container summary-lsa-onstartup {
            presence "true";
            leaf summary-lsa-val-onstartup {
              type uint32 {
                range "1..16777214";
              }
              default "16711680";
            }
          }
          container link-onstartup {
            leaf all-link-onstartup {
              type empty;
            }
            leaf ptp-link-onstartup {
              type empty;
            }
            leaf stub-link-onstartup {
              type empty;
            }
            leaf transit-link-onstartup {
              type empty;
            }
          }
        }
      }
    }
    list summary-address {
      key "sum-address sum-address-mask";
      leaf sum-address {
        type ospf-ipv4-address;
      }
      leaf sum-address-mask {
        type inet:ipv4-address;
      }
    }
    container timers {
      leaf lsa-group-pacing {
        type common-def:time-interval-sec {
          range "10..1800";
        }
      }
      container throttle {
        container spf {
          leaf init-delay {
            type common-def:time-interval-msec {
              range "0..60000";
            }
          }
          leaf hold-time {
            type common-def:time-interval-msec {
              range "0..60000";
            }
          }
          leaf max-hold-time {
            type common-def:time-interval-msec {
              range "0..60000";
            }
          }
        }
      }
    }
    container permit {
      list redistribute {
        key "redist-value route-option";
        leaf redist-value {
          type uint32 {
            range "1..64";
          }
        }
        leaf route-option {
          type route-option-type;
        }
        leaf address {
          type inet:ipv4-address;
        }
        leaf mask {
          type inet:ipv4-address;
        }
        leaf set-metric-val {
          type uint32 {
            range "1..4294967295";
          }
        }
        leaf match-metric-val {
          type uint32 {
            range "1..4294967295";
          }
        }
      }
    }
    container deny {
      list redistribute {
        key "redist-value route-option";
        leaf redist-value {
          type uint32 {
            range "1..64";
          }
        }
        leaf route-option {
          type route-option-type;
        }
        leaf address {
          type inet:ipv4-address;
        }
        leaf mask {
          type inet:ipv4-address;
        }
        leaf set-metric-val {
          type uint32 {
            range "1..4294967295";
          }
        }
        leaf match-metric-val {
          type uint32 {
            range "1..4294967295";
          }
        }
      }
    }
    leaf vrf-lite-capability {
      type empty;
    }
  }

  augment "/rbridge:rbridge-id/rbridge:router" {
    list ospf {
      key "vrf";
      leaf vrf {
        type string {
          length "1..64";
        }
      }
      uses global-ospf;
    }
  }
  augment "/rbridge:rbridge-id/interface:interface/interface:ve/ip-config:ip" {
    uses interface-vlan-ospf;
  }
  augment "/interface:interface-vlan/interface:interface/interface:ve/interface:ip" {
    uses interface-vlan-ospf;
  }
  augment "/rbridge:rbridge-id/interface:interface/intf-loopback:loopback/ip-config:ip" {
    uses interface-loopback-ospf;
  }
  augment "/interface:interface/interface:fortygigabitethernet/interface:ip" {
    uses interface-fo-ospf;
  }
  augment "/interface:interface/interface:tengigabitethernet/interface:ip" {
    uses interface-te-ospf;
  }
  augment "/interface:interface/interface:gigabitethernet/interface:ip" {
    uses interface-gi-ospf;
  }
}
