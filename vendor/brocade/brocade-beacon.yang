module beacon {
  namespace "urn:brocade.com:mgmt:brocade-beacon";
  prefix beacon;

  revision 2011-10-31 {
    description
      "Initial version of this management module.";
  }

  container beacon {
    container enable;
    container disable;
  }
}
