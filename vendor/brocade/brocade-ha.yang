module brocade-ha {
  namespace "urn:brocade.com:mgmt:brocade-ha";
  prefix ha;

  import brocade-common-def {
    prefix common-def;
  }
  import brocade-ras-ext {
    prefix ras-extensions;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This management module is an instrumentation to ha
     level commands";

  revision 2011-10-31 {
    description
      "Initial version of this management module.";
  }

  container ha {
    container sync;
  }
  augment "/common-def:show" {
    container ha;
  }
  augment "/common-def:show" {
    container redundancy;
  }
  container system;
}
