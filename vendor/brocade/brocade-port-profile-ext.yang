module brocade-port-profile-ext {
  namespace "urn:brocade.com:mgmt:brocade-port-profile-ext";
  prefix appm-extensions;

  import ietf-yang-types {
    prefix inet;
  }
  import brocade-common-def {
    prefix common-def;
  }
  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This management module is an extension to the port-profile
     model for 
        - Defining RPCs to retrieve port-profile related operational
          data in the managed device.";

  revision 2000-07-15 {
    description
      "Initial version of the management module
       port-profile-ext";
  }

  rpc get-port-profile-for-intf {
    description
      "This is a function that returns the port profiles applied 
       on port(s) and port-channels.";
    input {
      leaf rbridge-id {
        description
          "rbridge id of the node from which the data needs 
           to be fetched. When no rbridge id is given, data is fetched
           from all rbridges";
        type uint32;
        mandatory false;
      }
      choice request-type {
        case get-request {
          uses interface:interface-name-info {
            description
              "This indicates the name and type of the interface
                           to query. 
                           The rpc response contians the list of port-profiles 
                           applied on the given interface.
               
                           The rpc request would look as below:
                           get-port-profile-for-intf 
                           interface-type=fortygigabitethernet
                           interface-name=1/0/1.
                           
                           The rpc response contains the list of 
                           port-profiles applied on the interface fo 1/0/1.
                           
                           The rpc response has an attribute has-more, 
                           which will always be false, since the rpc response 
                           contains all the port-profiles applied on the given 
                           interface.";
          }
        }
        case getnext-request {
          container last-received-interface-info {
            uses interface:interface-name-info {
              description
                "This indicates the name and type of the last 
                 interface, for which the list of applied 
                 port-profiles is already received.";
            }
            description
              "The rpc returns the list of
               port-profiles associated with the next set of 
               interfaces.
               
               The rpc request would look as below:
               get-port-profile-for-intf
               last-received-interface-info/interface-type=
               fortygigabitethernet
               last-received-interface-info/interface-name=
               1/0/1.
               
               The rpc response will contain the list of 
               port-profiles applied on the interface fo 1/0/2,
               1/0/3 and so on till the page limit is reached.
               
               The rpc response has an attribute is-more, which 
               will be false, when all the interfaces are 
               exhausted.
               
               The getnext-request model can be used to retrieve
               the port-profiles applied on all the interfaces.
               
               The rpc returns the list of port-profiles applied 
               on the first set of interfaces when interface name 
               and interface type are not specified.";
          }
        }
      }
    }
    output {
      list interface {
        uses interface:interface-name-info {
          description
            "The list of all the interfaces on which
             Port Profile is applied. Each row 
             represents interface details(type,name) and the
             Port Profile name applied on the interface.";
        }
        list port-profile {
          description
            "The list of port profiles applied on this
             interface. Each row contains Port Profile 
             name.";
          leaf name {
            type common-def:name-string64;
            description
              "This indicates Port Profile name 
               associated to this interface.";
          }
        }
      }
      leaf has-more {
        type boolean;
        description
          "Value is :
           
           false, for get request model.
           false, when the port-profiled-ports are exhausted 
           in getnext request model.
           
           true, when more port-profiled ports exist in 
           getnext request model.";
      }
    }
  }
  rpc get-port-profile-status {
    description
      "This is a function that returns the status of a port 
       profile or all the port profiles.";
    input {
      leaf rbridge-id {
        description
          "rbridge id of the node from which the data needs
           to be fetched. When no rbridge id is given, data is fetched
           from all rbridges";
        type uint32;
        mandatory false;
      }
      leaf port-profile-name {
        type common-def:name-string64;
        mandatory false;
        description
          "This indicates the optional port profile name to
           query.It returns status of all profiles if no
           profile name is specified";
      }
      leaf port-profile-status {
        type enumeration {
          enum "activated" {
            value 1;
            description
              "Port Profile is activated.";
          }
          enum "associated" {
            value 2;
            description
              "Port Profile is associated to one or more
               MAC addresses.";
          }
          enum "applied" {
            value 3;
            description
              "Port Profile is applied on one or more
               interfaces.";
          }
        }
        mandatory false;
        description
          "This indicates query is based on the port profile 
           status. Profiles are not filtered based on the
           status when this parameter is not specified";
      }
      choice request-type {
        case getnext-request {
          container last-received-port-profile-info {
            leaf profile-name {
              type common-def:name-string64;
              mandatory false;
              description
                "This indicates the name of the last
                 received port-profile.";
            }
            leaf profile-mac {
              type inet:mac-address;
              mandatory false;
              description
                "This indicates the last received mac
                 address of the last received port-profile.";
            }
            description
              "get request : 
               provides data only for a given
               port profile based on the input attribute 
               port-profile-name.
               
               To begin with, user should provide 
               port-profile-name attribute and optional
               profile-mac value as 00:00:00:00:00:00.
               The response will contain the initial set of
               macs associated with the given port profile.
               
               For subsequent calls, user should provide 
               port-profile-name along with the 
               profile-mac value.
               Response will contain the next set of
               associated macs for the given port profile.
               
               Response has an attribute is-more, which
               will be false, when all the macs associated
               with a given port-profile are exhausted.
               
               getnext request : 
               To get the next record,
               provide both profile-name and profile-mac.
               
               To begin with, user can invoke the rpc 
               without providing profile-name and profile-mac
               attributes.
               The response will contain the initial set of 
               macs associated with the first port profile.
               
               For subsequent calls, user should provide 
               profile-name along with the profile-mac.
               
               If the user provides profile-name and last 
               profile mac associated with the profile, 
               the response will contain the next port profile
               info.
               
               Response has an attribute is-more, which will
               be false, when all the macs associated with all
               the port-profiles are exhausted.";
          }
        }
      }
    }
    output {
      list port-profile {
        key "name";
        description
          "The list of port profiles. Each row represents the
           port profile details, its status and its MAC
           associations.";
        leaf name {
          type common-def:name-string64;
          description
            "This indicates the name of the port profile.";
        }
        leaf ppid {
          type uint32;
          description
            "This indicates the id of the Port Profile.";
        }
        leaf is-active {
          type boolean;
          description
            "This indicates if this port-profile is 
             activated or not.";
        }
        list mac-association {
          key "mac";
          description
            "The list of MAC associations for this port 
             profile. Each row represents the MAC address 
             and the details of the interface to which
             the MAC is associated.";
          leaf mac {
            type inet:mac-address;
            description
              "This indicates the MAC addresses associated
               with this Port Profile.";
          }
          container applied-interface {
            uses interface:interface-name-info;
            description
              "This container provides the grouping of
               elements required to identify the 
               interface on which  which this MAC 
               association is applied. No interface name 
               will be listed when the port profile is not
               applied with respect to this MAC.";
          }
        }
        leaf has-more {
          type boolean;
          description
            "Value is :
             false, if no more macs exist for a given 
             port-profile in get request model 
             or 
             no more macs exist for the
             last profile in getnext request model.
                 
             true, if more macs exist for a given profile
             in get request model
             or
             more macs [or profiles] exist in 
             getnext request model.";
        }
      }
    }
  }
}
