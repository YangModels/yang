module brocade-bgp {
  namespace "urn:brocade.com:mgmt:brocade-bgp";
  prefix bgp;

  import brocade-rbridge {
    prefix rbridge;
  }
  import brocade-common-def {
    prefix common-def;
  }
  import ietf-inet-types {
    prefix inet;
  }

  organization "Brocade Communications Systems, Inc.";
  contact
    "Brocade Communications Systems, Inc.
     Postal: 130 Holger Way,
             San Jose, CA 95134
              U.S.A
     Tel: +1-408-333-8000
     E-mail: support@Brocade.com
     web: www.brocade.com.";
  description
    "This management module is an instrumentation to manage
     BGP Protocol.";

  revision 2010-11-29 {
    description
      "Initial version of this management module.";
  }

  typedef neighbor-description {
    type string {
      length "1..220";
    }
  }

  typedef attribute-map {
    type string {
      length "1..63";
    }
  }

  typedef advertise-map {
    type string {
      length "1..63";
    }
  }

  typedef suppress-map {
    type string {
      length "1..63";
    }
  }

  typedef holdover-interval {
    type uint32 {
      range "1..30";
    }
  }

  typedef min-tx {
    type uint32 {
      range "50..30000";
    }
  }

  typedef decimal-number {
    type uint32 {
      range "1..65535";
    }
  }

  typedef absolute-decimal-number {
    type uint32 {
      range "0..65535";
    }
  }

  typedef update-time-type {
    type uint32 {
      range "0..30";
    }
  }

  typedef cidentifier {
    type uint32 {
      range "1..4294967295";
    }
  }

  typedef as-num-show {
    type uint32 {
      range "1..4294967295";
    }
  }

  typedef htime {
    type uint32 {
      range "1..45";
    }
  }

  typedef damp-reuse-value {
    type uint32 {
      range "1..20000";
    }
  }

  typedef damp-start-suppress-value {
    type uint32 {
      range "1..20000";
    }
  }

  typedef damp-max-suppress-value {
    type uint32 {
      range "1..255";
    }
  }

  typedef rmap-type {
    type string {
      length "1..63";
    }
  }

  typedef ext-route-distance {
    type uint32 {
      range "1..255";
    }
  }

  typedef int-route-distance {
    type uint32 {
      range "1..255";
    }
  }

  typedef lcl-route-distance {
    type uint32 {
      range "1..255";
    }
  }

  typedef local-as-type {
    type string {
      pattern "((([0-9][0-9]{0,3})|([1-5][0-9]{4})|(6[0-4][0-9]{3})|(65[0-4][0-9]{2})|(655[0-2][0-9])|(6553[0-5]))\\.(([0-9][0-9]{0,3})|([1-5][0-9]{4})|(6[0-4][0-9]{3})|(65[0-4][0-9]{2})|(655[0-2][0-9])|(6553[0-5])))|([1-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])";
    }
  }

  typedef num-as-in-path {
    type uint32 {
      range "0..300";
    }
  }

  typedef ebgp-paths {
    type uint32 {
      range "1..8";
    }
  }

  typedef ibgp-paths {
    type uint32 {
      range "1..8";
    }
  }

  typedef rtime-type {
    type uint32 {
      range "1..3600";
    }
  }

  typedef ptime-type {
    type uint32 {
      range "1..3600";
    }
  }

  typedef st-time-type {
    type uint32 {
      range "1..3600";
    }
  }

  typedef conn-metric {
    type uint32 {
      range "1..4294967295";
    }
  }

  typedef sdistance {
    type uint32 {
      range "1..255";
    }
  }

  typedef adv-value {
    type uint32 {
      range "0..3600";
    }
  }

  typedef allow-as-value {
    type uint32 {
      range "1..10";
    }
  }

  typedef min-rx {
    type uint32 {
      range "50..30000";
    }
  }

  typedef multiplier {
    type uint32 {
      range "3..50";
    }
  }

  typedef ip-filter-num {
    type uint32 {
      range "1..199";
    }
  }

  typedef ip-filter-name {
    type string {
      length "1..63";
    }
  }

  typedef ip-filter-num-and-name {
    type union {
      type ip-filter-num;
      type ip-filter-name;
    }
    description
      "This data provides option of both ACL Name and number";
  }

  typedef nei-as-filter-name {
    type string {
      length "1..63";
    }
  }

  typedef local-as-num {
    type string {
      pattern "((([0-9][0-9]{0,3})|([1-5][0-9]{4})|(6[0-4][0-9]{3})|(65[0-4][0-9]{2})|(655[0-2][0-9])|(6553[0-5]))\\.(([0-9][0-9]{0,3})|([1-5][0-9]{4})|(6[0-4][0-9]{3})|(65[0-4][0-9]{2})|(655[0-2][0-9])|(6553[0-5])))|([1-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])";
    }
  }

  typedef num-as-in-as-path {
    type uint32 {
      range "0..300";
    }
  }

  typedef max-prefix-limit {
    type uint32 {
      range "1..2147483647";
    }
  }

  typedef max-prefix-threshold {
    type uint32 {
      range "1..100";
    }
  }

  typedef bgp-password {
    type string {
      length "1..63";
    }
  }

  typedef bgp-peergroup {
    type string {
      pattern "[a-zA-Z]{1}([-a-zA-Z0-9\\\\\\\\@#\\+\\*\\(\\)=\\{~\\}%<>=$_\\[\\]\\|]{0,63})";
    }
  }

  typedef nei-prefix-list-filter {
    type string {
      length "1..63";
    }
  }

  typedef bgp-remote-as {
    type string {
      pattern "((([0-9][0-9]{0,3})|([1-5][0-9]{4})|(6[0-4][0-9]{3})|(65[0-4][0-9]{2})|(655[0-2][0-9])|(6553[0-5]))\\.(([0-9][0-9]{0,3})|([1-5][0-9]{4})|(6[0-4][0-9]{3})|(65[0-4][0-9]{2})|(655[0-2][0-9])|(6553[0-5])))|([1-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])";
    }
  }

  typedef nei-keep-alive {
    type uint32 {
      range "0..65535";
    }
  }

  typedef nei-hold-time {
    type uint32 {
      range "0..65535";
    }
  }

  typedef sip-ipv4-address {
    type inet:ipv4-address;
  }

  typedef eth-interface {
    type string {
      length "1..63";
    }
  }

  typedef loopback-interface {
    type string {
      length "1..63";
    }
  }

  typedef ve-interface {
    type uint32 {
      range "1..8000";
    }
  }

  typedef nei-weight {
    type uint32 {
      range "0..65535";
    }
  }

  typedef rr-group-type {
    type uint32 {
      range "1..99";
    }
  }

  typedef action-t {
    type enumeration {
      enum "send" {
        value 1;
        description
          "Capability to SEND the ORF to this neighbor";
      }
      enum "receive" {
        value 2;
        description
          "Capability to RECEIVE the ORF from this neighbor";
      }
    }
  }

  typedef neighbor-address {
    type union {
      type inet:ipv4-address;
      type bgp-peergroup;
    }
  }

  typedef update-source-ethernet-type {
    type string {
      pattern "((([1-9]|[1-9][0-9]|1[0-9][0-9]|2[0-3][0-9])/)(([0-9]|[1][0-6]))/([1-9]|[1-9][0-9])(:[1-4])?)";
      length "3..16";
    }
    description
      "The definition for specifying a network interface name in
       a VCS environment. It is in 3-tuple canonical format:
       rbridge-id/slot/port.";
  }

  typedef community-number-decimal {
    type uint32 {
      range "1..4294967295";
    }
  }

  typedef community-number-aa-nn {
    type string;
  }

  typedef community-reg-exp {
    type string;
  }

  typedef route-index {
    type uint32 {
      range "1..4294967295";
    }
  }

  typedef bgp-ipv4-prefix {
    type inet:ipv4-prefix;
  }

  typedef bgp-ipv4-address {
    type inet:ipv4-address;
  }

  typedef bgp-ipv4-address-prefix {
    type union {
      type inet:ipv4-prefix;
      type inet:ipv4-address;
    }
  }

  grouping common-maxas-limit-group {
    container maxas-limit {
      container in {
        choice ch-maxas-limit {
          case ca-maxas-limit-enable {
            leaf num-as-in-as-path {
              type num-as-in-as-path;
            }
          }
          case ca-maxas-limit-disable {
            leaf maxas-limit-disable {
              type empty;
            }
          }
        }
      }
    }
  }

  grouping af-static-network-cmds {
    list static-network {
      key "static-network-address";
      leaf static-network-address {
        type inet:ipv4-prefix;
      }
      leaf static-network-distance {
        type sdistance;
      }
    }
  }

  grouping common-maximum-paths-grouping {
    container maximum-paths {
      leaf load-sharing-value {
        type uint32 {
          range "1..8";
        }
      }
      leaf ebgp {
        type ebgp-paths;
      }
      leaf ibgp {
        type ibgp-paths;
      }
      leaf use-load-sharing {
        type empty;
      }
    }
  }

  grouping af-ipv4-network-cmds {
    list network {
      key "network-ipv4-address";
      leaf network-ipv4-address {
        type inet:ipv4-prefix;
      }
      uses af-common-network-cmds;
    }
  }

  grouping af-common-network-cmds {
    leaf network-weight {
      type absolute-decimal-number;
    }
    leaf backdoor {
      type empty;
    }
    leaf network-route-map {
      type rmap-type;
    }
  }

  grouping address-family-group {
    container address-family {
      container ipv4 {
        container ipv4-unicast {
          presence "true";
          uses af-ipv4-uc-cmds;
        }
      }
    }
  }

  grouping af-ipv4-neighbor-cmds {
    container af-ipv4-neighbor-peergroup-holder {
      list af-ipv4-neighbor-peergroup {
        key "af-ipv4-neighbor-peergroup-name";
        leaf af-ipv4-neighbor-peergroup-name {
          type bgp-peergroup;
        }
        uses af-neighbor-cmds;
      }
    }
    container af-ipv4-neighbor-address-holder {
      list af-ipv4-neighbor-address {
        key "af-ipv4-neighbor-address";
        leaf af-ipv4-neighbor-address {
          type inet:ip-address;
        }
        uses af-neighbor-cmds;
      }
    }
  }

  grouping af-neighbor-cmds {
    leaf activate {
      type empty;
    }
    container filter-list {
      container direction-in {
        leaf filter-list-direction-in-acl-name {
          type ip-filter-name;
        }
        leaf filter-list-name-direction-in {
          type empty;
        }
      }
      container direction-out {
        leaf filter-list-direction-out-acl-name {
          type ip-filter-name;
        }
        leaf filter-list-name-direction-out {
          type empty;
        }
      }
    }
    container maximum-prefix {
      leaf max-prefix-limit {
        type max-prefix-limit;
      }
      container threshold-holder {
        leaf threshold {
          type max-prefix-threshold;
        }
        leaf teardown {
          type empty;
        }
      }
    }
    container default-originate {
      leaf default-originate-status {
        type empty;
      }
      leaf default-originate-route-map {
        type rmap-type;
      }
    }
    container prefix-list {
      description
        "either prefix list or distribution-list";
      container direction-in {
        leaf prefix-list-direction-in-prefix-name {
          type nei-prefix-list-filter;
        }
        leaf prefix-list-direction-in {
          type empty;
        }
      }
      container direction-out {
        leaf prefix-list-direction-out-prefix-name {
          type nei-prefix-list-filter;
        }
        leaf prefix-list-direction-out {
          type empty;
        }
      }
    }
    container neighbor-route-map {
      container neighbor-route-map-direction-in {
        leaf neighbor-route-map-name-direction-in {
          type common-def:name-string64;
        }
      }
      container neighbor-route-map-direction-out {
        leaf neighbor-route-map-name-direction-out {
          type common-def:name-string64;
        }
      }
    }
    leaf route-reflector-client {
      type empty;
    }
    container send-community {
      description
        "TODO default is standard.if extended is set, then the show run has to render the value as both";
      leaf send-community-status {
        type empty;
      }
      leaf both {
        type empty;
      }
      leaf extended {
        type empty;
      }
      leaf standard {
        type empty;
      }
    }
    container unsuppress-map {
      leaf map-name {
        type rmap-type;
      }
    }
    leaf af-nei-weight {
      type nei-weight;
    }
  }

  grouping router-bgp-neighbor-attributes {
    leaf description {
      type neighbor-description;
    }
    container shutdown {
      leaf shutdown-status {
        type empty;
      }
      leaf generate-rib-out {
        type empty;
      }
    }
    container local-as {
      leaf local-as-value {
        type local-as-num;
      }
      leaf no-prepend {
        type empty;
      }
    }
    container next-hop-self {
      choice ch-next-hop-self-type {
        case ca-next-hop-self-always {
          leaf next-hop-self-always {
            type empty;
          }
        }
        case ca-next-hop-self-status {
          leaf next-hop-self-status {
            type empty;
          }
        }
      }
    }
    container advertisement-interval {
      leaf value {
        type adv-value;
      }
    }
    container ebgp-multihop {
      choice ch-ebgp-multihop-type {
        case ca-ebgp-multihop-flag {
          leaf ebgp-multihop-flag {
            type empty;
          }
        }
        case ca-ebgp-multihop-count {
          leaf ebgp-multihop-count {
            type uint32 {
              range "1..255";
            }
          }
        }
      }
    }
    uses common-maxas-limit-group;
    leaf password {
      type bgp-password;
    }
    container enforce-first-as {
      leaf nei-enforce-first-as {
        type empty;
      }
      leaf nei-enforce-first-as-disable {
        type empty;
      }
    }
    container neighbor-capability {
      container as4 {
        leaf neighbor-as4-enable {
          type empty;
        }
        leaf neighbor-as4-disable {
          type empty;
        }
      }
    }
    container timers {
      leaf nei-keep-alive {
        type nei-keep-alive;
      }
      leaf nei-hold-time {
        type nei-hold-time;
      }
    }
    container update-source {
      choice ch-update-source {
        case ca-ipv4 {
          leaf sip-ipv4-address {
            type sip-ipv4-address;
          }
        }
        case ca-eth {
          container ethernet-interface {
            leaf interface-type {
              type enumeration {
                enum "gigabitethernet" {
                  value 1;
                }
                enum "tengigabitethernet" {
                  value 2;
                }
                enum "fortygigabitethernet" {
                  value 3;
                }
              }
            }
            leaf ethernet {
              type update-source-ethernet-type;
            }
          }
        }
        case ca-loopback {
          leaf loopback {
            type loopback-interface;
          }
        }
        case ca-ve {
          leaf ve-interface {
            type ve-interface;
          }
        }
      }
    }
    leaf remove-private-as {
      type empty;
    }
    leaf as-override {
      type empty;
    }
    container soft-reconfiguration {
      leaf inbound {
        type empty;
      }
    }
  }

  grouping router-bgp-neighbor-cmds {
    container peer-grps {
      list neighbor-peer-grp {
        key "router-bgp-neighbor-peer-grp";
        leaf router-bgp-neighbor-peer-grp {
          type bgp-peergroup;
        }
        leaf peer-group-name {
          type empty;
        }
        leaf remote-as {
          type bgp-remote-as;
        }
        uses router-bgp-neighbor-attributes;
      }
    }
    container neighbor-ips {
      list neighbor-addr {
        key "router-bgp-neighbor-address";
        leaf router-bgp-neighbor-address {
          type inet:ip-address;
        }
        leaf remote-as {
          type bgp-remote-as;
        }
        leaf associate-peer-group {
          type bgp-peergroup;
        }
        uses router-bgp-neighbor-attributes;
      }
    }
  }

  grouping af-redistrubute-unicast-grouping {
    container redistribute {
      container connected {
        leaf redistribute-connected {
          type empty;
        }
        leaf unicast-metric {
          type conn-metric;
        }
        leaf redistribute-route-map {
          type rmap-type;
        }
      }
      container ospf {
        leaf redistribute-ospf {
          type empty;
        }
        container match {
          leaf ospf-internal {
            type empty;
          }
          leaf ospf-external1 {
            type empty;
          }
          leaf ospf-external2 {
            type empty;
          }
        }
        leaf ospf-metric {
          type conn-metric;
        }
        leaf ospf-route-map {
          type rmap-type;
        }
      }
      container static {
        leaf redistribute-static {
          type empty;
        }
        leaf unicast-static-metric {
          type conn-metric;
        }
        leaf static-route-map {
          type rmap-type;
        }
      }
    }
  }

  grouping af-aggregate-ipv4-address-cmd {
    list aggregate-address {
      key "aggregate-ip-prefix";
      leaf aggregate-ip-prefix {
        type inet:ipv4-prefix;
      }
      uses common-aggregate-address-grouping;
    }
  }

  grouping common-aggregate-address-grouping {
    leaf advertise-map {
      type advertise-map;
    }
    leaf as-set {
      type empty;
    }
    leaf attribute-map {
      type attribute-map;
    }
    leaf summary-only {
      type empty;
    }
    leaf suppress-map {
      type suppress-map;
    }
  }

  grouping common-multipath-grouping {
    container multipath {
      leaf multipath_ebgp {
        type empty;
      }
      leaf multipath_ibgp {
        type empty;
      }
      leaf multi-as {
        type empty;
      }
    }
  }

  grouping af-ipv4-uc-and-vrf-cmds {
    container af-ipv4-uc-and-vrf-cmds-call-point-holder {
      leaf bgp-redistribute-internal {
        type empty;
      }
      uses af-redistrubute-unicast-grouping;
    }
    uses af-static-network-cmds;
  }

  grouping af-ipv4-uc-and-mc-cmds {
    uses af-ipv4-neighbor-cmds;
    container af-common-cmds-holder {
      uses af-common-cmds;
    }
  }

  grouping af-ipv4-uc-cmds {
    uses af-ipv4-uc-and-vrf-cmds {
      refine "af-ipv4-uc-and-vrf-cmds-call-point-holder";
    }
    uses af-aggregate-ipv4-address-cmd {
      refine "aggregate-address";
    }
    uses af-ipv4-network-cmds {
      refine "network";
    }
    uses af-ipv4-uc-and-mc-cmds {
      refine "af-common-cmds-holder";
    }
    leaf next-hop-recursion {
      type empty;
    }
  }

  grouping af-basic-cmds {
    uses common-maximum-paths-grouping;
    uses common-multipath-grouping;
    leaf always-propagate {
      type empty;
    }
    leaf default-information-originate {
      type empty;
    }
    leaf rib-route-limit {
      type decimal-number;
    }
  }

  grouping af-common-cmds {
    uses af-basic-cmds;
    leaf client-to-client-reflection {
      type empty;
    }
    container dampening {
      choice ch-dampening-source {
        case ca-dampening-flag {
          leaf dampening-flag {
            type empty;
            description
              "This Flag is to indicate dampening feature  is enabled";
          }
        }
        case ca-dampening-specify-values {
          container values {
            leaf half-time {
              type htime;
            }
            leaf reuse-value {
              type damp-reuse-value;
            }
            leaf start-suppress-time {
              type damp-start-suppress-value;
            }
            leaf max-suppress-time {
              type damp-max-suppress-value;
            }
          }
        }
        case ca-dampening-route-map {
          leaf dampening-route-map {
            type rmap-type;
          }
        }
      }
    }
    leaf default-metric {
      type decimal-number;
    }
    leaf next-hop-enable-default {
      type empty;
    }
    container table-map {
      leaf table-map-route-map {
        type rmap-type;
      }
    }
    leaf update-time {
      type update-time-type;
    }
  }

  grouping bgp-cmds {
    list bgp {
      key "vrf-name";
      leaf vrf-name {
        type string {
          length "1..255";
        }
      }
      container router-bgp-cmds-holder {
        uses router-bgp-cmds;
        uses address-family-group;
      }
    }
  }

  grouping router-bgp-cmds {
    container router-bgp-attributes {
      leaf local-as {
        type local-as-type;
      }
      leaf always-compare-med {
        type empty;
      }
      leaf compare-med-empty-aspath {
        type empty;
      }
      leaf med-missing-as-worst {
        type empty;
      }
      leaf as-path-ignore {
        type empty;
      }
      leaf compare-routerid {
        type empty;
      }
      leaf install-igp-cost {
        type empty;
      }
      container cluster-id {
        choice ch-cluster-id {
          case ca-cluster-id {
            leaf cluster-id-value {
              type decimal-number;
            }
          }
          case ca-cluster-id-ipv4-address {
            leaf cluster-id-ipv4-address {
              type inet:ipv4-address;
            }
          }
        }
      }
      leaf default-local-preference {
        type decimal-number;
      }
      container distance {
        leaf ext-route-distance {
          type ext-route-distance;
        }
        leaf int-route-distance {
          type int-route-distance;
        }
        leaf lcl-route-distance {
          type lcl-route-distance;
        }
      }
      container capability {
        leaf as4-enable {
          type empty;
        }
      }
      container maxas-limit {
        container in {
          leaf num-as-in-path {
            type num-as-in-path;
          }
        }
      }
      leaf enforce-first-as {
        type empty;
      }
      leaf fast-external-fallover {
        type empty;
      }
      container timers {
        leaf keep-alive {
          type nei-keep-alive;
        }
        leaf hold-time {
          type nei-hold-time;
        }
      }
      leaf log-dampening-debug {
        type empty;
      }
      uses router-bgp-neighbor-cmds;
    }
  }

  augment "/rbridge:rbridge-id/rbridge:router" {
    uses bgp-cmds;
  }
}
