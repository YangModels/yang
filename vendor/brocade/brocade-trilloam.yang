module brocade-trilloam {
  namespace "urn:brocade.com:mgmt:brocade-trilloam";
  prefix trilloam;

  import ietf-inet-types {
    prefix inet;
  }
  import brocade-interface {
    prefix interface;
  }
  import brocade-mac-access-list {
    prefix mac;
  }
  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This management submodule is an instrumentation to manage  
     trilloam commands";

  revision 2011-04-18 {
    description
      "Initial version of the management submodule trilloam-cmd.";
  }

  rpc l2traceroute {
    description
      "Trace a TRILL route from the provided host-source-mac to host-dest-mac";
    input {
      leaf src-mac {
        description
          "Source mac address of the host";
        type mac:mac-address-type;
        mandatory true;
      }
      leaf dest-mac {
        description
          "Destination mac address of the host";
        type mac:mac-address-type;
        mandatory true;
      }
      leaf vlan-id {
        description
          "VLAN Id";
        type interface:vlan-type;
        mandatory true;
      }
      leaf rbridge-id {
        type common-def:rbridge-id-type;
        description
          "rbridge-id";
        mandatory true;
      }
      choice protocolType {
        description
          "IP or FCoE protocol";
        mandatory false;
        case IP {
          leaf src-ip {
            description
              "Source IP address";
            type inet:ipv4-address;
            mandatory true;
          }
          leaf dest-ip {
            description
              "Destination IP address";
            type inet:ipv4-address;
            mandatory true;
          }
          leaf l4protocol {
            description
              "Layer 4 protocol, TCP or UDP";
            type enumeration {
              enum "TCP" {
                value 1;
              }
              enum "UDP" {
                value 2;
              }
            }
            mandatory true;
          }
          leaf l4-src-port {
            description
              "Source port number for the l4protocol";
            type inet:port-number;
            mandatory true;
          }
          leaf l4-dest-port {
            description
              "Destination port number for l4protocol";
            type inet:port-number;
            mandatory true;
          }
        }
        case FCoE;
      }
    }
    output {
      leaf session-id {
        description
          "Session Id given to client, zero in case of error";
        type uint32;
        mandatory true;
      }
      leaf reason {
        description
          "Reason for this return, error string or success";
        type string;
        mandatory true;
      }
    }
  }
  rpc l2traceroute-result {
    description
      " l2traceroute command result";
    input {
      leaf session-id {
        description
          "Session Id previously given by client to identify this session";
        type uint32;
        mandatory true;
      }
    }
    output {
      list l2-hop-results {
        container l2-hop {
          leaf rbridge-id {
            description
              "rbridge-id of a responding switch";
            type common-def:rbridge-id-type;
            mandatory false;
          }
          container ingress {
            description
              "ingress port";
            uses interface:interface-name-info;
          }
          container egress {
            description
              "egress port";
            uses interface:interface-name-info;
          }
          leaf roundtriptime {
            description
              "Round trip time from the initiator to responder in nanoseconds";
            type common-def:time-interval-musec;
            mandatory false;
          }
        }
      }
      leaf l2traceroutedone {
        description
          "Indicates that this is the final response";
        type boolean;
        mandatory true;
      }
      leaf reason {
        description
          "Reason for this return, error string or success";
        type string;
        mandatory true;
      }
    }
  }
  container trilloam;
}
