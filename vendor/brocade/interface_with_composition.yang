module interface_with_composition {
  namespace "http://brocade.com/ns/interface_composition";
  prefix interface_composition;

  container interfaces_with_composition {
    list interface {
      key "name";
      max-elements "1024";
      leaf name {
        type string;
      }
      list interface_rule {
        key "rule_id";
        leaf rule_id {
          type int32;
          mandatory true;
        }
        leaf isAllowed {
          type boolean;
          mandatory true;
        }
        leaf operationalRule {
          type uint32;
          mandatory true;
          config false;
        }
        leaf operationalRule1 {
          type uint32;
          mandatory true;
          config false;
        }
      }
    }
  }
}
