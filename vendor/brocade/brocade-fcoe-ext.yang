module brocade-fcoe-ext {
  namespace "urn:brocade.com:mgmt:brocade-fcoe-ext";
  prefix fcoe-extensions;

  import ietf-yang-types {
    prefix yang;
  }
  import brocade-common-def {
    prefix common-def;
  }
  import brocade-fcoe {
    prefix fcoe;
  }
  import brocade-interface {
    prefix interface;
  }

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an extension to FCOE model for
         - Defining RPCs to retrieve operational information of 
           the FCoE.
             
     Glossary of the terms used:
     ---------------------------
     ACC frame - Accept frame
     
     FCoE -      Fibre Channel over Ethernet (FCoE) is an 
                encapsulation of Fibre Channel frames over Ethernet
                networks. 
     
     FIP -       FCoE Intialization Protocol is the standard for 
                intilization of FCoE network.
     
     FCF -       Fibre Channel Forwarder is a network entity 
                responsible for forwarding the FCoE traffic.
     
     FLOGI -     Fabric Login is a frame used by the end devices to 
                login to a Fibre Channel or FCoE Fabric.
     
     FDISC -     Fabric Discovery is a frame used by the end devices 
                to perform logins of all the loop attached ports.
     
     LOGO -      Logout is a frame used by the end devices to logout 
                of the Fibre Channel or FCoE Fabric.
     
     ENODE -     End Node is the term used to refer End devices in 
                the FCoE network.
     
     VN-Port -   Virtual N-Port is the FCoE equivalent of the Fibre 
                Channel N-Port.
     
     CVL -       Clear Virtual Links is the frame to tear the Virtual
                Links in the FCoE Network.";
  reference "The FC-BB-5 standard ANSI/INCITS 462-2010.";

  revision 2011-07-15 {
    description
      "Initial version of the FCoE extension management module.";
  }

  typedef fcoe-port-mode-type {
    type enumeration {
      enum "VF" {
        value 1;
        description
          "Virtual F-port capable of carrying FCoE 
           frame.";
      }
    }
    description
      "This definition specifies the mode in which a fcoe port
       can be in.";
  }

  typedef fcoe-binding-type {
    type enumeration {
      enum "Static" {
        value 1;
        description
          "The ethernet port or Enode mac is
           statically bound to the fcoe interface.";
      }
      enum "Dynamic" {
        value 2;
        description
          "The ethernet port or Enode mac is
           dynamically bound to the fcoe interface.";
      }
      enum "Unknown" {
        value 3;
        description
          "The binding type between the ethernet
           port or Enode Mac and the fcoe interface
           is Unknown.";
      }
    }
    description
      "This definition specifies the binding type between
       the ethernet port or Enode Mac and the logical fcoe
       interface.";
  }

  typedef fcoe-counters-date-and-time-type {
    type string {
      pattern "\\d{4}-\\d{2}-\\d{2}\\s\\d{2}:\\d{2}:\\d{2}\\.\\d{6}";
    }
    description
      "The fcoe-counters-date-and-time-type is a slightly
       modified version of the yang data type date-and-time
       that has been reformatted to display the date and time
         according to the fcoe show output.";
  }

  typedef fcoe-port-state-type {
    type string {
      pattern "Up|Down|up|down";
    }
    description
      "This data type provides the operational state of the 
        fcoe port.";
  }

  typedef fcoe-map-name {
    type string {
      pattern "[a-zA-Z0-9_]{1,30}";
    }
    description
      "This data type provides the fcoe map names such as
       the fabric-map name, cee-map name, etc.";
  }

  rpc fcoe-get-interface {
    description
      "This function is to get the operational state of an FCoE
       interface(s).";
    input {
      leaf fcoe-intf-name {
        type fcoe:interface-fcoe-type;
        mandatory false;
        description
          "This specifies the specific FCoE interface for 
           which this rpc function is invoked. In response to
           this request, the managed device returns the FCoE 
           operational information for this interface.";
      }
      leaf fcoe-intf-rbridge-id {
        type common-def:rbridge-id-all-type;
        mandatory false;
        description
          "This specifies the rbridge-id for which this rpc 
           function is invoked. In response to this request,
           the managed device returns the FCoE operational 
           information for all the interfaces of this 
           rbridge-id or all rbridges if rbridge-id value is 'all'";
      }
      leaf fcoe-intf-include-stats {
        type boolean;
        mandatory false;
        description
          "This specifies if the FCoE interface statistics 
           should be included in the output.";
      }
    }
    output {
      list fcoe-intf-list {
        key "fcoe-intf-fcoe-port-id";
        description
          "The format of the output for this rpc function 
           will be a list of entries. Each row represents a 
           FCoE interface operational characteristics such as 
           fcoe port number, ethernet port number, the current
           operational mode of the port and Tx/Rx stats for 
           control traffic on that port.";
        leaf fcoe-intf-fcoe-port-id {
          type fcoe:interface-fcoe-type;
          description
            "This indicates the name of this FCoE 
             interface.";
        }
        leaf fcoe-intf-port-type {
          type fcoe-port-mode-type;
          description
            "This indicates the current operational mode
             of this FCoE interface.";
        }
        leaf fcoe-intf-config-port-type {
          type fcoe-port-mode-type;
          description
            "This indicates the configured mode of this
             FCoE interface.";
        }
        leaf fcoe-intf-port-state {
          type fcoe-port-state-type;
          description
            "This indicates the operational state of the 
             FCoE interface.";
        }
        leaf fcoe-intf-fabric-map-name {
          type fcoe-map-name;
          description
            "This indicates the fabric map name associated
             with this interface.";
        }
        leaf fcoe-intf-eth-port-id {
          type interface:interface-type;
          description
            "This indicates the name of the ethernet
             interface bound by this FCoE interface.
             This leaf will be deprecated, and the
             interface-name leaf in the interface-name-info
             grouping should be used instead.";
        }
        uses interface:interface-name-info {
          description
            "This indicates the ethernet port information.
             This grouping contains two parts: the 
             interface-name and the interface-type.";
        }
        leaf fcoe-intf-admin-status {
          type boolean;
          description
            "This indicates the administratively 
             configured state of the FCoE interface.";
        }
        leaf fcoe-intf-peer-fcf-mac {
          type yang:mac-address;
          description
            "The value of this leaf indicates the MAC 
             address of the neighboring FCF connected via 
             this VE interface.";
        }
        leaf fcoe-intf-device-count {
          type yang:zero-based-counter32;
          description
            "This indicates the number of devices logged in
             on this interface.";
        }
        leaf fcoe-intf-ifindex {
          type uint32;
          description
            "This indicates the Interface index of the Ethernet
             port.";
        }
        leaf fcoe-intf-wwn {
          type common-def:wwn-type;
          description
            "This indicates the Fabric WWN of this FCoE 
             interface.";
        }
        leaf fcoe-intf-enode-bind-type {
          type fcoe-binding-type;
          description
            "This indicates if the enode is statically bound to
             the fcoe interface or not i.e. if statically bound 
             this enode's mac will always login on the same fcoe
             port.";
        }
        leaf fcoe-intf-port-bind-type {
          type fcoe-binding-type;
          description
            "This indicates if the ethernet port is statically
             bound to the fcoe interface or not i.e. if statically
             bound the ethernet port and the fcoe interface will
             have a static 1-to-1 mapping.";
        }
        leaf fcoe-intf-enode-mac-address {
          type yang:mac-address;
          description
            "This indicates the enode mac-addresss of the
             device that is statically or dynamically 
             bound to the fcoe port.";
        }
        leaf fcoe-intf-rx-vlan-disc-req {
          type yang:zero-based-counter32;
          mandatory false;
          description
            "This indicates the number of FIP VLAN 
             Discovery requests received on this FCoE 
             interface.";
        }
        leaf fcoe-intf-rx-disc-solicitations {
          type yang:zero-based-counter32;
          mandatory false;
          description
            "This indicates the number of FCF Discovery 
                solicitations received on this FCoE interface.";
        }
        leaf fcoe-intf-rx-flogi {
          type yang:zero-based-counter32;
          mandatory false;
          description
            "This indicates the number of FLOGI requests 
                received on this FCoE interface.";
        }
        leaf fcoe-intf-rx-fdiscs {
          type yang:zero-based-counter32;
          mandatory false;
          description
            "This indicates the number of FDISC requests 
                received on this FCoE interface.";
        }
        leaf fcoe-intf-rx-logo {
          type yang:zero-based-counter32;
          mandatory false;
          description
            "This indicates the number of FIP LOGO requests 
                received on this FCoE interface.";
        }
        leaf fcoe-intf-rx-errors {
          type yang:zero-based-counter32;
          mandatory false;
          description
            "This indicates the Number of Errors 
             encountered on this FCoE interface.";
        }
        leaf fcoe-intf-tx-vlan-disc-resp {
          type yang:zero-based-counter32;
          mandatory false;
          description
            "This indicates the Number of FIP 
             VLAN Discovery response frames transmitted on 
             this FCoE interface.";
        }
        leaf fcoe-intf-tx-disc-sol-adv {
          type yang:zero-based-counter32;
          mandatory false;
          description
            "This indicates the number of FCF solicited  
                advertisements transmitted on this FCoE 
                interface.";
        }
        leaf fcoe-intf-tx-disc-unsol-adv {
          type yang:zero-based-counter32;
          mandatory false;
          description
            "This indicates the Number of unsolicited 
               advertisements transmitted on this FCoE 
               interface.";
        }
        leaf fcoe-intf-rx-enode-ka {
          type yang:zero-based-counter32;
          mandatory false;
          description
            "This indicates the number of ENODE keep-alive
             frames recieved.";
        }
        leaf fcoe-intf-rx-vnport-ka {
          type yang:zero-based-counter32;
          mandatory false;
          description
            "This indicates the number of VN-Port keep-alive
             frames recieved.";
        }
        leaf fcoe-intf-tx-accepts {
          type yang:zero-based-counter32;
          mandatory false;
          description
            "This indicates the number of ACC frames  
                transmitted on this FCoE interface in response
                to FLOGI/FDISC.";
        }
        leaf fcoe-intf-tx-ls-rjt {
          type yang:zero-based-counter32;
          mandatory false;
          description
            "This indicates the number of Reject frames 
                 transmitted on this FCoE interface in response
                 to FLOGI/FDISC/LOGO.";
        }
        leaf fcoe-intf-time-since-last-change {
          type fcoe-counters-date-and-time-type;
          mandatory false;
          description
            "This indicates the time elapsed since the 
             status of this FCoE port last changed.";
        }
        leaf fcoe-intf-last-counters-cleared {
          type fcoe-counters-date-and-time-type;
          mandatory false;
          description
            "This indicates the time when the interface 
             counters were last cleared.";
        }
        leaf fcoe-intf-tx-cvls {
          mandatory false;
          type yang:zero-based-counter32;
          description
            "This indicates the number of CVL frames
             transmitted.";
        }
      }
      leaf fcoe-intf-total-interfaces {
        type yang:zero-based-counter32;
        description
          "This leaf indicates the total Number of interfaces
           whose details are being returned by this 
           function.";
      }
    }
  }
  rpc fcoe-get-login {
    description
      "This function provides the login information on FCoE 
       End nodes that have logged in to the managed device.";
    input {
      leaf fcoe-login-interface {
        type fcoe:interface-fcoe-type;
        mandatory false;
        description
          "This specifies the fcoe interface for which this 
           rpc function is invoked. In response to this 
           request, the managed device returns the list of all
           FCoE devices that have logged in on this 
           interface.";
      }
      leaf fcoe-login-vfid {
        type fcoe:fcoe-vfid-type;
        mandatory false;
        description
          "This specifies the virtual fabric id for which 
           this rpc function is invoked. In response to this 
           request, the managed device returns a list of all
           FCoE devices that have logged in to this virtual
           fabric.";
      }
      leaf fcoe-login-vlan {
        type fcoe:fcoe-vlan-type;
        mandatory false;
        description
          "This specifies the vlan id for which this rpc
           function is invoked. In response to this request, 
           the managed device returns the list of all FCoE 
           devices that have logged in on this vlan.";
      }
      leaf fcoe-login-rbridge-id {
        type common-def:rbridge-id-all-type;
        mandatory false;
        description
          "This specifies the rbridge-id for which this rpc 
           function is invoked. In response to this request, 
           the managed device returns a list of all FCoE 
           devices that have logged in to given rbridge or 
           all rbridges if rbridge-id value is 'all'";
      }
    }
    output {
      list fcoe-login-list {
        key "fcoe-login-session-mac";
        description
          "This is a list of logged-in FCoE End nodes. 
           Each row represents a logged-in FCoE device 
           operational details such as ethernet port number, 
           the WWN and MAC address of the device that has 
           logged in and session MAC. The session MAC is used
           as the key for this list as it will be unique 
           for each entry.";
        leaf fcoe-login-session-mac {
          type yang:mac-address;
          description
            "This leaf indicates the fabric assigned 
             session MAC address of the End Node.";
        }
        leaf fcoe-login-fcoe-interface-name {
          type fcoe:interface-fcoe-type;
          description
            "This leaf indicates the FCoE interface name.";
        }
        leaf fcoe-login-interface-name {
          type union {
            type interface:interface-type;
            type interface:portchannel-type;
          }
          description
            "This leaf indicates the Interface name.
             This leaf will be deprecated, and the
             interface-name leaf in the interface-name-info
             grouping should be used instead.";
        }
        uses interface:interface-name-info {
          description
            "This leaf gives the ethernet port info.
             This grouping contains two parts: the
             interface-name and the interface-type.";
        }
        leaf fcoe-login-device-wwn {
          type common-def:wwn-type;
          description
            "This leaf indicates the World Wide Name of the
             End Node.";
        }
        leaf fcoe-login-device-mac {
          type yang:mac-address;
          description
            "This leaf indicates the MAC address of  
             the End Node.";
        }
        leaf fcoe-login-direct-attached {
          type boolean;
          description
            "This leaf indicates if the device is  directly 
             connected to the FCF.
                                     
             The value of 'true' indicates that this device 
             is directly attached. The value of 'false' 
             indicates that this device is not directly 
             attached.";
        }
        leaf fcoe-login-connected-peer-type {
          type enumeration {
            enum "peer-fcf" {
              value 1;
            }
            enum "peer-fcoe-device" {
              value 2;
            }
          }
          description
            "This leaf indicates the type of device 
             connected to the FCF.";
        }
      }
      leaf fcoe-login-total-logins {
        type yang:zero-based-counter32;
        description
          "This leaf indicates the Total Number of devices
           logged in.";
      }
    }
  }
}
