module brocade-qos {
  namespace "urn:brocade.com:mgmt:brocade-qos";
  prefix qos;

  import brocade-common-def {
    prefix common-def;
  }
  import ietf-inet-types {
    prefix inet;
  }
  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This module manages Quality Of Service (QOS)";

  revision 2010-04-28 {
    description
      "Initial version of this management module.";
  }

  typedef UI32DscpMutationRange {
    type string {
      pattern "(([0-9])|([1-5][0-9])|(6[0-3]))(-(([0-9])|([1-5][0-9])|(6[0-3])))?((,(([0-9])|([1-5][0-9])|(6[0-3]))(-(([0-9])|([1-5][0-9])|(6[0-3])))?)?)*" {
        description
          "NUMBER:0-63;;DSCP Value/DSCP Range; Example: 0,1,2,4-7,8,9-22,55-63.";
      }
    }
  }

  typedef RedProfileType {
    type int32 {
      range "0 .. 383" {
        description
          "0-383;Profile id";
      }
    }
  }

  typedef TMCChipNumber {
    type int8 {
      range "0 .. 47" {
        description
          "0-47;TMC chip id";
      }
    }
  }

  typedef map-name-type {
    type string {
      pattern "[a-zA-Z]{1}([-a-zA-Z0-9_]{0,63})";
    }
  }

  grouping dscp-grp {
    leaf dscp-in-values {
      type UI32DscpMutationRange;
    }
    leaf to {
      mandatory true;
      type int32 {
        range "0 .. 63" {
          description
            "0-63;;Dscp Mutation Out";
        }
      }
      description
        "0-63;;Dscp Mutation Out";
    }
  }

  typedef nas-ipv4-prefix {
    type inet:ipv4-prefix;
  }

  container qos {
    container map {
      list dscp-mutation {
        key "dscp-mutation-map-name";
        leaf dscp-mutation-map-name {
          type map-name-type;
        }
        list mark {
          key "dscp-in-values";
          uses dscp-grp;
        }
      }
      list dscp-traffic-class {
        key "dscp-traffic-class-map-name";
        leaf dscp-traffic-class-map-name {
          type map-name-type;
        }
        list mark {
          key "dscp-in-values";
          leaf dscp-in-values {
            type UI32DscpMutationRange;
          }
          leaf to {
            mandatory true;
            type int32 {
              range "0 .. 7" {
                description
                  "0-7;;Dscp Traffic Class value";
              }
            }
          }
        }
      }
      list dscp-cos {
        key "dscp-cos-map-name";
        leaf dscp-cos-map-name {
          type map-name-type;
        }
        list mark {
          key "dscp-in-values";
          leaf dscp-in-values {
            type UI32DscpMutationRange;
          }
          leaf to {
            mandatory true;
            type int32 {
              range "0 .. 7" {
                description
                  "0-7;;COS Mutation Out";
              }
            }
          }
        }
      }
      list cos-mutation {
        key "name";
        leaf name {
          type map-name-type;
        }
        leaf cos0 {
          type int32 {
            range "0 .. 7";
          }
        }
        leaf cos1 {
          type int32 {
            range "0 .. 7";
          }
        }
        leaf cos2 {
          type int32 {
            range "0 .. 7";
          }
        }
        leaf cos3 {
          type int32 {
            range "0 .. 7";
          }
        }
        leaf cos4 {
          type int32 {
            range "0 .. 7";
          }
        }
        leaf cos5 {
          type int32 {
            range "0 .. 7";
          }
        }
        leaf cos6 {
          type int32 {
            range "0 .. 7";
          }
        }
        leaf cos7 {
          mandatory true;
          type int32 {
            range "0 .. 7";
          }
        }
      }
      list cos-traffic-class {
        key "name";
        leaf name {
          type map-name-type;
        }
        leaf cos0 {
          type int32 {
            range "0 .. 7";
          }
        }
        leaf cos1 {
          type int32 {
            range "0 .. 7";
          }
        }
        leaf cos2 {
          type int32 {
            range "0 .. 7";
          }
        }
        leaf cos3 {
          type int32 {
            range "0 .. 7";
          }
        }
        leaf cos4 {
          type int32 {
            range "0 .. 7";
          }
        }
        leaf cos5 {
          type int32 {
            range "0 .. 7";
          }
        }
        leaf cos6 {
          type int32 {
            range "0 .. 7";
          }
        }
        leaf cos7 {
          mandatory true;
          type int32 {
            range "0 .. 7";
          }
        }
      }
    }
    list red-profile {
      key "profile-id";
      leaf profile-id {
        type RedProfileType;
      }
      leaf min-threshold {
        mandatory true;
        type int32 {
          range "0 .. 100" {
            description
              "0-100;;Minimum threshold in percentage";
          }
        }
      }
      leaf max-threshold {
        mandatory true;
        type int32 {
          range "0 .. 100" {
            description
              "0-100;;Maximum threshold in percentage";
          }
        }
      }
      leaf drop-probability {
        mandatory true;
        type int32 {
          range "0 .. 100" {
            description
              "0-100;;Drop Probability in percentage";
          }
        }
      }
    }
    container queue {
      container multicast {
        container scheduler {
          container dwrr {
            leaf dwrr-traffic-class0 {
              type int32 {
                range "0 .. 100";
              }
            }
            leaf dwrr-traffic-class1 {
              type int32 {
                range "0 .. 100";
              }
            }
            leaf dwrr-traffic-class2 {
              type int32 {
                range "0 .. 100";
              }
            }
            leaf dwrr-traffic-class3 {
              type int32 {
                range "0 .. 100";
              }
            }
            leaf dwrr-traffic-class4 {
              type int32 {
                range "0 .. 100";
              }
            }
            leaf dwrr-traffic-class5 {
              type int32 {
                range "0 .. 100";
              }
            }
            leaf dwrr-traffic-class6 {
              type int32 {
                range "0 .. 100";
              }
            }
            leaf dwrr-traffic-class7 {
              type int32 {
                range "0 .. 100";
              }
            }
          }
        }
      }
      container scheduler {
        container strict-priority {
          leaf priority-number {
            type int32 {
              range "0 .. 7";
            }
          }
          leaf scheduler-type {
            type enumeration {
              enum "dwrr" {
                value 0;
              }
            }
          }
          leaf dwrr-traffic-class0 {
            type int32 {
              range "0 .. 100";
            }
          }
          leaf dwrr-traffic-class1 {
            type int32 {
              range "0 .. 100";
            }
          }
          leaf dwrr-traffic-class2 {
            type int32 {
              range "0 .. 100";
            }
          }
          leaf dwrr-traffic-class3 {
            type int32 {
              range "0 .. 100";
            }
          }
          leaf dwrr-traffic-class4 {
            type int32 {
              range "0 .. 100";
            }
          }
          leaf dwrr-traffic-class5 {
            type int32 {
              range "0 .. 100";
            }
          }
          leaf dwrr-traffic-class6 {
            type int32 {
              range "0 .. 100";
            }
          }
          leaf dwrr-traffic-class-last {
            type int32 {
              range "0 .. 100";
            }
          }
        }
      }
    }
    container rcv-queue {
      container multicast {
        container threshold {
          leaf traffic-class0 {
            type int32 {
              range "1 .. 16383";
            }
          }
          leaf traffic-class1 {
            type int32 {
              range "1 .. 16383";
            }
          }
          leaf traffic-class2 {
            type int32 {
              range "1 .. 16383";
            }
          }
          leaf traffic-class3 {
            type int32 {
              range "1 .. 16383";
            }
          }
          leaf traffic-class4 {
            type int32 {
              range "1 .. 16383";
            }
          }
          leaf traffic-class5 {
            type int32 {
              range "1 .. 16383";
            }
          }
          leaf traffic-class6 {
            type int32 {
              range "1 .. 16383";
            }
          }
          leaf traffic-class7 {
            type int32 {
              range "1 .. 16383";
            }
          }
        }
        container rate-limit {
          leaf limit {
            type int32 {
              range "6500 .. 20000000";
            }
          }
          leaf burst {
            type int32 {
              range "50 .. 65535";
            }
          }
        }
      }
    }
  }

  grouping interface-qos-config-group {
    leaf default-cos {
      type int32 {
        range "0 .. 7";
      }
      default "0";
    }
    container trust {
      leaf trust-cos {
        type empty;
      }
      leaf trust-dscp {
        type empty;
      }
    }
    leaf cos-mutation {
      type map-name-type;
    }
    leaf cos-traffic-class {
      type map-name-type;
    }
    leaf dscp-mutation {
      type map-name-type;
    }
    leaf dscp-traffic-class {
      type map-name-type;
    }
    leaf dscp-cos {
      type map-name-type;
    }
    container random-detect {
      list cos {
        key "red-cos-value";
        leaf red-cos-value {
          type uint32 {
            range "0 .. 7";
          }
        }
        leaf red-profile-id {
          type uint32 {
            range "0 .. 383";
          }
        }
      }
    }
  }

  grouping link-level-flowcontrol-group {
    container link-level-flowcontrol {
      leaf flowcontrol-tx {
        type enumeration {
          enum "on" {
            value 1;
          }
          enum "off" {
            value 0;
          }
        }
      }
      leaf flowcontrol-rx {
        type enumeration {
          enum "on" {
            value 1;
          }
          enum "off" {
            value 0;
          }
        }
      }
    }
  }

  grouping pfc-flowcontrol-group {
    list pfc {
      key "pfc-cos";
      leaf pfc-cos {
        type int32 {
          range "0 .. 7";
        }
      }
      leaf pfc-flowcontrol-tx {
        mandatory true;
        type enumeration {
          enum "on" {
            value 1;
          }
          enum "off" {
            value 0;
          }
        }
      }
      leaf pfc-flowcontrol-rx {
        mandatory true;
        type enumeration {
          enum "on" {
            value 1;
          }
          enum "off" {
            value 0;
          }
        }
      }
    }
  }

  augment "/interface:interface/interface:tengigabitethernet" {
    leaf priority-tag-enable {
      type empty;
    }
    container qos {
      uses interface-qos-config-group;
      container rcv-queue {
        description
          "Configure Queue Parameters";
        container cos-threshold {
          description
            "Configure CoS Thresholds";
          leaf cos0-threshold {
            description
              "CoS 0 tail drop threshold";
            type uint32 {
              range "0 .. 100" {
                description
                  "0-100;;CoS 0 Threshold(%)";
              }
            }
          }
          leaf cos1-threshold {
            description
              "CoS 1 tail drop threshold";
            type uint32 {
              range "0 .. 100" {
                description
                  "0-100;;CoS 1 Threshold(%)";
              }
            }
          }
          leaf cos2-threshold {
            description
              "CoS 2 tail drop threshold";
            type uint32 {
              range "0 .. 100" {
                description
                  "0-100;;CoS 2 Threshold(%)";
              }
            }
          }
          leaf cos3-threshold {
            description
              "CoS 3 tail drop threshold";
            type uint32 {
              range "0 .. 100" {
                description
                  "0-100;;CoS 3 Threshold(%)";
              }
            }
          }
          leaf cos4-threshold {
            description
              "CoS 4 tail drop threshold";
            type uint32 {
              range "0 .. 100" {
                description
                  "0-100;;CoS 4 Threshold(%)";
              }
            }
          }
          leaf cos5-threshold {
            description
              "CoS 5 tail drop threshold";
            type uint32 {
              range "0 .. 100" {
                description
                  "0-100;;CoS 5 Threshold(%)";
              }
            }
          }
          leaf cos6-threshold {
            description
              "CoS 6 tail drop threshold";
            type uint32 {
              range "0 .. 100" {
                description
                  "0-100;;CoS 6 Threshold(%)";
              }
            }
          }
          leaf cos7-threshold {
            description
              "CoS 7 tail drop threshold";
            type uint32 {
              range "0 .. 100" {
                description
                  "0-100;;CoS 7 Threshold(%)";
              }
            }
          }
        }
      }
      container flowcontrol {
        uses link-level-flowcontrol-group;
        uses pfc-flowcontrol-group {
          refine "pfc";
        }
      }
    }
  }
  augment "/interface:interface/interface:gigabitethernet" {
    leaf priority-tag-enable {
      type empty;
    }
    container qos {
      uses interface-qos-config-group;
      container rcv-queue {
        description
          "Configure Queue Parameters";
        container cos-threshold {
          description
            "Configure CoS Thresholds";
          leaf cos0-threshold {
            description
              "CoS 0 tail drop threshold";
            type uint32 {
              range "0 .. 100" {
                description
                  "0-100;;CoS 0 Threshold(%)";
              }
            }
          }
          leaf cos1-threshold {
            description
              "CoS 1 tail drop threshold";
            type uint32 {
              range "0 .. 100" {
                description
                  "0-100;;CoS 1 Threshold(%)";
              }
            }
          }
          leaf cos2-threshold {
            description
              "CoS 2 tail drop threshold";
            type uint32 {
              range "0 .. 100" {
                description
                  "0-100;;CoS 2 Threshold(%)";
              }
            }
          }
          leaf cos3-threshold {
            description
              "CoS 3 tail drop threshold";
            type uint32 {
              range "0 .. 100" {
                description
                  "0-100;;CoS 3 Threshold(%)";
              }
            }
          }
          leaf cos4-threshold {
            description
              "CoS 4 tail drop threshold";
            type uint32 {
              range "0 .. 100" {
                description
                  "0-100;;CoS 4 Threshold(%)";
              }
            }
          }
          leaf cos5-threshold {
            description
              "CoS 5 tail drop threshold";
            type uint32 {
              range "0 .. 100" {
                description
                  "0-100;;CoS 5 Threshold(%)";
              }
            }
          }
          leaf cos6-threshold {
            description
              "CoS 6 tail drop threshold";
            type uint32 {
              range "0 .. 100" {
                description
                  "0-100;;CoS 6 Threshold(%)";
              }
            }
          }
          leaf cos7-threshold {
            description
              "CoS 7 tail drop threshold";
            type uint32 {
              range "0 .. 100" {
                description
                  "0-100;;CoS 7 Threshold(%)";
              }
            }
          }
        }
      }
      container flowcontrol {
        uses link-level-flowcontrol-group;
      }
    }
  }
  augment "/interface:interface/interface:fortygigabitethernet" {
    leaf priority-tag-enable {
      type empty;
    }
    container qos {
      uses interface-qos-config-group;
      container flowcontrol {
        uses link-level-flowcontrol-group;
        uses pfc-flowcontrol-group {
          refine "pfc";
        }
      }
    }
  }
  augment "/interface:interface/interface:port-channel" {
    leaf priority-tag-enable {
      type empty;
    }
    container qos {
      uses interface-qos-config-group {
        refine "random-detect";
      }
      container flowcontrol {
        uses link-level-flowcontrol-group;
        uses pfc-flowcontrol-group {
          refine "pfc";
        }
      }
    }
  }
  container nas {
    container auto-qos {
      presence "true";
      container set {
        leaf cos {
          type uint32 {
            range "0 .. 7";
          }
        }
        leaf dscp {
          type uint32 {
            range "0 .. 63";
          }
        }
      }
    }
    list server-ip {
      key "server-ip";
      leaf server-ip {
        type nas-ipv4-prefix;
      }
      list vrf {
        key "vrf-name";
        leaf vrf-name {
          type string {
            length "1..255";
          }
        }
      }
      list vlan {
        key "vlan-number";
        leaf vlan-number {
          type interface:vlan-type;
        }
      }
    }
  }
}
