module brocade-linecard-management {
  namespace "urn:brocade.com:mgmt:brocade-linecard-management";
  prefix linecard-management;

  import brocade-vcs {
    prefix brocade-vcs;
  }
  import brocade-common-def {
    prefix common-def;
  }
  import brocade-rbridge {
    prefix rbridge;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This linecard management module is used to manage linecards.
     It can be used to configure, show, or turn on/off a linecard.n";

  revision 2011-09-06 {
    description
      "Initial version of this management module.";
  }

  typedef linecardid {
    type string {
      pattern "([1-9]|[1][0-6])" {
        error-message "Invalid slot number. Slot number must be in the range 1..16";
      }
    }
  }

  grouping linecard-cmds {
    container linecard {
      list linecards {
        key "linecardName";
        leaf linecardName {
          type linecardid;
          mandatory true;
        }
        leaf linecardType {
          type enumeration {
            enum "LC48x10G" {
              value 1;
            }
            enum "LC12x40G" {
              value 2;
            }
            enum "LC72x1G" {
              value 8;
            }
            enum "LC48x1G" {
              value 9;
            }
          }
        }
      }
    }
  }

  augment "/rbridge:rbridge-id" {
    container global-lc-holder {
      uses linecard-cmds;
    }
  }

  typedef slotnum {
    type uint32;
  }

  typedef partition {
    type enumeration {
      enum "p0";
      enum "p1";
    }
  }

  typedef lcslotidtype {
    type string {
      length "2";
    }
  }

  augment "/common-def:show" {
    container linecardinfo;
    container sfminfo;
    container mminfor;
    container slotsinfor;
  }
  container linecardservice;
}
