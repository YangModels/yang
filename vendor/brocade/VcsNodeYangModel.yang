module VcsNodeYangModel {
  namespace "http://brocade.com/dcmd/local";
  prefix brocade;

  organization "Brocade Communications Inc.";
  description
    "DCMD Base Services manual CLI interface model definition";

  revision 2009-03-02;

  typedef mappedIdType {
    type uint16 {
      range "1..1023" {
        error-message "Mapped IDs must be in the range 1..1024";
      }
    }
    description
      "MappedId is a unique ID assigned to a switch by DCMD, it does not changefor the life of a switch in a network. MappedIds must be in the range 1..1023";
  }

  container vcs_node;
}
