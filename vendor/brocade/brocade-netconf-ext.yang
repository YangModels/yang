module brocade-netconf-ext {
  namespace "urn:brocade.com:mgmt:brocade-netconf-ext";
  prefix netconf-extensions;

  import ietf-yang-types {
    prefix ietfyang;
  }
  import ietf-inet-types {
    prefix inet;
  }

  organization "Brocade Communications Inc.";
  contact
    "Brocade Communications Systems, Inc.
     Postal: 130 Holger Way
        San Jose, CA 95134
        U.S.A
     Tel: +1-408-333-6061
     E-mail: support@Brocade.com
     web: www.brocade.com.";
  description
    "This sub module defines NETCONF information.
      Copyright(c) 2010-2011 by Brocade Communications Systems, Inc.
      All rights reserved.";
  reference "";

  revision 2012-02-03 {
    description
      "Added new RPC for NETCONF Client information for NETCONF 
       interface.";
    reference "";
  }

  rpc get-netconf-client-capabilities {
    description
      "This RPC displays the vendor information 
       of all the NETCONF clients";
    input {
      leaf session-id {
        type uint32;
        description
          "This specifies session id for which this function
           is invoked. This is optional input, when not
           specified means 'all' sessions.";
      }
    }
    output {
      list session {
        leaf session-id {
          type uint32;
          description
            "Session Id of the NETCONF client session.";
        }
        leaf user-name {
          type string;
          description
            "Login name of the user for the NETCONF client
             session.";
        }
        leaf vendor {
          type string;
          mandatory false;
          description
            "Vendor name of the NETCONF client session.";
        }
        leaf product {
          type string;
          mandatory false;
          description
            "Product name of the NETCONF client session.";
        }
        leaf version {
          type string;
          mandatory false;
          description
            "Product version of the NETCONF client
             session.";
        }
        leaf identity {
          type string;
          mandatory false;
          description
            "Identity of the NETCONF client session.";
        }
        leaf af-type {
          type enumeration {
            enum "IPV4" {
              value 2;
            }
            enum "IPV6" {
              value 10;
            }
          }
          description
            "This leaf indicates the address family type. If the value is IPV4
             then the client host IP will be present in the host-ip leaf.
             If the value is IPV6, then the client host IP will be present in
             host-ip-V6 leaf";
        }
        leaf host-ip-v6 {
          type inet:ipv6-address;
          description
            "IP Address of NETCONF client session";
        }
        leaf host-ip {
          type inet:ipv4-address;
          description
            "IP Address of NETCONF client session";
        }
        leaf time {
          type ietfyang:date-and-time;
          description
            "Login time of NETCONF client session";
        }
      }
    }
  }
}
