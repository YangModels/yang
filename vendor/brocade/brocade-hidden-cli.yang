module brocade-hidden-cli {
  namespace "urn:brocade.com:mgmt:brocade-hidden-cli";
  prefix hidden-cli;

  import brocade-common-def {
    prefix common-def;
  }
  import brocade-fabric-service {
    prefix fabric-service;
  }
  import brocade-license {
    prefix license;
  }
  import brocade-interface {
    prefix interface;
  }
  import brocade-xstp {
    prefix xstp;
  }

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an instrumentation to manage  hidden 
     cli commands which might be useful in debugging but not exposed
     to customer.";

  revision 2011-06-28 {
    description
      "Initial version of the brocade-hidden-cli module.";
  }

  augment "/common-def:show/fabric-service:fabric" {
    container showfabric;
  }
  augment "/common-def:clear" {
    container fabric;
  }
  container debug {
    container fabric;
  }
  augment "/license:license" {
    container showlicense;
  }
  container ras-debug {
    container prom-access;
  }
  augment "/common-def:show" {
    container ras-debug;
  }
  augment "/interface:protocol/xstp:spanning-tree/xstp:pvst" {
    leaf mac-address-reduction {
      type enumeration {
        enum "enable";
        enum "standard";
      }
      default "enable";
    }
  }
  augment "/interface:protocol/xstp:spanning-tree/xstp:pvst/xstp:vlan" {
    leaf aging-time {
      type uint32 {
        range "0..100000" {
          error-message "% Error: Value out of range at '^' marker";
        }
      }
    }
  }
  augment "/interface:protocol/xstp:spanning-tree/xstp:rpvst" {
    leaf mac-address-reduction {
      type enumeration {
        enum "enable";
        enum "standard";
      }
      default "enable";
    }
  }
  augment "/interface:protocol/xstp:spanning-tree/xstp:rpvst/xstp:vlan" {
    leaf aging-time {
      type uint32 {
        range "0..100000" {
          error-message "% Error: Value out of range at '^' marker";
        }
      }
    }
  }

  typedef slot-num {
    type uint32 {
      range "1..16" {
        error-message "Invalid slot number.";
      }
    }
  }

  container linecard-cli;

  grouping ampp-vlan-classifier {
    container classifier-vlan {
      container classifier {
        container activate {
          list group {
            key "groupid vlanclassifieroperation vlan";
            leaf groupid {
              type uint32 {
                range "1..16";
              }
            }
            leaf vlanclassifieroperation {
              type enumeration {
                enum "vlan" {
                  value 0;
                }
              }
            }
            leaf vlan {
              type uint32 {
                range "1..4090";
              }
            }
          }
        }
      }
    }
  }
}
