module brocade-system-monitor {
  namespace "urn:brocade.com:mgmt:brocade-system-monitor";
  prefix system-monitor;

  import brocade-rbridge {
    prefix rbridge;
  }
  import ietf-inet-types {
    prefix inet;
  }

  organization "Brocade Communications Systems, Inc.";
  contact
    "Address :  120 Holger Way
                San Jose, CA 95134
                U.S.A
     Phone    :  +1-408-333-8000
     E-mail   :  support@brocade.com
     Website  :  www.brocade.com";
  description
    "Data Model for Brocade's System Monitor configuration CLIs";

  revision 2011-11-16 {
    description
      "Addition of all FRUs";
  }
  revision 2011-04-29 {
    description
      "Initial modelling of Yang";
  }

  typedef supported-state {
    type bits {
      bit removed {
        position 0;
      }
      bit inserted {
        position 1;
      }
      bit on {
        position 2;
      }
      bit faulty {
        position 4;
      }
      bit none {
        position 5;
      }
      bit all {
        position 6;
      }
    }
  }

  typedef sfp-supported-state {
    type bits {
      bit removed {
        position 0;
      }
      bit inserted {
        position 1;
      }
      bit faulty {
        position 4;
      }
      bit none {
        position 5;
      }
      bit all {
        position 6;
      }
    }
  }

  typedef supported-actions {
    type bits {
      bit none {
        position 0;
      }
      bit all {
        position 1;
      }
      bit email {
        position 2;
      }
      bit raslog {
        position 3;
      }
    }
  }

  grouping system-monitor-group {
    container fan {
      container threshold {
        leaf marginal-threshold {
          type uint32;
        }
        leaf down-threshold {
          type uint32;
        }
      }
      container alert {
        leaf state {
          type supported-state;
        }
        leaf action {
          type supported-actions;
        }
      }
    }
    container power {
      container threshold {
        leaf marginal-threshold {
          type uint32;
        }
        leaf down-threshold {
          type uint32;
        }
      }
      container alert {
        leaf state {
          type supported-state;
        }
        leaf action {
          type supported-actions;
        }
      }
    }
    container temp {
      container threshold {
        leaf marginal-threshold {
          type uint32;
        }
        leaf down-threshold {
          type uint32;
        }
      }
    }
    container cid-card {
      container threshold {
        leaf marginal-threshold {
          type uint32;
        }
        leaf down-threshold {
          type uint32;
        }
      }
      container alert {
        leaf state {
          type supported-state;
        }
        leaf action {
          type supported-actions;
        }
      }
    }
    container sfp {
      container alert {
        leaf state {
          type sfp-supported-state;
        }
        leaf action {
          type supported-actions;
        }
      }
    }
    container compact-flash {
      container threshold {
        leaf marginal-threshold {
          type uint32;
        }
        leaf down-threshold {
          type uint32;
        }
      }
    }
    container MM {
      container threshold {
        leaf marginal-threshold {
          type uint32;
        }
        leaf down-threshold {
          type uint32;
        }
      }
    }
    container LineCard {
      container threshold {
        leaf marginal-threshold {
          type uint32;
        }
        leaf down-threshold {
          type uint32;
        }
      }
      container alert {
        leaf state {
          type supported-state;
        }
        leaf action {
          type supported-actions;
        }
      }
    }
    container SFM {
      container threshold {
        leaf marginal-threshold {
          type uint32;
        }
        leaf down-threshold {
          type uint32;
        }
      }
    }
  }

  augment "/rbridge:rbridge-id" {
    container system-monitor {
      uses system-monitor-group;
    }
  }
  container system-monitor {
    uses system-monitor-group;
  }
  container system-monitor-mail {
    container fru {
      leaf enable {
        type empty;
      }
      list email-list {
        key "email";
        max-elements "5";
        leaf email {
          type string;
        }
      }
    }
    container sfp {
      leaf enable {
        type empty;
      }
      list email-list {
        key "email";
        max-elements "5";
        leaf email {
          type string;
        }
      }
    }
    container security {
      leaf enable {
        type empty;
      }
      list email-list {
        key "email";
        max-elements "5";
        leaf email {
          type string;
        }
      }
    }
    container interface {
      leaf enable {
        type empty;
      }
      list email-list {
        key "email";
        max-elements "5";
        leaf email {
          type string;
        }
      }
    }
    list relay {
      max-elements "1";
      key "host-ip";
      leaf host-ip {
        type inet:host;
      }
      leaf domain-name {
        type string {
          length "0 .. 64" {
            error-message
              "Domain name should be
               in the range 0-64";
          }
        }
        default "";
      }
    }
  }
}
