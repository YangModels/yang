module brocade-cee-map {
  namespace "urn:brocade.com:mgmt:brocade-cee-map";
  prefix brocade-cee-map;

  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This management submodule is an instrumentation to 
     manage cee-map feature.";

  revision 2011-04-18 {
    description
      "Initial version of the management module cee-map.";
  }

  typedef qos-type-PGID {
    type string {
      pattern "[0-7]|15.[0-7]";
    }
  }

  list cee-map {
    key "name";
    leaf name {
      type common-def:name-string32;
    }
    leaf precedence {
      description
        "CEE map precedence value";
      type int32 {
        range "1 .. 100";
      }
    }
    list priority-group-table {
      key "PGID";
      leaf PGID {
        type qos-type-PGID;
      }
      leaf weight {
        type int32 {
          range "1 .. 100";
        }
      }
      leaf pfc {
        mandatory true;
        type enumeration {
          enum "on" {
            value 1;
          }
          enum "off" {
            value 0;
          }
        }
      }
    }
    container priority-table {
      description
        "Configure Priority Table";
      leaf map-cos0-pgid {
        type string {
          pattern "[0-7]|15.[0-7]";
          length "1..32";
        }
      }
      leaf map-cos1-pgid {
        type string {
          pattern "[0-7]|15.[0-7]";
          length "1..32";
        }
      }
      leaf map-cos2-pgid {
        type string {
          pattern "[0-7]|15.[0-7]";
          length "1..32";
        }
      }
      leaf map-cos3-pgid {
        type string {
          pattern "[0-7]|15.[0-7]";
          length "1..32";
        }
      }
      leaf map-cos4-pgid {
        type string {
          pattern "[0-7]|15.[0-7]";
          length "1..32";
        }
      }
      leaf map-cos5-pgid {
        type string {
          pattern "[0-7]|15.[0-7]";
          length "1..32";
        }
      }
      leaf map-cos6-pgid {
        type string {
          pattern "[0-7]|15.[0-7]";
          length "1..32";
        }
      }
      leaf map-cos7-pgid {
        type string {
          pattern "[0-7]|15.[0-7]";
          length "1..32";
        }
      }
    }
    container remap {
      container fabric-priority {
        leaf fabric-remapped-priority {
          type int32 {
            range "0 .. 6";
          }
        }
      }
      container lossless-priority {
        leaf lossless-remapped-priority {
          type int32 {
            range "0 .. 6";
          }
        }
      }
    }
  }
}
