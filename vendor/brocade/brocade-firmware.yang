module brocade-firmware {
  namespace "urn:brocade.com:mgmt:brocade-firmware";
  prefix firmware;

  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This management module is an instrumentation to firmware level
     level commands";

  revision 2011-04-11 {
    description
      "Initial version of this management module.";
  }

  typedef rbridge-ids-all-type {
    description
      "The unique identifier for a switch.  The usage of `all'
       refers to `all' rbridge-id's in the cluster.";
    type union {
      type common-def:ui32-range;
      type string {
        pattern "all";
      }
    }
  }

  grouping fwdl-parameters {
    leaf user {
      type string;
      mandatory true;
    }
    leaf password {
      type string;
      mandatory false;
    }
    leaf host {
      type string;
      mandatory true;
    }
    leaf directory {
      type string;
      mandatory true;
    }
    leaf file {
      type string;
      mandatory false;
    }
  }

  grouping fwdl-local-options {
    choice options {
      case manual {
        leaf manual {
          type empty;
          mandatory false;
        }
        leaf noreboot {
          type empty;
          mandatory false;
        }
        leaf nocommit {
          type empty;
          mandatory false;
        }
      }
      case noactivate {
        leaf noactivate {
          type empty;
          mandatory false;
        }
      }
    }
  }

  grouping fwdl-cluster-options {
    leaf rbridge-id {
      type rbridge-ids-all-type;
      mandatory true;
    }
    leaf auto-activate {
      type empty;
      mandatory false;
    }
  }

  grouping fwdl-output {
    leaf fwdl-tid {
      type int32;
    }
    leaf fwdl-status {
      type int32;
    }
    leaf fwdl-msg {
      type string;
    }
  }

  grouping fwdl-cluster-output {
    leaf fwdl-cmd-status {
      type int32;
    }
    leaf fwdl-cmd-msg {
      type string;
    }
    list cluster-output {
      leaf rbridge-id {
        type uint32;
      }
      leaf fwdl-status {
        type int32;
      }
      leaf fwdl-msg {
        type string;
      }
    }
  }

  container firmware {
    container download {
      container logical-chassis;
    }
    container auto-sync;
    container autoupgrade {
      leaf enable {
        type empty;
      }
    }
    container autoupgrade-params {
      leaf path {
        type string;
      }
      leaf protocol {
        type enumeration {
          enum "ftp" {
            value 1;
          }
          enum "scp" {
            value 2;
          }
          enum "sftp" {
            value 3;
          }
        }
      }
      leaf ipaddress {
        type string;
      }
      leaf username {
        type string;
      }
      leaf pass {
        type string;
      }
    }
  }
  rpc fwdl-status {
    input {
      leaf fwdl-tid {
        type int32;
      }
    }
    output {
      leaf number-of-entries {
        type uint32;
      }
      leaf fwdl-state {
        type enumeration {
          enum "in-progress" {
            value 1;
          }
          enum "downloaded" {
            value 2;
          }
          enum "failed" {
            value 3;
          }
          enum "completed" {
            value 4;
          }
        }
      }
      list fwdl-entries {
        leaf index {
          type uint32;
        }
        leaf message-id {
          type int32;
        }
        leaf date-and-time-info {
          type string;
        }
        leaf message {
          type string;
        }
        leaf blade-slot {
          type int32;
        }
        leaf blade-swbd {
          type int32;
        }
        leaf blade-name {
          type string;
        }
        leaf blade-state {
          type enumeration {
            enum "active" {
              value 0;
            }
            enum "standby" {
              value 1;
            }
          }
        }
        leaf blade-app {
          type string;
        }
      }
    }
  }
  rpc activate-status {
    input {
      leaf rbridge-id {
        type rbridge-ids-all-type;
        mandatory false;
      }
    }
    output {
      leaf overall-status {
        type int32;
      }
      leaf overall-error-msg {
        type string;
      }
      list activate-entries {
        leaf rbridge-id {
          type common-def:rbridge-id-type;
          mandatory false;
        }
        leaf status {
          type int32;
        }
      }
    }
  }
  rpc logical-chassis-fwdl-sanity {
    input {
      uses fwdl-parameters;
      uses fwdl-cluster-options;
      leaf protocol {
        mandatory true;
        type enumeration {
          enum "ftp" {
            value 1;
          }
          enum "scp" {
            value 2;
          }
          enum "sftp" {
            value 3;
          }
        }
      }
    }
    output {
      uses fwdl-cluster-output;
    }
  }
  rpc logical-chassis-fwdl-status {
    input {
      leaf rbridge-id {
        type rbridge-ids-all-type;
        mandatory false;
      }
    }
    output {
      leaf overall-status {
        type int32;
      }
      list cluster-fwdl-entries {
        leaf rbridge-id {
          type uint32;
          mandatory false;
        }
        leaf fwdl-state {
          type enumeration {
            enum "completed" {
              value 0;
            }
            enum "in-progress" {
              value 1;
            }
            enum "complete-no-reboot" {
              value 2;
            }
            enum "complete-no-activate" {
              value 3;
            }
            enum "commit-in-progress" {
              value 4;
            }
          }
        }
        list fwdl-entries {
          leaf index {
            type uint32;
          }
          leaf message-id {
            type int32;
          }
          leaf date-and-time-info {
            type string;
          }
          leaf message {
            type string;
          }
          leaf blade-slot {
            type int32;
          }
          leaf blade-swbd {
            type int32;
          }
          leaf blade-name {
            type string;
          }
          leaf blade-state {
            type enumeration {
              enum "active" {
                value 0;
              }
              enum "standby" {
                value 1;
              }
            }
          }
          leaf blade-app {
            type string;
          }
        }
      }
    }
  }
  container reboot;
  container dhcp {
    container auto-deployment;
  }
  augment "/common-def:show" {
    container dhcp-auto-deployment;
  }
}
