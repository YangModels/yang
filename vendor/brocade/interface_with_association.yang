module interface_with_association {
  namespace "http://brocade.com/ns/DcmInterfaceAssociation";
  prefix DcmInterfaceAssociation;

  typedef UI32Range {
    type string {
      pattern "[0-9]+(-[0-9]+)?(,[0-9]+(-[0-9]+)?)*";
    }
  }

  container samplevlan {
    list vlans {
      key "id";
      leaf id {
        type uint32;
        mandatory true;
      }
    }
  }
  container interfaces_with_association {
    list interface {
      key "name";
      max-elements "1024";
      leaf name {
        type string;
      }
      leaf vlanId {
        type leafref {
          path "/samplevlan/vlans/id";
        }
        mandatory true;
      }
      leaf nullObjectId {
        type leafref {
          path "/samplevlan/vlans/id";
        }
        mandatory false;
      }
      leaf-list vlanIdList {
        type leafref {
          path "/samplevlan/vlans/id";
        }
      }
      leaf vlanIdList2 {
        type UI32Range;
      }
    }
  }
}
