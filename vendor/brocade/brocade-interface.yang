module brocade-interface {
  namespace "urn:brocade.com:mgmt:brocade-interface";
  prefix brocade-interface;

  import ietf-inet-types {
    prefix inet;
  }
  import brocade-common-def {
    prefix common-def;
  }
  import brocade-rbridge {
    prefix rbridge;
  }
  import ietf-yang-types {
    prefix yang;
  }

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an instrumentation to manage  
     ethernet network interfaces sub-layers.
             
     The following ethernet interfaces can be managed using this 
     management module:
             
     +--------------------------------------------------------------+
     | List name                  Description                       |
     +--------------------------------------------------------------+
     | gigabitethernet            1G  Physical Ethernet interfaces  |
     | tengigabitethernet         10G Physical Ethernet interfaces  |
     | port-channel               Port-channel/LAG interfaces       |
     | management                 Management port/interfaces        |
     | vlan                       L2 Vlan interface.                |
     +--------------------------------------------------------------+
             
     This module provides mechanism:
        - to discover and characterize the interface sub-layers.
        - to configure various attributes of these interfaces.
        - to structure the interfaces such that various L2/L3 
        access/security policies, network discovery policies, QoS 
        policies and Link aggregation policies can be applied using 
        other modules supported by the managed entity.
             
     Glossary of the terms used:
     --------------------------- 
     TRILL   - Transparent Interconnection of Lots of Links.
     VLAN    - Virtual Local Area Network.
     Rbridge - Routing Bridge.
     ISL     - Inter switch Link.
     MTU     - Maximum transmission unit. The size of the largest 
              packet which can be sent/received on an interface.
     LAG     - IEEE Link Aggregation (IEEE 802.1AX).
     vLAG    - virtual LAG.";
  reference
    "K. McCloghrie, 'The Interfaces Group MIB', RFC 2863, 
     June 2000.";

  revision 2011-07-05 {
    description
      "Initial version of this management module.";
  }
  revision 2012-04-24 {
    description
      "Deprecated .../switchport/trunk/allowed/vlanoper.";
  }
  revision 2013-04-08 {
    description
      "Added openflow support";
  }

  typedef openflow-mode {
    type enumeration {
      enum "mode-native" {
        value 0;
      }
      enum "mode-hybrid" {
        value 1;
      }
    }
    default "mode-native";
  }

  typedef ui32-vlan-range {
    type string {
      pattern "(([1-9][0-9]{0,2})|([1-3][0-9]{3})|(40[0-8][0-9])|(4090))(-((1[0-9]{1,2})|([2-9][0-9]{0,2})|([1-3][0-9]{3})|(40[0-8][0-9])|(4090)))?((,((1[0-9]{1,2})|([2-9][0-9]{0,2})|([1-3][0-9]{3})|(40[0-8][0-9])|(4090))(-((1[0-9]{1,2})|([2-9][0-9]{0,2})|([1-3][0-9]{3})|(40[0-8][0-9])|(4090)))?)?)*";
      length "1..253";
    }
    description
      "The definition for specifying the vlan range.";
  }

  typedef ui32-eldvlan-range {
    type string {
      pattern "(([1-9][0-9]{0,2})|([1-7][0-9]{3})|(80[0-9]{2})|(81[0-8][0-9])|(819[01]))(-(([2-9])|([1-9][0-9]{1,2})|([1-7][0-9]{3})|(80[0-9]{2})|(81[0-8][0-9])|(819[01])))?((,(([2-9])|([1-9][0-9]{1,2})|([1-7][0-9]{3})|(80[0-9]{2})|(81[0-8][0-9])|(819[01]))(-(([3-9])|([1-9][0-9]{1,2})|([1-7][0-9]{3})|(80[0-9]{2})|(81[0-8][0-9])|(819[01])))?)?)*";
      length "1..253";
    }
    description
      "The definition for specifying the vlan range.";
  }

  typedef ui32-range-8091 {
    type string {
      pattern "(([1-9][0-9]{0,2})|([1-7][0-9]{3})|(80[0-9]{2})|(81[0-8][0-9])|(819[01]))(-(([2-9])|([1-9][0-9]{1,2})|([1-7][0-9]{3})|(80[0-9]{2})|(81[0-8][0-9])|(819[01])))?((,(([2-9])|([1-9][0-9]{1,2})|([1-7][0-9]{3})|(80[0-9]{2})|(81[0-8][0-9])|(819[01]))(-(([3-9])|([1-9][0-9]{1,2})|([1-7][0-9]{3})|(80[0-9]{2})|(81[0-8][0-9])|(819[01])))?)?)*";
      length "1..253";
    }
    description
      "The definition for specifying the vlan range.";
  }

  typedef interface-type {
    type string {
      pattern "((([1-9]|[1-9][0-9]|1[0-9][0-9]|2[0-3][0-9])/)?(([0-9]|[1][0-6]))/([1-9]|[1-9][0-9])(:[1-4])?)";
      length "3..16";
    }
    description
      "The definition for specifying a network interface name in
       a VCS environment. It is in 3-tuple canonical format:
       [rbridge-id]/slot/port.";
  }

  typedef man-interface-type {
    type string {
      pattern "([1-9]|[1-9][0-9]|1[0-9][0-9]|2[0-3][0-9])/([0-9]|[1-9][0-9])";
      length "3..16";
    }
    description
      "The definition for specifying a management network 
       interface name. It is in 2-tuple format: 
       rbridge-id/port.";
  }

  typedef vlan-type {
    type uint32 {
      range "1..8191";
    }
    description
      "The definition for specifying a vlan identifier. This 
       represents it represents an IEEE 802.1Q VLAN-ID.";
    reference
      "IEEE Std 802.1Q 2003 Edition, Virtual Bridged Local Area 
       Networks.";
  }

  typedef dot1q-vlan-type {
    type uint32 {
      range "1..4092";
    }
    description
      "The definition for specifying a dot1q vlan identifier. 
       This represents an IEEE 802.1Q VLAN-ID.";
    reference
      "IEEE Std 802.1Q 2003 Edition, Virtual Bridged Local Area
       Networks.";
  }

  typedef non-dot1q-vlan-type {
    type uint32 {
      range "4097..8191";
    }
    description
      "The definition for specifying a non dot1q vlan identifier.";
  }

  typedef ve-type {
    type uint32 {
      range "1..8191";
    }
    description
      "The definition for specifying a ve identifier.";
  }

  typedef portchannel-type {
    type uint32 {
      range "1..6144";
    }
    description
      "The definition for specifying a port-channel.";
  }

  typedef mtu-type {
    type uint32 {
      range "1522..9216";
    }
    units "Bytes";
    description
      "The definition for specifying the MTU in octets.";
  }

  typedef channel-group-type {
    type uint32 {
      range "1..6144";
    }
    description
      "The definition for specifying the LACP channel group on 
       an interface .";
  }

  typedef port-sec-violation {
    type enumeration {
      enum "no-action" {
        value 0;
        description
          "No action";
      }
      enum "restrict" {
        value 1;
        description
          "Set the action as restrict";
      }
      enum "shutdown" {
        value 2;
        description
          "Set the action as Shutdown.";
      }
    }
    description
      "The definition for specifying the violation of a 
       port-security.";
    default "no-action";
  }

  typedef po-mode {
    type enumeration {
      enum "active" {
        value 1;
        description
          "LACP negotiation enabled on a port.";
      }
      enum "passive" {
        value 2;
        description
          "LACP negotiation disabled on a port.";
      }
      enum "on" {
        value 3;
        description
          "LACP static link aggregation enabled on a port.";
      }
    }
    description
      "The definition for specifying the mode of a 
       port-channel.";
  }

  typedef po-type {
    type enumeration {
      enum "standard" {
        value 1;
        description
          "Standards (IEEE 802.3ad) based LAG.";
      }
      enum "brocade" {
        value 2;
        description
          "Brocade LAG.";
      }
    }
    description
      "The definition for specifying the type of a port-channel.";
  }

  typedef switchport-mode-type {
    type enumeration {
      enum "unknown" {
        value 0;
        description
          "Switchport in Unknown mode.";
      }
      enum "access" {
        value 1;
        description
          "Switchport in Access mode.";
      }
      enum "trunk" {
        value 2;
        description
          "Switchport in Trunk mode.";
      }
      enum "converged" {
        value 3;
        description
          "Switchport in Converged mode.";
      }
      enum "pvlan-promiscuous" {
        value 4;
        description
          "Switchport in PVLAN promiscuous mode.";
      }
      enum "pvlan-trunk-promiscuous" {
        value 5;
        description
          "Switchport in PVLAN trunk promiscuous mode.";
      }
      enum "pvlan-host" {
        value 6;
        description
          "Switchport in PVLAN host mode.";
      }
      enum "pvlan-trunk-host" {
        value 7;
        description
          "Switchport in PVLAN trunk host mode.";
      }
      enum "pvlan-trunk" {
        value 8;
        description
          "Switchport in PVLAN trunk mode.";
      }
    }
    description
      "The definition for specifying the mode of operation of the 
       Layer2 ethernet port.";
  }

  typedef l2-mode-type {
    type enumeration {
      enum "access" {
        value 1;
        description
          "Layer2 port in 'access' mode.";
      }
      enum "trunk" {
        value 2;
        description
          "Layer2 port in 'trunking' mode.";
      }
    }
    description
      "The definition for specifying the mode of operation of the 
       Layer2 ethernet port.
                   
       The ports are assigned to a single VLAN. These ports are 
       referred to as access ports and provide a connection for 
       end users or node devices.
                   
       The trunk links are required to pass VLAN information 
       between switches.";
  }

  typedef allowed-vlan-oper-type {
    type enumeration {
      enum "add" {
        value 1;
      }
      enum "remove" {
        value 2;
      }
      enum "except" {
        value 3;
      }
    }
    description
      "The definition to specify allowed vlan  on a ethernet 
       port.";
  }

  typedef fc-speed-cfg-type {
    type enumeration {
      enum "auto" {
        value 0;
      }
      enum "1gbps" {
        value 1;
      }
      enum "2gbps" {
        value 2;
      }
      enum "4gbps" {
        value 4;
      }
      enum "8gbps" {
        value 5;
      }
    }
    default "auto";
  }

  typedef fc-fillword-cfg-type {
    type enumeration {
      enum "idle-idle" {
        value 0;
      }
      enum "arbff-arbff" {
        value 1;
      }
      enum "idle-arbff" {
        value 2;
      }
      enum "aa-then-ia" {
        value 3;
      }
    }
    default "idle-idle";
  }

  typedef desire-distance-type {
    type uint32;
    description
      "To configure the desired distance.";
  }

  typedef interface-fc-config-mode-type {
    type enumeration {
      enum "auto" {
        value 1;
        description
          "Configures the port as a G-Port (locked).";
      }
      enum "eport" {
        value 2;
        description
          "Configures the port as a E-Port (locked).";
      }
      enum "nport" {
        value 3;
        description
          "Configures the port as a N-Port (locked).";
      }
      enum "fport" {
        value 4;
        description
          "Configures the port as a F-Port (locked).";
      }
    }
    default "auto";
  }

  typedef fc-long-distance-cfg-type {
    type enumeration {
      enum "l0" {
        value 0;
      }
      enum "le" {
        value 3;
      }
      enum "ld" {
        value 5;
      }
      enum "ls" {
        value 6;
      }
    }
    default "l0";
  }

  typedef fc-vc-link-init-cfg-type {
    type enumeration {
      enum "idle" {
        value 0;
      }
      enum "arb" {
        value 1;
      }
    }
    default "idle";
  }

  typedef vlan-range-cli-pattern {
    type string {
      pattern "(((([1-9][0-9]{0,2})|([1-7][0-9]{3})|(80[0-9]{2})|(81[0-8][0-9])|(819[01]))(,((([2-9])|([1-9][0-9]{1,2})|([1-7][0-9]{3})|(80[0-9]{2})|(81[0-8][0-9])|(819[01]))(-(([3-9])|([1-9][0-9]{1,2})|([1-7][0-9]{3})|(80[0-9]{2})|(81[0-8][0-9])|(819[01])))?)+))|(((([1-9][0-9]{0,2})|([1-7][0-9]{3})|(80[0-9]{2})|(81[0-8][0-9])|(819[01]))-(([2-9])|([1-9][0-9]{1,2})|([1-7][0-9]{3})|(80[0-9]{2})|(81[0-8][0-9])|(819[01])))(,(([3-9])|([1-9][0-9]{1,2})|([1-7][0-9]{3})|(80[0-9]{2})|(81[0-8][0-9])|(819[01]))(-(([4-9])|([1-9][0-9]{1,2})|([1-7][0-9]{3})|(80[0-9]{2})|(81[0-8][0-9])|(819[01])))?)*))";
      length "1..253";
    }
  }

  typedef port-channel-range-cli-pattern {
    type string {
      pattern "((([1-9][0-9]{0,2})|([1-5][0-9]{3})|(60[0-9][0-9])|(61[0-3][0-9])|(614[0-4]))(-(([1-9][0-9]{0,2})|([1-5][0-9]{3})|(60[0-9][0-9])|(61[0-3][0-9])|(614[0-4]))){1})|((([1-9][0-9]{0,2})|([1-5][0-9]{3})|(60[0-9][0-9])|(61[0-3][0-9])|(614[0-4]))(-(([1-9][0-9]{0,2})|([1-5][0-9]{3})|(60[0-9][0-9])|(61[0-3][0-9])|(614[0-4])))?)((,(([1-9][0-9]{0,2})|([1-5][0-9]{3})|(60[0-9][0-9])|(61[0-3][0-9])|(614[0-4]))(-(([1-9][0-9]{0,2})|([1-5][0-9]{3})|(60[0-9][0-9])|(61[0-3][0-9])|(614[0-4])))?){1})+";
      length "1..253";
    }
    description
      "The definition for specifying the port-channel range.";
  }

  typedef phy-interface-range-cli-pattern {
    type string {
      pattern "((([1-9]|[1-9][0-9]|1[0-9][0-9]|2[0-3][0-9])/)?(([0-9]|[1][0-6]))/([1-9]|[1-9][0-9]))(-([1-9]|[1-9][0-9])){1}|((([1-9]|[1-9][0-9]|1[0-9][0-9]|2[0-3][0-9])/)?(([0-9]|[1][0-6]))/([1-9]|[1-9][0-9]))((-([1-9]|[1-9][0-9]))?)((,([1-9]|[1-9][0-9])(-([1-9]|[1-9][0-9]))?){1})+";
      length "1..253";
    }
    description
      "The definition for specifying the Physical Interface range.";
  }

  typedef fcoe-interface-range {
    type string {
      pattern "(([1-9][0-9]{0,2}|[1-7][0-9]{3}|80[0-9]{2}|81[0-8][0-9]|819[0-2])/([1-9]|[1-9][0-9]|1[0-9][0-9]|2[0-3][0-9])/([1-9][0-9]{0,2}|1000))(-([1-9][0-9]{0,2}|1000)){1}|(([1-9][0-9]{0,2}|[1-7][0-9]{3}|80[0-9]{2}|81[0-8][0-9]|819[0-2])/([1-9]|[1-9][0-9]|1[0-9][0-9]|2[0-3][0-9])/([1-9][0-9]{0,2}|1000))((-([1-9][0-9]{0,2}|1000))?)((,([1-9][0-9]{0,2}|1000)(-([1-9][0-9]{0,2}|1000))?){1})+";
      length "1..253";
    }
    description
      "The definition for specifying the FCoE Interface range.";
  }

  typedef fc-interface-range-cli-pattern {
    type string {
      pattern "((([1-9]|[1-9][0-9]|1[0-9][0-9]|2[0-3][0-9])/)?(([0-9]|[1][0-6]))/([1-9]|[1-9][0-9]))(-(([2-9])|([1-9][0-9]))){1}|((([1-9]|[1-9][0-9]|1[0-9][0-9]|2[0-3][0-9])/)?(([0-9]|[1][0-6]))/([1-9]|[1-9][0-9]))((-(([2-9])|([1-9][0-9])))?)((,(([2-9])|([1-9][0-9]))(-(([2-9])|([1-9][0-9])))?){1})+";
      length "1..253";
    }
    description
      "The definition for specifying the fibrechannel Interface range.";
  }

  typedef mac-address-type {
    type string;
  }

  typedef mac-group-id-type {
    type uint32 {
      range "1..500";
    }
    description
      "The definition for specifying a mac-group-id.";
  }

  container interface {
    description
      "All the interface related elements of this managed device
       grouped under this container.";
  }
  container interface-vlan {
    description
      "An intermediary node that separates the vlan related 
       elements of this managed device.";
    container interface {
      description
        "The vlan interface configurations/data of this managed
         device.";
    }
  }
  container protocol;
  container reserved-vlan {
    leaf reserved-vlan-start {
      type uint32 {
        range "1..4090";
      }
    }
    leaf reserved-vlan-end {
      type uint32 {
        range "1..4090";
      }
    }
  }

  grouping interface-name-info {
    description
      "This denotes an interface name qualified with the type of 
       the interface. This grouping can be used to indicate 
       physical or logical interfaces.";
    leaf interface-type {
      type enumeration {
        enum "unknown" {
          value 1;
        }
        enum "gigabitethernet" {
          value 2;
        }
        enum "tengigabitethernet" {
          value 3;
        }
        enum "fortygigabitethernet" {
          value 4;
        }
        enum "port-channel" {
          value 5;
        }
        enum "l2vlan" {
          value 6;
        }
        enum "loopback" {
          value 7;
        }
        enum "fibrechannel" {
          value 8;
        }
      }
      description
        "The type of the interface. An 'unknown' type 
         represents error scenario and should not be used.";
    }
    leaf interface-name {
      type union {
        type brocade-interface:interface-type;
        type brocade-interface:portchannel-type;
        type brocade-interface:vlan-type;
      }
      description
        "The Interface value. The interface value is always 
         interpreted within the context of the value of 
         'interface-type' leaf:
         
         interface-type         interface-name
         -----------------      --------------------
         gigabitethernet        [mapped-id]/slot/port
         tengigabitethernet     [mapped-id]/slot/port
         fortygigabitethernet   [mapped-id]/slot/port
         port-channel           Port channel ID
         l2vlan                 Vlan ID
         unknown                Zero-length string.
         
         The value of an 'interface-name' must always be 
         consistent with the value of the associated 
         'interface-type'.  Attempts to set an interface-name
         to a value inconsistent with the associated 
         'interface-type' must fail with an error.";
    }
  }

  augment "/interface-vlan/interface" {
    list vlan {
      key "name";
      description
        "The list of vlans in the managed device. Each row 
         represents a vlan. User can create/delete an entry in 
         to this list.";
      leaf name {
        type vlan-type;
        description
          "The vlan identifier.";
      }
    }
    list ve {
      key "name";
      description
        "The list of ve interfaces in the managed device. Each row 
         represents a ve interface. User can create/delete an entry in 
         to this list.";
      leaf name {
        type ve-type;
      }
    }
  }

  grouping interface-vrf-config {
    container vrf {
      leaf forwarding {
        type common-def:vrf-name;
        description
          "This specifies the VRF that needs to be associated
           with interface.";
      }
    }
  }

  grouping phy-interface-parameters {
    leaf cee {
      type common-def:name-string32;
      description
        "The CEE map associated with this physical 
         interface.";
    }
    leaf speed {
      type enumeration {
        enum "auto" {
          value 0;
          description
            "Auto negotiated.";
        }
        enum "1000" {
          value 1;
          description
            "1 Gigabit per second.";
        }
        enum "10000" {
          value 2;
          description
            "10 Gigabit per second.";
        }
      }
      default "auto";
      description
        "This leaf specifies the administratively configured
         bandwidth for this physical interface.";
    }
  }

  grouping fortygig-interface-parameters {
    leaf cee {
      type common-def:name-string32;
      description
        "The CEE map associated with this physical
         interface.";
    }
  }

  augment "/interface" {
    list gigabitethernet {
      ordered-by user;
      key "name";
      description
        "The list of 1 GigabitEthernet interfaces in the 
         managed device. Each row represents a 1 GigabitEthernet 
         interface. The list provides a way to discover all the 
         1G physical interfaces in a managed device.
                         
         In case of logical-switch (VCS cluster), this list 
         comprises of all the 1G physical interfaces across 
         all the rbridges in the cluster.";
      leaf name {
        type interface-type;
        description
          "The name of the 1G ethernet interface.";
      }
    }
    list tengigabitethernet {
      ordered-by user;
      key "name";
      description
        "The list of 10 GigabitEthernet interfaces in the 
         managed device. Each row represents a 10 GigabitEthernet 
         interface. The list provides a way to discover all the 
         1G physical interfaces in a managed device.
                         
         In case of logical-switch (VCS cluster), this list 
         comprises of all the 10G physical interfaces across 
         all the rbridges in the cluster.";
      leaf name {
        type interface-type;
      }
      leaf long-distance-isl {
        type enumeration {
          enum "2000" {
            value 2000;
            description
              "2000 meter distance link (Warning: It May disable other ISLs in the port group)";
          }
          enum "5000" {
            value 5000;
            description
              "5000 meter distance link (Warning: It May disable other ISLs in the port group)";
          }
          enum "10000" {
            value 10000;
            description
              "10,000 meter distance link (Warning: It May disable other ISLs in the port group)";
          }
          enum "30000" {
            value 30000;
            description
              "30,000 meter distance link (Warning: It May disable other ISLs in the port group and DCB/FCoE capabilities will no longer be supported)";
          }
        }
        description
          "Configure the link as long-distance-link";
      }
      uses phy-interface-parameters;
    }
    list fortygigabitethernet {
      ordered-by user;
      key "name";
      description
        "The list of 40 GigabitEthernet interfaces in the 
         managed device. Each row represents a 40 GigabitEthernet 
         interface. The list provides a way to discover all the 
         1G physical interfaces in a managed device.
                         
         In case of logical-switch (VCS cluster), this list 
         comprises of all the 40G physical interfaces across 
         all the rbridges in the cluster.";
      leaf name {
        type interface-type;
      }
      uses fortygig-interface-parameters;
    }
    list port-channel {
      ordered-by user;
      key "name";
      description
        "The list of port-channels in the managed device. Each
         entry represents a port-channel.";
      leaf name {
        type portchannel-type;
        description
          "The port-channel identifier.";
      }
      leaf cee {
        type common-def:name-string32;
        description
          "The CEE map associated with this port-channel 
           interface.";
      }
      container vlag {
        description
          "The vLAG properties for this port-channel.";
        leaf ignore-split {
          type empty;
        }
      }
      leaf po-speed {
        type enumeration {
          enum "1000" {
            value 1;
            description
              "1Gbps.";
          }
          enum "10000" {
            value 2;
            description
              "10Gbps.";
          }
          enum "40000" {
            value 3;
            description
              "40Gbps.";
          }
        }
        default "10000";
        description
          "This specifies the administratively configured
           bandwidth for this physical interface.";
      }
    }
    list management {
      max-elements "1024";
      key "name";
      description
        "The list of management interfaces in the managed 
         device. Each row represents a management interface.";
      leaf name {
        type man-interface-type;
        description
          "The name of the management interface.";
      }
      container ip {
        description
          "The IPv4 configurations for this management 
           interface.";
        container icmp {
          description
            "The ICMP control for this management interface.";
          leaf unreachable {
            type empty;
            description
              "To enable generating ICMP Destination Unreachable message.";
          }
          leaf echo_reply {
            type empty;
            description
              "To enable sending ICMP Echo Reply in response Echo Request.";
          }
          leaf rate_limiting {
            type uint32;
            default "1000";
            description
              "To enable ICMP incoming packet response rate limiting";
          }
        }
        container address {
          description
            "The IPv4 address configuration for this 
             management interface.";
          leaf dhcp {
            type empty;
            description
              "This specifies if DHCP is enabled or not.
               The presence of this leaf indicates that 
               this interface is configured for DHCP.";
          }
          leaf ip-address {
            type common-def:ipv4-address-prefix-type;
            description
              "This specifies the IP address for this 
               management interface.";
          }
        }
        container gateway {
          description
            "The IP gateway configurations for this 
             management interface.";
          leaf gateway-address {
            type inet:ipv4-address;
            description
              "The gateway IP address for this management
               interface.";
          }
        }
        container oper-address {
          leaf oper-ip-address {
            type common-def:ipv4-address-prefix-type;
            config false;
            description
              "The assigned IPv4 address.";
          }
        }
        container oper-gateway-con {
          leaf oper-gateway {
            type inet:ipv4-address;
            config false;
            description
              "The assigned gateway address.";
          }
        }
      }
      container ipv6 {
        description
          "The IPv6 configurations for this management 
           interface.";
        container icmpv6 {
          description
            "The ICMPv6 control for this management interface.";
          leaf v6_unreachable {
            type empty;
            description
              "To enable generating ICMPv6 Destination Unreachable message.";
          }
          leaf v6_echo_reply {
            type empty;
            description
              "To enable sending ICMPv6 Echo Reply in response Echo Request.";
          }
          leaf v6_rate_limiting {
            type uint32;
            default "1000";
            description
              "To enable ICMPv6 incoming rate limiting";
          }
        }
        container ipv6-address-cont {
          description
            "The IPv6 address configuration for this 
             management interface.";
          leaf ipv6-global-address {
            type common-def:ipv6-address-prefix;
            description
              "IPv6 global address for this management 
               interface.";
          }
          leaf autoconfig {
            type empty;
            description
              "This specifies if this auto-configuration 
               for IP address allocation is enabled or not.
               The presence of this leaf indicates that 
               the auto-configuration is enabled.";
          }
          leaf dhcpv6 {
            type empty;
            description
              "This specifies if this ipv6 dhcp is enabled 
               or not. The presence of this leaf indicates that 
               the ipv6 dhcp is enabled.";
          }
        }
        leaf-list ipv6-address {
          type string;
          config false;
          description
            "The list of IPv6 addresses assigned for this 
             management interface.";
        }
        leaf-list ipv6-gateways {
          type string;
          config false;
          description
            "The list of IPv6 gateways assigned for this 
             management interface.";
        }
      }
      leaf speed {
        type enumeration {
          enum "auto" {
            value 0;
            description
              "Auto-negotiation.";
          }
          enum "10" {
            value 1;
            description
              "10 Mbps Full Duplex";
          }
          enum "100" {
            value 2;
            description
              "100 Mbps Full Duplex";
          }
        }
        default "auto";
        description
          "This specifies the administratively configured
           bandwidth for this management interface.";
      }
      container line-speed {
        description
          "The line-speed characteristics for this management 
           interface.";
        leaf actual {
          config false;
          type string;
          description
            "The actual line-speed for this management 
             interface.";
        }
        leaf configured {
          config false;
          type string;
          description
            "The configured line-speed for this management 
             interface.";
        }
      }
    }
    list fc-port {
      ordered-by user;
      key "name";
      description
        "The list of fibrechannel interfaces in the managed
         device. Each row represents a fibrechannel interface.
         The list provides a way to discover all the fibrechannel interfaces
         in a managed device.";
      leaf name {
        type interface-type;
        description
          "The name of the fibrechannel interface.";
      }
    }
  }

  grouping po-minimum-links-group {
    description
      "This specifies the minimum link group.";
    leaf minimum-links {
      type uint32;
      default "1";
      description
        "The least number of operationally 'UP' links to 
         indicate port-channel being UP.";
    }
  }

  grouping interface-po-group {
    description
      "The interface level configurations to setup a 
       port-channel.";
    container channel-group {
      description
        "A container of configuration leaf elements for managing
         the channel-group membership.";
      leaf port-int {
        type portchannel-type;
        description
          "The port channel number.";
      }
      leaf mode {
        type po-mode;
        description
          "The mode of the port channel.";
      }
      leaf type {
        type po-type;
        description
          "The type of the port-channel.";
      }
    }
  }

  grouping allowed-vlan-add-group {
    description
      "A set of elements defining the vlan access policy.";
    container allowed {
      description
        "Set the VLANs that will Xmit/Rx through the Layer2
         interface";
      container vlan {
        leaf all {
          type empty;
          description
            "This is to specify all vlans or not.
             Presence of this leaf indicates all
             vlans are allowed.";
        }
        leaf none {
          type empty;
          description
            "This is to specify 'no vlans' or not. 
             Presence of this leaf indicates no
             vlans are allowed.";
        }
        leaf add {
          type ui32-vlan-range;
          description
            "This specifies list of vlans to 
             be added.";
        }
        leaf except {
          type ui32-vlan-range;
          description
            "This specifies exception list of 
             vlans.";
        }
        leaf remove {
          type ui32-vlan-range;
          description
            "This specifies the list of vlans 
             to be removed.";
        }
      }
      container vlanoper {
        status deprecated;
        description
          "DEPRECATED
           NOS2.1.0 style data model for allowed vlans.
           Do not use in edit-config.";
        container vlan {
          leaf add {
            type ui32-vlan-range;
          }
          leaf remove {
            type ui32-vlan-range;
          }
        }
      }
    }
  }

  grouping gvlan-allowed-vlan-add-group {
    description
      "A set of elements defining the vlan access policy.";
    container gvlan {
      container allowed {
        description
          "Set the VLANs that will Xmit/Rx through the Layer2
           interface";
        container vlan {
          list add {
            key "gvlan-trunk-vlan-id gvlan-trunk-ctag-id";
            leaf gvlan-trunk-vlan-id {
              type non-dot1q-vlan-type;
            }
            leaf gvlan-trunk-ctag-id {
              type dot1q-vlan-type;
            }
          }
          list remove {
            key "gvlan-trunk-vlan-id gvlan-trunk-ctag-id";
            leaf gvlan-trunk-vlan-id {
              type non-dot1q-vlan-type;
            }
            leaf gvlan-trunk-ctag-id {
              type dot1q-vlan-type;
            }
          }
        }
      }
    }
  }

  grouping interface-sw-trunk-rspan-group {
    description
      "Common grouping for the switchport trunk rspan commands";
    container rspan-vlan {
      description
        "configure a rspan-vlan";
      leaf add-rspan-trunk-vlan {
        type ui32-vlan-range;
        description
          "Specify rspan-vlan id";
      }
      leaf remove-rspan-trunk-vlan {
        type ui32-vlan-range;
        description
          "This specifies the list of rspan vlans to be removed.";
      }
    }
  }

  grouping interface-sw-access-rspan-group {
    description
      "Common grouping for the switchport access rspan commands";
    container rspan-access {
      description
        "The access layer characteristics of this 
         interface.";
      leaf rspan-access-vlan {
        type vlan-type;
        default "1";
        description
          "Specify rspan-vlan id to set as access vlan";
      }
    }
  }

  grouping interface-sw-trunk-rspan-gvlan-group {
    description
      "A set of elements defining the vlan access policy.";
    container gvlan {
      container rspan-vlan {
        list add {
          key "rspan-gvlan-trunk-vlan-id rspan-gvlan-trunk-ctag-id";
          leaf rspan-gvlan-trunk-vlan-id {
            type non-dot1q-vlan-type;
          }
          leaf rspan-gvlan-trunk-ctag-id {
            type dot1q-vlan-type;
          }
        }
        list remove {
          key "rspan-gvlan-trunk-remove-vlan-id rspan-gvlan-trunk-remove-ctag-id";
          leaf rspan-gvlan-trunk-remove-vlan-id {
            type non-dot1q-vlan-type;
          }
          leaf rspan-gvlan-trunk-remove-ctag-id {
            type dot1q-vlan-type;
          }
        }
      }
    }
  }

  grouping interface-sw-access-rspan-gvlan-group {
    description
      "Common grouping for the switchport access rspan commands";
    container rspan-gvlan-mac-address {
      container access {
        description
          "The access layer characteristics of this interface.";
        list mac-addr-rspan-vlan {
          key "rspan-mac-address-classification-vlan rspan-mac-address-classification-address";
          leaf rspan-mac-address-classification-vlan {
            type vlan-type;
            description
              "Set the default VLAN for the interface";
          }
          leaf rspan-mac-address-classification-address {
            type mac-address-type;
            description
              "Associate the Mac address with a vlan";
          }
        }
      }
    }
    container rspan-gvlan-mac-group {
      container access {
        description
          "The access layer characteristics of this interface.";
        list mac-group-rspan-vlan {
          key "rspan-mac-group-classification-vlan rspan-mac-group-classification-group";
          leaf rspan-mac-group-classification-vlan {
            type vlan-type;
            description
              "Set the default VLAN for the interface";
          }
          leaf rspan-mac-group-classification-group {
            type mac-group-id-type;
            description
              "Associate a Mac group with a vlan";
          }
        }
      }
    }
  }

  grouping secure-macs {
    description
      "List of secure MACs";
    list port-secutiry-mac-address {
      description
        "Mac Address commands";
      key "mac-address port-sec-vlan";
      leaf mac-address {
        description
          "MAC address";
        type mac-address-type;
      }
      leaf port-sec-vlan {
        type vlan-type;
        description
          "Vlan is for MAC address";
      }
    }
  }

  grouping interface-eth-po-group {
    description
      "The common grouping to characterize a physical/logical
       interface.";
    leaf mtu {
      type mtu-type;
      default "2500";
      description
        "The size of the largest packet which can be sent/
         received on the interface, specified in bytes.  
         For interfaces that are used for transmitting network
         datagrams, this is the size of the largest network 
         datagram that can be sent on the interface.";
    }
    container openflow {
      leaf openflow-enable {
        type empty;
      }
    }
    container switchport {
      description
        "The L2 switching characteristics of an interface.";
      leaf basic {
        type empty;
      }
      container port-security {
        presence "true";
        description
          "Enable port-security feature";
        leaf port-sec-max {
          description
            "Maximum number of allowed MACs";
          type uint32;
        }
        leaf port-sec-violation {
          type port-sec-violation;
          description
            "Set the action on violation";
        }
        uses secure-macs;
        container sticky {
          presence "true";
          description
            "Sticky MAC";
          uses secure-macs;
        }
        list allowed-ouis {
          description
            "List of allowed OUIs";
          key "oui";
          leaf oui {
            description
              "OUI, only from this vendor traffic will be allowed";
            type mac-address-type;
          }
        }
        leaf shutdown-time {
          type uint32;
          description
            "Shutdown time for port";
        }
      }
      container mode {
        description
          "The mode of the Layer2 interface.";
        leaf vlan-mode {
          type l2-mode-type;
          description
            "The access/trunk mode of this interface.";
        }
        container private-vlan {
          container private-vlan-trunk {
            leaf trunk-basic {
              type empty;
            }
            leaf trunk-promiscuous {
              type empty;
            }
            leaf trunk-host {
              type empty;
            }
          }
          leaf promiscuous {
            type empty;
          }
          leaf host {
            type empty;
          }
        }
      }
      container access {
        description
          "The access layer characteristics of this 
           interface.";
        leaf accessvlan {
          type vlan-type;
          description
            "This specifies the access vlan for this 
             interface.";
        }
      }
      container gvlan {
        container access {
          description
            "The access layer characteristics of this 
             interface.";
          list vlan {
            key "access-gvlan index-address";
            leaf access-gvlan {
              type vlan-type;
              description
                "Set the default VLAN for the interface";
            }
            leaf index-address {
              type mac-address-type;
              description
                "Associate the Mac address with a vlan";
            }
          }
        }
        container private-vlan {
          container trunk {
            container allowed {
              description
                "Set the VLANs that will Xmit/Rx through the Layer2 interface";
              container vlan {
                list add {
                  key "gvlan-trunk-vlan-id gvlan-trunk-ctag-id";
                  leaf gvlan-trunk-vlan-id {
                    type non-dot1q-vlan-type;
                  }
                  leaf gvlan-trunk-ctag-id {
                    type dot1q-vlan-type;
                  }
                }
                list remove {
                  key "gvlan-trunk-vlan-id gvlan-trunk-ctag-id";
                  leaf gvlan-trunk-vlan-id {
                    type non-dot1q-vlan-type;
                  }
                  leaf gvlan-trunk-ctag-id {
                    type dot1q-vlan-type;
                  }
                }
              }
            }
          }
        }
      }
      container mac-group {
        container access {
          description
            "The access layer characteristics of this 
             interface.";
          list mac-group-vlan {
            key "mac-group-classification-vlan mac-group-classification-group";
            leaf mac-group-classification-vlan {
              type vlan-type;
              description
                "Set the default VLAN for the interface";
            }
            leaf mac-group-classification-group {
              type mac-group-id-type;
              description
                "Associate a Mac group with a vlan";
            }
          }
        }
      }
      container trunk {
        description
          "The trunking characteristics of this interface.";
        uses allowed-vlan-add-group;
        uses gvlan-allowed-vlan-add-group;
      }
      container private-vlan {
        description
          "Set Private-Vlan Configuration";
        container trunk {
          description
            "trunk";
          container native {
            description
              "Set the native VLAN characteristics of the
               Layer2 trunk interface";
            leaf pvlanNativevlan {
              type vlan-type;
            }
          }
          uses allowed-pvlan-trunk-cmds;
        }
        container host-association {
          description
            "Host-association";
          leaf host-pri-pvlan {
            type vlan-type;
          }
          leaf host-sec-pvlan {
            type vlan-type;
          }
        }
        container association {
          description
            "Association";
          list trunk {
            key "trunk-pri-pvlan trunk-sec-pvlan";
            leaf trunk-pri-pvlan {
              type vlan-type;
            }
            leaf trunk-sec-pvlan {
              type vlan-type;
            }
          }
        }
        list mapping {
          description
            "Promiscuous mapping";
          key "promis-pri-pvlan";
          leaf promis-pri-pvlan {
            type vlan-type;
          }
          leaf oper {
            type secVlan-opp-type;
          }
          leaf promis-sec-pvlan-range {
            type ui32-range-8091;
          }
        }
      }
    }
  }

  typedef secVlan-opp-type {
    type enumeration {
      enum "add" {
        value 1;
      }
      enum "delete" {
        value 2;
      }
    }
    description
      "Add/Remove secondary vlan ids";
  }

  grouping common-interface-group {
    leaf ifindex {
      config false;
      type uint64;
    }
    leaf description {
      type string {
        length "1 .. 63";
      }
    }
    leaf shutdown {
      type empty;
    }
  }

  grouping common-interface-group-vlan {
    leaf ifindex {
      config false;
      type uint64;
    }
    leaf description {
      type string {
        length "1 .. 63";
      }
    }
  }

  grouping interface-ipv6 {
    container ipv6 {
      description
        "The IPv6 configurations for an interface.";
    }
  }

  grouping interface-ipv6-phy-cfg {
    leaf ra-guard {
      type empty;
    }
  }

  grouping interface-ip {
    container ip {
      description
        "The IP configurations for an interface.";
    }
  }

  grouping interface-ip-standalone {
    container ip {
      description
        "The IP configurations for an interface.";
    }
  }

  typedef pvlan-type {
    type enumeration {
      enum "primary" {
        value 1;
      }
      enum "isolated" {
        value 2;
      }
      enum "community" {
        value 3;
      }
    }
  }

  grouping interface-vlan-pvlan-cmds {
    container private-vlan {
      description
        "Configure a Private Vlan";
      leaf pvlan-type-leaf {
        description
          "Set the PVLAN type of the VLAN interface";
        type pvlan-type;
      }
      container association {
        leaf sec-assoc-add {
          type ui32-range-8091;
        }
        leaf sec-assoc-remove {
          type ui32-range-8091;
        }
      }
    }
  }

  grouping allowed-pvlan-trunk-cmds {
    container allowed {
      description
        "Set the VLANs that will Xmit/Rx through the Layer2 interface";
      container vlan {
        description
          "VLAN(s) that will be added/removed";
        leaf pvlan_all {
          type empty;
        }
        leaf pvlan_none {
          type empty;
        }
        leaf pvlan_add {
          type ui32-vlan-range;
        }
        leaf pvlan_except {
          type ui32-vlan-range;
        }
        leaf pvlan_remove {
          type ui32-vlan-range;
        }
      }
    }
  }

  grouping interface-fc-port {
    leaf fc-speed-cfg {
      type fc-speed-cfg-type;
    }
    leaf fill-word {
      type fc-fillword-cfg-type;
    }
    leaf long-distance {
      type fc-long-distance-cfg-type;
    }
    leaf vc-link-init {
      type fc-vc-link-init-cfg-type;
    }
    leaf desire-distance {
      type desire-distance-type;
    }
    leaf isl-r_rdy-mode {
      type empty;
    }
    leaf trunk-enable {
      type empty;
    }
    leaf shutdown {
      type empty;
    }
    leaf config-mode {
      description
        "Port Mode Configuration";
      type interface-fc-config-mode-type;
    }
  }

  augment "/interface/fc-port" {
    uses interface-fc-port;
  }

  grouping portcfg-fabric {
    container fabric {
      description
        "This specifies configurations that affects the 
         ethernet fabric (in VCS environment).";
      container isl {
        description
          "The ISL characteristics for an interface.";
        leaf isl-enable {
          type empty;
          description
            "This specifies if the ISL capability is 
             enabled or not. The presence of this leaf 
             indicates that the ISL is enabled.";
        }
      }
      container trunk {
        description
          "The trunking characteristics.";
        leaf trunk-enable {
          type empty;
          description
            "This specifies if the trunk is enabled or 
             not.  The presence of this leaf indicates  that 
             the trunk is enabled.";
        }
      }
    }
  }

  augment "/interface/tengigabitethernet" {
    uses common-interface-group;
    uses interface-po-group;
    uses interface-eth-po-group {
      refine "switchport/port-security";
      refine "switchport/port-security/sticky";
      refine "switchport/port-security/port-secutiry-mac-address";
      refine "switchport/port-security/sticky/port-secutiry-mac-address";
      refine "switchport/port-security/allowed-ouis";
      refine "switchport/private-vlan/association/trunk";
      refine "switchport/private-vlan/mapping";
    }
    uses interface-ip;
    uses interface-vrf-config;
    uses interface-ipv6;
    container vepa {
      leaf vepa-enable {
        type empty;
      }
    }
    container edge-loop-detection {
      leaf eldprio {
        type uint32 {
          range "0..256";
        }
        default "128";
      }
      leaf eldvlan {
        type ui32-eldvlan-range;
      }
    }
  }
  augment "/interface/gigabitethernet" {
    uses common-interface-group;
    uses interface-po-group;
    uses interface-eth-po-group {
      refine "switchport/port-security";
      refine "switchport/port-security/sticky";
      refine "switchport/port-security/port-secutiry-mac-address";
      refine "switchport/port-security/sticky/port-secutiry-mac-address";
      refine "switchport/port-security/allowed-ouis";
      refine "switchport/private-vlan/association/trunk";
      refine "switchport/private-vlan/mapping";
    }
    uses interface-ip;
    uses interface-vrf-config;
    uses interface-ipv6;
    container edge-loop-detection {
      leaf eldprio {
        type uint32 {
          range "0..256";
        }
        default "128";
      }
      leaf eldvlan {
        type ui32-eldvlan-range;
      }
    }
  }
  augment "/interface/fortygigabitethernet" {
    uses common-interface-group;
    uses interface-po-group;
    uses interface-eth-po-group {
      refine "switchport/port-security";
      refine "switchport/port-security/sticky";
      refine "switchport/port-security/port-secutiry-mac-address";
      refine "switchport/port-security/sticky/port-secutiry-mac-address";
      refine "switchport/port-security/allowed-ouis";
      refine "switchport/private-vlan/association/trunk";
      refine "switchport/private-vlan/mapping";
    }
    uses interface-ip;
    uses interface-vrf-config;
    uses interface-ipv6;
    container edge-loop-detection {
      leaf eldprio {
        type uint32 {
          range "0..256";
        }
        default "128";
      }
      leaf eldvlan {
        type ui32-eldvlan-range;
      }
    }
  }
  augment "/interface-vlan/interface/vlan" {
    uses common-interface-group-vlan;
    uses interface-vlan-pvlan-cmds;
    container ip {
      description
        "The IP configurations for an interface.";
    }
  }
  augment "/interface-vlan/interface/ve" {
    uses interface-ip;
  }
  augment "/interface/port-channel" {
    uses common-interface-group;
    uses po-minimum-links-group;
    uses interface-eth-po-group {
      refine "switchport/port-security";
      refine "switchport/port-security/sticky";
      refine "switchport/port-security/port-secutiry-mac-address";
      refine "switchport/port-security/sticky/port-secutiry-mac-address";
      refine "switchport/port-security/allowed-ouis";
      refine "switchport/private-vlan/association/trunk";
      refine "switchport/private-vlan/mapping";
      refine "switchport/gvlan";
      refine "switchport/mac-group";
      refine "switchport/trunk/gvlan/allowed/vlan/add";
      refine "switchport/trunk/gvlan/allowed/vlan/remove";
      refine "switchport/gvlan/private-vlan/trunk/allowed/vlan/add";
      refine "switchport/gvlan/private-vlan/trunk/allowed/vlan/remove";
    }
    uses interface-ip;
    uses interface-ipv6;
    container edge-loop-detection {
      description
        "Enable edge-loop-detection on the selected interface";
      leaf eldprio {
        description
          "Set eld-priority value to interface";
        type uint32 {
          range "0..256";
        }
        default "128";
      }
      leaf eldvlan {
        description
          "Enable for specific VLAN on selected interface";
        type ui32-eldvlan-range;
      }
    }
    leaf load-balance {
      type enumeration {
        enum "dst-mac-vid" {
          value 1;
        }
        enum "src-mac-vid" {
          value 2;
        }
        enum "src-dst-mac-vid" {
          value 3;
        }
        enum "src-dst-ip" {
          value 4;
        }
        enum "src-dst-ip-mac-vid" {
          value 5;
        }
        enum "src-dst-ip-port" {
          value 6;
        }
        enum "src-dst-ip-mac-vid-port" {
          value 7;
        }
      }
      default "src-dst-ip-mac-vid-port";
    }
  }
  augment "/interface/tengigabitethernet/switchport/trunk" {
    container tag {
      presence "tag";
      description
        "This specifies vlan tagging characteristics for a 
         trunk port.";
      leaf native-vlan {
        type empty;
        description
          "This specifies if the native vlan should be used 
           for classifying the un-tagged traffic.";
      }
    }
    leaf nativevlanid {
      type uint32 {
        range "2..8191";
      }
      description
        "The native vlan for an interface.";
    }
  }
  augment "/interface/tengigabitethernet/switchport/trunk/allowed" {
    uses interface-sw-trunk-rspan-group;
    uses interface-sw-trunk-rspan-gvlan-group;
  }
  augment "/interface/tengigabitethernet/switchport/access" {
    uses interface-sw-access-rspan-group;
  }
  augment "/interface/tengigabitethernet/switchport" {
    uses interface-sw-access-rspan-gvlan-group;
  }
  augment "/interface/gigabitethernet/switchport/trunk" {
    container tag {
      presence "tag";
      leaf native-vlan {
        type empty;
      }
    }
    leaf nativevlanid {
      type uint32 {
        range "2..8191";
      }
      description
        "The native vlan for an interface.";
    }
  }
  augment "/interface/gigabitethernet/switchport/trunk/allowed" {
    uses interface-sw-trunk-rspan-group;
    uses interface-sw-trunk-rspan-gvlan-group;
  }
  augment "/interface/gigabitethernet/switchport/access" {
    uses interface-sw-access-rspan-group;
  }
  augment "/interface/gigabitethernet/switchport" {
    uses interface-sw-access-rspan-gvlan-group;
  }
  augment "/interface/fortygigabitethernet/switchport/trunk" {
    container tag {
      presence "tag";
      description
        "This specifies vlan tagging characteristics for a
         trunk port.";
      leaf native-vlan {
        type empty;
        description
          "This specifies if the native vlan should be used
           for classifying the un-tagged traffic.";
      }
    }
    leaf nativevlanid {
      type uint32 {
        range "2..8191";
      }
      description
        "The native vlan for an interface.";
    }
  }
  augment "/interface/fortygigabitethernet/switchport/trunk/allowed" {
    uses interface-sw-trunk-rspan-group;
    uses interface-sw-trunk-rspan-gvlan-group;
  }
  augment "/interface/fortygigabitethernet/switchport/access" {
    uses interface-sw-access-rspan-group;
  }
  augment "/interface/fortygigabitethernet/switchport" {
    uses interface-sw-access-rspan-gvlan-group;
  }
  augment "/interface/port-channel/switchport/trunk" {
    container tag {
      presence "tag";
      leaf native-vlan {
        type empty;
      }
    }
    leaf nativevlanid {
      type uint32 {
        range "2..8191";
      }
      description
        "The native vlan for an interface.";
    }
  }
  augment "/interface/tengigabitethernet/ipv6" {
    uses interface-ipv6-phy-cfg;
  }
  augment "/interface/gigabitethernet/ipv6" {
    uses interface-ipv6-phy-cfg;
  }
  augment "/interface/fortygigabitethernet/ipv6" {
    uses interface-ipv6-phy-cfg;
  }
  augment "/interface/port-channel/ipv6" {
    uses interface-ipv6-phy-cfg;
  }
  augment "/rbridge:rbridge-id" {
    container protocol {
      description
        "Protocol configuration.";
    }
    container interface {
      list ve {
        key "name";
        leaf name {
          type ve-type;
        }
      }
    }
  }
}
