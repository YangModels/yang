module brocade-threshold-monitor-ext {
  namespace "urn:brocade.com:mgmt:brocade-threshold-monitor-ext";
  prefix threshold-monitor-extensions;

  import brocade-common-def {
    prefix common-def;
  }

  organization "Brocade Communications Inc.";
  contact
    "Brocade Communications Systems, Inc.
     Postal: 130 Holger Way
             San Jose, CA 95134
             U.S.A
     Tel: +1-408-333-6061
     E-mail: support@Brocade.com
     web: www.brocade.com.";
  description
    "This sub module defines show threshold-monitor data model
     Copyright (c) 2011 by Brocade Communications Systems, Inc.
     All rights reserved.";

  revision 2011-05-05 {
    description
      "Initial version of this module.";
  }

  typedef threshold-monitor-state-enum {
    type enumeration {
      enum "No-Change" {
        value 0;
      }
      enum "In-Range" {
        value 1;
      }
      enum "Out-Of-Range" {
        value 2;
      }
    }
  }

  typedef threshold-monitor-pause-enum {
    type enumeration {
      enum "Paused" {
        value 0;
      }
      enum "Monitoring" {
        value 1;
      }
    }
  }

  typedef threshold-monitor-area {
    type enumeration {
      enum "MissingTerminationCharacter" {
        value 0;
      }
      enum "CRCAlignErrors" {
        value 1;
      }
      enum "SymbolErrors" {
        value 2;
      }
      enum "IFG" {
        value 3;
      }
      enum "CFI" {
        value 4;
      }
    }
  }

  typedef sfp-type {
    type enumeration {
      enum "1GSR" {
        value 0;
      }
      enum "1GLR" {
        value 1;
      }
      enum "10GSR" {
        value 2;
      }
      enum "10GLR" {
        value 3;
      }
      enum "10GUSR" {
        value 4;
      }
      enum "QSFP" {
        value 5;
      }
    }
  }

  augment "/common-def:show/common-def:defaults" {
    container threshold;
  }
}
