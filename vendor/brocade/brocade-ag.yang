module brocade-ag {
  namespace "urn:brocade.com:mgmt:brocade-ag";
  prefix ag;

  import brocade-interface {
    prefix interface;
  }
  import brocade-rbridge {
    prefix rbridge;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This management module is an instrumentation to manage AG 
     feature.";

  typedef port-type {
    type string {
      length "1..16";
    }
  }

  typedef wwn-type {
    type string {
      pattern "([0-9a-f]{2}(:[0-9a-f]{2}){7})|([a,A][n.N][y,Y])|([n,N][o,O][n,N][e,E])";
    }
    description
      "World Wide Name (Only lower case allowed)";
  }

  typedef nport-interfaces-type-optional {
    type string {
      length "1..250";
    }
  }

  typedef fport-interfaces-type-optional {
    type string {
      length "1..250";
    }
  }

  typedef nport-interfaces-type {
    type string {
      length "1..250";
    }
  }

  typedef fport-interfaces-type {
    type string {
      length "1..250";
    }
  }

  typedef pgid-type {
    type uint32;
  }

  typedef pg-type {
    type string {
      length "1..250";
    }
  }

  typedef ag-policy-types {
    type string {
      length "1..10";
    }
  }

  typedef pg-policy-types {
    type string {
      length "1..10";
    }
  }

  augment "/rbridge:rbridge-id" {
    container ag {
      list nport {
        key "agNPortNb";
        leaf agNPortNb {
          type nport-interfaces-type;
          mandatory true;
        }
        uses nportclis;
      }
      list pg {
        key "pgid";
        leaf pgid {
          type pgid-type;
          mandatory true;
        }
        uses pgclis;
      }
      container policyenable {
        leaf-list agPolicy {
          type ag-policy-types;
          min-elements 0;
        }
      }
      container timeout {
        leaf fnmtovalue {
          type uint32;
        }
      }
      container counter {
        leaf reliabilitycountervalue {
          type uint32;
        }
      }
    }
  }

  grouping nportclis {
    container map {
      container map-fport {
        container map-fport-interface {
          leaf-list map-fcoe {
            type fport-interfaces-type;
          }
        }
      }
    }
    container staticmap {
      container staticmap-fport {
        container staticmap-fport-interface {
          leaf-list staticmap-fcoe {
            type fport-interfaces-type;
          }
        }
      }
    }
    container failover {
      leaf failoverenable {
        type empty;
      }
    }
    container failback {
      leaf failbackenable {
        type empty;
      }
    }
  }

  grouping pgclis {
    container nport {
      container pg-nport-interface {
        leaf-list nports {
          type nport-interfaces-type;
        }
      }
    }
    leaf-list modes {
      type pg-policy-types;
    }
    leaf rename {
      type string;
    }
  }
}
