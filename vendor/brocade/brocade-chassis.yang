module brocade-chassis {
  namespace "urn:brocade.com:mgmt:brocade-chassis";
  prefix chassis;

  import brocade-rbridge {
    prefix rbridge;
  }
  import brocade-common-def {
    prefix common-def;
  }
  import brocade-vcs {
    prefix vcs;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "Module for implementing switch configurable
     enable/disable CLIs";

  revision 2011-04-11 {
    description
      "Initial version of this management module.";
  }

  grouping chassis-config-cmds {
    container chassis {
      leaf virtual-ip {
        type common-def:ipv4-address-prefix-type;
      }
      leaf virtual-ipv6 {
        type common-def:ipv6-address-prefix;
      }
      container oper-address {
        leaf virtual-oper-Vip-address {
          type common-def:ipv4-address-prefix-type;
          config false;
          description
            "The assigned chassis IPv4 address.";
        }
        leaf-list virtual-oper-VipV6-address {
          type string;
          config false;
          description
            "The assigned chassis IPv6 address.";
        }
      }
    }
  }

  augment "/rbridge:rbridge-id" {
    uses chassis-config-cmds;
  }
  container hide-virtual-ip-holder {
    when "/vcs:vcsmode/vcs:vcs-mode = \"false\"";
    uses chassis-config-cmds;
  }
  container chassis {
    container beacon;
    container fan {
      container airflow-direction;
    }
  }
}
