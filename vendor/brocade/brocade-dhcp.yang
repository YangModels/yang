module brocade-dhcp {
  namespace "urn:brocade.com:mgmt:brocade-dhcp";
  prefix dhcp;

  import brocade-rbridge {
    prefix rbridge;
  }
  import brocade-interface {
    prefix interface;
  }
  import brocade-ip-config {
    prefix ip-config;
  }
  import brocade-common-def {
    prefix common-def;
  }
  import ietf-inet-types {
    prefix inet;
  }

  organization "Brocade Communications Systems, Inc.";
  contact
    "Brocade Communications Systems, Inc.
     Postal: 130 Holger Way,
             San Jose, CA 95134 
              U.S.A
     Tel: +1-408-333-8000
     E-mail: support@Brocade.com 
     web: www.brocade.com.";
  description
    "This management module is an instrumentation to manage 
     DHCP functionality.";

  revision 2013-05-20 {
    description
      "Initial version of this management module.";
  }

  typedef dhcp-ipv4-address {
    type inet:ipv4-address;
  }

  grouping interface-fo-dhcp {
    container interface-fo-dhcp-conf {
      uses interface-dhcp;
    }
  }

  grouping interface-te-dhcp {
    container interface-te-dhcp-conf {
      uses interface-dhcp;
    }
  }

  grouping interface-gi-dhcp {
    container interface-gi-dhcp-conf {
      uses interface-dhcp;
    }
  }

  grouping interface-ve-dhcp {
    container interface-ve-dhcp-conf {
      uses interface-dhcp;
    }
  }

  grouping interface-dhcp {
    container dhcp {
      container relay {
        list servers {
          key "relay-ip-addr";
          max-elements "4";
          leaf relay-ip-addr {
            type dhcp-ipv4-address;
            description
              "DHCP server IP address";
          }
        }
      }
    }
  }

  augment "/rbridge:rbridge-id/interface:interface/interface:ve/ip-config:ip" {
    uses interface-ve-dhcp;
  }
  augment "/interface:interface/interface:fortygigabitethernet/interface:ip" {
    uses interface-fo-dhcp;
  }
  augment "/interface:interface/interface:tengigabitethernet/interface:ip" {
    uses interface-te-dhcp;
  }
  augment "/interface:interface/interface:gigabitethernet/interface:ip" {
    uses interface-gi-dhcp;
  }
}
