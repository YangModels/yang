module brocade-span {
  namespace "urn:brocade.com:mgmt:brocade-span";
  prefix span;

  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "This module manages Port Mirroring (SPAN)";

  revision 2010-04-28 {
    description
      "Initial version of this management module.";
  }

  typedef session-type {
    type uint32 {
      range "0..511" {
        description
          "0-511;;Description Session_Id";
      }
    }
  }

  typedef span-if-type {
    type string {
      length "3..16";
    }
  }

  augment "/interface:interface-vlan/interface:interface/interface:vlan" {
    leaf remote-span {
      type empty;
    }
  }
  container monitor {
    list session {
      key "session-number";
      leaf session-number {
        type session-type;
      }
      leaf description {
        type string {
          length "1..64" {
            error-message "The length of the description should be in the range 1-64";
          }
        }
      }
      container span-command {
        leaf source {
          type enumeration {
            enum "source" {
              value 0;
            }
          }
        }
        leaf src-tengigabitethernet {
          type enumeration {
            enum "gigabitethernet" {
              value 0;
            }
            enum "tengigabitethernet" {
              value 1;
            }
            enum "fortygigabitethernet" {
              value 2;
            }
          }
        }
        leaf src-tengigabitethernet-val {
          type span-if-type;
        }
        leaf destination {
          type enumeration {
            enum "destination" {
              value 0;
            }
          }
        }
        leaf dest-tengigabitethernet {
          type enumeration {
            enum "gigabitethernet" {
              value 0;
            }
            enum "tengigabitethernet" {
              value 1;
            }
            enum "fortygigabitethernet" {
              value 2;
            }
            enum "rspan-vlan" {
              value 3;
            }
          }
        }
        leaf dest-tengigabitethernet-val {
          type span-if-type;
        }
        leaf dest-vlan-val {
          default "1";
          type interface:vlan-type;
        }
        leaf direction {
          type enumeration {
            enum "tx" {
              value 0;
            }
            enum "rx" {
              value 1;
            }
            enum "both" {
              value 2;
            }
          }
        }
      }
    }
  }
}
