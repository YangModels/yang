module brocade-snmp {
  namespace "urn:brocade.com:mgmt:brocade-snmp";
  prefix snmp-server;

  import brocade-rbridge {
    prefix rbridge;
  }
  import ietf-inet-types {
    prefix inet;
  }
  import brocade-common-def {
    prefix common-def;
  }

  organization "Brocade Communications Systems, Inc.";
  contact
    "Address :  120 Holger Way
                San Jose, CA 95134
                U.S.A
     Phone    :  +1-408-333-8000
     E-mail   :  support@brocade.com
     Website  :  www.brocade.com";
  description
    "Data Model for SNMP Server and related configuration CLIs";

  revision 2011-03-18 {
    description
      "Formatting yang model according to guidelines";
  }

  typedef host-port {
    type uint32 {
      range "0 .. 65535" {
        error-message "Port number should be in the range 0-65535";
      }
    }
    default "162";
  }

  typedef host-version {
    type enumeration {
      enum "1" {
        value 0;
      }
      enum "2c" {
        value 1;
      }
    }
  }

  typedef community-access {
    type enumeration {
      enum "ro" {
        value 0;
      }
      enum "rw" {
        value 1;
      }
    }
  }

  typedef snmp-engineID {
    type string {
      pattern "[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]:[0-9a-fA-F][0-9a-fA-F]";
    }
  }

  typedef system-contact {
    type string {
      length "4 .. 256" {
        error-message
          "Invalid Contact String length. String size 
           must be between 4 and 255";
      }
    }
  }

  typedef system-location {
    type string {
      length "4 .. 256" {
        error-message
          "Invalid Location String length. String size
           must be between 4 and 255";
      }
    }
  }

  typedef system-description {
    type string {
      length "4 .. 256" {
        error-message
          "Invalid System Description String length.
           String size must be between 4 and 255";
      }
    }
  }

  typedef sev-level {
    type enumeration {
      enum "None";
      enum "Critical";
      enum "Error";
      enum "Warning";
      enum "Info";
      enum "Debug";
    }
    default "None";
  }

  container snmp-server {
    list context {
      description
        "provides the  mapping of SNMP context (represented by
         the value of vacmContextName) to the various entities
         within the entities within the managed device";
      key "context-name";
      max-elements "256";
      leaf context-name {
        type string;
      }
      leaf vrf-name {
        type string;
      }
    }
    list community {
      key "community";
      max-elements "256";
      leaf community {
        type string;
      }
      leaf access {
        type community-access;
        default "ro";
      }
    }
    list user {
      key "username";
      max-elements "6";
      leaf username {
        type string {
          length "1 .. 16" {
            error-message "Username length should be in the range 1-16";
          }
        }
      }
      leaf groupname {
        type string;
        default "snmpuser";
      }
      leaf auth {
        type enumeration {
          enum "md5" {
            value 0;
          }
          enum "sha" {
            value 1;
          }
          enum "noauth" {
            value 2;
          }
        }
        default "noauth";
      }
      leaf auth-password {
        type string;
        default "";
      }
      leaf priv {
        type enumeration {
          enum "DES" {
            value 0;
          }
          enum "nopriv" {
            value 1;
          }
          enum "AES128" {
            value 2;
          }
        }
        default "nopriv";
      }
      leaf priv-password {
        type string;
        default "";
      }
      leaf encrypted {
        type empty;
        mandatory false;
      }
    }
    list v3host {
      key "hostip username";
      max-elements "6";
      leaf hostip {
        type inet:host;
      }
      leaf username {
        type string;
      }
      leaf udp-port {
        type host-port;
      }
      leaf notifytype {
        type enumeration {
          enum "traps" {
            value 0;
          }
          enum "informs" {
            value 1;
          }
        }
        default "traps";
      }
      leaf engineid {
        type string;
        default "00:00:00:00:00:00:00:00:00";
      }
      leaf severity-level {
        type sev-level;
      }
    }
    list host {
      key "ip community";
      max-elements "12";
      leaf ip {
        type inet:host;
      }
      leaf version {
        type host-version;
        default "1";
      }
      leaf community {
        type string;
      }
      leaf udp-port {
        type host-port;
      }
      leaf severity-level {
        type sev-level;
      }
    }
    container agtconfig {
      leaf contact {
        type system-contact;
      }
      leaf location {
        type system-location;
      }
      leaf sys-descr {
        type system-description;
      }
    }
    container engineID-drop {
      uses engineID-group;
    }
  }

  grouping engineID-group {
    container engineID {
      leaf local {
        type snmp-engineID;
      }
    }
  }

  augment "/rbridge:rbridge-id" {
    container snmp-server {
      uses engineID-group;
    }
  }
}
