module ieee-1906-dot1-system
{
  yang-version 1.1;
  namespace "urn:ieee:std:1906.1:yang:ieee-1906-dot1-system";
  prefix "system";

  import ietf-interfaces { prefix if; }
  import ieee-1906-dot1-types { prefix types; }
  import ieee-1906-dot1-metrics { prefix metrics; }
  import ieee-1906-dot1-components { prefix components; }

  organization 	"P1906.1.1/D1.0 Draft Standard Data Model for Nanoscale Communication Systems  Working Group";

  contact 	"IEEE P1906.1.1 Working Group
			Chair: Stephen F. Bush <bushsf@research.ge.com>
			Secretary: Guillaume Mantelet <guillaume.mantelet@ge.com>";

  description  "This experimental YANG module is an individual contribution, and
			    does not represent a formally sanctioned YANG module by IEEE.
				Therefore, this YANG module will change in incompatible ways
				from its current revision to the formally published YANG
				module for IEEE 1906.1.1 Standard Data Model for Nanoscale
				Communication Systems.

				This is the YANG model for the IEEE 1906.1-2015 - Recommended
                Practice for Nanoscale and Molecular Communication Framework.
                Clause 5 - Framework of a molecular and nanoscale communication
                network

                This YANG module is committed to providing a 'flat' description
                of a nanoscale system. A nanoscale system is comprised of a set
                (a list) of components.";

  revision 2020-02-14
  {
    description "Initial version.";

	reference "[1] 'IEEE Recommended Practice for Nanoscale and Molecular
	                Communication Framework,' in IEEE Std 1906.1-2015, pp.1-64,
	                Jan. 11 2016 doi: 10.1109/IEEESTD.2016.7378262

			   [2] S. F. Bush, 'Active network architecture' in Nanoscale
			       Communication Networks, pp. 209-217, 2010, Artech House.

			   [3] S. F. Bush, J. L. Paluh, G. Piro, V. Rao, R. V. Prasad and
			       A. Eckford, 'Defining Communication at the Bottom,' in IEEE
			       Transactions on Molecular, Biological and Multi-Scale
			       Communications, vol. 1, no. 1, pp. 90-96, March 2015.
			       doi: 10.1109/TMBMC.2015.2465513

			   [4] K. Kyoda, Y. Tohsato, K. H. L. Ho and S. Onami, 'Biological
			       Dynamics Markup Language (BDML): an open format for
			       representing quantitative biological dynamics data,' in
			       Oxford University Press, Bioinformatics, pp. 1044-1052,
			       2015. doi: 10.1093/bioinformatics/btu767";
  }

  container nanoscale-system
  {
    description "As defined in IEEE 1906.1-2015.";

    leaf identifier
    {
      type types:urn;
      mandatory true;
      description "Identifies the system to make it a resource available
                   online.";
    }

    leaf title
    {
      type string;
      description "A short, optional title for this nanoscale system. May be
                   the name of the research tool or product.";
    }

    leaf-list organization
    {
      type string;
      description 	"The name of the vendor or the authority providing research
					organization providing this tool.";
    }

    leaf-list contact
    {
      type string;
      description 	"List of contact names. It is recommended to append the
					email address of the contact as well.";
    }

    leaf description
    {
      type string;
      description 	"An optional leaf describing what this nanoscale communication
					system is intended to do.";
    }

    leaf version
    {
      type string;
      default "1.0";
      description 	"The version number of this system. No pattern control for
					this leaf is defined. Simple numbering or a date and time,
					or a mix of both may be used.";
    }

    leaf license
    {
      type string;
      description "The name of the license governing rights to this system.";
    }

	  //
    // Definitions and their relationship to component need to be clarified in
    // future versions.
    //
    // By definition we mean here, transmitter, receiver, medium, message.
    // They may also require a specific set of metrics as well.
    // Then, there is also the non-standard physics, some properties as well
    // etc.
    //
    container definitions
    {

    }

    container components
    {
      list component
      {
        key identifier;
        uses components:component;
        description "A list of components that may be augmented.";
      }

      description 	"This containers stores the list of components that are part
					of the system.";
    }

    list-leaf child-node
    {
      type types:urn;
      description 	"Identifies the list of child nodes that are direct parts of
					the system. A child node may be a definition or a component.

					A child node may point to an online resource that is not
					defined by this system. However, this practice is
					discouraged.

					This list-leaf is optional. There may be zero or more child
					nodes and child components can be of any type defined by,
					or inheriting from, ieee-1906-dot1-types.yang.

					For example, a nanoscale interface may be comprised of a
					transmitter and a receiver child nodes, and a transmitter
					may be comprised of a perturbation and a field
					child-nodes while the receiver is made of a specificity
					child-node.";
    }

    uses metrics:system-metrics;
  }
}
