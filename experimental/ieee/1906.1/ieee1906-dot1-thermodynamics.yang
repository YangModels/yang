module ieee-1906-dot1-thermodynamics
{
  yang-version 1.1;
  namespace "urn:ieee:std:1906.1:yang:ieee-1906-dot1-thermodynamics";
  prefix "ieee-1906-dot1-thermodynamics";

  import ieee-1906-dot1-math {  prefix ieee-1906-dot1-math;  }
  import ieee-1906-dot1-function {  prefix ieee-1906-dot1-function;  }
  import ieee-1906-dot1-si-units {  prefix ieee-1906-dot1-si-units;  }

  organization "P1906.1.1/D1.0 Draft Standard Data Model for Nanoscale Communication Systems Working Group";

  contact  "IEEE P1906.1.1 Working Group
			Chair: Stephen F. Bush <bushsf@research.ge.com>
			Secretary: Guillaume Mantelet <guillaume.mantelet@ge.com>";

  description 	"This experimental YANG module is an individual contribution, and
			    does not represent a formally sanctioned YANG module by IEEE.
				Therefore, this YANG module will change in incompatible ways
				from its current revision to the formally published YANG
				module for IEEE 1906.1.1 Standard Data Model for Nanoscale 
				Communication Systems.
				
				These are intended to be units used primarly in thermodynamics:
				+----------------------+----+------------+---------------------------------------+
				| name                 |symb| units      | equation                              |
				+----------------------+----+------------+---------------------------------------+
				| flow-velocity        |  v | m.s-1      |                                       |
				| mass-flow-rate       |mdot| kg.s-1     | mdot = rho.Q = rho.v.A = jm.A         |
				| mass-flux            | jm | kg.s-1.m-2 | jm = rho.v                            |
				| volumetric-flow-rate |  Q | m3.s-1     | Q = v.A                               |
				+----------------------+----+------------+---------------------------------------+";

  revision 2020-02-14
  {
    description "Initial version.";
	reference "IEEE 1906.1-2015 Clause 5.2 (b) 2.";
  }

  typedef diffusion-coefficient
  {
	type ieee-1906-dot1-function:variable;
	units meter^2.second-1;
	description "Diffusivity or diffusion coefficient is a proportionality
	            constant between the molar flux due to molecular diffusion
	            and the gradient in the concentration of the species (or the
	            driving force for diffusion).";
  }

  grouping flow-velocity
  {
    uses ieee-1906-dot1-math:vector;
    ieee-1906-dot1-si-units:units meter/second;
    description "The flow velocity of the mass of message carriers.";
  }

  // Note: Can we remove this comment?
  //grouping mass-flux
  //{
  //  ieee-1906-dot1-math:equation mass-flux
  //  {
  //    ieee-1906-dot1-math:symbol jm;
  //    ieee-1906-dot1-math:value;
  //    units "kilogram second^-1 meter^-2";
  //
  //    ieee-1906-dot1-math:expression
  //    {
  //      leaf density
  //      {
  //        ieee-1906-dot1-math:symbol rho;
  //        type ieee-1906-dot1-si-units:mass-density;
  //        description "The mass density of the fluid";
  //      }
  //      uses flow-velocity;
  //    }
  //  }
  //
  //  description "A reusable mass flux equation.";
  //}

  typedef mass-flux
  {
    type ieee-1906-dot1-function:variable;
    units "kilogram second^-1 meter^-2";
    description "A reusable mass flux equation.";
  }

  grouping volumetric-flow-rate
  {
    ieee-1906-dot1-math:equation volumetric-flow-rate
    {
      ieee-1906-dot1-math:symbol "Vdot Q";
      ieee-1906-dot1-math:value;
      units "meter^3 second^-1";

      ieee-1906-dot1-math:expression
      {
        uses flow-velocity;
        uses ieee-1906-dot1-math:vector-area;
      }

      description	"Volume of fluid which passes per unit time. The volume flow rate of the
					message carrier. The volume of fluid which passes per unit time; usually 
					represented by the symbols Vdot or Q.";
    }

    description "A volumetric flow rate equation.";
  }


  grouping mass-flow-rate
  {
    ieee-1906-dot1-math:equation mass-flow-rate
    {
      ieee-1906-dot1-math:symbol mdot;
      ieee-1906-dot1-math:value;
      units kilogram.second-1;

      ieee-1906-dot1-math:expression
      {
        leaf density
        {
          ieee-1906-dot1-math:symbol rho;
          type ieee-1906-dot1-si-units:mass-density;
          description "A mass density.";
        }
        uses volumetric-flow-rate;
      }

      ieee-1906-dot1-math:expression
      {
        leaf density
        {
          ieee-1906-dot1-math:symbol rho;
          type ieee-1906-dot1-si-units:mass-density;
          description "A mass density.";
        }
        uses flow-velocity;
        uses ieee-1906-dot1-math:vector-area;
      }

      ieee-1906-dot1-math:expression
      {
        uses mass-flux;
        uses ieee-1906-dot1-math:vector-area;
      }
    }

    description "A reusable mass flow rate equation.";
  }
}
