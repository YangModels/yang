module ieee1906-dot1-components
{
  yang-version 1.1;
  namespace "urn:ieee:std:1906.1:yang:ieee1906-dot1-components";
  prefix "ieee1906-components";

  import ietf-interfaces { prefix if; }
  import ieee1906-dot1-types { prefix ieee1906-dot1-types; }
  import ieee1906-dot1-metrics { prefix ieee1906-dot1-metrics; }

  organization "P1906.1.1/D1.0 Draft Standard Data Model for Nanoscale Communication Systems Working Group";

  contact 	"IEEE P1906.1.1 Working Group
			Chair: Stephen F. Bush <bushsf@research.ge.com>
			Secretary: Guillaume Mantelet <guillaume.mantelet@ge.com>";

  description	"This experimental YANG module is an individual contribution, and
				does not represent a formally sanctioned YANG module by IEEE.
				Therefore, this YANG module will change in incompatible ways
				from its current revision to the formally published YANG
				module for IEEE 1906.1.1 Standard Data Model for Nanoscale
				Communication Systems.

				This is the YANG model for the IEEE 1906.1-2015 - Recommended
                Practice for Nanoscale and Molecular Communication Framework.
                Clause 5 - Framework of a molecular and nanoscale communication
                network.

				This module defines components, the system, and unsolicited notications.";

  revision 2020-02-14
  {
    description "Initial version.";

	reference	"[1] P1906.1.1/D1.0 Draft Standard for Nanoscale and Molecular
					 Communication Framework.

				 [2] 'IEEE Recommended Practice for Nanoscale and Molecular
				 	 Communication Framework,' in IEEE Std 1906.1-2015, pp.1-64,
					 Jan. 11 2016 doi: 10.1109/IEEESTD.2016.7378262.

				 [3] S. F. Bush, 'Active network architecture' in Nanoscale
					 Communication Networks, pp. 209-217, 2010, Artech House.

				 [4] S. F. Bush, J. L. Paluh, G. Piro, V. Rao, R. V. Prasad and
					 A. Eckford, 'Defining Communication at the Bottom,' in IEEE
					 Transactions on Molecular, Biological and Multi-Scale
					 Communications, vol. 1, no. 1, pp. 90-96, March 2015.
					 doi: 10.1109/TMBMC.2015.2465513.";
  }

  grouping component
  {
    list component
    {
      key identifier;

      leaf name
      {
        type string;
        description "An optional name that describes the IEEE 1906.1-2015 component
					in the nanoscale implementation or simulation.

                    For example, a neuron model conforming to the  IEEE 1906.1-2015
                    framework could use 'axon' as a name for one of its components.";
      }

      leaf identifier
      {
        type string;
        description "An optional string that describes the IEEE 1906.1-2015 component
					in the nanoscale implementation or simulation.

                    For example, a neuron model conforming to the IEEE 1906.1-2015
                    framework could specify what this 'axon' is intended to do in
					its corresponding model.";
      }

      leaf type-of-component
      {
         type identityref { base 'ieee1906-dot1-types:component'; }
         mandatory true;
         description	"Identifies the IEEE 1906.1-2015 component extended in this model.

                        For example, a neurotransmitter can be considered a 'message-carrier'.
						This leaf automatically selects the correct type of metric to display.

						See the following list of 'uses'. The underlying Metrics define a 'when'
						statement making them valid and usable if the type-of-components matches
						them.";
      }

      uses ieee1906-dot1-metrics:message-metrics;
      uses ieee1906-dot1-metrics:motion-metrics;
      uses ieee1906-dot1-metrics:field-metrics;
      uses ieee1906-dot1-metrics:specificity-metrics;

      description	"A list of IEEE 1906.1-2015 compatible objects.";
    }

    description	"This is the main grouping for the IEEE 1906.1-2015 framework. This relates any
				conceptual object to a 'component' and provides access to the corresponding metrics
				and configuration data.";
  }


  grouping nanoscale-system
  {
    container nanoscale-system
    {
      if-feature ieee1906-dot1-types:nanoscale-communication;

      leaf name
      {
        type string;
        description	"An optional name to describe the IEEE 1906.1-2015 component extended in this model.

                    For example, a neuron model reusing 1906.1 framework could use 'axon' as a name for
					one of its components.";
      }

      leaf identifier
      {
        type string;
        description	"A unique identifier for this component to be extended in the model.

                    For example, a neuronal axon may be comprised of multiple sections.
					Each section should be uniquely identified by the underlying model to
					store statistics or retrieve configuration, simulate a fault, etc.";
      }

      uses component;
      uses ieee1906-dot1-metrics:system-metrics;

      description	"Describes a compound object storing a list of IEEE 1906.1-2015
					components.";
    }

    description	"Use this grouping when you want to define a system storing a system
				storing... and so on recursively.

                Cyclic reference is prohibited by YANG. This is why a component cannot
				'uses' a component. We use a compound definition instead.";
  }

  augment "/if:interfaces/if:interface"
  {
    uses nanoscale-system { when "if:type = 'ieee1906-dot1-types:nanoscale-communication-interface'"; }
    description	"Addition of data nodes for the nanoscale communication interface to the
                standard Interface data model, for interfaces of the type 'nanoscale-communication-interface'.";
  }










}
