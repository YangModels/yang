module ieee1906-dot1-types
{
  yang-version 1.1;
  namespace "urn:ieee:std:1906.1:yang:ieee1906-dot1-types";
  prefix "ieee1906-types";

  import iana-if-type { prefix ianaift; }

  organization "P1906.1.1/D1.0 Draft Standard Data Model for Nanoscale Communication Systems Working Group";

  contact 	"IEEE P1906.1.1 Working Group
			Chair: Stephen F. Bush <bushsf@research.ge.com>
			Secretary: Guillaume Mantelet <guillaume.mantelet@ge.com>";

  description  "This experimental YANG module is an individual contribution, and
				does not represent a formally sanctioned YANG module by IEEE.
				Therefore, this YANG module will change in incompatible ways
				from its current revision to the formally published YANG
				module for IEEE 1906.1.1 Standard Data Model for Nanoscale
				Communication Systems.

				This is the YANG model for the IEEE 1906.1-2015 - Recommended
                Practice for Nanoscale and Molecular Communication Framework.
                Clause 5 - Framework of a molecular and nanoscale communication
                network:
                +---------------------+-----------------------------------+
                | Component name      | Type of component                 |
                +---------------------+-----------------------------------+
                | iana-interface-type | nanoscale-communication-interface |
                +---------------------+-----------------------------------+
                | message-carrier     | bacterium                         |
                |                     | calcium-ion                       |
                |                     | charge                            |
                |                     | electromagnetic-wave              |
                |                     | ligand                            |
                |                     | motor                             |
                | motion              | diffusion                         |
                |                     | motion-type                       |
                |                     | potential-difference              |
                |                     | walking                           |
                |                     | wave-guided                       |
                | field               | compartmentalized                 |
                |                     | concentration-gradient            |
                |                     | directional-antenna               |
                |                     | microtubule                       |
                |                     | nanostructure-orientation         |
                | perturbation        | concentration-change              |
                |                     | electrical-current-variation      |
                |                     | electromagnetic-wave-variation    |
                |                     | molecular-structure               |
                |                     | transmission-rate                 |
                | specificity-type    | antenna-aperture                  |
                |                     | receptor-sensitivity              |
                |                     | electrical-charge                 |
                +---------------------+-----------------------------------+

                NOTE: The following 1906 definitions are not included in this
                      framework. As the framework ultimately augments IETF
                      interface model, the following 'classical' definitions
                      can be handled by the corresponding ietf nodes:
                +---------------------+-----------------------------------+
                | transmitter         |                                   |
                | receiver            |                                   |
                | medium              |                                   |
                | message             |                                   |
                +---------------------+-----------------------------------+";

  revision 2020-02-14
  {
    description "Initial version.";

	reference "[1] 'IEEE Recommended Practice for Nanoscale and Molecular
	                Communication Framework,' in IEEE Std 1906.1-2015, pp.1-64,
	                Jan. 11 2016 doi: 10.1109/IEEESTD.2016.7378262

			   [2] S. F. Bush, 'Active network architecture' in Nanoscale
			       Communication Networks, pp. 209-217, 2010, Artech House.

			   [3] S. F. Bush, J. L. Paluh, G. Piro, V. Rao, R. V. Prasad and
			       A. Eckford, 'Defining Communication at the Bottom,' in IEEE
			       Transactions on Molecular, Biological and Multi-Scale
			       Communications, vol. 1, no. 1, pp. 90-96, March 2015.
			       doi: 10.1109/TMBMC.2015.2465513";
  }

  feature nanoscale-communication {
    description "This feature means that the server describes a system that
        supports at least an interface, an experiment, a model or a system
        that is compliant with the IEEE Std. 1906.1-2015 model";
  }

  // Note: pyang does not like the negative lookahead in this pattern.
  // And maybe many other things. This regex works with pythex, negative lookahead seems to be right on tutorials etc.
  typedef urn
  {
    type string {
      pattern "[uU][rR][nN]:"; //[uU][rR][nN]:(?![uU][rR][nN]:)[a-zA-Z0-9][a-zA-Z0-9-]{1,31}:(?:[a-zA-Z0-9()+,-.:=@;$_!*'%/?#]|%([2][1-9a-fA-F]|[3-9a-fA-F][0-9a-fA-F]))+";
    }
    description "Describes a Uniform Resource Name";
  }


  //=============================================================================================
  //
  //                                     IANA INTERFACE TYPE
  //
  //=============================================================================================
  //identity nanoscale-communication-interface
  //{
  //  base ianaift:ieee19061nanocom ;
  //  description "Interface identity for a nanoscale communication interface.
//
//				The following entry is in the ifType and transmission number registries:
//				Decimal: 299
//				Name: ieee19061nanocom
//				Description: Nanoscale and Molecular Communication
//				Reference: [IEEE 1906.1-2015]
//				Please see
//				https://www.iana.org/assignments/smi-numbers
//				and the corresponding MIB and YANG modules:
//				https://www.iana.org/assignments/ianaiftype-mib
//				https://www.iana.org/assignments/yang-parameters";
//  }


  //=============================================================================================
  //
  //                                       COMPONENT TYPES
  //
  //=============================================================================================
  identity component
  {
    description "A required element of the IEEE 1906.1-2015 framework that
				provides a service for nanoscale communication.

                This model allows for flexibility and reconfigurability and
                does not assume anything about the 'topology' or the way your
                biolgoical or nanoscale model is defined AS LONG AS you link
				each element of your model to the corresponding type of component
                listed in this module to access to their corresponding
                metrics.

                To use the framework, each of the components of your module
                SHALL have a leaf entitled 'type-of-component' of type
                'identityref' which SHALL have for its base this 'component' base
                identity.

                For example:

                list neuron-elements
                {
                  key 'identifier';
                  leaf name
                  {
                    type string;
                    description 'Acts as a type in our model. Like soma, synapse etc.';
                  }

                  leaf identifier
                  {
                    type string;
                    description 'Acts as an identifier in our model. Like SOMA_00_01 etc.';
                  }

                  leaf type-of-component
                  {
                    type identityref { base 'ieee1906-types:component' };
                  }

                  uses ieee1906-metrics:message-carrier;
                }

                will generate:
                <neuron-elements>
                  <name>bdnf</name>
                  <type-of-component>message-carrier</type-of-component>
                  <message-metrics>
                   <message-deliverability>0.92</message-deliverability>
                    ...
                  </message-metrics>
                </neuron-elements>

                As a valid XML output.";

    reference "IEEE 1906.1-2015 Clause 5.2";
  }

  identity message-carrier
  {
    base component;
    description "The message carrier provides the service of transporting the
                 message.";
	reference "IEEE 1906.1-2015 Clause 5.2 (a)";
  }

  identity motion
  {
    base component;
    description "Defines the movement capability for Message Carrier.";
	reference "IEEE 1906.1-2015 Clause 5.2 (b)";
  }

  identity field
  {
    base component;
    description "Defines organized movement of Motion.";
	reference "IEEE 1906.1-2015 Clause 5.2 (c)";
  }

  identity perturbation
  {
    base component;
    description "Defines the signal transported by Message Carrier.";
	reference "IEEE 1906.1-2015 Clause 5.2 (d)";
  }

  identity specificity
  {
    base component;
    description "Defines targeted reception of Perturbation.";
	reference "IEEE 1906.1-2015 Clause 5.2 (e)";
  }


  //=============================================================================================
  //
  //                                    MESSAGE CARRIER TYPES
  //
  //=============================================================================================
  identity message-carrier-type
  {
    description "Base type describing the type of IEEE 19006.1-2015 message carrier.";
    base component;
  }

  identity calcium-ion
  {
    base message-carrier-type;
    description "Calcium ion.";
  }

  identity ligand
  {
    base message-carrier-type;
    description "Ligand-receptor.";
  }

  identity motor
  {
    base message-carrier-type;
    description "Molecular motor.";
  }

  identity charge
  {
    base message-carrier-type;
    description "Electric charge.";
  }

  identity bacterium
  {
    base message-carrier-type;
    description "Bacterium.";
  }

  identity electromagnetic-wave
  {
    base message-carrier-type;
    description "Electromagnetic wave.";
  }


  //=============================================================================================
  //
  //                                         MOTION TYPES
  //
  //=============================================================================================
  identity motion-type
  {
    description "Base identity for IEEE 19006.1-2015 motion types.";
    base component;
  }

  identity diffusion
  {
    base motion-type;
    description "Diffusion.";
  }

  identity walking
  {
    base motion-type;
    description "Walking.";
  }

  identity potential-difference
  {
    base motion-type;
    description "Electrical potential difference.";
  }

  identity wave-guided
  {
    base motion-type;
    description "Follows a wave guide.";
  }


  //=============================================================================================
  //
  //                                         FIELD TYPES
  //
  //=============================================================================================
  identity field-type
  {
    description "Base identity for IEEE 19006.1-2015 field types.";
    base component;
  }

  identity concentration-gradient
  {
    base field-type;
    description "Concentration gradient.";
  }

  identity compartmentalized
  {
    base field-type;
    description "Use of compartments to hold or direct nanoscale message flow.";
  }

  identity microtubule
  {
    base field-type;
    description "Microtubules.";
  }

  identity nanostructure-orientation
  {
    base field-type;
    description "Nanostructure orientation, e.g. nanotube orientation.
				Note: This seems redundant with microtubule? Or microtubule is a more specific implementation of this type?";
  }

  identity directional-antenna
  {
    base field-type;
    description "Directional antenna.";
  }


  //=============================================================================================
  //
  //                                      PERTURBATION TYPES
  //
  //=============================================================================================
  identity perturbation-type
  {
    description "Base identity for IEEE 19006.1-2015 perturbation types.";
    base component;
  }

  identity transmission-rate
  {
    base perturbation-type;
    description "Transmission rate is varied to create bits?
				Note: Isn't this the same asa concentration-change?";
  }

  identity concentration-change
  {
    base perturbation-type;
    description "Concentration is varied to create bits.";
  }

  identity molecular-structure
  {
    base perturbation-type;
    description "Molecular structure is changed to represent bits.";
  }

  identity electric-current-variation
  {
    base perturbation-type;
    description "Electric current is varied to create bits.";
  }

  identity electromagnetic-wave-variation
  {
    base perturbation-type;
    description "The electromagnetic wave is varied to create bits.";
  }


  //=============================================================================================
  //
  //                                      SPECIFICITY TYPES
  //
  //=============================================================================================
  identity specificity-type
  {
    description "Base identity for IEEE 19006.1-2015 specificity types.";
    base component;
  }

  identity receptor-sensitivity
  {
    base specificity-type;
    description "A biological receptor threshold range. Typically in units of concentration.";
  }

  identity electric-charge
  {
    base specificity-type;
    description "Electric charge or voltage threshold range. Typically in units of coulomb, amperes, or voltage.";
  }

  identity antenna-aperture
  {
    base specificity-type;
    description "Antenna aperture and orientation thresholds range. Typically in units of area and angle.";
  }

  identity frequency-tuning
  {
    base specificity-type;
    description "Specific (center) frequency threshold range. Typically in units of hertz.";
  }
}
