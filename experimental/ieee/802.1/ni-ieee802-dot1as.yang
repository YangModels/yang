module ni-ieee802-dot1as {
  yang-version 1.1;
  namespace "http://ni.com/ns/yang/ni-ieee802-dot1as";
  prefix "dot1as";

  import ietf-yang-types {
    prefix yang;
  }
  import ni-ieee1588-ptp {
    prefix ptp;
  }
  
  organization "National Instruments";
  contact
    "Rodney Cummings
     National Instruments
     11500 N. Mopac Expwy
     Bldg. C
     Austin, TX 78759-3504
     Email: Rodney.Cummings@ni.com";
  description
    "This YANG module defines a data model for the configuration
     and state of IEEE Std 802.1AS clocks. 
     IEEE Std 802.1AS is a profile of IEEE Std 1588, which means
     that it specifies additional requirements and features, but
     uses 1588 as its foundation. Therefore, this YANG module
     for 1588 is designed as augments to the YANG module for 1588.";

  revision "2018-08-24" {
    description 
      "This revision is an experimental contribution, 
       made under the following assumptions:
       A. This module is intended as input to a future project in the
         IEEE 802.1 Working Group, to specify YANG for the data sets
         (information model) of IEEE Std 802.1AS-2019.
       B. Once an 802.1 project exists (i.e. PAR approved), and a draft
         YANG module for that project is uploaded to GitHub
         (e.g. /standard/ieee/802.1/draft/ieee802-dot1as.yang),
         this experimental module will be removed soon after.
       C. This module is not intended for use in a shipping project.
      
       This experimental YANG module does not represent a formally
       sanctioned YANG module of IEEE. Therefore, this YANG module
       will change in incompatible ways from its current revision 
       to the formally published YANG module for IEEE Std 802.1AS.
       Since it is not possible to prevent use of this module in a
       shipping product, the module name and module namespace are
       both defined as vendor-specific, using the affiliated company
       of the editor. This helps to avoid naming collisions with
       the future YANG module specified as part of 
       IEEE Std 802.1AS.";
    reference 
      "To be replaced with first IEEE 802.1AS standard that
       contains a YANG module. Such a project is anticipated
       to begin after IEEE RevCom approval of
       IEEE Std 802.1AS-2019.";
  }

  typedef scaled-ns-type {
    type binary {
      length "12";
    }
    description
      "The IEEE Std 802.1AS ScaledNs type represents
       signed values of time and time interval in units
       of 2^16 ns.
       YANG does not support a signed 96-bit integer,
       so this type is represented as 12 octets of
       binary data.";
    reference
      "IEEE Std 802.1AS-2019: 6.4.3.1";
  }
  
  typedef uscaled-ns-type {
    type binary {
      length "12";
    }
    description
      "The IEEE Std 802.1AS ScaledNs type represents
       unsigned values of time and time interval in units
       of 2^16 ns.
       YANG does not support an unsigned 96-bit integer,
       so this type is represented as 12 octets of
       binary data.";
    reference
      "IEEE Std 802.1AS-2019: 6.4.3.2";
  }
  
  typedef float64-type {
    type binary {
      length "8";
    }
    description
      "The IEEE Std 802.1AS Float64 type represents
       IEEE Std 754 binary64 (64-bit
       double-precision floating-point format).
       YANG does not support floating-point,
       so this type is represented as 8 octets of
       binary data.";
    reference
      "IEEE Std 802.1AS-2019: 6.4.2";
  }
  
  typedef system-time-type {
    type uint32;
    description
      "System time represented as an unsigned
       32-bit integer in units of 10 milliseconds.";
    reference
      "IEEE Std 802.1AS-2019: 14.3.10";
  }
  
  augment "/ptp:ptp/ptp:instance-list/ptp:default-ds" {
    description
      "Augment IEEE Std 1588 defaultDS.";
    
    leaf gm-capable {
      type boolean;
      config false;
      description
        "The value is true if the time-aware system is capable
         of being a grandmaster, and false if the time-aware
         system is not capable of being a grandmaster.";
      reference
        "IEEE Std 802.1AS-2019: 14.2.6";
    }
    
    leaf current-utc-offset-valid {
      type boolean;
      description
        "The value of current-utc-offset-valid shall be true
         if the values of current-utc-offset, leap59, and leap61
         are known to be correct, otherwise it shall be false.
         NOTE - The constraint for leap59 and leap61 did not 
         exist in IEEE Std 1588-2008, and for compatibility, 
         corresponding YANG when statements are not included
         for those leafs.";
      reference
        "IEEE Std 1588-2019: 14.2.8";
    }
    
    leaf current-utc-offset {
      when "../current-utc-offset-valid='true'";
      type int16;
      description
        "Specified as <dLS> in IERS Bulletin C, this provides
         the offset from UTC (TAI - UTC).
         The offset is in units of seconds.
         This leaf applies to the ClockMaster entity 
         (i.e., local only, unrelated to a remote GM).";
      reference
        "IEEE Std 1588-2019: 14.2.7";
    }    
 
    leaf leap59 {
      type boolean;
      description
        "If the timescale is PTP, a true value for leap59
         shall indicate that the last minute of the
         current UTC day contains 59 seconds.
         If the timescale is not PTP, the value shall be 
         false.
         This leaf applies to the ClockMaster entity 
         (i.e., local only, unrelated to a remote GM).";
      reference
        "IEEE Std 1588-2019: 14.2.9";
    }
 
    leaf leap61 {
      type boolean;
      description
        "If the timescale is PTP, a true value for leap61
         shall indicate that the last minute of the
         current UTC day contains 61 seconds.
         If the timescale is not PTP, the value shall be 
         false.
         This leaf applies to the ClockMaster entity 
         (i.e., local only, unrelated to a remote GM).";
     reference
       "IEEE Std 1588-2019: 14.2.10";
    }
 
    leaf time-traceable {
      type boolean;
      description
        "The value of time-traceable shall be true if the 
         timescale is traceable to a primary reference;
         otherwise, the value shall be false.
         This leaf applies to the ClockMaster entity 
         (i.e., local only, unrelated to a remote GM).";
      reference
        "IEEE Std 1588-2019: 14.2.11";
    }
 
    leaf frequency-traceable {
      type boolean;
      description
        "The value of time-traceable shall be true if the 
         frequency determining the timescale is traceable 
         to a primary reference; otherwise, the value shall
         be false.
         This leaf applies to the ClockMaster entity 
         (i.e., local only, unrelated to a remote GM).";
     reference
       "IEEE Std 1588-2019: 14.2.12";
    }
 
    leaf ptp-timescale {
      type boolean;
      description
        "If ptp-timescale is true, the timescale of
         the ClockMaster entity is PTP, which is
         the elapsed time since the PTP epoch measured 
         using the second defined by International Atomic 
         Time (TAI).
         If ptp-timescale is false, the timescale of
         the ClockMaster entity is ARB, which is
         the elapsed time since an arbitrary epoch.
         This leaf is local only, unrelated to a remote GM).";
      reference
        "IEEE Std 1588-2019: 14.2.13";
    }
 
    leaf time-source {
      type uint8;
      description
        "The source of time used by the ClockMaster entity
        This leaf is local only, unrelated to a remote GM).";
      reference
        "IEEE Std 1588-2019: 14.2.14";
    }
  }
  
  augment "/ptp:ptp/ptp:instance-list/ptp:current-ds" {
    description
      "Augment IEEE Std 1588 currentDS.";
    
    leaf last-gm-phase-change {
      type scaled-ns-type;
      config false;
      description
        "Phase change that occurred on the most recent
         change in either grandmaster or gm-timebase-indicator.";
      reference
        "IEEE Std 802.1AS-2019: 10.2.4.16, 14.3.3";
    }
    
    leaf last-gm-freq-change {
      type float64-type;
      config false;
      description
        "Frequency change that occurred on the most recent
         change in either grandmaster or gm-timebase-indicator.";
      reference
        "IEEE Std 802.1AS-2019: 10.2.4.17, 14.3.4";
    }
    
    leaf gm-timebase-indicator {
      type uint16;
      config false;
      description
        "The timeBaseIndicator of the current grandmaster.";
      reference
        "IEEE Std 802.1AS-2019: 9.2.2.3, 14.3.5";
    }
    
    leaf gm-change-count {
      type uint32;
      config false;
      description
        "This statistics counter tracks the number of times
         the grandmaster has changed in a gPTP domain.";
      reference
        "IEEE Std 802.1AS-2019: 14.3.6";
    }
    
    leaf time-of-last-gm-change {
      type system-time-type;
      config false;
      description
        "System time when the most recent grandmaster change 
         occurred in a gPTP domain.";
      reference
        "IEEE Std 802.1AS-2019: 14.3.7";
    }
    
    leaf time-of-last-phase-change {
      type system-time-type;
      config false;
      description
        "System time when the most recent change in grandmaster
         phase occurred, due to a change of either the grandmaster
         or the grandmaster time base.";
      reference
        "IEEE Std 802.1AS-2019: 14.3.8";
    }
    
    leaf time-of-last-freq-change {
      type system-time-type;
      config false;
      description
        "System time when the most recent change in grandmaster
        frequency occurred, due to a change of either the grandmaster
        or the grandmaster time base.";
      reference
        "IEEE Std 802.1AS-2019: 14.3.9";
    }
  }
  
  augment "/ptp:ptp/ptp:instance-list/ptp:parent-ds" {
    description
      "Augment IEEE Std 1588 parentDS.";
    
    leaf cumulative-rate-ratio {
      type int32;
      config false;
      description
        "Estimate of the ratio of the frequency of the grandmaster
         to the frequency of the LocalClock entity of this
         time-aware system. cumulative-rate-ratio is expressed as
         the fractional frequency offset multiplied by 2^41, 
         i.e., the quantity (rateRatio – 1.0)(2^41).";
      reference
        "IEEE Std 802.1AS-2019: 14.4.2";
    }
  }
  
  augment "/ptp:ptp/ptp:instance-list/ptp:port-ds-list" {
    description
      "Augment IEEE Std 1588 portDS.";
    
    leaf ptp-port-enabled {
      type leafref {
        path "/ptp:ptp/ptp:instance-list/ptp:port-ds-list/ptp:port-enable";
      }
      description
        "Boolean that is administratively set to true if time 
         synchronization is to be enabled on this port.
         This leaf is semantically equivalent to the 
         IEEE Std 1588 data set member portEnable.";
      reference
        "IEEE Std 802.1AS-2019: 10.2.5.13, 14.8.4";
    }
    
    leaf is-measuring-delay {
      type boolean;
      config false;
      description
        "Boolean that is true if the port is measuring link 
         propagation delay.";
      reference
        "IEEE Std 802.1AS-2019: 11.2.13.6, 14.8.6";
    }
    
    leaf as-capable {
      type boolean;
      config false;
      description
        "Boolean that is true if and only if it is determined
         that this time-aware system and the time-aware system
         at the other end of the link attached to this port
         can interoperate with each other via the IEEE Std 
         802.1AS protocol.";
      reference
        "IEEE Std 802.1AS-2019: 10.2.5.1, 14.8.7";
    }
    
    leaf mean-link-delay-thresh {
      type ptp:time-interval-type;
      description
        "Propagation time threshold for mean-link-delay, 
         above which a port is not considered capable of
         participating in the IEEE Std 802.1AS protocol.";
      reference
        "IEEE Std 1588-2019: 14.8.9";
    }
    
    leaf neighbor-rate-ratio {
      type int32;
      config false;
      description
        "Estimate of the ratio of the frequency of the LocalClock
         entity of the time-aware system at the other end of the
         link attached to this port, to the frequency of the 
         LocalClock entity of this time-aware system.
         neighbor-rate-ratio is expressed as the fractional
         frequency offset multiplied by 2^41, 
         i.e., the quantity (rateRatio – 1.0)(2^41).";
      reference
        "IEEE Std 802.1AS-2019: 14.8.11";
    }

    leaf initial-log-announce-interval {
      type int8;
      description
        "When use-mgt-log-announce-interval is false
         (i.e., change with Signaling message), this is the
         the logarithm to base 2 of the announce
         interval used when the port is initialized.";
      reference
        "IEEE Std 802.1AS-2019: 14.8.12";
    }

    leaf current-log-announce-interval {
      type int8;
      config false;
      description
        "Current logarithm to base 2 of the announce
         interval.";
      reference
        "IEEE Std 802.1AS-2019: 14.8.13";
    }

    leaf use-mgt-log-announce-interval {
      type boolean;
      description
        "Boolean that determines the source of the 
         announce interval.
         If the value is true, the announce interval
         (current-log-announce-interval) is set equal to the value
         of mgt-log-announce-interval.
         If the value is false, the announce interval is determined
         by the AnnounceIntervalSetting state machine (i.e., changed
         with Signaling message).";
      reference
        "IEEE Std 802.1AS-2019: 14.8.14";
    }
    
    leaf mgt-log-announce-interval {
      type leafref {
        path "/ptp:ptp/ptp:instance-list/ptp:port-ds-list/ptp:log-announce-interval";
      }
      description
        "Logarithm to base 2 of the announce interval, used if 
         use-mgt-log-announce-interval is true. This value is not 
         used if use-mgt-log-announce-interval is false.
         This leaf is semantically equivalent to the 
         IEEE Std 1588 data set member logAnnounceInterval.";
      reference
        "IEEE Std 802.1AS-2019: 14.8.15";
    }
    
    leaf initial-log-sync-interval {
      type int8;
      description
        "When use-mgt-log-sync-interval is false
         (i.e., change with Signaling message), this is the
         the logarithm to base 2 of the sync
         interval used when the port is initialized.";
      reference
        "IEEE Std 802.1AS-2019: 14.8.17";
    }

    leaf current-log-sync-interval {
      type int8;
      config false;
      description
        "Current logarithm to base 2 of the sync
         interval.";
      reference
        "IEEE Std 802.1AS-2019: 14.8.18";
    }

    leaf use-mgt-log-sync-interval {
      type boolean;
      description
        "Boolean that determines the source of the 
         sync interval.
         If the value is true, the sync interval
         (current-log-sync-interval) is set equal to the value
         of mgt-log-sync-interval.
         If the value is false, the sync interval is determined
         by the SyncIntervalSetting state machine (i.e., changed
         with Signaling message).";
      reference
        "IEEE Std 802.1AS-2019: 14.8.19";
    }
    
    leaf mgt-log-sync-interval {
      type leafref {
        path "/ptp:ptp/ptp:instance-list/ptp:port-ds-list/ptp:log-sync-interval";
      }
      description
        "Logarithm to base 2 of the sync interval, used if 
         use-mgt-log-sync-interval is true. This value is not 
         used if use-mgt-log-sync-interval is false.
         This leaf is semantically equivalent to the 
         IEEE Std 1588 data set member logSyncInterval.";
      reference
        "IEEE Std 802.1AS-2019: 14.8.20";
    }
    
    leaf sync-receipt-timeout {
      type uint8;
      description
        "Number of sync intervals that a slave port waits without
         receiving synchronization information, before assuming
         that the master is no longer transmitting synchronization
         information and that the BMCA needs to be run, 
         if appropriate.";
      reference
        "IEEE Std 802.1AS-2019: 14.8.21";
    }
 
    leaf sync-receipt-timeout-interval {
      type uscaled-ns-type;
      config false;
      description
        "Time interval after which sync receipt timeout occurs
         if time-synchronization information has not been
         received during the interval.";
      reference
        "IEEE Std 802.1AS-2019: 14.8.22";
    }
 
    leaf initial-log-pdelay-req-interval {
      type int8;
      description
        "When use-mgt-log-pdelay-req-interval is false
         (i.e., change with Signaling message), this is the
         the logarithm to base 2 of the Pdelay_Req transmit
         interval used when the port is initialized.";
      reference
        "IEEE Std 802.1AS-2019: 14.8.23";
    }

    leaf current-log-pdelay-req-interval {
      type int8;
      config false;
      description
        "Current logarithm to base 2 of the Pdelay_Req transmit
         interval.";
      reference
        "IEEE Std 802.1AS-2019: 14.8.24";
    }

    leaf use-mgt-log-pdelay-req-interval {
      type boolean;
      description
        "Boolean that determines the source of the 
         Pdelay_Req transmit interval.
         If the value is true, the Pdelay_Req transmit interval
         (current-log-pdelay-req-interval) is set equal to the value
         of mgt-log-pdelay-req-interval.
         If the value is false, the Pdelay_Req transmit interval is
         determined by the LinkDelayIntervalSetting state machine
         (i.e., changed with Signaling message).";
      reference
        "IEEE Std 802.1AS-2019: 14.8.25";
    }
    
    leaf mgt-log-pdelay-req-interval {
      type int8;
      description
        "Logarithm to base 2 of the Pdelay_Req transmit interval,
         used if use-mgt-log-pdelay-req-interval is true. 
         This value is not used if use-mgt-log-pdelay-req-interval
         is false.";
      reference
        "IEEE Std 802.1AS-2019: 14.8.26";
    }
    
    leaf initial-log-gptp-cap-interval {
      type int8;
      description
        "When use-mgt-log-gptp-cap-interval is false
         (i.e., change with Signaling message), this is the
         the logarithm to base 2 of the gPTP capable message
         interval used when the port is initialized.";
      reference
        "IEEE Std 802.1AS-2019: 14.8.27";
    }

    leaf current-log-gptp-cap-interval {
      type int8;
      config false;
      description
        "Current logarithm to base 2 of the gPTP capable message
         interval.";
      reference
        "IEEE Std 802.1AS-2019: 14.8.28";
    }

    leaf use-mgt-log-gptp-cap-interval {
      type boolean;
      description
        "Boolean that determines the source of the 
         gPTP capable message interval.
         If the value is true, the gPTP capable message interval
         (current-log-gptp-cap-interval) is set equal to the value
         of mgt-gptp-cap-req-interval.
         If the value is false, the gPTP capable message interval is
         determined by the GptpCapableMessageIntervalSetting
         state machine (i.e., changed with Signaling message).";
      reference
        "IEEE Std 802.1AS-2019: 14.8.29";
    }
    
    leaf mgt-log-gptp-cap-interval {
      type int8;
      description
        "Logarithm to base 2 of the gPTP capable message interval,
         used if use-mgt-log-gptp-cap-interval is true. 
         This value is not used if use-mgt-log-pdelay-req-interval
         is false.";
      reference
        "IEEE Std 802.1AS-2019: 14.8.30";
    }
           
    leaf initial-compute-rate-ratio {
      type int8;
      description
        "When use-mgt-compute-rate-ratio is false
         (i.e., change with Signaling message), this is the
         initial value of computeNeighborRateRatio.";
      reference
        "IEEE Std 802.1AS-2019: 14.8.31";
    }

    leaf current-compute-rate-ratio {
      type int8;
      config false;
      description
        "Current value of computeNeighborRateRatio.";
      reference
        "IEEE Std 802.1AS-2019: 14.8.32";
    }

    leaf use-mgt-compute-rate-ratio {
      type boolean;
      description
        "Boolean that determines the source of 
         computeNeighborRateRatio..
         If the value is true, computeNeighborRateRatio
         is set equal to the value of mgt-compute-rate-ratio.
         If the value is false, computeNeighborRateRatio is
         determined by the LinkDelayIntervalSetting
         state machine (i.e., changed with Signaling message).";
      reference
        "IEEE Std 802.1AS-2019: 14.8.33";
    }
    
    leaf mgt-compute-rate-ratio {
      type int8;
      description
        "Value of computeNeighborRateRatio, used if 
         use-mgt-compute-rate-ratio is true. 
         This value is not used if use-mgt-compute-rate-ratio
         is false.";
      reference
        "IEEE Std 802.1AS-2019: 14.8.34";
    }
           
    leaf initial-compute-mean-link-delay {
      type int8;
      description
        "When use-mgt-compute-mean-link-delay is false
         (i.e., change with Signaling message), this is the
         initial value of computeMeanLinkDelay.";
      reference
        "IEEE Std 802.1AS-2019: 14.8.35";
    }

    leaf current-compute-mean-link-delay {
      type int8;
      config false;
      description
        "Current value of computeMeanLinkDelay.";
      reference
        "IEEE Std 802.1AS-2019: 14.8.36";
    }

    leaf use-mgt-compute-mean-link-delay {
      type boolean;
      description
        "Boolean that determines the source of 
         computeMeanLinkDelay.
         If the value is true, computeMeanLinkDelay
         is set equal to the value of mgt-compute-mean-link-delay.
         If the value is false, computeMeanLinkDelay is
         determined by the LinkDelayIntervalSetting
         state machine (i.e., changed with Signaling message).";
      reference
        "IEEE Std 802.1AS-2019: 14.8.37";
    }
    
    leaf mgt-compute-mean-link-delay {
      type int8;
      description
        "Value of computeMeanLinkDelay, used if 
         use-mgt-compute-mean-link-delay is true. 
         This value is not used if use-mgt-compute-mean-link-delay
         is false.";
      reference
        "IEEE Std 802.1AS-2019: 14.8.38";
    }
           
    leaf allowed-lost-responses {
      type uint8;
      description
        "Number of Pdelay_Req messages for which a valid response
         is not received, above which a port is considered to not
         be exchanging peer delay messages with its neighbor.";
      reference
        "IEEE Std 802.1AS-2019: 14.8.39";
    }
     
    leaf allowed-faults {
      type uint8;
      description
        "Number of faults above which asCapable is set to false.";
      reference
        "IEEE Std 802.1AS-2019: 14.8.40";
    }
    
    // TODO: logGptpCapableMessageInterval (14.8.41) is redundant, 
    // since it is already covered by 14.8.27 through 14.8.30.
    // The 802.1AS editor and author of this YANG agree that it should
    // be removed at sponsor ballot, so it is not added here.
    
    leaf gptp-cap-receipt-timeout {
      type uint8;
      description
        "Number of transmission intervals that a port waits without
         receiving the gPTP capable TLV, before assuming that the
         neighbor port is no longer invoking the gPTP protocol.";
      reference
        "IEEE Std 802.1AS-2019: 14.8.42";
    }
  
    leaf nup {
      type float64-type;
      description
        "For an OLT port of an IEEE Std 802.3 EPON link, this value
         is the effective index of refraction for the EPON
         upstream wavelength light of the optical path";
      reference
        "IEEE Std 802.1AS-2019: 14.8.44";
    }
    
    leaf ndown {
      type float64-type;
      description
        "For an OLT port of an IEEE 802.3 EPON link, this value
         is the effective index of refraction for the EPON
         downstream wavelength light of the optical path";
      reference
        "IEEE Std 802.1AS-2019: 14.8.45";
    }
     
    leaf one-step-tx-oper {
      type boolean;
      config false;
      description
        "This value is true if the port is sending one-step 
         Sync messages, and false if the port is sending 
         two-step Sync and Follow-Up messages.";
      reference
        "IEEE Std 802.1AS-2019: 14.8.47";
    }
    
    leaf one-step-receive {
      type boolean;
      config false;
      description
        "This value is true if the port is capable of
         receiving and processing one-step Sync messages.";
      reference
        "IEEE Std 802.1AS-2019: 14.8.48";
    }
    
    leaf one-step-transmit {
      type boolean;
      config false;
      description
        "This value is true if the port is capable of
        transmitting one-step Sync messages.";
      reference
        "IEEE Std 802.1AS-2019: 14.8.49";
    }
    
    leaf initial-one-step-tx-oper {
      type int8;
      description
        "When use-mgt-one-step-tx-oper is false
         (i.e., change with Signaling message), this is the
         initial value of current-one-step-tx-oper.";
      reference
        "IEEE Std 802.1AS-2019: 14.8.50";
    }

    leaf current-one-step-tx-oper {
      type int8;
      config false;
      description
        "This value is true if it is desired that the port
         transmit one-step Sync messages. If both
         current-one-step-tx-oper and one-step-transmit
         are true, the port transmits one-step Sync messages
         (i.e., one-step-tx-oper true).";
      reference
        "IEEE Std 802.1AS-2019: 14.8.51";
    }

    leaf use-mgt-one-step-tx-oper {
      type boolean;
      description
        "Boolean that determines the source of 
         current-one-step-tx-oper.
         If the value is true, current-one-step-tx-oper
         is set equal to the value of mgt-one-step-tx-oper.
         If the value is false, current-one-step-tx-oper is
         determined by the OneStepTxOperSetting
         state machine (i.e., changed with Signaling message).";
      reference
        "IEEE Std 802.1AS-2019: 14.8.52";
    }
    
    leaf mgt-one-step-tx-oper {
      type int8;
      description
        "Value of current-one-step-tx-oper, used if 
         use-mgt-one-step-tx-oper is true. 
         This value is not used if use-mgt-one-step-tx-oper
         is false.";
      reference
        "IEEE Std 802.1AS-2019: 14.8.53";
    }
           
    leaf sync-locked {
      type boolean;
      config false;
      description
        "This value is true if the port will transmit a Sync as soon as
         possible after the slave port receives a Sync message.";
      reference
        "IEEE Std 802.1AS-2019: 14.8.54";
    }
    
    leaf-list pdelay-truncated-timestamps {
      type uint64;
      description
        "For full-duplex IEEE Std 802.3 media, and CSN media that use 
         the peer-to-peer delay mechanism to measure path delay, 
         the values of the four elements of this leaf-list correspond
         to the timestamps t1, t2, t3, and t4, listed in that order.
         Each timestamp is expressed in units of 2^-16 ns (i.e., the 
         value of each array element is equal to the remainder obtained
         upon dividing the respective timestamp, expressed in units of 
         2^-16 ns, by 2^48). At any given time, the timestamp values 
         stored in the array are for the same, and most recently
         completed, peer delay message exchange. For each timestamp, 
         only 48-bits are valid (the upper 16-bits are always zero).";
      reference
        "IEEE Std 802.1AS-2019: 14.8.55";
    }    
    
    container port-statistics-ds {
      description
        "Provides counters associated with the port of the
         time-aware system.";
      reference
        "IEEE Std 802.1AS-2019: 14.10";

      // TODO: Since IEEE Std 802.1AS does not specify that these
      // counters reset to zero at power-on, this YANG uses
      // counter64, which is typical for YANG counters. The IEEE
      // 802.1 Working Group will need to decide whether
      // to keep counter64.
      
      leaf rx-sync-count {
        type yang:counter64;
        description
          "Counter that increments every time synchronization
           information is received.";
        reference
          "IEEE Std 802.1AS-2019: 14.10.2";
      }
      
      leaf rx-one-step-sync-count {
        type yang:counter64;
        description
          "Counter that increments every time a one-step Sync
           message is received.";
        reference
          "IEEE Std 802.1AS-2019: 14.10.3";
      }
      
      leaf rx-follow-up-count {
        type yang:counter64;
        description
          "Counter that increments every time a Follow_Up
           message is received.";
        reference
          "IEEE Std 802.1AS-2019: 14.10.4";
      }
      
      leaf rx-pdelay-req-count {
        type yang:counter64;
        description
          "Counter that increments every time a Pdelay_Req
           message is received.";
        reference
          "IEEE Std 802.1AS-2019: 14.10.5";
      }
      
      leaf rx-pdelay-resp-count {
        type yang:counter64;
        description
          "Counter that increments every time a Pdelay_Resp
           message is received.";
        reference
          "IEEE Std 802.1AS-2019: 14.10.6";
      }
      
      leaf rx-pdelay-resp-follow-up-count {
        type yang:counter64;
        description
          "Counter that increments every time a Pdelay_Resp_Follow_Up
           message is received.";
        reference
          "IEEE Std 802.1AS-2019: 14.10.7";
      }
      
      leaf rx-announce-count {
        type yang:counter64;
        description
          "Counter that increments every time an Announce
           message is received.";
        reference
          "IEEE Std 802.1AS-2019: 14.10.8";
      }
      
      leaf rx-packet-discard-count {
        type yang:counter64;
        description
          "Counter that increments every time a PTP message
           of the respective PTP Instance is discarded.";
        reference
          "IEEE Std 802.1AS-2019: 14.10.9";
      }
      
      leaf sync-receipt-timeout-count {
        type yang:counter64;
        description
          "Counter that increments every time a sync receipt
           timeout occurs.";
        reference
          "IEEE Std 802.1AS-2019: 14.10.10";
      }
      
      leaf announce-receipt-timeout-count {
        type yang:counter64;
        description
          "Counter that increments every time an announce receipt
          timeout occurs.";
        reference
          "IEEE Std 802.1AS-2019: 14.10.11";
      }
      
      leaf pdelay-allowed-lost-exceeded-count {
        type yang:counter64;
        description
          "Counter that increments every time the value of the
           variable lostResponses exceeds the value of the variable
           allowedLostResponses, in the RESET state of the 
           MDPdelayReq state machine.";
        reference
          "IEEE Std 802.1AS-2019: 14.10.12";
      }
      
      leaf tx-sync-count {
        type yang:counter64;
        description
          "Counter that increments every time synchronization
           information is transmitted.";
        reference
          "IEEE Std 802.1AS-2019: 14.10.13";
      }
      
      leaf tx-one-step-sync-count {
        type yang:counter64;
        description
          "Counter that increments every time a one-step Sync
           message is transmitted.";
        reference
          "IEEE Std 802.1AS-2019: 14.10.14";
      }
      
      leaf tx-follow-up-count {
        type yang:counter64;
        description
          "Counter that increments every time a Follow_Up
           message is transmitted.";
        reference
          "IEEE Std 802.1AS-2019: 14.10.15";
      }
      
      leaf tx-pdelay-req-count {
        type yang:counter64;
        description
          "Counter that increments every time a Pdelay_Req
           message is transmitted.";
        reference
          "IEEE Std 802.1AS-2019: 14.10.16";
      }
      
      leaf tx-pdelay-resp-count {
        type yang:counter64;
        description
          "Counter that increments every time a Pdelay_Resp
           message is transmitted.";
        reference
          "IEEE Std 802.1AS-2019: 14.10.17";
      }
      
      leaf tx-pdelay-resp-follow-up-count {
        type yang:counter64;
        description
          "Counter that increments every time a Pdelay_Resp_Follow_Up
           message is transmitted.";
        reference
          "IEEE Std 802.1AS-2019: 14.10.18";
      }
      
      leaf tx-announce-count {
        type yang:counter64;
        description
          "Counter that increments every time an Announce
           message is transmitted.";
        reference
          "IEEE Std 802.1AS-2019: 14.10.19";
      }
    }
    
    container asymmetry-measurement-ds {
      description
        "Represents the capability to enable/disable the Asymmetry
        Compensation Measurement Procedure on a port. This data set
        is used instead of the CMLDS asymmetry-measurement-ds when
        only a single PTP Instance is present (i.e., CMLDS 
        is not used).";
      reference
        "IEEE Std 802.1AS-2019: 14.13, Annex G";
      
      leaf enabled {
        type boolean;
        description
          "For full-duplex IEEE Std 802.3 media, the value is true
           if an asymmetry measurement is being performed for the 
           link attached to this port, and false otherwise. For all
           other media, the value shall be false.";
      }
    }
  }
  
  augment "/ptp:ptp/ptp:common-services/ptp:cmlds/ptp:port-list" {
    description
      "Augment IEEE Std 1588 cmldsLinkPortDS.";
    
    leaf ptp-link-port-enabled {
      type boolean;
      config false;
      description
        "Boolean that is true if both delay-mechanism is common-p2p
         and the value of ptp-port-enabled is true, for at least one
         PTP Port that uses the CMLDS; otherwise, the value is false.";
      reference
        "IEEE Std 802.1AS-2019: 11.2.18.1, 14.16.3";
    }

    leaf is-measuring-delay {
      type boolean;
      config false;
      description
        "This leaf is analogous to is-measuring-delay
        for a PTP Port, but applicable to this Link Port.";
      reference
        "IEEE Std 802.1AS-2019: 14.16.4";
    }
    
    leaf as-capable-across-domains {
      type boolean;
      config false;
      description
        "This leaf is true when all PTP Instances (domains) 
         for this Link Port detect proper exchange of Pdelay
         messages.";
      reference
        "IEEE Std 802.1AS-2019: 11.2.2, 14.16.5";
    }
   
    leaf mean-link-delay-thresh {
      type ptp:time-interval-type;
      description
        "Propagation time threshold for mean-link-delay, 
         above which a Link Port is not considered capable of
         participating in the IEEE Std 802.1AS protocol.";
      reference
        "IEEE Std 1588-2019: 14.16.7";
    }
    
    leaf initial-log-pdelay-req-interval {
      type int8;
      description
        "This leaf is analogous to initial-log-pdelay-req-interval
         for a PTP Port, but applicable to this Link Port.";
      reference
        "IEEE Std 802.1AS-2019: 14.16.10";
    }

    leaf current-log-pdelay-req-interval {
      type int8;
      config false;
      description
        "This leaf is analogous to current-log-pdelay-req-interval
         for a PTP Port, but applicable to this Link Port.";
      reference
        "IEEE Std 802.1AS-2019: 14.16.11";
    }

    leaf use-mgt-log-pdelay-req-interval {
      type boolean;
      description
        "This leaf is analogous to use-mgt-log-pdelay-req-interval
         for a PTP Port, but applicable to this Link Port.";
      reference
        "IEEE Std 802.1AS-2019: 14.16.12";
    }
    
    leaf mgt-log-pdelay-req-interval {
      type int8;
      description
        "This leaf is analogous to mgt-log-pdelay-req-interval
         for a PTP Port, but applicable to this Link Port.";
      reference
        "IEEE Std 802.1AS-2019: 14.16.13";
    }
    
    leaf initial-compute-rate-ratio {
      type int8;
      description
        "This leaf is analogous to initial-compute-rate-ratio
         for a PTP Port, but applicable to this Link Port.";
      reference
        "IEEE Std 802.1AS-2019: 14.16.14";
    }

    leaf current-compute-rate-ratio {
      type int8;
      config false;
      description
        "This leaf is analogous to current-compute-rate-ratio
         for a PTP Port, but applicable to this Link Port.";
      reference
        "IEEE Std 802.1AS-2019: 14.16.15";
    }

    leaf use-mgt-compute-rate-ratio {
      type boolean;
      description
        "This leaf is analogous to use-mgt-compute-rate-ratio
         for a PTP Port, but applicable to this Link Port.";
      reference
        "IEEE Std 802.1AS-2019: 14.16.16";
    }
    
    leaf mgt-compute-rate-ratio {
      type int8;
      description
        "This leaf is analogous to mgt-compute-rate-ratio
         for a PTP Port, but applicable to this Link Port.";
      reference
        "IEEE Std 802.1AS-2019: 14.16.17";
    }
           
    leaf initial-compute-mean-link-delay {
      type int8;
      description
        "This leaf is analogous to initial-compute-mean-link-delay
         for a PTP Port, but applicable to this Link Port.";
      reference
        "IEEE Std 802.1AS-2019: 14.16.18";
    }

    leaf current-compute-mean-link-delay {
      type int8;
      config false;
      description
        "This leaf is analogous to current-compute-mean-link-delay
         for a PTP Port, but applicable to this Link Port.";
      reference
        "IEEE Std 802.1AS-2019: 14.16.19";
    }

    leaf use-mgt-compute-mean-link-delay {
      type boolean;
      description
        "This leaf is analogous to use-mgt-compute-mean-link-delay
         for a PTP Port, but applicable to this Link Port.";
      reference
        "IEEE Std 802.1AS-2019: 14.16.20";
    }
    
    leaf mgt-compute-mean-link-delay {
      type int8;
      description
        "This leaf is analogous to mgt-compute-mean-link-delay
         for a PTP Port, but applicable to this Link Port.";
      reference
        "IEEE Std 802.1AS-2019: 14.16.21";
    }
           
    leaf allowed-lost-responses {
      type uint8;
      description
        "This leaf is analogous to allowed-lost-responses
         for a PTP Port, but applicable to this Link Port.";
      reference
        "IEEE Std 802.1AS-2019: 14.16.22";
    }
     
    leaf allowed-faults {
      type uint8;
      description
        "This leaf is analogous to allowed-faults
         for a PTP Port, but applicable to this Link Port.";
      reference
        "IEEE Std 802.1AS-2019: 14.16.23";
    }
    
    leaf-list pdelay-truncated-timestamps {
      type uint64;
      description
        "This leaf is analogous to pdelay-truncated-timestamps
         for a PTP Port, but applicable to this Link Port.";
      reference
        "IEEE Std 802.1AS-2019: 14.16.25";
    } 
    
    container port-statistics-ds {
      description
        "This container is analogous to port-statistics-ds
         for a PTP Port, but applicable to this Link Port.";
      reference
        "IEEE Std 802.1AS-2019: 14.17";

      leaf rx-pdelay-req-count {
        type yang:counter64;
        description
          "This leaf is analogous to rx-pdelay-req-count
           for a PTP Port, but applicable to this Link Port.";
        reference
          "IEEE Std 802.1AS-2019: 14.17.2";
      }
      
      leaf rx-pdelay-resp-count {
        type yang:counter64;
        description
          "This leaf is analogous to rx-pdelay-resp-count
           for a PTP Port, but applicable to this Link Port.";
        reference
          "IEEE Std 802.1AS-2019: 14.17.3";
      }
      
      leaf rx-pdelay-resp-follow-up-count {
        type yang:counter64;
        description
          "This leaf is analogous to rx-pdelay-resp-follow-up-count
           for a PTP Port, but applicable to this Link Port.";
        reference
          "IEEE Std 802.1AS-2019: 14.17.4";
      }
      
      leaf rx-packet-discard-count {
        type yang:counter64;
        description
          "This leaf is analogous to rx-packet-discard-count
           for a PTP Port, but applicable to this Link Port.";
        reference
          "IEEE Std 802.1AS-2019: 14.17.5";
      }
      
      leaf pdelay-allowed-lost-exceeded-count {
        type yang:counter64;
        description
          "This leaf is analogous to 
           pdelay-allowed-lost-exceeded-count
           for a PTP Port, but applicable to this Link Port.";
        reference
          "IEEE Std 802.1AS-2019: 14.17.6";
      }
      
      leaf tx-pdelay-req-count {
        type yang:counter64;
        description
          "This leaf is analogous to tx-pdelay-req-count
          for a PTP Port, but applicable to this Link Port.";
        reference
          "IEEE Std 802.1AS-2019: 14.17.7";
      }
      
      leaf tx-pdelay-resp-count {
        type yang:counter64;
        description
          "This leaf is analogous to tx-pdelay-resp-count
          for a PTP Port, but applicable to this Link Port.";
        reference
          "IEEE Std 802.1AS-2019: 14.17.8";
      }
      
      leaf tx-pdelay-resp-follow-up-count {
        type yang:counter64;
        description
          "This leaf is analogous to tx-pdelay-resp-follow-up-count
          for a PTP Port, but applicable to this Link Port.";
        reference
          "IEEE Std 802.1AS-2019: 14.17.9";
      }
    }
    
    container asymmetry-measurement-ds {
      description
        "This container is analogous to asymmetry-measurement-ds
        for a PTP Port, but applicable to this Link Port.";
      reference
        "IEEE Std 802.1AS-2019: 14.18";
      
      leaf enabled {
        type boolean;
        description
          "This leaf is analogous to enabled
          for a PTP Port, but applicable to this Link Port.";
      }
    }
  }
  
  // TODO: Notifications are deferred, but will presumably augment
  // the notifications of the 1588 Working Group.
}
