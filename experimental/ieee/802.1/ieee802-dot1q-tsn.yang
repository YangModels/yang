module ieee802-dot1q-tsn {
  namespace "urn:ieee:std:802.1Q:yang:ieee802-dot1q-tsn";
  prefix dot1q-tsn;

  import ietf-interfaces {
    prefix if;
  }
  import ieee802-dot1q-bridge {
    prefix dot1q;
  }

  organization "Huawei";
  contact
    "Web URL: http://www.huawei.com
     Lihao Chen
     lihao.chen@huawei.com";
  description
    "This module provides capabilities to bridges and bridge
     components for supporting TSN enabling technologies, e.g, 
     Scheduled Traffic, Frame Preemption, Per-Stream Filtering and
     Policing. This experimental YANG module is an individual 
     contribution, does not represent a formally sanctioned YANG 
     module of IEEE. Therefore, this YANG module will change in 
     incompatible ways from its current revision to the formally 
     published YANG module for IEEE Std 802.1Q.";

  revision 2017-12-29 {
    description
      "Initial model that outline the structure of TSN enabling 
       technology parameters augmented into 802.1Qcp based models.";
    reference
      "IEEE 802.1Q-2017, Media Access Control (MAC) Bridges and 
       Virtual Bridged Local Area Networks.";
  }

  identity tsn-port {
    base dot1q:type-of-port;
    description
      "Base identity for a TSN port.";
  }

  augment "/if:interfaces/if:interface/dot1q:bridge-port" {
    when "dot1q:port-type = 'dot1q-tsn:tsn-port'" {
      description
        "Applies to TSN Bridges ports";
    }
    description
      "Augment Interface model with TSN bridge port configuration 
       specific nodes.";
    list port {
      key "port-number";
      description
        "Specify bridge port.";
      leaf port-number {
        type uint16;
        description
          "Specify the port's number.";
      }
      container preemption {
        description
          "Definition of Frame Preemption capabilities. More to 
           be determined.";
        leaf preemption-enable {
          type boolean;
          default "false";
          description
            "Indication of Frame Preemption enablement associated 
             with the Port.";
        }
      }
      container scheduling {
        description
          "Definition of Scheduled Traffic capabilities. More to 
           be determined.";
      }
      container policing {
        description
          "Definition of Per-Stream Filtering and Policing 
           capabilities. More to be determined.";
      }
      container time-sync {
        description
          "Definition of Timing and Synchronization capabilities. 
           More to be determined.";
      }
    }
  }
}
