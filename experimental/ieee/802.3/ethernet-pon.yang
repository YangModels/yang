module ethernet-pon {

  /*** NAMESPACE / PREFIX DEFINITION ***/

  namespace "urn:ieee:params:xml:ns:yang:ethernet-pon";

  prefix epon;

  /*** LINKAGE (IMPORTS / INCLUDES) ***/
  
  import ietf-yang-types { prefix yang; }
  
  import ietf-interfaces { prefix if; }

  import ethernet { prefix eth; }

  /*** META INFORMATION ***/

  organization
    "IEEE 802.3 Working Group";

  contact
    "Marek Hajduczenia, marek.hajduczenia@mybrighthouse.com";

  description 
    "This module contains a collection of YANG definitions
 for managing the Multi Point Control Protocol, as defined in IEEE Std 802.3, Clause 64/77
     
This YANG module augments the 'ethernet' module.";
    reference 
     "IEEE Std 802.3-2015, Clause 64/77, unless dated explicitly
      IEEE Std 802.3.1-2013, Clause 9, unless dated explicitly";


  revision 2015-11-27 {
    description
      "Initial version";
    reference
      "IEEE Std 802.3-2015, unless dated explicitly in reference
       IEEE Std 802.3.1-2013, unless dated explicitly in reference";
  }
    typedef mpcp-llid {
        type uint32 {
            range "0 .. 32767";
        }
        description 
         "The third and fourth octets following the SLD contain the mode and logical_link_id values. OLTs and ONUsact upon these values in a different manner.
          If the device is an OLT, then the following comparison is made:
          a)The received mode bit is ignored.
          b)If the received logical_link_id value matches 0x7FFF or 0x7FFE and an enabled MAC exists with alogical_link_id variable with the same value, then the comparison is considered a match to thatMAC.
          c)If the received logical_link_id has a value other than 0x7FFF or 0x7FFE and an enabled MAC existswith a mode variable with a value of 0 and a logical_link_id variable matching the receivedlogical_link_id value, then the comparison is considered a match to that MAC.
          If the device is an ONU then the following comparison is made:
          d)If the received mode bit is equal to 0 and the received logical_link_id value matches the logi-cal_link_id variable, then the comparison is considered a match.
          e)If the received mode bit is equal to 1 and the received logical_link_id value does not match thelogical_link_id variable, or the received logical_link_id matches 0x7FFE, then the comparison isconsidered a match.
          f)If the received logical_link_id value matches one of the assigned multicast LLIDs, then thecomparison is considered a match.
          If no match is found, then the packet shall be discarded within the RS. If a match is found, then the packet isintended to be transferred. If the packet is transferred, then both octets of the LLID field shall be replacedwith normal preamble octets.
          If the packet is transferred, the one octet preceding the LLID is passed without modification. A number ofLLIDs have been reserved (see IEEE Std 802.3, Figure 76–4) for various purposes including downstream broadcast,discovery messages, and upstream registration request messages. An additional block of LLIDs has been setaside for future use and definition. A registered ONU shall not transmit frames with one of these reservedLLIDs.";
        reference "IEEE Std 802.3, 76.2.6.1.3.2 (1G-EPON and 10G-EPON)";
    }


  typedef mpcp-mode {
    type enumeration {
      enum olt {
        value 1;
        description "mpcp mode: olt (1) = server";
      }
      enum onu {
        value 2;
        description "mpcp mode: onu (2) = client";
      }
    }
    description
      "Enumeration of valid mpcp modes for Ethernet interfaces";
    reference    
        "IEEE Std 802.3, 30.3.5.1.3
         IEEE Std 802.3.1, dot3MpcpMode";
  }

  typedef mpcp-state {
    type enumeration {
      enum unregistered {
        value 1;
        description "MPCP registration state: logical link is NOT registered";
      }
      enum registering {
        value 2;
        description "MPCP registration state: logical link is currently in the process of registering";
      }
      enum registered {
        value 3;
        description "MPCP registration state: logical link is currently registered";
      }
    }
    description
      "Enumeration of valid MPCP registration states for Ethernet interfaces";
    reference    
        "IEEE Std 802.3, 30.3.5.1.6
         IEEE Std 802.3.1, dot3MpcpRegistrationState";
  }

  typedef ompe-mode {
    type enumeration {
      enum unknown {
        value 1;
        description "omp-emulation mode: unknown (1) = system is initializing";
      }
      enum olt {
        value 2;
        description "omp-emulation mode: olt (2) = server";
      }
      enum onu {
        value 3;
        description "omp-emulation mode: onu (3) = client";
      }
    }
    description
      "Enumeration of valid OMP-Emulation modes for Ethernet interfaces";
    reference    
        "IEEE Std 802.3, 30.3.7.1.2
         IEEE Std 802.3.1, dot3OmpEmulationType";
  }
    typedef fec-capability {
        type enumeration {
            enum unknown {
                value 1;
                description "FEC capability: unknown (1) = system is initializing";
            }
            enum supported {
                value 2;
                description "FEC capability: supported (2)";
            }
            enum "not supported" {
                value 3;
                description "FEC capability: not supported (3)";
            }
        }
        description "Enumeration of valid FEC capability values for Ethernet interfaces with enabled MPCP";
        reference 
         "IEEE Std 802.3, 30.5.1.1.15
          IEEE Std 802.3.1, dot3EponFecAbility";
    }


  typedef fec-mode {
    type enumeration {
      enum unknown {
        value 1;
        description "FEC mode: unknown (1) = system is initializing";
      }
      enum disabled {
        value 2;
        description "FEC mode: disabled (2)";
      }
      enum enabled {
        value 3;
        description "FEC mode: enabled (3)";
      }
    }
    description
      "Enumeration of valid FEC modes for Ethernet interfaces";
    reference    
        "IEEE Std 802.3, 30.5.1.1.16
         IEEE Std 802.3.1, dot3EponFecMode";
  }

  augment "/if:interfaces/if:interface/eth:ethernet" {
    description
      "Augments definition of Ethernet interface (/if:interfaces/if:interface/eth:ethernet) operational state model with nodes
 specific to Ethernet MPCP";
        leaf fec-mode {
            type fec-mode;
            config true;
            description 
             "An object that defines the mode of operation of the optional FEC sublayer of the 1000BASE-PX PHY, specified in IEEE Std 802.3, 65.2, and reflects its state. 
              A write operation changes the mode of operation of the PHY to the indicated value at any time. 
              The value of unknown (1) is assigned in the initialization for non FEC support state or type not yet known. 
              The value of disabled (2) is assigned when the FEC sublayer is operating in disabled mode. 
              The value of enabled (3) is assigned when the FEC sublayer is operating in FEC mode. 
              Changing the value of fec-mode can lead to disabling the Forward Error Correction on the respective interface, which can lead to a degradation of the optical link, and therefore may lead to an interruption of service for the users connected to the respective EPON interface. 
              This object is applicable for an OLT and an ONU. 
              At the OLT, it has a distinct value for each logical link. ";
            reference 
             "IEEE Std 802.3, 30.5.1.1.16
              IEEE Std 802.3.1, dot3EponFecMode";
        }

  }

  augment "/if:interfaces-state/if:interface/eth:Ethernet" {
    description
      "Augments definition of Ethernet interface (/if:interfaces-state/if:interface/eth:ethernet) operational state model with nodes
 specific to Ethernet MPCP";

    container epon {
      presence
        "Implies EPON is suported on the selected Ethernet interface";
      description
        "Various EPON-related operational state and counter nodes for the selected Ethernet interface, including physical interfaces and logical link interfaces. 
         The LLID field, as defined in IEEE Std 802.3, is a 2-byte register (15-bit field and a broadcast bit) limiting the number of logical links to 32768. Typically the number of expected logical links in a PON is like the number of ONUs, which is 32-64, plus an additional entry for broadcast LLID. 
         An ONU interface instance is created at system initialization. 
         An OLT interface instance, corresponding to the broadcast logical link, is created at system initialization. 
         An OLT interface instance, corresponding to a unicast logical link, is created when a logical link is established (an ONU registers) and deleted when the logical link is deleted (the ONU deregisters).";

      container statistics-mpcp {
        description "This container defines a set of MPCP-related statistics counters of an Ethernet interface implementing MPCP, as defined in IEEE Std 802.3, Clause 64 and Clause 77. ";

        leaf mpcp-mac-ctrl-pkts-out {
          type yang:counter64;
                    units frames;
                    config false;

          description
            "A count of MPCP frames passed to the MAC sublayer for transmission. 
             This counter is incremented when a MA_CONTROL.request service primitive is generated within the MAC control sublayer with an opcode indicating an MPCP frame. 
             This object is applicable for an OLT and an ONU. 
             At the OLT it has a distinct value for each logical link. 
             Discontinuities of this counter can occur at re-initialization of the management system, and at other times as indicated by the value of the ifCounterDiscontinuityTime object. ";
                    reference 
                     "IEEE Std 802.3, 30.3.5.1.7
                      IEEE Std 802.3.1, dot3MpcpMACCtrlFramesTransmitted";

        }

        leaf mpcp-mac-ctrl-pkts-in {
          type yang:counter64;
                    units frames;
                    config false;

          description
            "A count of MPCP frames passed by the MAC sublayer to the MAC Control sublayer. 
             This counter is incremented when a ReceiveFrame function call returns a valid frame with:
             1) a lengthOrType field value equal to the reserved Type for 802.3_MAC_Control as specified in IEEE Std 802.3 31.4.1.3, and 
             2) an opcode indicating an MPCP frame. 
             This object is applicable for an OLT and an ONU. 
             At the OLT, it has a distinct value for each logical link. 
             Discontinuities of this counter can occur at re-initialization of the management system and at other times, as indicated by the value of the ifCounterDiscontinuityTime object.";
                    reference 
                     "IEEE Std 802.3, 30.3.5.1.8
                      IEEE Std 802.3.1, dot3MpcpMACCtrlFramesReceived";

        }

        leaf mpcp-discovery-window-count {
          type yang:counter64;
                    units "discovery windows";
                    config false;

          description
            "A count of discovery windows generated by the OLT. 
             The counter is incremented by one for each generated discovery window. 
             This object is applicable for an OLT and an ONU. 
             At the OLT, it has a distinct value for each logical link. 
             At the ONU, the value should be zero. 
             Discontinuities of this counter can occur at re-initialization of the management system and at other times, as indicated by the value of the ifCounterDiscontinuityTime object. ";
                    reference 
                     "IEEE Std 802.3, 30.3.5.1.22
                      IEEE Std 802.3.1, dot3MpcpDiscoveryWindowsSent";

        }

        leaf mpcp-discovery-timeout-count {
          type yang:counter64;
                    units "discovery timeouts";
                    config false;

          description
            "A count of the number of times a discovery timeout occurs. 
             This counter is incremented by one for each discovery processing state-machine reset resulting from timeout waiting for message arrival. 
             This object is applicable for an OLT and an ONU. 
             At the OLT, it has a distinct value for each logical link. 
             Discontinuities of this counter can occur at re-initialization of the management system and at other times, as indicated by the value of the ifCounterDiscontinuityTime object. ";
                    reference 
                     "IEEE Std 802.3, 30.3.5.1.23
                      IEEE Std 802.3.1, dot3MpcpDiscoveryTimeout";

        }

        leaf mpcp-register-req-out {
          type yang:counter64;
                    units frames;
                    config false;

          description
            "A count of the number of times a REGISTER_REQ MPCP frame transmission occurs. 
             Increment the counter by one for each REGISTER_REQ MPCP frame transmitted as defined in IEEE Std 802.3, Clause 64 and Clause 77. 
             This object is applicable for an OLT and an ONU. 
             At the OLT, it has a distinct value for each logical link. 
             At the ONU, the value should be zero. 
             Discontinuities of this counter can occur at re-initialization of the management system and at other times, as indicated by the value of the ifCounterDiscontinuityTime object .";
                    reference 
                     "IEEE Std 802.3, 30.3.5.1.12
                      IEEE Std 802.3.1, dot3MpcpTxRegRequest";

        }

        leaf mpcp-register-req-in {
          type yang:counter64;
                    units frames;
                    config false;

          description
            "A count of the number of times a REGISTER_REQ MPCP frame receiption occurs. 
             Increment the counter by one for each REGISTER_REQ MPCP frame received as defined in IEEE Std 802.3, Clause 64 and Clause 77. 
             This object is applicable for an OLT and an ONU. 
             At the OLT, the value should be zero for each logical link. 
             Discontinuities of this counter can occur at re-initialization of the management system and at other times, as indicated by the value of the ifCounterDiscontinuityTime object .";
                    reference 
                     "IEEE Std 802.3, 30.3.5.1.17
                      IEEE Std 802.3.1, dot3MpcpRxRegRequest";

        }

        leaf mpcp-register-ack-out {
          type yang:counter64;
                    units frames;
                    config false;

          description
            "A count of the number of times a REGISTER_ACK MPCP frame transmission occurs. 
             Increment the counter by one for each REGISTER_ACK MPCP frame transmitted as defined in IEEE Std 802.3, Clause 64 and Clause 77. 
             This object is applicable for an OLT and an ONU. 
             At the OLT, the value should be zero for each logical link. 
             Discontinuities of this counter can occur at re-initialization of the management system and at other times, as indicated by the value of the ifCounterDiscontinuityTime object .";
                    reference 
                     "IEEE Std 802.3, 30.3.5.1.10
                      IEEE Std 802.3.1, dot3MpcpTxRegAck";

        }

        leaf mpcp-register-ack-in {
          type yang:counter64;
                    units frames;
                    config false;

          description
            "A count of the number of times a REGISTER_ACK MPCP frame reception occurs. 
             Increment the counter by one for each REGISTER_ACK MPCP frame received as defined in IEEE Std 802.3, Clause 64 and Clause 77. 
             This object is applicable for an OLT and an ONU. 
             At the OLT, it has a distinct value for each logical link.
             At the ONU, the value should be zero. 
             Discontinuities of this counter can occur at re-initialization of the management system and at other times, as indicated by the value of the ifCounterDiscontinuityTime object .";
                    reference 
                     "IEEE Std 802.3, 30.3.5.1.15
                      IEEE Std 802.3.1, dot3MpcpRxRegAck";

        }

        leaf mpcp-report-out {
          type yang:counter64;
                    units frames;
                    config false;

          description
            "A count of the number of times a REPORT MPCP frame transmission occurs. 
             Increment the counter by one for each REPORT MPCP frame transmitted as defined in IEEE Std 802.3, Clause 64 and Clause 77. 
             This object is applicable for an OLT and an ONU. 
             At the OLT, the value should be zero for each logical link. 
             Discontinuities of this counter can occur at re-initialization of the management system and at other times, as indicated by the value of the ifCounterDiscontinuityTime object .";
                    reference 
                     "IEEE Std 802.3, 30.3.5.1.13
                      IEEE Std 802.3.1, dot3MpcpTxReport";

        }

        leaf mpcp-report-in {
          type yang:counter64;
                    units frames;
                    config false;

          description
            "A count of the number of times a REPORT MPCP frame reception occurs. 
             Increment the counter by one for each REPORT MPCP frame received as defined in IEEE Std 802.3, Clause 64 and Clause 77. 
             This object is applicable for an OLT and an ONU. 
             At the OLT, it has a distinct value for each logical link.
             At the ONU, the value should be zero. 
             Discontinuities of this counter can occur at re-initialization of the management system and at other times, as indicated by the value of the ifCounterDiscontinuityTime object .";
                    reference 
                     "IEEE Std 802.3, 30.3.5.1.18
                      IEEE Std 802.3.1, dot3MpcpRxReport";

        }

        leaf mpcp-gate-out {
          type yang:counter64;
                    units frames;
                    config false;

          description
            "A count of the number of times a GATE MPCP frame transmission occurs. 
             Increment the counter by one for each GATE MPCP frame transmitted as defined in IEEE Std 802.3, Clause 64 and Clause 77. 
             This object is applicable for an OLT and an ONU. 
             At the OLT, it has a distinct value for each logical link. 
             At the ONU, the value should be zero. 
             Discontinuities of this counter can occur at re-initialization of the management system and at other times, as indicated by the value of the ifCounterDiscontinuityTime object .";
                    reference 
                     "IEEE Std 802.3, 30.3.5.1.9
                      IEEE Std 802.3.1, dot3MpcpTxGate";

        }

        leaf mpcp-gate-in {
          type yang:counter64;
                    units frames;
                    config false;

          description
            "A count of the number of times a GATE MPCP frame receiption occurs. 
             Increment the counter by one for each GATE MPCP frame received as defined in IEEE Std 802.3, Clause 64 and Clause 77. 
             This object is applicable for an OLT and an ONU. 
             At the OLT, the value should be zero for each logical link. 
             Discontinuities of this counter can occur at re-initialization of the management system and at other times, as indicated by the value of the ifCounterDiscontinuityTime object .";
                    reference 
                     "IEEE Std 802.3, 30.3.5.1.14
                      IEEE Std 802.3.1, dot3MpcpRxGate";

        }

        leaf mpcp-register-out {
          type yang:counter64;
                    units frames;
                    config false;

          description
            "A count of the number of times a REGISTER MPCP frame transmission occurs. 
             Increment the counter by one for each REGISTER MPCP frame transmitted as defined in IEEE Std 802.3, Clause 64 and Clause 77. 
             This object is applicable for an OLT and an ONU. 
             At the OLT, it has a distinct value for each logical link. 
             At the ONU, the value should be zero. 
             Discontinuities of this counter can occur at re-initialization of the management system and at other times, as indicated by the value of the ifCounterDiscontinuityTime object .";
                    reference 
                     "IEEE Std 802.3, 30.3.5.1.11
                      IEEE Std 802.3.1, dot3MpcpTxRegister ";

        }

        leaf mpcp-register-in {
          type yang:counter64;
                    units frames;
                    config false;

          description
            "A count of the number of times a REGISTER MPCP frame receiption occurs. 
             Increment the counter by one for each REGISTER MPCP frame received as defined in IEEE Std 802.3, Clause 64 and Clause 77. 
             This object is applicable for an OLT and an ONU. 
             At the OLT, the value should be zero for each logical link. 
             Discontinuities of this counter can occur at re-initialization of the management system and at other times, as indicated by the value of the ifCounterDiscontinuityTime object .";
                    reference 
                     "IEEE Std 802.3, 30.3.5.1.16
                      IEEE Std 802.3.1, dot3MpcpRxRegister";

        }
      }

      container statistics-ompe {
        description "This container defines a set of OMP-Emulation-related statistics counters of an Ethernet interface implementing MPCP, as defined in IEEE Std 802.3, Clause 65 and Clause 76. ";
                reference "IEEE Std 802.3.1, dot3OmpEmulationStatEntry";


        leaf ompe-pkts-in-errored-sld {
          type yang:counter64;
                    units frames;
                    config false;

          description
            "A count of frames received that do not contain a valid SLD field as defined in IEEE Std 802.3, 65.1.3.3.1 or 76.2.6.1.3.1, as appropriate. 
             This object is applicable for an OLT and an ONU. 
             At the OLT, it has a distinct value for each logical link interface.
             Discontinuities of this counter can occur at re-initialization of the management system and at other times, as indicated by the value of the ifCounterDiscontinuityTime object.";
                    reference 
                     "IEEE Std 802.3, 30.3.7.1.3
                      IEEE Std 802.3.1, dot3OmpEmulationSLDErrors";

        }

        leaf ompe-pkts-in-errored-crc8 {
          type yang:counter64;
                    units frames;
                    config false;

          description
            "A count of frames received that contain a valid SLD field, as defined in IEEE Std 802.3, 65.1.3.3.1 or 76.2.6.1.3.1 as appropriate, but do not pass the CRC-8 check as defined in IEEE Std 802.3, 65.1.3.3.3 or 76.2.6.1.3.3 as appropriate. 
             This object is applicable for an OLT and an ONU. 
             At the OLT, it has a distinct value for each logical link interface.
             Discontinuities of this counter can occur at re-initialization of the management system and at other times, as indicated by the value of the ifCounterDiscontinuityTime object.";
                    reference 
                     "IEEE Std 802.3, 30.3.7.1.4
                      IEEE Std 802.3.1, dot3OmpEmulationCRC8Errors";

        }

        leaf ompe-pkts-in-with-bad-llid {
          type yang:counter64;
                    units frames;
                    config false;

          description
            "A count of frames received that contain a valid SLD field, as defined in IEEE Std 802.3, 65.1.3.3.1 or 76.2.6.1.3.1, as appropriate, and pass the CRC-8 check as defined in IEEE Std 802.3, 65.1.3.3.3 or 76.2.6.1.3.3, as appropriate. 
             This object is applicable for an OLT and an ONU.
             At the OLT, it has a distinct value for each logical link interface. 
             Discontinuities of this counter can occur at re-initialization of the management system and at other times, as indicated by the value of the ifCounterDiscontinuityTime object.";
                    reference 
                     "IEEE Std 802.3, 30.3.7.1.5
                      IEEE Std 802.3.1, dot3OmpEmulationGoodLLID";

        }

        leaf ompe-pkts-in-with-good-llid {
          type yang:counter64;
                    units frames;
                    config false;

          description
            "A count of frames received that contain a valid SLD field, as defined in IEEE Std 802.3, 65.1.3.3.1 or 76.2.6.1.3.1 as appropriate, but do not pass the CRC-8 check as defined in IEEE Std 802.3, 65.1.3.3.3 or 76.2.6.1.3.3 as appropriate. 
             This object is applicable for an OLT and an ONU. 
             At the OLT, it has a distinct value for each logical link interface.
             Discontinuities of this counter can occur at re-initialization of the management system and at other times, as indicated by the value of the ifCounterDiscontinuityTime object.";
                    reference 
                     "IEEE Std 802.3, 30.3.7.1.4
                      IEEE Std 802.3.1, dot3OmpEmulationBadLLID";

        }

        leaf ompe-pkts-in {
          type yang:counter64;
                    units frames;
                    config false;

          description
            "A count of frames received that contain a valid SLD field, as defined in IEEE Std 802.3, 65.1.3.3.1 or 76.2.6.1.3.1, as appropriate, and pass the CRC-8 check as defined in IEEE Std 802.3, 65.1.3.3.3 or 76.2.6.1.3.3, as appropriate. 
             This object is applicable for an OLT and an ONU. 
             At the OLT, it has a distinct value for each logical link. 
             Discontinuities of this counter can occur at re-initialization of the management system and at other times, as indicated by the value of the ifCounterDiscontinuityTime object.";
                    reference 
                     "IEEE Std 802.3, 30.3.7.1.6 (ONU) and 30.3.7.1.7 (OLT)
                      IEEE Std 802.3.1, dot3OmpEmulationOnuPonCastLLID (ONU) and dot3OmpEmulationOltPonCastLLID (OLT)";

        }

        leaf ompe-pkts-in-not-match-onu-llid-broadcast {
                    when "../../ompe-mode = 'onu'";

          type yang:counter64;
                    units frames;
                    config false;

          description
            "A count of frames received that contain a valid SLD field, as defined in IEEE Std 802.3, 65.1.3.3.1 or 76.2.6.1.3.1, as appropriate, pass the CRC-8 check, as defined in IEEE Std 802.3, 65.1.3.3.3 or 76.2.6.1.3.3, as appropriate, and contain the broadcast bit in the LLID and not the ONU's LLID (frame accepted) as defined in IEEE Std 802.3, Clause 65 and Clause 76, as appropriate. 
             This object is applicable for an ONU only. 
             Discontinuities of this counter can occur at re-initialization of the management system and at other times, as indicated by the value of the ifCounterDiscontinuityTime object.";
                    reference "IEEE Std 802.3.1, dot3OmpEmulationBroadcastBitNotOnuLlid";

        }

        leaf ompe-pkts-in-match-onu-llid-not-broadcast {
                    when "../../ompe-mode = 'onu'";

          type yang:counter64;
                    units frames;
                    config false;

          description
            "A count of frames received that contain a valid SLD field, as defined in IEEE Std 802.3, 65.1.3.3.1 or 76.2.6.1.3.1, as appropriate, pass the CRC-8 check, as defined in IEEE Std 802.3, 65.1.3.3.3 or 76.2.6.1.3.3, as appropriate, and contain the ONU's LLID (frame accepted) as defined in IEEE Std 802.3, Clause 65 and Clause 76, as appropriate. 
             This object is applicable for an ONU only. 
             Discontinuities of this counter can occur at re-initialization of the management system and at other times, as indicated by the value of the ifCounterDiscontinuityTime object.";
                    reference "IEEE Std 802.3.1, dot3OmpEmulationOnuLLIDNotBroadcast";

        }

        leaf ompe-pkts-in-match-onu-llid-broadcast {
                    when "../../ompe-mode = 'onu'";

          type yang:counter64;
                    units frames;
                    config false;

          description
            "A count of frames received that contain a valid SLD field, as defined in IEEE Std 802.3, 65.1.3.3.1 or 76.2.6.1.3.1, as appropriate, pass the CRC-8 check, as defined in IEEE Std 802.3, 65.1.3.3.3 or 76.2.6.1.3.3, as appropriate, and contain the broadcast bit in the LLID and the ONU's LLID (frame accepted) as defined in IEEE Std 802.3, Clause 65 and Clause 76, as appropriate. 
             This object is applicable for an ONU only. 
             Discontinuities of this counter can occur at re-initialization of the management system and at other times, as indicated by the value of the ifCounterDiscontinuityTime object.";
                    reference "IEEE Std 802.3.1, dot3OmpEmulationBroadcastBitPlusOnuLlid";

        }

        leaf ompe-pkts-in-not-match-onu-llid-not-broadcast {
                    when "../../ompe-mode = 'onu'";

          type yang:counter64;
                    units frames;
                    config false;

          description
            "A count of frames received that contain a valid SLD field, as defined in IEEE Std 802.3, 65.1.3.3.1 or 76.2.6.1.3.1, as appropriate, pass the CRC-8 check, as defined in IEEE Std 802.3, 65.1.3.3.3 or 76.2.6.1.3.3, as appropriate, do not contain the broadcast bit in the LLID and do not the ONU's LLID (frame is NOT accepted) as defined in IEEE Std 802.3, Clause 65 and Clause 76, as appropriate. 
             This object is applicable for an ONU only. 
             Discontinuities of this counter can occur at re-initialization of the management system and at other times, as indicated by the value of the ifCounterDiscontinuityTime object.";
                    reference "IEEE Std 802.3.1, dot3OmpEmulationNotBroadcastBitNotOnuLlid";

        }
      }

      container statistics-fec {
        description "This container defines a set of FEC-related statistics counters of an Ethernet interface implementing MPCP, as defined in IEEE Std 802.3, Clause 65 and Clause 76. ";
                reference "IEEE Std 802.3.1, dot3OmpEmulationStatEntry";


        leaf fec-code-group-violations {
          type yang:counter64;
                    units code-group;
                    config false;

          description
            "For 1G-EPON, it is a count of the number of times an invalid codeword is received, other than the /V/ code-group. The /V/ denotes a special 8b10b codeword of the IEEE Std 802.3 Clause 36 1000 Mb/s PCS layer, reused in 1G-EPON.
             For 10G-EPON, it is a count of the number of times an invalid codeword is received.
             This object is applicable for an OLT and an ONU. 
             At the OLT, it has a distinct value for each logical link. 
             Discontinuities of this counter can occur at re-initialization of the management system and at other times, as indicated by the value of the ifCounterDiscontinuityTime object.";
                    reference 
                     "IEEE Std 802.3, 30.5.1.1.14
                      IEEE Std 802.3.1, dot3EponFecPCSCodingViolation ";

        }

        leaf fec-buffer-head-coding-violations {
                    when "../../fec-capability = 'supported' ../../../fec-mode = 'enabled'";

          type yang:counter64;
                    units code-group;
                    config false;

          description
            "For 1000BASE-PX PHY, this object represents the count of the number of invalid code-group received directly from the link. 
             For 10GBASE-PR or 10/1GBASE-PRX PHYs, this object is always set to zero. 
             This object is applicable for an OLT and an ONU. 
             At the OLT, it has a distinct value for each logical link. 
             Discontinuities of this counter can occur at re-initialization of the management system and at other times, as indicated by the value of the ifCounterDiscontinuityTime object.";
                    reference "IEEE Std 802.3.1, dot3EponFecBufferHeadCodingViolation ";

        }

        leaf fec-code-word-corrected-errors {
                    when "../../fec-capability = 'supported' ../../../fec-mode = 'enabled'";

          type yang:counter64;
                    units code-group;
                    config false;

          description
            "For 1000BASE-PX, 10GBASE-PR or 10/1GBASE-PRX PHYs, it is a count of corrected FEC blocks. 
             This counter increments by one for each received FEC block that contained detected errors and was corrected by the FEC function in the PHY. 
             This object is applicable for an OLT and an ONU. 
             At the OLT, it has a distinct value for each logical link. 
             Discontinuities of this counter can occur at re-initialization of the management system and at other times, as indicated by the value of the ifCounterDiscontinuityTime object.";
                    reference 
                     "IEEE Std 802.3, 30.5.1.1.17
                      IEEE Std 802.3.1, dot3EponFecCorrectedBlocks ";

        }

        leaf fec-code-word-uncorrected-errors {
                    when "../../fec-capability = 'supported' ../../../fec-mode = 'enabled'";

          type yang:counter64;
                    units code-group;
                    config false;

          description
            "For 1000BASE-PX, 10GBASE-PR or 10/1GBASE-PRX PHYs, it is a count of uncorrectable FEC blocks. 
             This counter increments by one for each received FEC block that contained detected errors and was not corrected by the FEC function in the PHY. 
             This object is applicable for an OLT and an ONU. 
             At the OLT, it has a distinct value for each logical link. 
             Discontinuities of this counter can occur at re-initialization of the management system and at other times, as indicated by the value of the ifCounterDiscontinuityTime object.";
                    reference 
                     "IEEE Std 802.3, 30.5.1.1.18
                      IEEE Std 802.3.1, dot3EponFecUncorrectableBlocks ";

        }
      }
            leaf fec-capability {
                type fec-capability;
                config false;
                description 
                 "An object that indicates the support of operation of the optional FEC sublayer of the 1000BASE-PX PHY specified in IEEE Std 802.3, 65.2. 
                  The value of unknown (1) is assigned in the initialization, for non FEC support state or type not yet known. 
                  The value of not supported (3) is assigned when the sublayer is not supported. 
                  The value of supported (2) value is assigned when the sublayer is supported. 
                  This object is applicable for an OLT, with the same value for all logical links, and for an ONU. 
                  All objects in the fec/statistics container will have a zero value when the interface is not supporting FEC. ";
                reference 
                 "IEEE Std 802.3, 30.5.1.1.15
                  IEEE Std 802.3.1, dot3EponFecAbility";
            }
            leaf fec-mode {
                type fec-mode;
                config false;
                description 
                 "An object that defines the mode of operation of the optional FEC sublayer of the 1000BASE-PX PHY, specified in IEEE Std 802.3, 65.2, and reflects its state. 
                  A read operation returns the current mode of operation of the PHY. 
                  The value of unknown (1) is assigned in the initialization for non FEC support state or type not yet known. 
                  The value of disabled (2) is assigned when the FEC sublayer is operating in disabled mode. 
                  The value of enabled (3) is assigned when the FEC sublayer is operating in FEC mode. 
                  At the OLT, it has a distinct value for each logical link. ";
                reference 
                 "IEEE Std 802.3, 30.5.1.1.16
                  IEEE Std 802.3.1, dot3EponFecMode";
            }
            leaf mpcp-mode {
                type mpcp-mode;
                config false;
                description 
                 "This object is used to identify the operational state of the MultiPoint MAC Control sublayer as defined in IEEE Std 802.3, Clause 64 and Clause 77. 
                  Reading olt(1) for an OLT (server) mode and onu(2) for an ONU (client) mode. 
                  This object is used to identify the operational mode for the MPCP objects. 
                  This object is applicable for an OLT, with the same value for all virtual interfaces, and for an ONU. ";
                reference 
                 "IEEE Std 802.3, 30.3.5.1.3
                  IEEE Std 802.3.1, dot3MpcpMode";
            }
            leaf mpcp-sync-time {
                type uint32;
                units "TQ (16ns)";
                config false;
                description 
                 "An object that reports the 'sync lock time' of the OLT receiver in units of Time Quanta (TQ; 1 TQ = 16 ns; see IEEE Std 802.3, Clause 64 and Clause 77). 
                  The value returned shall be equal to [sync lock time ns]/16, rounded up to the nearest TQ. If this value exceeds 2^32 - 1 TQ, the value 2^32 - 1 TQ shall be returned. 
                  This object is applicable for an OLT, with distinct values for all virtual interfaces, and for an ONU. ";
                reference 
                 "IEEE Std 802.3, 64.3.3.2
                  IEEE Std 802.3.1, dot3MpcpSyncTime";
            }
            leaf mpcp-logical-link-id {
                type mpcp-llid;
                config false;
                description 
                 "This object is used to identify the operational state of the MultiPoint MAC Control sublayer as defined in IEEE Std 802.3, Clause 64 and Clause 77. 
                  Reading olt(1) for an OLT (server) mode and onu(2) for an ONU (client) mode. 
                  This object is used to identify the operational mode for the MPCP objects. 
                  This object is applicable for an OLT, with the same value for all virtual interfaces, and for an ONU. ";
                reference 
                 "IEEE Std 802.3, 30.3.5.1.3
                  IEEE Std 802.3.1, dot3MpcpMode";
            }
            leaf mpcp-remote-mac-address {
                type yang:mac-address;
                config false;
                description 
                 "An object that identifies the source_address parameter of the last MPCPDUs passed to the MAC Control. This value is updated on reception of a valid frame with:
                  1) a destination Field equal to the reserved multicast address for MAC Control as specified in IEEE Std 802.3, Annex 31A; 
                  2) the lengthOrType field value equal to the reserved Type for MAC Control as specified in IEEE Std 802.3, Annex 31A; 
                  3) an MPCP subtype value equal to the subtype reserved for MPCP as specified in IEEE Std 802.3, Annex 31A. 
                  This object is applicable for an OLT and an ONU. At the OLT, it has a distinct value for each virtual interface. 
                  The value reflects the MAC address of the remote entity and therefore the OLT holds a value for each LLID, which is the MAC address of the ONU.
                  The ONU has a single value that is the OLT MAC address. ";
                reference 
                 "IEEE Std 802.3, 30.3.5.1.5
                  IEEE Std 802.3.1, dot3MpcpRemoteMACAddress";
            }
            leaf mpcp-logical-link-state {
                type mpcp-state;
                config false;
                description 
                 "An object that identifies the registration state of the MultiPoint MAC Control sublayer as defined in IEEE Std 802.3, Clause 64 and Clause 77. 
                  When this object has the enumeration unregistered(1), the interface is unregistered and may be used for registering a link partner. 
                  When this object has the enumeration registering(2), the interface is in the process of registering a link-partner. 
                  When this object has the enumeration registered(3), the interface has an established link-partner. 
                  This object is applicable for an OLT and an ONU. 
                  At the OLT, it has a distinct value for each virtual interface.";
                reference 
                 "IEEE Std 802.3, 30.3.5.1.6
                  IEEE Std 802.3.1, dot3MpcpRegistrationState";
            }
            leaf mpcp-elapsed-time-out {
                type uint32;
                units "TQ (16ns)";
                config false;
                description 
                 "An object that reports the interval from the last MPCP frame transmission in increments of Time Quanta (TQ; 1 TQ = 16 ns; see IEEE Std 802.3, Clause 64 and Clause 77). 
                  The value returned shall be equal to [interval from last MPCP frame transmission on this Ethernet interface, expressed in ns]/16. If this value exceeds 2^32 - 1 TQ, the value 2^32 - 1 TQ shall be returned. 
                  This object is applicable for an OLT and an ONU. 
                  At the OLT, it has a distinct value for each virtual interface.";
                reference 
                 "IEEE Std 802.3, 30.3.5.1.19
                  IEEE Std 802.3.1, dot3MpcpTransmitElapsed";
            }
            leaf mpcp-elapsed-time-in {
                type uint32;
                units "TQ (16ns)";
                config false;
                description 
                 "An object that reports the interval from the last MPCP frame reception in increments of Time Quanta (TQ; 1 TQ = 16 ns; see IEEE Std 802.3, Clause 64 and Clause 77). 
                  The value returned shall be equal to [interval from last MPCP frame receiption on this Ethernet interface, expressed in ns]/16. If this value exceeds 2^32 - 1 TQ, the value 2^32 - 1 TQ shall be returned. 
                  This object is applicable for an OLT and an ONU. 
                  At the OLT, it has a distinct value for each virtual interface.";
                reference 
                 "IEEE Std 802.3, 30.3.5.1.20
                  IEEE Std 802.3.1, dot3MpcpReceiveElapsed";
            }
            leaf mpcp-round-trip-time {
                type uint16;
                units "TQ (16ns)";
                config false;
                description 
                 "An object that reports the MPCP round trip time in increments of Time Quanta (TQ; 1 TQ = 16 ns; see IEEE Std 802.3, Clause 64 and Clause 77). 
                  The value returned shall be equal to [round trip time in ns]/16. 
                  If this value exceeds 2^16 - 1 TQ, the value 2^16 - 1 TQ shall be returned. 
                  This object is applicable for an OLT. 
                  At the OLT, it has a distinct value for each virtual interface. ";
                reference 
                 "IEEE Std 802.3, 30.3.5.1.21
                  IEEE Std 802.3.1, dot3MpcpRoundTripTime";
            }
            leaf ompe-mode {
                type ompe-mode;
                config false;
                description 
                 "An object that indicates the mode of operation of the Reconciliation Sublayer for Point-to-Point Emulation (see IEEE Std 802.3, 65.1 or 76.2 as appropriate). 
                  The value of unknown(1) is assigned in initialization; true state or type is not yet known. 
                  The value of olt(2) is assigned when the sublayer is operating in OLT mode. 
                  The value of onu(3) is assigned when the sublayer is operating in ONU mode. 
                  This object is applicable for an OLT and an ONU.
                  At the OLT, it has the same value for each logical link interface. ";
                reference 
                 "IEEE Std 802.3, 30.3.7.1.2
                  IEEE Std 802.3.1, dot3OmpEmulationType";
            }
            leaf mpcp-maximum-grant-count {
                type uint8;
                config false;
                description 
                 "An object that reports the maximum number of grants that an ONU can store for handling. The maximum number of grants that an ONU can store for handling has a range of 0 to 255. 
                  This object is applicable for an OLT and an ONU. 
                  At the OLT, it has a distinct value for each virtual interface. 
                  At the OLT, the value should be zero.";
                reference 
                 "IEEE Std 802.3, 30.3.5.1.24
                  IEEE Std 802.3.1, dot3MpcpMaximumPendingGrants";
            }

    }
  }
}
