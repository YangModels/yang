module ethernet {
  namespace "urn:ieee:params:xml:ns:yang:ethernet";
  prefix eth;

  import ietf-interfaces {
    prefix if;
  }

  import iana-if-type {
    prefix ianaift;
  }

  organization
    "Cisco Systems, Inc.
     Customer Service
     
     Postal: 170 W Tasman Drive
     San Jose, CA 95134
     
     Tel: +1 1800 553-NETS
     
     E-mail: cs-yang@cisco.com";

  contact
    "Robert Wilton - rwilton@cisco.com";
  
  description
    "This module contains YANG definitions for configuring 802.3
     Ethernet Interfaces, with the hope that it forms the basis of a
     standardized 802.3 Ethernet interface configuration YANG
     model.";
  
  revision 2015-11-23 {
    description
      "Initial revision of YANG model for IEEE Std 802.3 Ethernet interfaces";
    reference 
        "IEEE Std 802.3-2015, unless explicitly dated in the text.";  
  }
  
  identity eth-if-speed {
    description 
 "Representing the configured or negotiated speed of
  an Ethernet interface.  Definitions are only
  required for PHYs that can run at different speeds
  (e.g. BASE-T).";
  }
  identity eth-if-speed-10mb {
    base eth-if-speed;
    description "10 Mb/s";
  }
  identity eth-if-speed-100mb {
    base eth-if-speed;
    description "100 Mb/s";
  }
  identity eth-if-speed-1gb {
    base eth-if-speed;
    description "1 Gb/s";
  }
  identity eth-if-speed-2.5gb {
    base eth-if-speed;
    description "2.5 Gb/s";
        reference "IEEE P802.3bz (http://www.ieee802.org/3/bz/)";

  }  
  identity eth-if-speed-5gb {
    base eth-if-speed;
    description "5 Gb/s";
        reference "IEEE P802.3bz (http://www.ieee802.org/3/bz/)";

  }  
  identity eth-if-speed-10gb {
    base eth-if-speed;
    description "10 Gb/s";
  }
  identity eth-if-speed-40gb {
    base eth-if-speed;
    description "40 Gb/s";
  }
  identity eth-if-speed-100gb {
    base eth-if-speed;
    description "100 Gb/s";
  }

  typedef flow-control-settings {
    type enumeration {
    
      enum true {
        description 
          "The value of 'true' for IEEE Std 802.3 Ethernet interfaces operating at speeds above 1000 Mb/s that support Rate Control through lowering the average data rate of the MAC sublayer, with frame granularity.
           ";
      }
      
      enum false {
        description
         "The value of 'false' for IEEE Std 802.3 Ethernet interfaces operating at speeds above 1000 Mb/s that do not support Rate Control through lowering the average data rate of the MAC sublayer, with frame granularity.";
      }
    }
    description
      "Enumerates the possible values for the 'rate-control-ability' object";
        reference "IEEE Std 802.3, 30.3.1.1.33, aRateControlAbility";

  }

  typedef rate-control {
       
    type enumeration {
    
      enum disabled {
                value 1;

        description 
          "The Rate Control is disabled";
      }
    
      enum enabled {
                value 2;

        description 
          "The Rate Control is enabled";
      }
    
      enum unknown {
                value 3;

        description 
          "The Rate Control status is undefined";
      }
    }
    description
      "Enumerates the possible values for the 'rate-control-status' object";
        reference "IEEE Std 802.3, 30.3.1.1.34, aRateControlStatus";

  }

  typedef pause-control {
       
    type enumeration {
    
      enum disabled {
                value 1;

        description 
          "The PAUSE Control is disabled";
      }
    
      enum enabled-Tx {
                value 2;

        description 
          "The PAUSE operation is enabled in transmit direction only";
      }
    
      enum enabled-Rx {
                value 3;

        description 
          "The PAUSE operation is enabled in receive direction only";
      }
    
      enum enabled-bidirectional {
                value 4;

        description 
          "The PAUSE operation is enabled in receive and transmit directions";
      }
    }
    description
      "Enumerates the possible values for the 'macc-pause-control' object";
        reference "IEEE Std 802.3.1, dot3PauseAdminMode and dot3PauseOperMode";

  }

  typedef macc-control {
       
    type enumeration {
    
      enum PAUSE {
                value 0;

        description 
          "IEEE Std 802.3 Ethernet PAUSE flow control";
      }
    
      enum MPCP {
                value 1;

        description 
          "IEEE Std 802.3 Ethernet Multi-Point Control Protocol";
      }
    
      enum PFC {
                value 2;

        description 
          "IEEE Std 802.3 Ethernet Priority-based Flow Control";
      }
    }
    description
      "Enumerates the possible values for the 'macc-control' object";
        reference "IEEE Std 802.3.1, dot3ControlFunctionsSupported";

  }

  augment "/if:interfaces/if:interface" {
    when "if:type = 'ianaift:ethernetCsmacd'" {
      description "Applies to all P2P Ethernet interfaces";
    }
    description 
 "Augment interface model with IEEE Std 803.2 Ethernet
  specific configuration nodes";

    container ethernet {
      description
        "Contains all Ethernet interface related configuration";
      choice transmission-mode {
        description
          "Indicates whether the transmission parameters are manually
           configured or automatically negotiated with the peer
           device";
           
        case auto-negotiation {
          description 
 "Transmission parameters are automatically
  negotiated";
                       
          container auto-negotiation {
          
            description
              "Contains auto-negotiation transmission parameters";
            reference "IEEE Std 802.3 section 28 and annexes 28A-D";
            
            leaf status {
            
              type enumeration {
              
                enum enabled {
                  description
                    "Auto-negotiation function is enabled";
                }
                
                enum disabled {
                  description
                    "Auto-negotiation function is disabled";
                }
                
              }
              
              description
                "Allows auto-negotiation to be explicitly
                 enabled/disabled.  If the leaf is not present then
                 the default behaviour is vendor/interface
                 specific.";
            }
            
            leaf duplex {
            
              type enumeration {
              
                enum full {
                  description
                    "Restricts auto-negotiation to advertising full
                     duplex only.  Negotiation will fail, and the
                     link will not come up, if the peer device only
                     allows for half duplex during negotiation.";
                }
                
                enum half {
                  description
                    "Restricts auto-negotiation to advertising half
                     duplex only.  Negotiation will fail, and the
                     link will not come up, if the peer device only
                     allows for full duplex during negotiation.";
                }
                
              }
              
              description
                "Allows the advertised duplex value in the
                 negotiation to be restricted.  Half duplex can
                 only be negotiated for some interface types - as
                 specified in 802.3, annex section 28B.3.  If not
                 specified then the default behaviour is to
                 negotiate all available values for the particular
                 type of Ethernet PHY associated with the
                 interface.";
            }
            
            leaf speed {
            
              type identityref {
                base eth-if-speed;
              }
              
              description
                "Allows the advertised speed value in the negotiation
                 to be restricted. Speed is only negotiated for some
                 PHYs, many higher speed PHYs operate at a fixed
                 speed.  If this leaf is not set then the default
                 behaviour is to negotiate all available speeds,
                 generally choosing the fastest speed as per 802.3
                 Annex 28B.3.";
                 
              reference "IEEE Std 802.3 Annex section 28B.3";
            }
            
            leaf advertised-flow-control {
              type enumeration {
                enum disabled {
                  description
                    "Explicitly prevents ingress or egress
                     flow-control from being negotiated with the peer
                     device.";
                  reference 
 "IEEE Std 802.3 Table 28B-2,
  Capability: No PAUSE";
                  
                }
                enum ingress-only {
                  description
                    "Allows only ingress flow-control to be
                     negotiated with the peer device";
                  reference
                    "IEEE Std 802.3 Table 28B-2, Capability:
                     Asymmetric PAUSE towards link partner";
                  
                }
                enum bi-directional-only {
                  description
                    "Allows only bi-directional flow-control to be
                     negotiated with the peer device.";
                  reference
                    "IEEE Std 802.3 Table 28B-2, Capability:
                     Symmetric PAUSE";
                }
              }
              description
                "By default, the flow control capabilities that are
                 negotiated allows for bi-directional or egress-only
                 flow control to be negotiated (depending on the peer
                 device capabilities/configuration).";
              reference
                "IEEE Std 802.3 Table 28B-2, Capability:
                 Both Symmetric PAUSE and Asymmetric PAUSE toward
                 local device";
            }
            
            leaf forced-flow-control {
              type macc-control;
              description
                "Explicitly force the local flow control settings
                 regardless of what has been negotiated.  Since the
                 auto-negotiation of flow-control settings doesn't
                 allow all sane combinations to be negotiated (e.g.
                 consider a device that is only capable of sending
                 PAUSE frames connected to a peer device that is only
                 capable of receiving and acting on PAUSE frames) and
                 failing to agree on the flow-control settings
                 doesn't cause the auto-negotation to fail
                 completely, then it is sometimes useful to be able
                 to explicitly enable particular flow control
                 settings on the local device regardless of what is
                 being advertised or negotiated";
              reference
                "IEEE Std 802.3 Table 28B-3-Pause resolution";
            }
          }
        }
        
        case manual {
          description
            "Transmission parameters are manually configured (as
             required)";
          container manual {
            description
              "Manually configured transmission parameters";
            leaf duplex {
              type enumeration {
                enum full {
                  description
                    "Forces the interface to run in full duplex
                     mode.";
                  
                }
                enum half {
                  description
                    "Forces the interface to run in half duplex mode.
                     Not applicable to many PHY types.";
                }
              }
              default full;
              description 
 "Configures the interface to run in either
  full or half duplex mode.";
            }
            
            leaf speed {
              type identityref {
                base eth-if-speed;
              }
              description
                "For PHY types that may operate at various speeds,
                 this leaf allows the interface to be forced to
                 operate at a particular speed.  Without any explicit
                 configuration, Ethernet interfaces run at the
                 maximum speed that they are capable of operating
                 at";
            }
            
            leaf flow-control {
              type macc-control;
              description
                "The default flow-control capabilities are
                 vendor/interface specific";
            }
          }
        }
      }
    }
  }
  
  /*
   * Operational State.
   */
  augment "/if:interfaces-state/if:interface" {
    when "if:type = 'ianaift:ethernetCsmacd'" {
      description "Applies to all Ethernet interfaces";
    }
    description 
 "Augments interfaces-state model with 803.2 Ethernet
  specific operational state nodes";

    container Ethernet {
      description
        "Contains operational state for Ethernet interfaces";

      container auto-negotiation {
        presence "Indicates that auto-negotiation is enabled";
        description "Contains auto-negotiation status";
        
        leaf status {
          type enumeration {
            enum successful {
              description
                "Auto-negotation has completed successfully";
            }
            enum failed {
              description "Auto-negotiation has failed";
            }
            enum unknown {
              description
                "The auto-negotiation status is not currently known,
                 this may be because it is still negotiating or the
                 protocol cannot run (e.g. if no medium is present)";
            }
          }
          description
            "The status of the auto-negotiation protocol";
        } 
      }

      leaf duplex {
        type enumeration {
          enum unknown {
                        value 1;

            description 
 "current  duplex mode could not be determined
  ";
                        reference 
                         "IEEE Std 802.3, 30.3.1.1.32, aDuplexStatus
                          ";

          }
          enum half {
                        value 2;

            description "Half duplex";
                        reference "IEEE Std 802.3, 30.3.1.1.32, aDuplexStatus";

          }
          enum full {
                        value 3;

            description "Full duplex";
                        reference "IEEE Std 802.3, 30.3.1.1.32, aDuplexStatus";

          }
        }
        description 
 "The current mode of operation of the IEEE Std 802.3 Ethernet interface. 
  The value of 'unknown' indicates that the current duplex mode could not be determined. 
  The value of 'full' indicates that the IEEE Std 802.3 Ethernet interface operates in full duplex mode. 
  The value of 'half' indicates that the IEEE Std 802.3 Ethernet interface operates in half duplex mode. ";
                reference "IEEE Std 802.3, 30.3.1.1.32, aDuplexStatus";
 
      }
      
      leaf speed {
        type uint64;
        units Mb/s;
        description "Operational speed setting of the interface";
      }
      
      leaf flow-control { 
        type flow-control-settings;
        description
          "Operation flow-control setting on the interface";
      }
            leaf rate-control {
                type rate-control;
                description "The current Rate Control mode of operation of the MAC sublayer of this IEEE Std 802.3 Ethernet interface";
                reference "IEEE Std 802.3, 30.3.1.1.34, aRateControlStatus";
            }
            leaf macc-extension-control {
                type boolean;
                description "A value that identifies the current (when read) or target (when set) operational state of the EXTENSION MAC Control function (when read), as specified in IEEE Std 802.3, Annex 31C.";
                reference 
                 "IEEE Std 802.3, 30.3.8.3 aEXTENSIONMACCtrlStatus
                  IEEE Std 802.3.1, dot3ExtensionMacCtrlStatus ";
            }
            leaf macc-pfc-control {
                type boolean;
                description 
                 "A value that identifies the current (when read) or target (when set) operational state of the PFC MAC Control function (when read), as specified in IEEE Std 802.3, Annex 31C.
                  When set, the value of this object determines the operational PFC mode of the IEEE Std 802.3 Ethernet interface. A set to this object will force the IEEE Std 802.3 Ethernet interface into the specified mode. Note that the value of this object is ignored when the IEEE Std 802.3 Ethernet interface is not operating in full-duplex mode.
                  When read, the value of this object reflects the current operational PFC mode of the IEEE Std 802.3 Ethernet interface.";
                reference 
                 "IEEE Std 802.3, 30.3.3.6, aPFCenableStatus
                  IEEE Std 802.3.1, dot3PFCAdminMode and dot3PFCOperMode";
            }
            leaf macc-pause-control {
                type pause-control;
                description 
                 "A value that identifies the current (when read) or target (when set) operational state of the PAUSE MAC Control function (when read).
                  This object is used to configure the default administrative PAUSE mode for this IEEE Std 802.3 Ethernet interface. 
                  When set, this value of this object represents the administratively-configured PAUSE mode for this IEEE Std 802.3 Ethernet interface. If Auto-Negotiation is not enabled or is not implemented for the active MAU attached to this IEEE Std 802.3 Ethernet interface, the value of this object determines the operational PAUSE mode of the IEEE Std 802.3 Ethernet interface whenever it is operating in full-duplex mode. In this case, a set to this object will force the IEEE Std 802.3 Ethernet interface into the specified mode. If Auto-Negotiation is implemented and enabled for the MAU attached to this IEEE Std 802.3 Ethernet interface, the PAUSE mode for this IEEE Std 802.3 Ethernet interface is determined by Auto-Negotiation, and the value of this object denotes the mode to which the IEEE Std 802.3 Ethernet interface will automatically revert if/when Auto-Negotiation is later disabled. 
                  Note that the value of this object is ignored when the IEEE Std 802.3 Ethernet interface is not operating in full-duplex mode. An attempt to set this object to 'enabled-Tx' or 'enabled-Rx' will fail on IEEE Std 802.3 Ethernet interfaces that do not support operation at greater than 100 Mb/s.\" 
                  When read, the value of this object reflects the current operational PAUSE Control function of the IEEE Std 802.3 Ethernet interface.";
                reference "IEEE Std 802.3.1, dot3PauseAdminMode and dot3PauseOperMode";
            }
            leaf macc-control {
                type macc-control;
                config false;
                description "A list of the possible MAC Control functions implemented for this interface.";
                reference "IEEE Std 802.3.1, dot3ControlFunctionsSupported";
            }
            leaf frame-limit-slow-protocol {
                type uint64;
                units fps;
                default 10;
                description "The maximum number of Slow Protocol frames of a given subtype that can be transmitted in a one second interval. The default value is 10. ";
                reference 
                 "IEEE Std 802.3, 30.3.1.1.38, aSlowProtocolFrameLimit
                  IEEE Std 802.3.1, dot3SlowProtocolFrameLimit";
            }

    }
  }
  
  /*
   * Operational State.
   */
  augment "/if:interfaces-state/if:interface/if:statistics" {
    when "if:type = 'ianaift:ethernetCsmacd'" {
      description "Applies to all IEEE Std 802.3 Ethernet interfaces";
    }
    description "Augments 'statistics' container in ietf-interfaces/interfaces-state model for IEEE Std 802.3 Ethernet interfaces";

    container Ethernet {
      description
        "Contains statistics specific to IEEE Std 802.3 Ethernet interfaces";
            leaf in-pkts-errors-FCS {
                type uint64;
                units frames;
                description 
                 "A count of frames received on a particular interface that are an integral number of octets in length but do not pass the FCS check. This count does not include frames received with frame-too-long or frame-too-short error. The count represented by an instance of this object is incremented when the frameCheckError status is returned by the MAC service to the LLC (or other MAC user). Received frames for which multiple error conditions pertain are, according to the conventions of IEEE 802.3 Layer Management, counted exclusively according to the error status presented to the LLC. Note: Coding errors detected by the Physical Layer for speeds above 10 Mb/s will cause the frame to fail the FCS check. Discontinuities in the value of this counter can occur at re-initialization of the management system, and at other times as indicated by the value of ifCounterDiscontinuityTime.
                  A frame that is counted by an instance of this object is also counted by the corresponding instance of 'in-errors' object.";
                reference "IEEE Std 802.3, 30.3.1.1.6, aFrameCheckSequenceErrors";
            }
            leaf in-pkts-errors-alignment-FCS {
                type uint64;
                units frames;
                description 
                 "A count of frames received on a particular interface that are not an integral number of octets in length and do not pass the FCS check. The count represented by an instance of this object is incremented when the alignmentError status is returned by the MAC service to the LLC (or other MAC user). Received frames for which multiple error conditions pertain are, according to the conventions of IEEE 802.3 Layer Management, counted exclusively according to the error status presented to the LLC. This counter does not increment for group encoding schemes greater than 4 bits per group. Discontinuities in the value of this counter can occur at re-initialization of the management system, and at other times as indicated by the value of ifCounterDiscontinuityTime.
                  A frame that is counted by an instance of this object is also counted by the corresponding instance of 'in-errors' object.";
                reference "IEEE Std 802.3, 30.3.1.1.7, aAlignmentErrors";
            }
            leaf in-giant-pkts {
                type uint64;
                units frames;
                description "A count of frames received on a particular interface that exceed the maximum permitted frame size. The count represented by an instance of this object is incremented when the frameTooLong status is returned by the MAC service to the LLC (or other MAC user). Received frames for which multiple error conditions pertain are, according to the conventions of IEEE 802.3 Layer Management, counted exclusively according to the error status presented to the LLC. Discontinuities in the value of this counter can occur at re-initialization of the management system, and at other times as indicated by the value of ifCounterDiscontinuityTime.";
                reference "IEEE Std 802.3, 30.3.1.1.25, aFrameTooLongErrors";
            }
            leaf in-giant-threshold-pkts {
                type uint64;
                units octets;
                description "This indicates the MAC frame length at which the 'in-giants-pkts' counter is incremented ";
                reference "IEEE Std 802.3, 30.3.1.1.37, aMaxFrameLength";
            }
            leaf in-errors-symbol {
                type uint64;
                units errors;
                description 
                 "For an IEEE Std 802.3 Ethernet operating at 100 Mb/s, the number of times there was an invalid data symbol when a valid carrier was present. 
                  For an IEEE Std 802.3 Ethernet operating in half-duplex mode at 1000 Mb/s, the number of times the receiving media is non-idle (a carrier event) for a period of time equal to or greater than slotTime, and during which there was at least one occurrence of an event that causes the PHY to indicate 'Data reception error' or 'carrier extend error' on the GMII. 
                  For an IEEE Std 802.3 Ethernet operating in full-duplex mode at 1000 Mb/s, the number of times the receiving media is non-idle (a carrier event) for a period of time equal to or greater than minFrameSize, and during which there was at least one occurrence of an event that causes the PHY to indicate 'Data reception error' on the GMII. 
                  For an IEEE Std 802.3 Ethernet operating at 10 Gb/s, 40 Gb/s, and 100 Gb/s, it is a count of the number of times the receiving media is non-idle (the time between the Start of Packet Delimiter and the End of Packet Delimiter) for a period of time equal to or greater than minFrameSize, and during which there was at least one occurrence of an event that causes the PHY to indicate 'Receive Error' on the XGMII, the XLGMII, or the CGMII. The count represented by an instance of this object is incremented at most once per carrier event, even if multiple symbol errors occur during the carrier event. 
                  This count does not increment if a collision is present. 
                  This counter does not increment when the IEEE Std 802.3 Ethernet is operating at 10 Mb/s. 
                  Discontinuities in the value of this counter can occur at re-initialization of the management system, and at other times as indicated by the value of ifCounterDiscontinuityTime ";
                reference 
                 "IEEE Std 802.3, 30.3.2.1.5, aSymbolErrorDuringCarrier
                  ";
            }
            leaf rate-control-ability {
                type boolean;
                description 
                 "The value of 'false' for IEEE Std 802.3 Ethernet interfaces operating at speeds above 1000 Mb/s that do not support Rate Control through lowering the average data rate of the MAC sublayer, with frame granularity.
                  The value of 'true' for IEEE Std 802.3 Ethernet interfaces operating at speeds above 1000 Mb/s that support Rate Control through lowering the average data rate of the MAC sublayer, with frame granularity.";
                reference "IEEE Std 802.3, 30.3.1.1.33, aRateControlAbility";
            }
            container statistics-csmacd {
                description "Group of statistics specific to CSMA/CD operation of selected IEEE Std 802.3 Ethernet interfaces. ";
                leaf in-errors-sqe-test {
                    type uint64;
                    units errors;
                    description 
                     "A count of times that the SQE TEST ERROR is received on a particular interface. The SQE TEST ERROR is set in accordance with the rules for verification of the SQE detection mechanism in the PLS Carrier Sense Function as described in IEEE Std 802.3, 7.2.4.6. 
                      This counter does not increment on IEEE Std 802.3 Ethernet interfaces operating at speeds greater than 10 Mb/s, or on IEEE Std 802.3 Ethernet interfaces operating in full-duplex mode. 
                      Discontinuities in the value of this counter can occur at re-initialization of the management system, and at other times as indicated by the value of ifCounterDiscontinuityTime ";
                    reference 
                     "IEEE Std 802.3, 7.2.4.6, also 30.3.2.1.4,  aSQETestErrors
                      ";
                }
                leaf in-errors-MAC-internal {
                    type uint64;
                    units errors;
                    description 
                     "A count of frames for which reception on a particular IEEE Std 802.3 Ethernet interface fails due to an internal MAC sublayer receive error. 
                      A frame is only counted by an instance of this object if it is not counted by the corresponding instance of either the 'in-pkts-too-long' object, the 'in-pkts-errors-alignment-FCS' object, or the 'in-pkts-errors-FCS' object. The precise meaning of the count represented by an instance of this object is implementation-specific. 
                      In particular, an instance of this object may represent a count of receive errors on a particular IEEE Std 802.3 Ethernet interface that are not otherwise counted. 
                      Discontinuities in the value of this counter can occur at re-initialization of the management system, and at other times as indicated by the value of ifCounterDiscontinuityTime ";
                    reference "IEEE Std 802.3, 30.3.1.1.15, aFramesLostDueToIntMACRcvError";
                }
                leaf out-pkts-collision-single {
                    type uint64;
                    units frames;
                    description 
                     "A count of frames that are involved in a single collision, and are subsequently transmitted successfully. A frame that is counted by an instance of this object is also counted by the corresponding instance of either 'out-unicast-ptks', 'out-broadcast-pkts', or 'out-multicast-pkts', and is not counted by the corresponding instance of the 'out-ptks-collision-multiple'. 
                      This counter does not increment when the IEEE Std 802.3 Ethernet interface is operating in full-duplex mode. 
                      Discontinuities in the value of this counter can occur at re-initialization of the management system, and at other times as indicated by the value of ifCounterDiscontinuityTime. ";
                    reference "IEEE Std 802.3, 30.3.1.1.3, aSingleCollisionFrames";
                }
                leaf out-pkts-collision-multiple {
                    type uint64;
                    units frames;
                    description 
                     "A count of frames that are involved in multiple collisions, and are subsequently transmitted successfully. A frame that is counted by an instance of this object is also counted by the corresponding instance of either 'out-unicast-ptks', 'out-broadcast-pkts', or 'out-multicast-pkts', and is not counted by the corresponding instance of the 'out-ptks-collision-single'. 
                      This counter does not increment when the IEEE Std 802.3 Ethernet interface is operating in full-duplex mode. 
                      Discontinuities in the value of this counter can occur at re-initialization of the management system, and at other times as indicated by the value of ifCounterDiscontinuityTime. ";
                    reference "IEEE Std 802.3, 30.3.1.1.4, aMultipleCollisionFrames";
                }
                leaf out-pkts-deferred {
                    type uint64;
                    units frames;
                    description 
                     "A count of frames for which the first transmission attempt on a particular IEEE Std 802.3 Ethernet interface is delayed because the medium is busy. 
                      A deferred frame that is not subject to any number of collisions is not counted by an instance of 'out-pkts-collision-single' or 'out-pkts-collision-multiple' objects. 
                      This counter does not increment when the IEEE Std 802.3 Ethernet interface is operating in full-duplex mode. 
                      Discontinuities in the value of this counter can occur at re-initialization of the management system, and at other times as indicated by the value of ifCounterDiscontinuityTime. ";
                    reference "IEEE Std 802.3, 30.3.1.1.9, aFramesWithDeferredXmissions";
                }
                leaf out-pkts-collisions-excessive {
                    type uint64;
                    units frames;
                    description 
                     "A count of frames for which transmission on a particular IEEE Std 802.3 Ethernet interface fails due to excessive collisions. 
                      This counter does not increment when the IEEE Std 802.3 Ethernet interface is operating in full-duplex mode. 
                      Discontinuities in the value of this counter can occur at re-initialization of the management system, and at other times as indicated by the value of ifCounterDiscontinuityTime ";
                    reference "IEEE Std 802.3, 30.3.1.1.11, aFramesAbortedDueToXSColls";
                }
                leaf out-collisions-late {
                    type uint64;
                    units collisions;
                    description 
                     "The number of times that a collision is detected on a particular IEEE Std 802.3 Ethernet interface later than one slotTime into the transmission of a packet. 
                      A (late) collision included in a count represented by an instance of this object is also considered as a (generic) collision for purposes of other collision-related statistics. 
                      This counter does not increment when the IEEE Std 802.3 Ethernet interface is operating in full-duplex mode. 
                      Discontinuities in the value of this counter can occur at re-initialization of the management system, and at other times as indicated by the value of ifCounterDiscontinuityTime ";
                    reference "IEEE Std 802.3, 30.3.1.1.10, aLateCollisions";
                }
                leaf out-errors-MAC-internal {
                    type uint64;
                    units errors;
                    description 
                     "A count of frames for which transmission on a particular IEEE Std 802.3 Ethernet interface fails due to an internal MAC sublayer transmit error. 
                      A frame is only counted by an instance of this object if it is not counted by the corresponding instance of either the 'out-collisions-late' object, the 'out-pkts-collisions-excessive' object, or the 'out-errors-carrier-sense' object. The precise meaning of the count represented by an instance of this object is implementation-specific. In particular, an instance of this object may represent a count of transmission errors on a particular IEEE Std 802.3 Ethernet interface that are not otherwise counted. 
                      Discontinuities in the value of this counter can occur at re-initialization of the management system, and at other times as indicated by the value of ifCounterDiscontinuityTime ";
                    reference "IEEE Std 802.3, 30.3.1.1.12, aFramesLostDueToIntMACXmitError";
                }
                leaf out-errors-carrier-sense {
                    type uint64;
                    units errors;
                    description 
                     "The number of times that the carrier sense condition was lost or never asserted when attempting to transmit a frame on a particular IEEE Std 802.3 Ethernet interface. 
                      The count represented by an instance of this object is incremented at most once per transmission attempt, even if the carrier sense condition fluctuates during a transmission attempt. 
                      This counter does not increment when the IEEE Std 802.3 Ethernetinterface is operating in full-duplex mode. 
                      Discontinuities in the value of this counter can occur at re-initialization of the management system, and at other times as indicated by the value of ifCounterDiscontinuityTime ";
                    reference "IEEE Std 802.3, 30.3.1.1.13, aCarrierSenseErrors";
                }
                list collision-histogram {
                    key eth:collision-count;
                    description "A collection of collision histograms for a particular interface.";
                    reference "IEEE Std 802.3, 30.3.1.1.30, aCollisionFrames";
                    leaf collision-count {
                        type uint64;
                        units collisions;
                        description "The number of per-frame media collisions for which a particular collision histogram cell represents the frequency on a particular interface.";
                    }
                    leaf collision-count-pkts {
                        type uint64;
                        units frames;
                        description 
                         "A count of individual MAC frames for which the transmission (successful or otherwise) on a particular interface occurs after the frame has experienced exactly the number of collisions in the associated dot3CollCount object. 
                          For example, a frame which is transmitted on an interface after experiencing exactly 4 collisions would be indicated by incrementing only collision-count-pkts object associated with the collision-count value of 4. No other instance of collision-count-pkts would be incremented in this example. 
                          This counter does not increment when the interface is operating in full-duplex mode. 
                          Discontinuities in the value of this counter can occur at re-initialization of the management system, and at other times as indicated by the value of ifCounterDiscontinuityTime. ";
                    }
                }
            }
            container statistics-macc {
                description "Group of statistics specific to MAC Control operation of selected IEEE Std 802.3 Ethernet interfaces. ";
                reference 
                 "IEEE Std 802.3
                  IEEE Std 802.3.1, dot3ExtensionTable";
                leaf in-pkts-macc-extension {
                    type uint64;
                    units frames;
                    description 
                     "A count of Extension MAC Control frames received on this IEEE Std 802.3 Ethernet interface. 
                      Discontinuities in the value of this counter can occur at re-initialization of the management system, and at other times as indicated by the value of ifCounterDiscontinuityTime. ";
                    reference 
                     "IEEE Std 802.3, 30.3.8.2 aEXTENSIONMACCtrlFramesReceived
                      IEEE Std 802.3.1, dot3HCInExtensionFrames";
                }
                leaf in-pkts-macc-pfc {
                    type uint64;
                    units frames;
                    description 
                     "A count of PFC MAC Control frames received on this IEEE Std 802.3 Ethernet interface. 
                      Discontinuities in the value of this counter can occur at re-initialization of the management system, and at other times as indicated by the value of ifCounterDiscontinuityTime. ";
                    reference "IEEE Std 802.3.1, dot3HCInPFCFrames";
                }
                leaf in-pkts-macc-pause {
                    type uint64;
                    units frames;
                    description 
                     "A count of PAUSE MAC Control frames received on this IEEE Std 802.3 Ethernet interface. 
                      This counter does not increment when the IEEE Std 802.3 Ethernet interface is operating in half-duplex mode 
                      Discontinuities in the value of this counter can occur at re-initialization of the management system, and at other times as indicated by the value of ifCounterDiscontinuityTime. ";
                    reference 
                     "IEEE Std 802.3, 30.3.4.3,aPAUSEMACCtrlFramesReceived
                      IEEE Std 802.3.1, dot3HCInPauseFrames and dot3InPauseFrames";
                }
                leaf in-pkts-macc-unknown {
                    type uint64;
                    units frames;
                    description 
                     "A count of  MAC Control frames with unknown/undefined/unsupported received on this IEEE Std 802.3 Ethernet interface. 
                      This counter does not increment when the IEEE Std 802.3 Ethernet interface is operating in half-duplex mode 
                      Discontinuities in the value of this counter can occur at re-initialization of the management system, and at other times as indicated by the value of ifCounterDiscontinuityTime. ";
                    reference 
                     "IEEE Std 802.3, 30.3.3.5 aUnsupportedOpcodesReceived
                      IEEE Std 802.3.1, dot3ControlInUnknownOpcodes and dot3HCControlInUnknownOpcodes";
                }
                leaf out-pkts-macc-extension {
                    type uint64;
                    units frames;
                    description 
                     "A count of Extension MAC Control frames transmitted on this IEEE Std 802.3 Ethernet interface. 
                      Discontinuities in the value of this counter can occur at re-initialization of the management system, and at other times as indicated by the value of ifCounterDiscontinuityTime. ";
                    reference 
                     "IEEE Std 802.3, 30.3.8.1 aEXTENSIONMACCtrlFramesTransmitted
                      IEEE Std 802.3.1, dot3HCOutExtensionFrames ";
                }
                leaf out-pkts-macc-pfc {
                    type uint64;
                    units frames;
                    description 
                     "A count of PFC MAC Control frames transmitted on this IEEE Std 802.3 Ethernet interface. 
                      Discontinuities in the value of this counter can occur at re-initialization of the management system, and at other times as indicated by the value of ifCounterDiscontinuityTime. ";
                    reference "IEEE Std 802.3.1, dot3HCOutPFCFrames ";
                }
                leaf out-pkts-macc-pause {
                    type uint64;
                    units frames;
                    description 
                     "A count of PAUSE MAC Control frames transmitted on this IEEE Std 802.3 Ethernet interface. 
                      This counter does not increment when the IEEE Std 802.3 Ethernet interface is operating in half-duplex mode 
                      Discontinuities in the value of this counter can occur at re-initialization of the management system, and at other times as indicated by the value of ifCounterDiscontinuityTime. ";
                    reference 
                     "IEEE Std 802.3, 30.3.4.2,aPAUSEMACCtrlFramesTransmitted
                      IEEE Std 802.3.1, dot3HCOutPauseFrames and dot3OutPauseFrames";
                }
            }
            container statistics-lpi {
                description "Group of statistics specific to MAC Control operation of selected IEEE Std 802.3 Ethernet interfaces. ";
                leaf in-lpi-transiton-count {
                    type uint64;
                    units microsends;
                    description 
                     "A count of occurrences of the transition from DEASSERT to ASSERT of the LPI_INDICATE parameter. The indication reflects the state of the PHY according to the requirements of the RS (see IEEE Std 802.3 22.7, 35.4, and 46.4). 
                      This counter has a maximum increment rate of 50 000 counts per second at 100 Mb/s; 90 000 counts per second at 1000 Mb/s; and 230 000 counts per second at 10 Gb/s. ";
                    reference "IEEE Std 802.3, 30.3.2.1.11 aReceiveLPITransitions";
                }
                leaf in-lpi-ms {
                    type uint64;
                    units microsends;
                    description 
                     "A count reflecting the amount of time that the LPI_REQUEST parameter has the value ASSERT. 
                      The request is indicated to the PHY according to the requirements of the RS (see IEEE Std 802.3 22.7, 35.4, and 46.4). 
                      This counter has a maximum increment rate of 1 000 000 counts per second. ";
                    reference "IEEE Std 802.3, 30.3.2.1.8 aTransmitLPIMicroseconds";
                }
                leaf out-lpi-transiton-count {
                    type uint64;
                    units microsends;
                    description 
                     "A count of occurrences of the transition from state LPI_DEASSERTED to state LPI_ASSERTED of the LPI transmit state diagram is the RS. The state transition corresponds to the assertion of the LPI_REQUEST parameter. The request is indicated to the PHY according to the requirements of the RS (see IEEE Std 802.3 22.7, 35.4, 46.4.) 
                      This counter has a maximum increment rate of 50 000 counts per second at 100 Mb/s; 90 000 counts per second at 1000 Mb/s; and 230 000 counts per second at 10 Gb/s. ";
                    reference "IEEE Std 802.3, 30.3.2.1.10 aTransmitLPITransitions";
                }
                leaf out-lpi-ms {
                    type uint64;
                    units microsends;
                    description 
                     "A count reflecting the amount of time that the LPI_INDICATION parameter has the value ASSERT. 
                      The request is indicated to the PHY according to the requirements of the RS (see IEEE Std 802.3 22.7, 35.4, and 46.4). 
                      This counter has a maximum increment rate of 1 000 000 counts per second. ";
                    reference "IEEE Std 802.3, 30.3.2.1.9 aReceiveLPIMicroseconds";
                }
            }

    }
  }
}
