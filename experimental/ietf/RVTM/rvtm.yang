module rvtm {
  namespace "urn:ietf:params:xml:ns:yang:rvtm";
  prefix rvtm;

     import ietf-inet-types {
       prefix "inet";
     }

     //import ietf-interfaces {
       //prefix "if";
     //}

  organization "IETF NETMOD (NETCONF Data Modeling Language) Working Group";
  contact
    "WG Web:   <http://tools.ietf.org/wg/netmod/>
     WG List:  <mailto:netmod@ietf.org>
     
     WG Chair: Juergen Schoenwaelder
               <mailto:j.schoenwaelder@jacobs-university.de>

     WG Chair: Tom Nadeau
               <mailto:tnadeau@brocade.com>
     
     Editor:   Agrahara Kiran Koushik
               <mailto:kkoushik@brocade.com>

     Editor:   Ramki Krishnan
               <mailto:ramk@brocade.com>";
  description
    "This module contains a collection of YANG definitions 
     for RVTM(Real-Time Volumetric Traffic Management).";

  revision 2014-06-17 {
    description
      "Initial revision.";
  }

      grouping TRAFFIC-PATTERN {
         description "Definitions for various attack traffic patterns";

         leaf reflection-attack-traffic-pattern {
            description "Represent all types of Reflection attack traffic
                         pattern";
 
            type enumeration {
               enum ntp-reflection-attack-pattern {
                 value "0";
                 description "NTP Reflection attack traffic pattern";
               }

               enum dns-reflection-attack-pattern {
                 value "1";
                 description "DNS Reflection attack traffic pattern";
               }
             }
         } 

         leaf flood-attack-traffic-pattern {
            description "Represent all types of Flood attack traffic
                         pattern";
 
            type enumeration {
               enum udp-flood-attack-pattern {
                 value "0";
                 description "UDP flood attack traffic pattern";
               }

               enum icmp-flood-attack-pattern {
                 value "1";
                 description "ICMP flood attack traffic pattern";
               }
               enum syn-flood-attack-pattern {
                 value "2";
                 description "SYN flood attack traffic pattern";
               }
            }
         }
      }


     grouping MITIGATION-ACTIONS {
            choice flow-handling {
                case drop {
                   leaf drop-packet {
                      type empty;
                   }
                }
                case re-mark {
                    leaf dscp {
                     type uint8;
                    }
                    leaf onep {
                     type uint8;
                    }
                }
               
                case rate-limit {
                    leaf Mbps {
                     type uint32;
                    }
                }

                case re-direct {
                    leaf nexthop {
                     type inet:ipv4-address;
                    }

                    leaf tunnel-id {
                     type uint32;
                    }

                    leaf lag-id {
                     type uint32;
                    }

                    leaf outgoing-interface {
                     type uint32; //if:interface-ref;
                    }
                }
            }
      }

  container rvtm-cfg {
    description
      "Configuration container for RVTM";
    config true;

    list match-pattern-entries {
      description
        "List of entries with patterns to match";

      key pattern-name;
        //ordered-by-user;
        leaf pattern-name {
           description "Name of this Matching pattern rule";
           type string;
        }
      
      container rvtm-traffic-pattern {
         description "Specific Traffic pattern to match";
         uses TRAFFIC-PATTERN;
      }
      
      container rvtm-mitigation-actions {
         description "Define Mitigation Action criteria";
         uses MITIGATION-ACTIONS;
      }

     leaf bandwidth-threshold {
       description "Bandwidth Threshold to start a trigger";
       type uint32;
       units "MBPS";
     }          
   }
  }


  container rvtm-oper {
    description
      "Operational data container for RVTM";
    config false;

    list rvtm-matched-entries {
      description
        "List of attack patterns matched and mitigation actions applied";

      key sequence-number;
      //ordered-by-system;
      leaf sequence-number {
         description "Index into the matched entry";
         type uint64;
        }
      leaf pattern-name {
         description "Name of this Matched pattern rule";
         type string;
      }
      container rvtm-traffic-patterns-matched {
         description "Traffic patterns matched";
         uses TRAFFIC-PATTERN;
      }
      
      container rvtm-mitigation-actions-applied {
         description "Mitigation actions applied";
         uses MITIGATION-ACTIONS;
      }

     leaf bandwidth-threshold-used {
       description " What is this used for Ramki?";
       type uint32;
       units "MBPS";
     } 
   }
  }

   notification rvtm-detect-notification {
      description   
        "This notification is sent to the NMS when an attack pattern is
         matched and a mitigation action is applied.";

      container rvtm-detect-notif-seq-number {
         leaf seq-num {
            type leafref {
               path "/rvtm:rvtm-oper/rvtm:rvtm-matched-entries/rvtm:sequence-number";
            }
            description   
              "Automagically generated leafref leaf to identify matched entry.";
         }
      }
   }
}
