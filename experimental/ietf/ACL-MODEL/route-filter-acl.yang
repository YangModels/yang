module route-filter-acl {
  yang-version 1;

  namespace "urn:juniper:params:xml:ns:yang:rtf-acl";

  prefix rtf-acl;

  import ietf-inet-types {
    prefix "types";    
  }
  
  import ietf-acl {
    prefix "ietf-acl";
  }

  organization "Juniper Networks";
  contact "Dean Bogdanovic <deanb@juniper.net>";

  revision 2014-08-15 {
    description "creating Route-Filter extensions to ietf-acl model";
  }

  augment "/ietf-acl:access-list/ietf-acl:access-list-entries/ietf-acl:matches" {
    choice route-prefix{
      description "Define route filter match criteria";
      case range {
        choice ipv4-range {
	  leaf v4_lower_bound {
	    type types:ipv4-prefix;
	  }
	  leaf v4_upper_bound {
	    type types:ipv4-prefix;
	  }
	  mandatory true;
	}
	choice ipv6-range {
	  leaf v6_lower_bound {
	    type types:ipv6-prefix;
	  }
	  leaf v6_upper_bound {
	    type types:ipv6-prefix;
	  }
	  mandatory true;
	}
      }
    }
  }
}
