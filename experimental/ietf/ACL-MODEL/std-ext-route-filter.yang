module std-ext-route-filter {
  yang-version 1;

  namespace "urn:ietf:params:xml:ns:yang:ietf-route-filter";

  prefix std-ext-route-filter;

  import ietf-inet-types {
  	prefix "inet";
  }

  import ietf-acl {
  	prefix "ietf-acl";
  }
  organization
  "IETF NETMOD (NETCONF Data Modeling Language) Working Group";

  contact
  "WG Web: http://tools.ietf.org/wg/netmod/
  WG List: netmod@ietf.org

  WG Chair: Juergen Schoenwaelder
  j.schoenwaelder@jacobs-university.de

  WG Chair: Tom Nadeau
  tnadeau@lucidvision.com

  Editor: Dean Bogdanovic
  deanb@juniper.net

  Editor: Kiran Agrahara Sreenivasa
  kkoushik@brocade.com

  Editor: Lisa Huang
  yihuan@cisco.com

  Editor: Dana Blair
  dblair@cisco.com";

  description "
    This module describes route filter as a collection of
    match prefixes. When specifying a match prefix, you
    can specify an exact match with a particular route or
    a less precise match. You can configure either a
    common action that applies to the entire list or an
    action associated with each prefix.
    ";

  revision 2015-02-14 {
    description "creating Route-Filter extension model based on ietf-acl model";
    reference " ";
  }

  augment "/ietf-acl:access-lists/ietf-acl:access-list/ietf-acl:access-list-entries/ietf-acl:access-list-entry/ietf-acl:matches"{
    description "
      This module augments the matches container in the ietf-acl
      module with route filter specific actions
      ";
    choice route-prefix{
      description "Define route filter match criteria";
      case range {
        description "
        Route falls between the lower prefix/prefix-length and the upper
        prefix/prefix-length.
        ";
        choice ipv4-range {
          description "Defines the lower IPv4 prefix/prefix range";
          leaf v4-lower-bound {
            type inet:ipv4-prefix;
            description "Defines the lower IPv4 prefix/prefix length";
          }
          leaf v4-upper-bound {
            type inet:ipv4-prefix;
            description "Defines the upper IPv4 prefix/prefix length";
          }
        }
        choice ipv6-range {
          description "Defines the IPv6 prefix/prefix range";
          leaf v6-lower-bound {
            type inet:ipv6-prefix;
            description "Defines the lower IPv6 prefix/prefix length";
          }
          leaf v6-upper-bound {
          	type inet:ipv6-prefix;
          	description "Defines the upper IPv6 prefix/prefix length";
          }
        }
      }
    }
  }
}
