module ietf-syslog-types {
  namespace "urn:ietf:params:xml:ns:yang:ietf-syslog-types";
  prefix syslogtypes;

  organization "IETF NETMOD (NETCONF Data Modeling Language) Working Group";
  contact
    "WG Web:   <http://tools.ietf.org/wg/netmod/>
     WG List:  <mailto:netmod@ietf.org>
     
     WG Chair: David Kessens
               <mailto:david.kessens@nsn.com>
     
     WG Chair: Juergen Schoenwaelder
               <mailto:j.schoenwaelder@jacobs-university.de>
     
     Editor:   Ladislav Lhotka
               <mailto:lhotka@nic.cz>";
  description
    "This module contains a collection of YANG type definitions for Syslog.";

  revision 2014-06-03 {
    description
      "Version 1.0";
  }

  typedef Severity {
    type enumeration {
      enum "emergency" {
        value 0;
        description
          "Emergency Level Msg";
      }
      enum "alert" {
        value 1;
        description
          "Alert Level Msg";
      }
      enum "critical" {
        value 2;
        description
          "Critical Level Msg";
      }
      enum "error" {
        value 3;
        description
          "Error Level Msg";
      }
      enum "warning" {
        value 4;
        description
          "Warning Level Msg";
      }
      enum "notice" {
        value 5;
        description
          "Notification Level Msg";
      }
      enum "info" {
        value 6;
        description
          "Informational Level Msg";
      }
      enum "debug" {
        value 7;
        description
          "Debugging Level Msg";
      }
    }
    description
      "The definitions for Syslog message severity.";
  }

  identity syslog-facility {
    description
      "The base identity to represent syslog facilities";
  }

  identity kern {
    base syslog-facility;
  }

  identity user {
    base syslog-facility;
  }

  identity mail {
    base syslog-facility;
  }

  identity daemon {
    base syslog-facility;
  }

  identity auth {
    base syslog-facility;
  }

  identity syslog {
    base syslog-facility;
  }

  identity lpr {
    base syslog-facility;
  }

  identity news {
    base syslog-facility;
  }

  identity uucp {
    base syslog-facility;
  }

  identity cron {
    base syslog-facility;
  }

  identity authpriv {
    base syslog-facility;
  }

  identity ftp {
    base syslog-facility;
  }

  identity ntp {
    base syslog-facility;
  }

  identity audit {
    base syslog-facility;
  }

  identity console {
    base syslog-facility;
  }

  identity cron2 {
    base syslog-facility;
  }

  identity local0 {
    base syslog-facility;
  }

  identity local1 {
    base syslog-facility;
  }

  identity local2 {
    base syslog-facility;
  }

  identity local3 {
    base syslog-facility;
  }

  identity local4 {
    base syslog-facility;
  }

  identity local5 {
    base syslog-facility;
  }

  identity local6 {
    base syslog-facility;
  }

  identity local7 {
    base syslog-facility;
  }
}
