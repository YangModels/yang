module newco-acl {
    yang-version 1;

    namespace "urn:newco:params:xml:ns:yang:newco-acl";

    prefix newco-acl;

    import ietf-acl {
      prefix "ietf-acl";
    }

    revision 2014-05-21{
      description "creating newo proprietary extensions to ietf-acl model";
    }

    augment "/ietf-acl:access-list/ietf-acl:access-list-entries/ietf-acl:matches" {
      description "Newco proprietry simple filter matches";
         choice protocol-payload-choice {
           list protocol-payload {
             key value-keyword;
             ordered-by user;
             description "Match protocol payload";
             uses match-simple-payload-protocol-value;
           }
      }   
    }

    augment "/ietf-acl:access-list/ietf-acl:access-list-entries/ietf-acl:actions" {
      description "Newco proprietary simple filter actions";
      choice action {
         case count {
            description "Count the packet in the named counter";
               leaf count {
                  type string;
               }
            }
         case policer {
           description "Name of policer to use to rate-limit traffic";
            leaf policer {
               type string;
            }
         }
         case hiearchical-policer {
           description "Name of hierarchical policer to use to rate-limit traffic";
           leaf hierarchitacl-policer{
              type string;
           }
         }
      }
    }

  grouping match-simple-payload-protocol-value {
     leaf value-keyword {
       description "(null)";
       type enumeration {
         enum icmp {
           description "Internet Control Message Protocol";
         }
         enum icmp6 {
           description "Internet Control Message Protocol Version 6";
         }
         enum range {
           description "Range of values";
         }
       }
     }
   }
}
