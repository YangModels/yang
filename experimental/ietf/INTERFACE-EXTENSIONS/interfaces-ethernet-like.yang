module interfaces-ethernet-like {
  namespace "urn:ietf:params:xml:ns:yang:interfaces-ethernet-like";
  prefix ethlike;

  import ietf-interfaces {
    prefix if;
  }

  import ietf-yang-types {
    prefix yang;
  }
  
  import iana-if-type {
    prefix ianaift;
  }

  organization
    "Cisco Systems, Inc.
     Customer Service

     Postal: 170 W Tasman Drive
     San Jose, CA 95134

     Tel: +1 1800 553-NETS
     
     E-mail: cs-yang@cisco.com";

  contact
    "Robert Wilton - rwilton@cisco.com";
    
  description
    "This module contains YANG definitions for configuration for
     'Ethernet-like' interfaces.  It is applicable to all interface
     types that use Ethernet framing and expose an Ethernet MAC
     layer, and includes such interfaces as physical Ethernet
     interfaces, Ethernet LAG interfaces and VLAN sub-interfaces.";
  
  revision 2015-06-26 {
    description "Updated reference to new internet draft name.";
    
    reference
      "Internet draft: draft-wilton-netmod-intf-ext-yang-00";
  }

  /*
   * Configuration parameters for Etherlike interfaces.
   */
  augment "/if:interfaces/if:interface" {
    when "if:type = 'ianaift:ethernetCsmacd' or
          if:type = 'ianaift:ieee8023adLag' or
          if:type = 'ianaift:l2vlan' or
          if:type = 'ianaift:ifPwType'"   {
      description "Applies to all Ethernet-like interfaces";
    }
    description
      "Augment the interface model with configuration parameters for
       all Ethernet-like interfaces";

    container ethernet-like {
      description "Contains configuration parameters for interfaces
                   that use Ethernet framing and expose an Ethernet
                   MAC layer.";
      leaf mac-address {
        type yang:mac-address;
        description
          "The configured MAC address of the interface.";
      }
    }
  }
  
  /*
   * Operational state for Etherlike interfaces.
   */
  augment "/if:interfaces-state/if:interface" {
    when "if:type = 'ianaift:ethernetCsmacd' or
          if:type = 'ianaift:ieee8023adLag' or
          if:type = 'ianaift:l2vlan' or
          if:type = 'ianaift:ifPwType'"   {
      description "Applies to all Ethernet-like interfaces";
    }
    description
      "Augments the interface model with operational state parameters
       for all Ethernet-like interfaces.";
    container ethernet-like {
      description "Contains operational state parameters for
                   interfaces that use Ethernet framing and expose an
                   Ethernet MAC layer.";
      leaf mac-address {
        type yang:mac-address;
        description
          "The operational MAC address of the interface, if
           applicable";
      }
      
      leaf bia-mac-address {
        type yang:mac-address;
        description
          "The 'burnt-in' MAC address.  I.e the default MAC address
           assigned to the interface if none is explicitly
           configured.";
      }
    }
  }
}
