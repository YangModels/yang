module ietf-erp {
  namespace "urn:ietf:params:xml:ns:yang:ietf-erp";
  prefix erp;

  import ietf-yang-types {
    prefix yang;
  }

  import ietf-interfaces {
    prefix "if";
  }

  import dot1q-types  {
    prefix "dot1q";
  }

  organization "Cisco Systems, Inc.";
  contact
    "Cisco Systems, Inc.
    Customer Service

    Postal: 170 W Tasman Drive
    San Jose, CA 95134

    Tel: +1 1800 553-NETS

    E-mail: cs-yang@cisco.com";

  description
    "This YANG module describes configuration and operational
     data model for ITU.T G.8032 Ethernet Ring Protocol (ERP).

     G.8032 provides a loop avoidance and protection switching
     mechanism in ethernet ring network.

            -----                 -----
           |  A  |---------------|  B  |
            -----                 -----
              |                     |
              |        Ring         |
              |                     |
            -----                 -----
           |  D  |---------------|  C  |
            -----                 -----

     A Ethernet ring node is connected to adjacent Ethernet ring
     nodes participating in the same Ethernet ring, using two
     independent links. A ring link is bounded by two adjacent
     Ethernet ring nodes and a port for a ring link is called a
     ring port. The minimum number of Ethernet ring nodes in
     an Ethernet ring is two.

     An Automatic Protection Switching(APS) protocol is used to
     coordinate the protection actions over the ring.

      APS:   Automatic Protection Switching
      CCM:   Continuity Check Message
      DNF:   Do Not Flush
      ERP:   Ethernet Ring Protection
      PDU:   Protocol Data Unit
      R-APS: Ring APS
      RPL:   Ring Protection Link
      STP:   Spanning Tree Protocol
      VLAN:  Virtual LAN
      VPLS:  Virtual Private LAN Service
      WTB:   Wait To Block
      WTR:   Wait To Restore";
  revision 2015-07-13 {
    description
      "Proposed";
    reference
      "Rec. ITU-T G.8032/Y.1344 (02/2012)";
  }

  feature sub-ring {
    description
      "This feature represents ability to support G.8032 sub-ring
      without R-APS virtual channel";
    reference
      "Rec. ITU-T G.8032/Y.1344 (02/2012), Section 9.7.3";
  }

  feature sub-ring-virtual-channel {
    description
      "This feature represents ability to support G.8032 ring with
       R-APS virtual channel.";
    reference
      "Rec. ITU-T G.8032/Y.1344 (02/2012), Section 9.7.3";
  }

  feature ring-profile-template {
    description
      "This feature represents ability to support profile
       templates.";
  }

  typedef ring-type {
    type enumeration {
      enum major-ring {
        description
          "G.8032 major ring. In this type of rings, nodes are
           connected in full circular topology.";
      }
      enum sub-ring {
        description
          "G.8032 sub-ring or open-ring. This type does not support
           R-APS virtual channel.";
      }
      enum sub-ring-with-virtual-channel {
        description
          "G.8032 sub-ring or open-ring with support to R-APS virtual
           channel.";
      }
    }
    description
      "Supported ring topologies.";
  }

  typedef reversion-mode {
    type enumeration {
      enum revertive {
        description
          "Represents revertive mode operation of a G.8032
           ethernet ring.";
      }
      enum non-revertive {
        description
          "Represents non-revertive mode operation of a G.8032
           ethernet ring.";
      }
    }
    description
      "This typedef defines G.8032 ring protection operation mode.";
    reference
      "Rec. ITU-T G.8032/Y.1344 (02/2012), Section 9.2";
  }

  typedef rpl-port-type {
    type enumeration {
      enum normal {
        description
          "Represents normal node in the ring.";
      }
      enum owner {
        description
          "Represents owner node in the ring.";
      }
      enum neighbour {
        description
          "Represents neighbour node in the ring.";
      }
      enum next-neighbour {
        description
          "Represents next-neighbour node in the ring.";
      }
    }
    description
      "Ring port role types.";
  }

  typedef ring-state {
    type enumeration {
      enum initializing {
        description
          "Ring protocol state machine is initializing and it is not
           yet operational.";
      }
      enum idle {
        description
          "Ring is operational in normal state, RPL link is blocked
           and no failure or administrative condition exists. Owner
           node is transmitting R-APS (NR, RB) PDUs.";
      }
      enum pending {
        description
          "Ring does not have any failure or administrative condition
           however RPL is blocked. In case of revertive mode
           operation wait-to-restore timer is running.";
      }
      enum protection {
        description
          "One or more failure condition exists on the ring. Failed
           nodes are transmitting R-APS (SF) PDUs. Upon reaching to
           protection state ring unblocks RPL link to allow user
           traffic.";
      }
      enum manual-switch {
        description
          "User has manually switched ring. This is usually done to
           perform maintenance operation on the ring node.";
      }
      enum force-switch {
        description
          "User has force-switched ring. This state overrides
           protection state.";
      }
    }
    description
      "Protocol states for a ring instance.";
  }

  typedef ring-id-type {
    type uint8 {
      range "1..255";
    }
    description
      "G.8032 Ring ID";
  }

  typedef port-id-type {
    type enumeration {
      enum port0 {
        description
          "Port 0 of the ring node.";
      }
      enum port1 {
        description
          "Port 1 of the ring node.";
      }
    }
    description
      "Each ring instance has maximum of two ports. This definition
       labels these ports as port0 and port1 for identifications.";
  }

  grouping ring-identifier {
    description
      "This grouping defines ring-name and ring id combination.";
    leaf ring-name {
      type string;
      mandatory true;
      description
        "G.8032 ring name.";
    }

    leaf ring-id {
      type ring-id-type;
      mandatory true;
      description
        "G.8032 Ring instance id.";
    }

    leaf aps-vlan {
      type dot1q:dot1q-vlan-id;
      mandatory true;
      description
        "APS channel VLAN-ID";
    }
  }

  grouping ring-profile-config {
    description
      "This grouping defines configuration parameters for ring
      instance.";
    leaf mode {
      type reversion-mode;
      default revertive;
      description
        "This leaf defines G.8032 ring protection mode. A ring
         may operate in revertive or non-revertive mode.

         In revertive operation, after the condition(s) causing a
         switch has cleared, the traffic channel is restored to
         the working transport entity, i.e., blocked on the RPL.

         In non-revertive operation, the traffic channel
         continues to use the RPL, if it has not failed, after a
         switch condition has cleared.";
      reference
        "Rec. ITU-T G.8032/Y.1344 (02/2012), Section 9.2";
    }

    container timers {
      description
        "This container defines G.8032 timers.";
      leaf guard {
        type uint16 {
          range "10..2000";
        }
        units "milliseconds";
        default "500";
        description
          "The guard timer is used to prevent Ethernet ring nodes
           from acting upon outdated R-APS messages and prevents
           the possibility of forming a closed loop.

           This timer period SHOULD be greater than the maximum
           expected forwarding delay in which an R-APS message
           traverses the entire ring.

           The period of the guard timer MAY be configured by the
           operator in 10 ms steps between 10 ms and 2 seconds";
        reference
          "Rec. ITU-T G.8032/Y.1344 (02/2012), Section 10.1.5";
      }

      leaf wtr {
        type uint8 {
          range "1..12";
        }
        units "minutes";
        default "5";
        description
          "In revertive mode the 'wait to restore' (WTR) timer
           is used to prevent frequent operation of the
           protection switching due to intermittent signal
           failure defects.

           When recovering from a Signal fail, the delay timer
           must be long enough to allow the recovering network to
           become stable.

           WTR timer is activated on RPL owner node. When WTR
           timer is expired RPL owner node initiates the
           reversion process by transmitting an R-APS (NR, RB)
           message.";
        reference
          "Rec. ITU-T G.8032/Y.1344 (02/2012), Section 10.1.4";
      }

      leaf hold-off {
        type uint16 {
          range "0..10000";
        }
        units "milliseconds";
        default "0";
        description
          "The hold-off timer is used to coordinate the timing of
           protection switches.

           When a new defect or more severe defect occurs
           (new SF), this event is not to be reported immediately
           to protection switching if the provisioned hold-off
           timer value is non-zero. Instead, the hold-off timer
           is started. When the hold-off timer expires, the trail
           that started the timer is checked as to whether a
           defect still exists. If one does exist, that defect is
           reported to protection switching.

           Hold off timer values SHOULD be specified in multiple of
           100";
        reference
          "Rec. ITU-T G.8032/Y.1344 (02/2012), Section 10.1.8";
      }
    }
  }

  //config container
  container erp-config {
    description
      "This container defines configuration data elements for G.8032
       ring.";

    leaf notification-enabled {
      type boolean;
      default false;
      description
        "Enable/disable ring status change notification.

         If true, any change in ring state will be notified via
        'ring-state-change' notification.";
    }

    container profiles {
      if-feature ring-profile-template;
      description
        "This container defines G.8032 ring profiles.";
      list profile {
        key "name";
        description
          "G.8032 ring profile name.";

        leaf name {
          type string {
            length "1..32";
          }
          description
            "Name of a ring profile.";
        }

        uses ring-profile-config {
          description
            "Ring mode and timer configurations";
        }
      }
    }

    container rings {
      description
        "This container defines configuration model of G.8032
         rings.";
      list ring {
        key "name";
        description
          "Collection of G.8032 rings configurations on a device.";
        leaf name {
          type string {
            length "1..255";
          }
          description
            "G.8032 ring name. This leaf uniquely identifies a ring
             on the network device.";
        }

        leaf description {
          type string {
            length "1..255";
          }
          description
            "Textual description of the ring.";
        }

        leaf ring-type {
          type ring-type;
          default major-ring;
          description
            "This leaf defines type of a ethernet ring. A ring can be
             configured as complete ring where ring nodes are
             connected in closed loop. In another configuration
             variation a ring may not have a complete closed loop,
             such ring is defined as open-ring or sub-ring.";
        }

        container ring-ports {
          description
            "Ring port configurations.";
          list port {
            key "port-id";
            max-elements 2;
            description
              "List of the ring ports. This list MUST have at least
              one port (in case of sub-ring) and at most two ports.";
            leaf port-id {
              type port-id-type;
              description
                "Port identifier (port0 or port1).";
            }

            leaf interface {
              type if:interface-ref;
              mandatory true;
              description
                "Reference to an ethernet interface. ";
            }
          }
        }

        leaf excluded-vlan-ids {
          type dot1q:dot1q-vlan-id-ranges;
          description
            "List of VLAN-IDs not protected by ring instance. For
             example '50-60,90,1000-4000'

             Exclusion list defines VLANs that are not directly
             controlled by G.8032 ring instances on ring ports. VLANs
             which are neither part of this list nor controlled by
             ring instances, are explicitly blocked on the ring
             ports.";
        }

        container instances {
          description
            "A physical topology ring may contain one or more ring
             instances. Each ring instance is responsible for
             protection of a subset of VLAN traffic on the physical
             ring.";
          list instance {
            key "ring-id aps-vlan";
            max-elements 255;
            description
              "Collection of G.8032 ring instances.";

            leaf ring-id {
              type ring-id-type;
              description
                "G.8032 ring instance identifier (Ring ID). ";
            }

            leaf aps-vlan {
              type dot1q:dot1q-vlan-id;
              description
                "APS channel VLAN-ID";
            }

            leaf description {
              type string {
                length "1..255";
              }
              description
                "Textual description of the ring instance.";
            }

            leaf profile-name {
              if-feature ring-profile-template;
              type string;
              description
                "G.8032 ring profile name. If this profile exists
                 in the profile configuration list, profile
                 parameters will be imported from it, default
                 values will be used otherwise.

                 Profile parameters imported by this template can
                 be overridden by directly configured parameters
                 under 'profile-parameters' container.
                 ";
            }

            container profile-parameters {
              description
                "Ring profile parameters configurations.";
              uses ring-profile-config {
                description
                  "Ring mode and timer configurations.";
              }
            }

            leaf vlan-ids {
              type dot1q:dot1q-vlan-id-ranges;
              mandatory true;
              description
                "List of VLAN-IDs, protected by ring instance. For
                example '2, 3-7, 9, 10-100'

                VLAN-IDs MUST not overlap with VLAN-IDs of any other
                instance of the same physical ring or with excluded
                VLAN-IDs.";
            }

            leaf aps-level {
              type uint8 {
                range "0..7";
              }
              default 0;
              description
                "Maintainance Endpoint Level (MEL) at which R-APS
                 PDU is transmitted.All nodes in the ring must be
                 configured with same APS level value";
              reference
                "Rec. ITU-T G.8032/Y.1344 (02/2012), Section 10.3";
            }

            container ports {
              description
                "Port specific configurations for ring instances.";
              list port {
                key "port-id";
                max-elements 2;
                description
                  "List of the ring ports.";
                leaf port-id {
                  type port-id-type;
                  description
                    "Port id of the ring instance. This leaf identify
                    one of the two ring ports.";
                }

                leaf rpl-port-role {
                  type rpl-port-type;
                  default normal;
                  description
                    "RPL port role for the ring instance.";
                }
              } // end port
            } // end ports
          } // end list instance
        } // end container instances
      } // end ring
    } // end container rings
  }
// -- end config --
  container erp-state {
    config false;
    description
      "This container defines ring operation data.";

    leaf max-rings-supported {
      type uint32;
      mandatory true;
      description
        "Maximum number of G.8032 rings supported on the device.";
    }

    leaf max-instances-supported {
      type uint32;
      mandatory true;
      description
        "Maximum number of G.8032 rings instances supported on
         the device.";
    }

    leaf max-instances-per-ring-supported {
      type uint32;
      mandatory true;
      description
        "Maximum number of G.8032 rings instances supported per
         physical ring.";
    }

    container rings {
      description
        "This container defines operations data for G.8032 rings.";
      list ring {
        key "name";
        description
          "Collection of G.8032 rings operational data on a device.";
        leaf name {
          type string {
            length "1..255";
          }
          description
            "G.8032 ring name. This leaf uniquely identifies a ring
             on the network device.";
        }
        container instances {
          description
            "Collection of ring instances";
          list instance {
            key "ring-id aps-vlan";
            description "List of ring instances.";
            leaf ring-id {
              type ring-id-type;
              description
                "G.8032 ring instance id.";
            }

            leaf aps-vlan {
              type dot1q:dot1q-vlan-id;
              description
                "APS channel VLAN-ID";
            }

            leaf state {
              type ring-state;
              mandatory true;
              description
                "Ring instance state. This represent protocol state
                 machine state.";
            }

            container ports {
              description
                "Operational state for ring instance ports.";
              list port {
                key port-id;
                max-elements 2;
                description
                  "Collection of ring port states";

                leaf port-id {
                  type port-id-type;
                  description
                    "Port id of the ring instance. This leaf identify
                     one of the two ring ports.";
                }

                container remote {
                  description
                    "Remote node-id, bpr values, used by flush
                     logic of the ERP control process.";

                  reference
                    "Rec. ITU-T G.8032/Y.1344 (02/2012),
                     Section 10.1.10";

                  leaf node-id {
                    type yang:mac-address;
                    mandatory true;
                    description
                      "Node ID of the last R-APS message received
                       over the ring port.

                       During initialization this value is set to
                       00:00:00:00:00:00 by ERP control process.";
                  }

                  leaf bpr {
                    type uint8 {
                      range "0 | 1";
                    }
                    mandatory true;
                    description
                      "Blocked port reference (BPR) of the last R-APS
                       message received over the ring port.

                       During initialization this value is set to 0
                       by ERP control process.";
                  }
                }

                leaf port-state {
                  type enumeration {
                    enum normal {
                      description
                        "Ring port is in normal state and ready to
                         forward traffic ring controlled data
                         traffic.";
                    }
                    enum blocked {
                      description
                        "Ring port is blocked and it is not
                         forwarding any data traffic. In normal
                         operations a port is blocked if it is a RPL
                         port.";
                    }
                    enum failed {
                      description
                        "Ring port has local failure. Port is blocked
                         and it is not forwarding any traffic.";
                    }
                    enum local-ms {
                      description
                        "Ring port has been blocked by administrative
                         manual switch action.";
                    }
                    enum local-fs {
                      description
                        "Ring port has been blocked by administrative
                         force switch action.";
                    }
                  }
                  mandatory true;
                  description
                    "Ring port state";
                }
                container aps-statistics {
                  description
                    "R-APS packet statistics";
                  leaf tx-raps {
                    type uint32;
                    description
                      "Number of R-APS messages transmitted";
                  }
                  leaf rx-raps {
                    type uint32;
                    description
                      "Number of R-APS messages received";
                  }
                }
              }
            }
          } // end instance
        } // end instances
      } // end ring
    } // end rings
    container summary {
      description
        "Ring summary statistics";
      list ring-counters {
        key state;
        description
          "Collection of ring counters for each state.";
        leaf state {
          type ring-state;
          description
            "Ring instance state. This represent protocol state
             machine state.";
        }
        leaf count {
          type uint64;
          mandatory true;
          description
            "Number of ring instances currently in the given state.";
        }
      }
    }
  }
// -- end erp-state --
// -- start notifications --
  notification ring-state-change-event {
    description
      "Notify ring state change events.";
    uses ring-identifier {
      description
        "Uniquely identifies a ring instance.";
    }

    leaf current-state {
      type ring-state;
      mandatory true;
      description
        "New state of the ring.";
    }

    leaf previous-state {
      type ring-state;
      mandatory true;
      description
        "Old state of the ring.";
    }
  }

  notification fop-event {
    description
      "Failure of Protocol (FOP) events.";
    uses ring-identifier {
      description
        "Uniquely identifies a ring instance.";
    }

    leaf event-type {
      type enumeration {
        enum fop-pm {
          description
            "Failure of Protocol, Provisioning Mismatch (FOP-PM)
             event.

            This event is generated when a node ID mismatch is
            detected by ERP control process by comparing the node
            ID of the RPL owner and the node ID in a received
            R-APS(NR, RB) frame.";
        }
        enum fop-pm-clear {
          description
            "This event is generated when Protocol, Provisioning
            Mismatch (FOP-PM) defect is cleared";
        }
        enum fop-to {
          description
            "Failure of Protocol, Timeout (FOP-TO) event.

            This event is generated when ERP control process does
            not receive periodic R-APS frame for a defined timeout
            interval ( >= 3.5 times R-APS interval)";
        }
        enum fop-to-clear {
          description
            "This event is generated when Protocol, Timeout
            (FOP-TO) defect is cleared";
        }
      }
      description
        "G.8032 Failure of Protocol event types.";
    }

    reference
      "Rec. ITU-T G.8021/Y.1341 (04/2015), Section 6.1.4.3";
  }
// -- end notifications --
// -- start rpcs --
  rpc clear-statistics {
    description
      "Clear ring statistics.";
    input {
      uses ring-identifier {
        description
          "Uniquely identifies ring instance.";
      }
    }
    output {
      leaf errstr {
        type string;
        description
          "Error message from the device if RPC failed.";
      }
    }
  }

  rpc clear-ring {
    description
      "Clear an existing Forced-Switch (FS) or Manual-Switch (MS)
       condition on the ring port.";
    input {
      uses ring-identifier {
        description
          "Uniquely identifies ring instance.";
      }
    }
    output {
      leaf errstr {
        type string;
        description
          "Error message from the device if RPC failed.";
      }
    }
  }

  rpc switch-ring {
    description
      "Perform administrative action on the ring (instance).";
    input {
      uses ring-identifier {
        description
          "Uniquely identifies ring instance.";
      }

      leaf port-id {
        type port-id-type;
        mandatory true;
        description
          "Ring port to perform switch operation.";
      }

      leaf operation {
        type enumeration {
          enum manual {
            description
              "Trigger manual switch. This operation is allowed only
               when a ring instance is in idle or pending state.

               This action allows administrator to temporarily block
               another ring port and unblock RPL link to perform
               maintenance operation in the ring.";
          }
          enum forced {
            description
              "Trigger force switch. This operation overrides all
               other state of the ring.";
          }
        }
        mandatory true;
        description
          "G.8032 administrative operation types.";
      }
    }
    output {
      leaf errstr {
        type string;
        description
          "Error message from the device if RPC failed, including
          failures where switch operation is not permitted on the
          ring instance under protocol restrictions.";
      }
    }
  }
  // -- end rpcs --
}
