module hncp-topology {

  yang-version 1;

  namespace
    "urn:ietf:params:xml:ns:yang:hncp-topology";

  prefix "hncp";

  import network-topology {
    prefix "nt";
    revision-date 2013-10-21;
  }

  import l3-unicast-igp-topology {
    prefix "l3t";
    revision-date 2013-10-21;
  }

  organization
    "TBD";

  contact "Luka Perkov <lperkov@cisco.com>";

  description
    "This module contains the HNCP topology model";

  revision "2014-08-04" {
    description "Initial version";
    reference "draft-ietf-homenet-hncp-01";
  }


  typedef update {
    type uint32;
    description
      "HNCP node number of topology updates";
  }

  typedef age {
    type uint64;
    units "milliseconds";
    description
      "HNCP node uptime in milliseconds";
  }

  typedef version {
    type uint32;
    description
      "HNCP node version";
  }

  typedef user-agent {
    type string;
    description
      "HNCP node user-agent";
  }

  typedef authoritative {
    type boolean;
    description
      "HNCP prefix authoritative";
  }

  typedef priority {
    type uint16;
    description
      "HNCP prefix priority";
  }

  typedef link {
    type uint32;
    description
      "HNCP prefix link";
  }

  typedef link-id {
    type uint32;
    description
      "HNCP address link-id";
  }


  grouping hncp-topology-type {
    description
      "HNCP topology type";

    container hncp {
      presence "Indicates HNCP Topology";

      description
        "HNCP topology type";
    }
  }


  augment "/nt:network-topology/nt:topology/nt:topology-types/l3t:l3-unicast-igp-topology" {
    description
      "Add support for HNCP";

    uses hncp-topology-type;
  }

  augment "/nt:network-topology/nt:topology/nt:node/l3t:igp-node-attributes" {
    when "../../nt:topology-types/l3t:l3-unicast-igp-topology/hncp" {
      description
        "Condition based HNCP extension";
    }
    uses hncp-node-attributes;

    description
      "Add support for HNCP";
  }

  augment "/nt:network-topology/nt:topology/nt:node/l3t:igp-node-attributes/l3t:prefix" {
    when "../../../nt:topology-types/l3t:l3-unicast-igp-topology/hncp" {
      description
        "Condition based HNCP extension";
    }
    uses hncp-prefix-attributes;

    description
      "Add support for HNCP";
  }

  augment "/nt:network-topology/nt:topology/nt:node/nt:termination-point/l3t:igp-termination-point-attributes" {
    when "../../../nt:topology-types/l3t:l3-unicast-igp-topology/hncp" {
      description
        "Condition based HNCP extension";
    }
    uses hncp-termination-point-attributes;

    description
      "Add support for HNCP";
  }


  grouping hncp-node-attributes {
    description
      "HNCP node attributes";

    container hncp-node-attributes {
      description
        "HNCP node attributes";

      leaf update {
        type update;
        description
          "HNCP node number of topology updates";
      }

      leaf age {
        type age;
        description
          "HNCP node age in milliseconds";
      }

      leaf version {
        type version;
        description
          "HNCP node version";
      }

      leaf user-agent {
        type user-agent;
        description
          "HNCP node user-agent";
      }
    }
  }

  grouping hncp-prefix-attributes {
    description
      "HNCP prefix attributes";

    container hncp-prefix-attributes {
      description
        "HNCP prefix attributes";

      leaf authoritative {
        type authoritative;
        description
          "HNCP prefix authoritative";
      }
      leaf priority {
        type priority;
        description
          "HNCP prefix priority";
      }
      leaf link {
        type link;
        description
          "HNCP prefix link";
      }
    }
  }

  grouping hncp-termination-point-attributes {
    description
      "HNCP termination point attributes";

    container hncp-termination-point-attributes {
      description
        "HNCP termination point attributes";

      leaf link-id {
        type link-id;
        description
          "HNCP address link-id";
      }
    }
  }


  augment "/l3t:igp-node-event" {
    uses hncp-topology-type;
    uses hncp:hncp-node-attributes;

    description
      "HNCP /l3t:igp-node-event extensions";
  }

  augment "/l3t:igp-prefix-event" {
    uses hncp-topology-type;
    uses hncp:hncp-prefix-attributes;

    description
      "HNCP /l3t:igp-prefix-event extensions";
  }

  augment "/l3t:termination-point-event" {
    uses hncp-topology-type;
    uses hncp:hncp-prefix-attributes;

    description
      "HNCP /l3t:termination-point-event extensions";
  }
}
