module service-function {

  namespace "urn:cisco:params:xml:ns:yang:sfc-sf";

  prefix sfc-sf;

  import ietf-inet-types { prefix inet; }
  import ietf-yang-types { prefix yang; }
  import service-function-type {prefix sfc-sft;}
  import service-locator {prefix sfc-sl;}

  organization "Cisco Systems, Inc.";
  contact "Reinaldo Penno <repenno@cisco.com>";


  description
    "This module contains a collection of YANG definitions for
     managing service function.

     It follows closely the constructs of
     http://tools.ietf.org/html/draft-ietf-netmod-interfaces-cfg-12

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
    "Changes based on Opendaylight Testing.";
  }


  typedef service-function-ref {
    type leafref {
      path "/sfc-sf:service-functions/sfc-sf:service-function/"
          + "sfc-sf:name";
    }
    description
      "This type is used by data models that need to reference
       configured service functions.";
  }

  grouping service-function-entry {
    description
      "This group bundles together all information related to a
       single service function";
    leaf name {
      type string;
      description
          "The name of the service function.";
    }
    leaf type {
      type string;
      mandatory true;
      description
        "Service Function Type from service-function-type yang
         model";
    }
    leaf ip-mgmt-address {
      type inet:ip-address;
      description
        "The IP and port used to configure this service-node";
    }
    leaf nsh-aware {
      type boolean;
      description "Whether this SF can process NSH headers";
    }

    list sf-data-plane-locator {
      description
        "A network data-plane locator";
      key "name";
      leaf name {
        type string;
        description
          "A unique string that represents this
           data-plane-locator";
      }
      uses sfc-sl:data-plane-locator;
      leaf service-function-forwarder {
        type string;
        description
          "The service function forwarder associated with this
           locator";
      }
    }
  }

  container service-functions {
    description
      "A function that is responsible for specific
      treatment of received packets.  A Service Function can act at
      various layers of a protocol stack (e.g., at the network layer
      or other OSI layers).  A Service Function can be a virtual
      element or be embedded in a physical network element.  One of
      multiple Service Functions can be embedded in the same network
      element.  Multiple occurrences of the Service Function can be
      enabled in the same administrative domain.

      One or more Service Functions can be involved in the delivery
      of added-value services.  A non-exhaustive list of Service
      Functions includes: firewalls, WAN and application
      acceleration, Deep Packet Inspection (DPI),a LI (Lawful
      Intercept) module, server load balancers, NAT44 [RFC3022],
      NAT64 [RFC6146], NPTv6 [RFC6296], HOST_ID injection, HTTP
      Header Enrichment functions, TCP optimizer, etc.

      An SF may be SFC encapsulation aware, that is it receives, and
      acts on information in the SFC encapsulation, or unaware in
      which case data forwarded to the service does not contain the
      SFC encapsulation.";

    list service-function {
      description
        "This list holds configuration data for all service functions
         in the domain";
      key "name";
      uses service-function-entry;
    }
  }

  container service-functions-state {
    description
      "This container hold operational state for all service
       functions";
    config false;
    list service-function-state {
      description
        "This list holds operational data for all service functions
         in the domain";
      key "name";
      leaf name {
        type string;
        description
          "the name of the service function";
      }
      leaf-list sf-service-function-path {
        type string;
        description
        "A list of all service function paths that contain this
         service function";
      }
    }
  }

  rpc delete-all-service-function {
  description
    "Deletes all service functions";
  }

  rpc put-service-function {
    description
      "Creates a service function";
    input {
      uses service-function-entry;
    }
  }
  rpc read-service-function {
    description
      "Reads a service function";
    input {
      leaf name {
        type string;
        mandatory true;
        description "The name of the service function.";
      }
    }
    output {
      uses service-function-entry;
    }
  }
  rpc delete-service-function {
    description
      "Deletes a service function";
    input {
      leaf name {
        type string;
        mandatory true;
        description "The name of the service function.";
      }
    }
  }
}
