module service-function-type {

  namespace "urn:cisco:params:xml:ns:yang:sfc-sft";

  prefix sfc-sft;

  import ietf-inet-types { prefix inet; }
  import ietf-yang-types { prefix yang; }


  organization "Cisco Systems, Inc.";
  contact "Reinaldo Penno <repenno@cisco.com>";


  description
    "This module contains a collection of YANG definitions for
     managing service function types.

     It follows closely the constructs of
     http://tools.ietf.org/html/draft-ietf-netmod-interfaces-cfg-12

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
    "Changes based on Opendaylight Testing.";
  }


  // Service Function

  // Service Function Type definitions

  identity service-function-type-identity {
    description
      "Base identity from which specific service function
       types are derived.";
  }

  identity firewall {
    base "service-function-type-identity";
    description "Firewall";
  }

  identity dpi {
    base "service-function-type-identity";
    description "Deep Packet Inspection";
  }

  identity napt44 {
    base "service-function-type-identity";
    description "Network Address and Port Translation 44";
  }

  typedef service-function-type {
    type identityref {
      base "service-function-type-identity";
    }
    description "This type is used to reference all
      registered service function types";
  }

  container service-function-types {
    description
      "A list of Service function Types. For each type we keep
       a list of Service Functions";

    list service-function-type {
      key "type";
      leaf type {
        type string;
        description
            "The service function type";
      }
      list sft-service-function-name {
        key "name";
        leaf name {
          type string;
          description
            "The name of the service function.";
        }
        description
          "The list of all service functions of a specific type";
      }
      description
        "A list of all service types. Each service-type entry holds
         a list of all service functions of the type";
    }
  }
}
