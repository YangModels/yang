module service-function-path {

  namespace "urn:cisco:params:xml:ns:yang:sfc-sfp";

  prefix sfc-sfp;

  import ietf-inet-types { prefix inet; }
  import ietf-yang-types { prefix yang; }
  import service-function {prefix sfc-sf; }


  organization "Cisco Systems, Inc.";
  contact "Reinaldo Penno <repenno@cisco.com>";


  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
      "Changes based on Opendaylight Testing and IETF SFC ml.";
  }

  typedef service-function-path-ref {
    type leafref {
      path "/sfc-sfp:service-function-paths/sfc-sfp:service-function-path/sfc-sfp:name";
    }
    description
      "This type is used by data models that need to reference
       configured service functions.";
  }

  // Service Function Path

  container service-function-paths {
    description
      "The SFP provides a level of indirection
       between the fully abstract notion of service chain as an
       abstract sequence of functions to be delivered, and the
       fully specified notion of exactly what SFF/SFs the packet
       will visit when it actually traverses the network.  By
       allowing the control components to specify the use of this
       level of indirection, the deployment may choose the degree
       of SFF/SF selection authority that is delegated to the
       network";
    list service-function-path {
      description
        "A list that holds configuration data for all SFPs in the
         domain";
      key "name";
      leaf name {
        type string;
        description
          "The name of this service function path";
      }
      list service-path-hop {
        key "hop-number";
        leaf hop-number {
          type uint8;
          description
            "A Monotonically increasing number";
        }
        leaf service-function-name {
          type string;
          description
            "Service Function name";
        }
        leaf service-function-forwarder {
          type string;
          description
            "Service Function Forwarder name";
        }
        leaf service_index {
          type uint8;
          description
            "Provides location within the service path.
             Service index MUST be decremented by service functions
             or proxy nodes after performing required services.  MAY
             be used in conjunction with service path for path
             selection.  Service Index is also valuable when
             troubleshooting/reporting service paths.  In addition to
             location within a path, SI can be used for loop
             detection.";
        }
        ordered-by user;
        description
          "A list of service functions that compose the
           service path";
      }
      leaf service-chain-name {
        type string;
        mandatory true;
        description
          "The Service Function Chain used as blueprint for this
           path";
      }
      leaf starting-index {
        type uint8;
        description
          "Starting service index";
      }
      leaf path-id {
        type uint32 {
          range "0..16777216";
        }
        description
          "Identifies a service path.
           Participating nodes MUST use this identifier for path
           selection.  An administrator can use the service path
           value for reporting and troubleshooting packets along
           a specific path.";
      }
    }
  }
}
