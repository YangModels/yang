module service-function-forwarder-ovs {
  yang-version 1;

  namespace "urn:cisco:params:xml:ns:yang:sfc-sff-ovs";

  prefix sfc-sff-ovs;

  import service-function-forwarder {
    prefix "sfc-sff";
  }

  import ietf-inet-types {
    prefix "inet";
  }

  import ietf-yang-types {
    prefix "yang";
    revision-date 2013-07-15;
  }

  organization "Cisco Systems, Inc.";
  contact "Reinaldo Penno <repenno@cisco.com>";

  revision 2014-07-01 {
    description "Augmentation of SFF for OVS";
  }

  augment "/sfc-sff:service-function-forwarders/"
        + "sfc-sff:service-function-forwarder/" {

    container ovs {
      leaf uuid {
        description "OVSDB bridge UUID";
        type yang:uuid;
      }
      list external-ids {
        description "The list of external ids associated with this bridge";
        key "name";
        leaf name {
          type string;
          description
            "A unique string that represents this external-id such as attached-mac";
        }
        leaf value {
          type string;
          description
            "A unique string that represents the value of the external-id such as fa:16:3e:56:47:10";
        }
      }
      leaf bridge-name {
        description "OVSDB bridge name";
        type string;
      }
      leaf rest-uri {
        description "URI of REST based management";
        type inet:uri;
      }
    }
  }
}
