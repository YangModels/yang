module ietf-acl {
  yang-version 1;

  namespace "urn:ietf:params:xml:ns:yang:ietf-acl";

  prefix ietf-acl;

  import ietf-yang-types {
    prefix "ietf";
  }

  import packet-fields {
    prefix "packet-fields";
  }

  revision 2014-05-20{
    description "creating base model for netmod";
  }

  typedef acl-ref {
    description "This type is used by data models that need to referenced an acl";
    type leafref {
      path "/ietf-acl:access-list/ietf-acl:acl-name";
    }
  }

  container access-lists {
    description "
       An access list (acl) is an ordered list of access list
       entries (ace). Each ace has a sequence number to define
       the order, list of match criteria, and a list of actions.
       Since there are several kinds of acls implementeded
       with different attributes for each and different for
       each vendor, this model accomodates customizing acls
       for each kind and for each vendor.
       ";
    list access-list {
      key "acl-name";

      leaf acl-name {
        description "name of access-list";
        type string;
      }

      container acl-oper-data {
        config false;
        description "Overall ACL operational data";
        leaf match-counter {
          description "Total match count for ACL";
          type ietf:counter64;
        }
        leaf permit-counter {
          description "Total permit count for ACL";
          type ietf:counter64;
        }
        leaf deny-counter {
          description "Total deny count";
          type ietf:counter64;
        }
        leaf-list targets {
          description "List of targets where ACL is applied";
          type string;
        }
      }

      list access-list-entries {
        key rule-name;
        ordered-by user;
        leaf rule-name {
            description "Entry name";
            type string;

        }

        container matches {
          description "Define match criteria";
          choice ace-type {
            case ace-ip {
              uses packet-fields:acl-ip-header-fields;
              choice ace-ip-version {
                case ace-ipv4 {
                  uses packet-fields:acl-ipv4-header-fields;
                }
                case ace-ipv6 {
                  uses packet-fields:acl-ipv6-header-fields;
                }
              }
            }
            case ace-eth {
              uses packet-fields:acl-eth-header-fields;
            }
          }
          uses packet-fields:metadata;
        }

        container actions {
          description "Define action criteria";
          choice packet-handling {
            default deny;
            case deny {
              leaf deny {
              type empty;
              }
            }
            case permit {
              leaf permit {
                type empty;
              }
            }
          }
        }

        container ace-oper-data {
          description "Per ace operational data";
          leaf match-counter {
            description "Number of matches for an ace";
            type ietf:counter64;
          }
        }
      } // access-list-entries

      container default-actions {
        description "Actions that occur if no access-list entry is matched.";
        leaf deny {
          type empty;
        }
      }
    } // list access-list
  } // container access-lists
}
