module service-function-chain {

  namespace "urn:cisco:params:xml:ns:yang:sfc-sfc";

  prefix sfc-sfc;

  import ietf-inet-types { prefix inet; }
  import ietf-yang-types { prefix yang; }
  import service-function {prefix sfc-sf; }


  organization "Cisco Systems, Inc.";
  contact "Reinaldo Penno <repenno@cisco.com>";


  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
    "Revised based on Opendaylight Project feedback";
  }

  grouping service-function-chain-grouping {
    list service-function-chain {
      description
        "A list that holds all service function chains in the
         domain";
      key "name";
      leaf name {
        type string;
        description
          "the name of the service function chain";
      }
      leaf symmetric {
        type boolean;
        description
          "If the chain is symmetric we will create two service
           paths, one ingress and another egress. Packets traverse
           the egress service path in the reverse order of the
           ingress path";
      }
      list sfc-service-function {
        key "name";
        leaf name {
          type string;
          description
            "A unique handle that describes the service function
             that will be chosen for this type, such as
             ingress-dpi. This is not the service function name";
        }
        leaf type {
          type string;
          mandatory true;
          description
            "Service Function Type from service-function-type.yang";
        }
        ordered-by user;
        description
          "A list of service functions that compose the service
           chain";
      }
    }
    description
      "This group bundles together all service function chains in the
       domain";
  }

  // Service Function Chains

  container service-function-chains {
    uses service-function-chain-grouping;
    description
      "A service Function chain defines an
       abstract set of service functions and their ordering
       constraints that must be applied to packets and/or frames
       selected as a result of classification.  The implied order
       may not be a linear progression as the architecture allows
       for nodes that copy to more than one branch, and also allows
       for cases where there is flexibility in the order in which
       services need to be applied. The term service chain is often
       used as shorthand for service function chain.";
  }

  container service-function-chains-state {
    config false;
    list service-function-chain-state {
      description
        "A list that contains operational service function
         chain state";
      key "name";
      leaf name {
        type string;
        description
          "the name of the service function chain";
      }
      leaf-list sfc-service-function-path {
        type string;
        description
        "A list of all service function paths instantiated from
         this chain";
      }
    }
    description
      "This containers holds operational service function
        chain state and their associated service path";
  }

// Remote procedure calls

// (main feature: instantiation of a SFC)

  rpc instantiate-service-function-chain {
    description
      "Instantiates a single service function";
    input {
      leaf name {
        type string;
          mandatory true;
          description
          "The name of the service function chain to be
           instantiated.";
      }
    }
    output {
      leaf name {
        type string;
        description
          "The name of the created service function path.";
      }
    }
  }

    // (RPC for testing)
  rpc put-service-function-chains {
    description
      "Creates Service-Functions";
    input {
      uses service-function-chain-grouping;
    }
  }
}
