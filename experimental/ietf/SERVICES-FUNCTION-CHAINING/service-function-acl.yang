module service-function-acl {
  yang-version 1;

  namespace "urn:cisco:params:xml:ns:yang:sfc-acl";

  prefix sfc-acl;

  import ietf-acl {
    prefix "ietf-acl";
  }

  organization "Cisco Systems, Inc.";
  contact "Reinaldo Penno <repenno@cisco.com>";

  revision 2014-07-01 {
    description "creating Service Function Chaining extensions to ietf-acl model";
  }


  augment "/ietf-acl:access-lists/ietf-acl:access-list/ietf-acl:access-list-entries/ietf-acl:actions" {
    description "SFC simple filter actions";
    choice sfc-action {
    case acl-service-function-path {
      description "Determine the Service Function Path the packet the packet will
      traverse";
      leaf service-function-path {
        type string;
      }
     }
    }
  }
}
