module augment-leaflist {
  namespace "ns:augment:leaflist";  
  prefix "auglflst";

  
  import yang {prefix yng; revision-date 2013-11-26;}	


  revision "2013-11-26" {    
  }
  
	augment "/yng:cont" {
		leaf-list lflst1 {
			type string;
		}
	}
	

	  
}
