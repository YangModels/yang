// vi: set smarttab et sw=4 tabstop=4:
module config-jmx-it {
    yang-version 1;
    namespace "urn:opendaylight:params:xml:ns:yang:controller:config:jmx:generator:it";
    prefix "jmxIt";

    import config { prefix config; revision-date 2013-04-05; }



    description
        "Testing API";

    revision "2013-06-13" {
        description
            "Initial revision";
    }

    identity testing {
        description
            "Test api";

        base "config:service-type";
        config:java-class "java.lang.AutoCloseable";
    }
}
