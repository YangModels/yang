module simple-container-yang {
  namespace "simple:container:yang";  

  prefix "smpdtp";
  revision 2013-11-12 {    
  }
  
  container cont {
  	container cont1 {
  	}
  	list lst1 {
  	}
  	leaf-list lflst1 {
  		type string;
  	}
  	leaf lf1 {
  		type string;
  	}
  }
}
