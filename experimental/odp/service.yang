module service {
    yang-version 1;
    namespace "urn:opendaylight:coe:northbound:service";
    prefix "coe";

    description
        "This YANG module defines the generic configuration data for Container Orchestration Engine.";

    revision "2017-06-11" {
        description "Initial revision.";
    }

    import ietf-inet-types {
        prefix inet;
        revision-date "2013-07-15";
    }

    import ietf-yang-types {
        prefix yang;
        revision-date "2013-07-15";
    }

    organization "OpenDaylight COE Group";

    contact "COE Developers <coe-dev@lists.opendaylight.org>";

    container service-information {
        description
            "Service container configuration.";

        list services {
            key "uid";

            description
                "List of all configured services.";

            leaf uid {
                type yang:uuid;
                description "UUID representing the service.";
            }

            leaf name {
                type string;
                description "The service name as reported by Kubernetes.";
            }

            leaf cluster-id {
                type yang:uuid;
                description "UUID representing the K8s cluster";
            }

            leaf cluster-ip-address {
                type inet:ip-address;
                description
                    "Front-end IP address for all the pods tagged under the service.";
            }

            leaf network-NS {
                type string;
                description "Network namespace defines the space for the service. The empty namespace
                    is equivalent to the default namespace.";
                status deprecated;
            }

            leaf-list external-ip-address {
                type inet:ip-address;
                description
                    "list of external IP Addresses that route the traffic into and from the service.";
            }

            leaf load-balancer-IP {
                type inet:ip-address;
                description
                    "Only applies to Service Type: LoadBalancer. A loadBalancer will get created with
                    the IP specified in this field.";
            }

            leaf-list ingress-ip-address {
                type inet:ip-address;
                description
                    "List of ingress IP addresses that are assigned to the service.";
            }

            list service-ports {
                description "List of the associated ports.";
                uses service-ports-info;
            }
        }
    }

    grouping service-ports-info {
        description "service ports info";

        leaf name {
            type string;
            description "The name of this port within the service. This maps to
                the 'Name' field in EndpointPort objects.";
        }

        leaf port {
            type int32;
            description "The port that will be exposed by this service.";
        }

        leaf target-port {
            type string;
            description "Number or name of the port to access on the pods targeted by the service.";
        }

        leaf node-port {
            type int32;
            description "The port on each node on which this service is exposed when
                type equal to NodePort or LoadBalancer.";
        }
    }

    container endpoints-info {
        description "Endpoints container configuration.";

        list endpoints {
            key "uid";

            leaf uid {
                type yang:uuid;
                description "UUID representing the endpoint.";
            }

            leaf name {
                type string;
                description "The endpoint name (should match service name).";
            }

            leaf network-NS {
                type string;
                description "Network namespace defines the space for the endpoint. The empty namespace
                    is equivalent to the default namespace.";
                status deprecated;
            }

            list endpoint-addresses {
                uses endpoint-addresses-info;
            }

            list endpoint-ports {
                uses endpoint-ports-info;
            }
        }
    }

    grouping endpoint-addresses-info {
        description "Endpoint IP-Addresses information.";

        leaf ip-address {
            type inet:ip-address;
            description
                "The IP address of this endpoint corresponding to the Pod IP-Address.";
        } 

        leaf host-name {
            type string;
            description "The host name of the endpoint.";
        }

        leaf node-name {
            type string;
            description "Name of the node that host this endpoint.";
        }
    }

    grouping endpoint-ports-info {
        description "Endpoint ports information.";

        leaf name {
            type string;
            description "Name of this port within the endpoint (should match ServicePort.Name).";
        }

        leaf port {
            type int32;
            description "The endpoint port number.";
        }
    }
}
