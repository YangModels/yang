module data-list-yang {
  namespace "data:list:yang"; 
  
  prefix "dtlstyg";

  import data-container-yang {
  	prefix "dtconyg";
  	revision-date 2013-11-19;
  }
  
  
  revision 2013-11-19 {    
  }
	


  augment "/dtconyg:cont" {
  	leaf lf1 {
  		type string;
  	}
  }	
}
