module opendaylight-sal-dom-broker-impl {
	yang-version 1;
    namespace "urn:opendaylight:params:xml:ns:yang:controller:md:sal:dom:impl";
    prefix "binding-impl";

	import config { prefix config; revision-date 2013-04-05; }
 	import opendaylight-md-sal-dom {prefix sal;}
 	import opendaylight-md-sal-common {prefix common;}

    description
        "Service definition for Binding Aware MD-SAL.";
 
    revision "2013-10-28" {
        description
            "Initial revision";
    }

    identity dom-broker-impl {
        base config:module-type;
        config:provided-service sal:dom-broker-osgi-registry;
        config:java-name-prefix DomBrokerImpl;
    }    
    
    
    identity dom-inmemory-data-broker {
        base config:module-type;
        config:provided-service sal:dom-async-data-broker;
    }
    
    identity hash-map-data-store {
        base config:module-type;
        config:provided-service sal:dom-data-store;
        config:java-name-prefix HashMapDataStore;
    }
    
    identity schema-service-singleton {
        base config:module-type;
        config:provided-service sal:schema-service;
        config:java-name-prefix SchemaServiceImplSingleton;
    }

    augment "/config:modules/config:module/config:configuration" {
        case dom-broker-impl {
            when "/config:modules/config:module/config:type = 'dom-broker-impl'";
            container data-store {
                uses config:service-ref {
                    refine type {
                        mandatory false;
                        config:required-identity sal:dom-data-store;
                    }
                }
            }
            
            container async-data-broker {
                uses config:service-ref {
                    refine type {
                        mandatory false;
                        config:required-identity sal:dom-async-data-broker;
                    }
                }
            
            }
        }
    }
    
    augment "/config:modules/config:module/config:configuration" {
        case dom-inmemory-data-broker {
            when "/config:modules/config:module/config:type = 'dom-inmemory-data-broker'";
            
            container schema-service {
                uses config:service-ref {
                    refine type {
                        mandatory false;
                        config:required-identity sal:schema-service;
                    }
                }
            
            }
        }
    }
    
    augment "/config:modules/config:module/config:state" {
        case hash-map-data-store {
            when "/config:modules/config:module/config:type = 'hash-map-data-store'";
        }
    }
    
    augment "/config:modules/config:module/config:state" {
        case schema-service-singleton {
            when "/config:modules/config:module/config:type = 'schema-service-singleton'";
        }
    }
    
    augment "/config:modules/config:module/config:state" {
        case dom-broker-impl {
            when "/config:modules/config:module/config:type = 'dom-broker-impl'";
            container data {
                uses common:data-state;
            } 
        }
    }
}
