module ntfbench-payload {
    yang-version 1;
    namespace "urn:opendaylight:params:xml:ns:yang:ntfbench-payload";
    prefix "ntfbenchmark";

    revision "2015-07-09" {
        description "Initial revision of ntfbenchmark model";
    }

    grouping payload {
        list payload {
            description
                "The payload for the notification";
            key id;
            leaf id {
                type int32;
            }
        }
    }

    notification ntfbench {
        uses payload;
    }
}
