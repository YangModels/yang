module augment-main-b {
  namespace "ns:augment:main:b";  
  prefix "aumab";

  
  import main {prefix mn; revision-date 2014-01-21;}   


  revision "2014-01-21" {    
  }
  
  augment "/mn:cont" {
    container cont1 {
        leaf lf11 {
            type string;
        }
    }
  }
  
}
