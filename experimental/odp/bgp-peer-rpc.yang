module bgp-peer-rpc {
    namespace "urn:opendaylight:params:xml:ns:yang:bgp-peer-rpc";
    prefix "bgp-rpc";

    import bgp-multiprotocol { prefix bgp-mp; revision-date 2018-03-29; }
    import bgp-rib { prefix rib; revision-date 2018-03-29; }
    import yang-ext { prefix ext; revision-date 2013-07-09; }

    organization "Cisco Systems, Inc.";
    contact "Iveta Halanova <ihalanov@cisco.com>";

    description
        "Module contains rpc for route refresh request, which is described in rfc2918.

        Copyright (c) 2016 Cisco Systems, Inc. All rights reserved.

        This program and the accompanying materials are made available
        under the terms of the Eclipse Public License v1.0 which
        accompanies this distribution, and is available at
        http://www.eclipse.org/legal/epl-v10.html";

    revision "2018-03-29" {
        description "Add support for add-path for all afi/safi.";
    }

    revision 2017-12-07 {
        description "Add support for add-path in base BGP NLRI.";
    }

    revision 2017-10-27 {
        description "Add reset session RPC";
    }

    revision 2016-03-22 {
        description "Initial revision";
    }

    identity peer-context {
        description "Identity used to mark the Peer context for binding RPCs in a particular RIB.";
    }

    typedef peer-ref {
        type instance-identifier;
        ext:context-reference "peer-context";
    }

    grouping peer-reference {
        leaf peer-ref {
            type peer-ref;
            mandatory true;
            ext:context-reference "peer-context";
        }
    }

    grouping rr-msg-args {
        uses peer-reference;
        uses bgp-mp:bgp-table-type;
    }

    rpc route-refresh-request {
        input {
            uses rr-msg-args;
        }
    }

    augment "/rib:bgp-rib/rib:rib/rib:peer" {
        ext:context-instance "peer-context";
    }

    rpc reset-session {
        description "Resets the peer session";
        input {
            uses peer-reference;
        }
    }

    rpc restart-gracefully {
        description "Perform graceful restart with peer";
        input {
            uses peer-reference;
            leaf selection-deferral-time {
                description
                    "Time to wait with route selection in seconds. Route selection is postponed until
                    End of Rib marker is received or this timer expires.";
                type uint32;
                units seconds;
                mandatory true;
            }
        }
    }
}
