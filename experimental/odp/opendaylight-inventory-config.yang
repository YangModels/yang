module opendaylight-inventory-config {
    namespace "urn:opendaylight:inventory:config";
    prefix inv-config;

    import yang-ext {prefix ext; revision-date "2013-07-09";}
    import opendaylight-inventory {prefix inv; revision-date "2013-08-19";}


    revision "2013-08-19" {
        description "Initial revision of Inventory model";
    }
    /** Base structure **/
    container nodes {
        list node {
            key "id";
            ext:context-instance "node-context";

            uses inv:node;
        }
    }    
}
