/*
 * Copyright (c) 2018 Redhat Inc. and others.  All rights reserved.
 *
 * This program and the accompanying materials are made available under the
 * terms of the Eclipse Public License v1.0 which accompanies this distribution,
 * and is available at http://www.eclipse.org/legal/epl-v10.html
 */
module neutron-mtu-ext {

    yang-version 1;

    namespace "urn:opendaylight:neutron-mtu-ext";

    prefix neutron-mtu-ext;

    import neutron { prefix "neutron"; }
    import neutron-mtu { prefix "mtu"; }
    import yang-ext { prefix "ext"; }

    organization "OpenDaylight Neutron Group";

    description "This YANG module defines Openstack Neutron mtu extensions model";

    revision "2018-11-14" {
        description
                "OpenDaylight Neon release";
    }

    augment "/neutron:neutron/neutron:networks/neutron:network"{
        description "This module augments the networks container
                in the neutron-networks module with mtu information.";
        ext:augment-identifier "network-mtu-extension";
        uses mtu:mtu-attributes;
    }
}
