module service-function-path {

  namespace "urn:cisco:params:xml:ns:yang:sfc-sfp";

  prefix sfc-sfp;

  import service-function-path-metadata {
      prefix sfc-md;
      revision-date 2014-07-01;
  }
  import service-locator {
      prefix sfc-sl;
      revision-date 2014-07-01;
  }
  import sfc-common {
      prefix sfc-common;
      revision-date 2015-10-17;
  }

  organization "Cisco Systems, Inc.";
  contact "Reinaldo Penno <repenno@cisco.com>";


  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2014-07-01 {
    description
      "Changes based on Opendaylight Testing and IETF SFC ml.";
    reference "https://tools.ietf.org/html/draft-penno-sfc-yang";
  }

  // Service Function Path

  container service-function-paths {
    description
      "The SFP provides a level of indirection
       between the fully abstract notion of service chain as an
       abstract sequence of functions to be delivered, and the
       fully specified notion of exactly what SFF/SFs the packet
       will visit when it actually traverses the network.  By
       allowing the control components to specify the use of this
       level of indirection, the deployment may choose the degree
       of SFF/SF selection authority that is delegated to the
       network";
    list service-function-path {
      key "name";
      description
        "A list that holds configuration data for all SFPs in the
         domain";
      leaf name {
        type sfc-common:sfp-name;
        description
          "The name of this service function path";
      }

      leaf transport-type {
        type sfc-sl:sl-transport-type-def;
        default "sfc-sl:vxlan-gpe";
        description
          "Transport type between SFF from service-locator.yang.";
      }

      leaf sfc-encapsulation {
        type sfc-sl:sfc-encapsulation-type;
        description
          "The type of encapsulation used in this path for passing
          SFC information along the chain";
      }

      leaf symmetric {
        type boolean;
        description
          "If the chain is symmetric we will create two service
           paths, one ingress and another egress. Packets traverse
           the egress service path in the reverse order of the
           ingress path. If present, this value will override the
           setting in the SF-Type. If not present, if at least one
           SF is of an SF-Type that sets the bidirectionality flag
           to true, then the RSP will be symmetric.";
      }
      leaf classifier {
        type string;
        description "The classifier responsible for directing"
          + "packets to this service path";
      }
      leaf symmetric-classifier {
        type string;
        description "The classifier responsible for directing"
          + "packets to this service path";
      }
      leaf context-metadata {
        type sfc-md:context-metadata-ref;
        description
          "The name of the associated context metadata";
      }
      leaf variable-metadata {
        type sfc-md:variable-metadata-ref;
        description
          "The name of the associated variable metadata";
      }
      leaf tenant-id {
        type string;
        description
          "This SFP was created for a specific tenant-id";
      }
      list service-path-hop {
        key "hop-number";
        leaf hop-number {
          type uint8;
          description
            "A Monotonically increasing number";
        }
        leaf service-function-name {
          type sfc-common:sf-name;
          description
            "Service Function name";
        }
        leaf service-function-group-name {
          type string;
          description
            "Service Function group name";
        }
        leaf service-function-forwarder {
          type sfc-common:sff-name;
          description
            "Service Function Forwarder name";
        }
        leaf service-index {
          type uint8;
          description
            "Provides location within the service path.
             Service index MUST be decremented by service functions
             or proxy nodes after performing required services.  MAY
             be used in conjunction with service path for path
             selection.  Service Index is also valuable when
             troubleshooting/reporting service paths.  In addition to
             location within a path, SI can be used for loop
             detection.";
        }

        ordered-by user;
        description
          "A list of service functions that compose the
           service path";
      }
      leaf service-chain-name {
        type sfc-common:sfc-name;
        mandatory true;
        description
          "The Service Function Chain used as blueprint for this
           path";
      }
      leaf starting-index {
        type uint8;
        description
          "Starting service index";
      }
      leaf path-id {
        type uint32 {
          range "0..16777216";
        }
        description
          "Identifies a service path.
           Participating nodes MUST use this identifier for path
           selection.  An administrator can use the service path
           value for reporting and troubleshooting packets along
           a specific path.";
      }
    }
  }

  container service-function-paths-state {
    config false;
    description
      "This container hold operational state for all service
       function paths";
    list service-function-path-state {
      key "name";
      description
        "This list holds operational data for all service function
         paths in the domain";
      leaf name {
        type sfc-common:sfp-name;
        description
          "The name of the service function path";
      }
      list sfp-rendered-service-path {
        key "name";
        leaf name {
          type sfc-common:rsp-name;
          description
            "The name of the Rendered Service Path";
        }
        description
        "A list of all rendered service paths instantiated
         from this service path";
      }
    }
  }

}
