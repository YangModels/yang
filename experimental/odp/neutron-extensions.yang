/*
 * Copyright (c) 2016 Intel Corporation.  All rights reserved.
 *
 * This program and the accompanying materials are made available under the
 * terms of the Eclipse Public License v1.0 which accompanies this distribution,
 * and is available at http://www.eclipse.org/legal/epl-v10.html
 */

module neutron-extensions {
    yang-version 1;

    namespace "urn:opendaylight:neutron-extensions";

    prefix neutron-extensions;

    organization "OpenDaylight Neutron Group";

    contact "Isaku Yamahata <isaku.yamahata@gmail.com>";

    description "This YANG module defines neutron extensions attributes that are used
        by OpenDaylight Neutron YANG modules.
        http://developer.openstack.org/api-ref-networking-v2-ext.html#neutron_extensions";

    revision "2016-06-17" {
        description
                "OpenDaylight Boron release";
    }

    grouping extension-attributes {
        leaf name {
            type string;
            description "The name of the extension";
        }
        leaf alias {
            type string;
            description "The alias for the extension";
        }
        leaf configuration {
            type string;
            description "The configuration of this extension";
        }
    }

    grouping extensions-attributes {
        container extensions {
            config false;
            list extension {
                key "alias";
                uses extension-attributes;
            }
        }
    }

    identity service-provider-feature-type-base {
        description "Base identity for Feature that openstack service provider
                    supports.";
    }

    // The list of openstack service provider features.
    // Maintain the list of features as they are introduced
    // identity extension-report {
    //     description "extensions-attributes is populated";
    //     base service-provider-feature-type-base;
    // }
    // identity port-status {
    //     description "port status is updated";
    //     base service-provider-feature-type-base;
    // }

    identity bgpvpn-vni {
        description "Support for vni attribute in bgpvpn resource";
        base service-provider-feature-type-base;
    }

    identity operational-port-status {
        description "port status update when port created";
        base service-provider-feature-type-base;
    }

    identity qos-rules {
        description "The qos rules supported. The configuration leaf should
        contain a json string such that models the supported_rules
        parameter of neutron_lib.services.qos.DriverBase";

        base service-provider-feature-type-base;
    }

    grouping service-provider-feature-attributes {
        leaf service-provider-feature {
            type identityref {
                base service-provider-feature-type-base;
            }
            description "supported features by openstack service provider";
        }
        leaf configuration {
            type string;
            description "The configuration of this feature";
        }
    }

    grouping service-provider-features-attributes {
        description "List of features that openstack service provider supports.
                    networking-odl will retrieve this list and configures itself
                    to use what features.
                    This is for networking-odl to support multiple versions
                    ODL and multiple openstack service providers";
        container features {
            config false;
            list feature {
                key "service-provider-feature";
                uses service-provider-feature-attributes;
            }
        }
    }
}
