module simple-list-yang2 {
  namespace "simple:list:yang2";  

  prefix "smplstyg";
  revision 2013-11-12 {    
  }
  
  list lst {
  	container cont1 {
  	}
  	list lst1 {
  	}
  	leaf-list lflst1 {
  		type string;
  	}
  	leaf lf1 {
  		type string;
  	}
  }
}
