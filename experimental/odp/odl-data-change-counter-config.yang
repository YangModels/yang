// vi: set smarttab et sw=4 tabstop=4:
module odl-data-change-counter-config {
    yang-version 1;
    namespace "urn:opendaylight:params:xml:ns:yang:bgpcep:data-change-counter-config";
    prefix "dcc-cfg";

    description
        "This module contains the base YANG definitions for
         topology data-change counter configuration.

        This program and the accompanying materials are made available
        under the terms of the Eclipse Public License v1.0 which
        accompanies this distribution, and is available at
        http://www.eclipse.org/legal/epl-v10.html";

    revision "2017-04-24" {
        description
            "Initial revision";
    }

    list data-change-counter-config {
        key "counter-id";
        leaf counter-id {
            type string;
            mandatory true;
        }
        leaf topology-name {
            type string;
            mandatory true;
        }
    }
}
