module opendaylight-topology-view  {
    yang-version 1;
    namespace "urn:opendaylight:model:topology:view";
    // replace with IANA namespace when assigned
    prefix "nt";

    import yang-ext { prefix "ext"; }
    import network-topology {prefix "topo"; revision-date "2013-10-21"; }

    organization "TBD";

    contact "WILL-BE-DEFINED-LATER";

    revision 2013-10-30 {
        description
            "Initial revision.";
    }
    

    grouping aggregate-topology {
        leaf-list original-topology {
            type topo:topology-ref;	
        }
    }

    grouping aggregate-node {
        list original-node {
            leaf topology {
                type topo:topology-ref;
            }
            leaf node {
                type topo:node-ref;
            }
        }
    }

    augment "/topo:network-topology/topo:topology" {
        ext:augment-identifier "aggregated-topology";
        uses aggregate-topology;
    }

    augment "/topo:network-topology/topo:topology/topo:node" {
        ext:augment-identifier "aggregated-node";
        uses aggregate-node;
    }
}
