module forwarding-rules-manager-config {
    yang-version 1;
    namespace "urn:opendaylight:params:xml:ns:yang:openflowplugin:app:forwardingrules-manager:config";
    prefix "frm";

    description
        "Configuration for Forwarding Rules Manager application..";

    revision "2016-05-11" {
        description
            "Initial revision.";
    }

    container forwarding-rules-manager-config {
        leaf disable-reconciliation {
            type boolean;
            default false;
        }

        leaf stale-marking-enabled {
            type boolean;
            default false;
        }

        leaf reconciliation-retry-count {
            type uint16;
            default 5;
        }

        leaf bundle-based-reconciliation-enabled {
            type boolean;
            default false;
        }
    }
}
