module k8s {
    yang-version 1;
    namespace "urn:opendaylight:k8s";
    prefix "k8s";

    description
        "This YANG module defines a top level for the kubernetes models in opendaylight.";

    revision "2018-12-05" {
        description "Initial revision.";
    }

    import network-policy { prefix network-policy; revision-date "2018-12-05"; }

    organization "OpenDaylight COE Group";

    contact "COE Developers <coe-dev@lists.opendaylight.org>";

    container k8s {
        uses network-policy:network-policy;
    }
}
