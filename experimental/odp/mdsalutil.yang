/*
Copyright (c) 2017 Red Hat Inc. and others.  All rights reserved.

This program and the accompanying materials are made available under the
terms of the Eclipse Public License v1.0 which accompanies this distribution,
and is available at http://www.eclipse.org/legal/epl-v10.html
*/

module genius-mdsalutil {
    yang-version 1.1;
    namespace "urn:opendaylight:params:xml:ns:yang:mdsalutil";
    prefix "genius-mdsalutil";

    revision "2017-08-30" {
        description "genius mdsalutil models";
    }

    container config {
        leaf upgradeInProgress {
            type boolean;
            default false;
        }
    }
}
