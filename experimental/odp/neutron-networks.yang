/*
 * Copyright (c) 2015 Brocade Communications Systems, Inc. and others.  All rights reserved.
 *
 * This program and the accompanying materials are made available under the
 * terms of the Eclipse Public License v1.0 which accompanies this distribution,
 * and is available at http://www.eclipse.org/legal/epl-v10.html
 */
module neutron-networks {

    yang-version 1;

    namespace "urn:opendaylight:neutron-networks";

    prefix neutron-networks;

    import neutron-attrs { prefix "attrs"; }

    organization "OpenDaylight Neutron Group";

    contact "J. Gregory Hall <ghall@brocade.com>, Kiran Sreenivasa <kkoushik@brocade.com>";

    description "This YANG module defines Openstack Neutron Network model";

    revision "2015-07-12" {
        description
                "OpenDaylight Beryllium release";
    }
    identity network-type-base {
        description
                "Base Network type for all Network type identifiers.";
    }

    identity network-type-flat {
        base network-type-base;
        description
                "Flat network type identity.";
    }
    identity network-type-vlan {
        base network-type-base;
        description
                "VLAN network type identity.";
    }
    identity network-type-vxlan {
        base network-type-base;
        description
                "VXLAN network type identity.";
    }
    identity network-type-gre {
        base network-type-base;
        description
                "GRE network type identity.";
    }

    typedef network-type {
        type identityref {
            base network-type-base;
        }
        description
                "This type is used to refer to a Network Type.";
    }

    grouping networks-attributes {
        container networks {
            list network {

                description "A network is a virtual isolated layer-2 broadcast domain which
                            is typically reserved to the tenant who created it, unless the
                            network has been explicitly configured to be shared. Tenants can
                            create multiple networks, until they reach the thresholds specified
                            by per-tenant Quotas. The network is the principal entity for 
                            the Neutron API. Ports and Subnets must always be associated 
                            with a network.";

                key "uuid";

                leaf shared {
                    type boolean;
                    default "false";
                    description "Indicates whether this network or subnet is shared across all
                                tenants. By default, only administrative users can change this
                                value.";
                }

                leaf vlan-transparent {
                    type boolean;
                    default "false";
                    description "The state of the network, which is VLAN transparent (true) or
                                not VLAN transparent (false)";
                }

                uses attrs:base-attributes;
                uses attrs:admin-attributes;
            }
        }
    }
}
