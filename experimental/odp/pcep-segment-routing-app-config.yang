module pcep-segment-routing-app-config {
    yang-version 1;
    namespace "urn:opendaylight:params:xml:ns:yang:controller:pcep:segment-routing-app-config";
    prefix "pcep-segment-routing-app-config";

    description
      "Configuration for the PCEP segment routing extension.";

    revision "2016-07-07" {
        description
            "Initial revision.

            Copyright (c) 2016 Brocade Communications Systems, Inc. All rights reserved.

            This program and the accompanying materials are made available
            under the terms of the Eclipse Public License v1.0 which
            accompanies this distribution, and is available at
            http://www.eclipse.org/legal/epl-v10.html";
    }

    container pcep-segment-routing-config {
        leaf iana-sr-subobjects-type {
            description "If false (default) SR-ERO type (=5) and SR-RRO type (=6) is used,
                    else proposed type (36) is used for parsing/serialization";
            type boolean;
            default false;
        }

        leaf sr-capable {
            description "Advertize segment-routing capability";
            type boolean;
            default true;
        }
    }
}
