module odl-bgp-peer-acceptor-config {
    yang-version 1;
    namespace "urn:opendaylight:params:xml:ns:yang:odl-bgp-peer-acceptor-config";
    prefix bgp-peer-acceptor-config;

    import ietf-inet-types { prefix inet; revision-date 2013-07-15; }

    description
        "This module contains the base YANG definitions for
         BGP Peer Acceptor Configuration.
         Copyright (c)2016 Cisco Systems, Inc. All rights reserved.;

         This program and the accompanying materials are made available
         under the terms of the Eclipse Public License v1.0 which
         accompanies this distribution, and is available at
         http://www.eclipse.org/legal/epl-v10.html";

    revision "2016-10-03" {
        description
            "Initial revision.";
    }

    list bgp-peer-acceptor-config {
        key "config-name";
        leaf config-name {
            type string;
        }

        leaf binding-address {
            description "IP address to bind to";
            type inet:ip-address;
            default "0.0.0.0";
        }

        leaf binding-port {
            description "Port to bind to";
            type inet:port-number;
            default "179";
        }
    }
}
