module reconciliation-result-state {
	yang-version 1;
    namespace "urn:opendaylight:params:xml:ns:yang:openflowplugin:rf:state";
    prefix "rf-state";

    description
        "Reconciliation framework result state enumeration";

    revision "2017-07-13" {
        description
            "Initial proposal.";
    }


    typedef result-state {
        description "Reconciliation result state.";
        type enumeration {
            enum DO_NOTHING {
                description "Reconciliation wasn't successful but not important.";
            }
            enum DISCONNECT {
                description "Reconciliation wasn't successful but is mandatory, disconnect device.";
            }
        }
    }
}
