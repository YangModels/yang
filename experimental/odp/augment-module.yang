module augment-module {
  namespace "augment:module";  

  prefix "amodule";
  
  import instance-identifier-module {prefix imodule; revision-date 2014-01-17;}
   
  revision 2014-01-17 {    
  }
  
	augment "/imodule:cont/imodule:cont1" {
	   list lst11 {
	       key "keyvalue111 keyvalue112";
	       leaf keyvalue111 {
	           type string;
	       }
	       leaf keyvalue112 {
	           type string;
	       }
	   }	   
	}
	  
}
