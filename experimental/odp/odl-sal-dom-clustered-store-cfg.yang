module odl-sal-dom-clustered-store-cfg {
	yang-version 1;
    namespace "urn:opendaylight:params:xml:ns:yang:controller:md:sal:dom:cluster:store";
    prefix "binding-impl";

	import config { prefix config; revision-date 2013-04-05; }
 	import opendaylight-md-sal-dom {prefix sal;}

    description
        "Service definition for MD-SAL Clustered Store.";
 
    revision "2013-10-28" {
        description
            "Initial revision";
    }

    identity dom-clustered-store-impl {
        base config:module-type;
        config:provided-service sal:dom-data-store;
        config:java-name-prefix ClusteredDataStoreImpl;
    }

    augment "/config:modules/config:module/config:state" {
        case dom-clustered-store-impl {
            when "/config:modules/config:module/config:type = 'dom-clustered-store-impl'";
        }
    }
    
}
