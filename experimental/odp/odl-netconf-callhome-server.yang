module odl-netconf-callhome-server {

  namespace "urn:opendaylight:params:xml:ns:yang:netconf-callhome-server";
  prefix "callhome";

  organization
   "OpenDaylight Project";

  contact
   "netconf-dev@lists.opendaylight.org";

  description
   "This module defines the northbound interface for OpenDaylight NETCONF Callhome.";

  revision "2016-11-09" {
    description "Initial version";
  }

  grouping credentials {
    container credentials {
      presence "Credentials to device.";
      leaf username {
        mandatory true;
        description "Username to be used for authentication";
        type string {
          length "1..max";
        }
      }
      leaf-list passwords {
        description "Passwords to be used for authentication.";
        type string;
      }
    }
  }

  container netconf-callhome-server {
    description "Settings for call home server administration";

    container global {
      presence "global credentials are enabled.";
      uses credentials;
      leaf accept-all-ssh-keys {
        type boolean;
        default false;
      }
    }

    container allowed-devices {
      description "A list of allowed devices";
      list device {
        key unique-id;
        leaf unique-id {
          description "Identifier of device, which will be used to identify device.";
          type string;
        }
        leaf ssh-host-key {
          description "BASE-64 encoded public key which device will use during connection.";
          type string;
        }
        unique ssh-host-key;
        uses credentials;
      }
    }
  }
}
