module shutdown-impl {
    yang-version 1;
    namespace "urn:opendaylight:params:xml:ns:yang:controller:shutdown:impl";
    prefix "shutdown-impl";

    import shutdown { prefix shutdown; revision-date 2013-12-18; }
    import config { prefix config; revision-date 2013-04-05; }
    import rpc-context { prefix rpcx; revision-date 2013-06-17; }

    organization "Cisco Systems, Inc.";

    description
        "This module contains the base YANG definitions for
         shutdown implementation.

        Copyright (c)2013 Cisco Systems, Inc. All rights reserved.;

        This program and the accompanying materials are made available
        under the terms of the Eclipse Public License v1.0 which
        accompanies this distribution, and is available at
        http://www.eclipse.org/legal/epl-v10.html";

    revision "2013-12-18" {
        description
            "Initial revision.";
    }

    identity shutdown {
        base config:module-type;
        config:provided-service shutdown:shutdown;
    }

    augment "/config:modules/config:module/config:configuration" {
        case shutdown {
            when "/config:modules/config:module/config:type = 'shutdown'";
            leaf secret {
                type string;
                default "";
            }
        }
    }

    augment "/config:modules/config:module/config:state" {
        case shutdown {
            when "/config:modules/config:module/config:type = 'shutdown'";
            rpcx:rpc-context-instance "shutdown-rpc";
        }
    }

    identity shutdown-rpc;

    rpc shutdown {
        input {
            uses rpcx:rpc-context-ref {
                refine context-instance {
                    rpcx:rpc-context-instance shutdown-rpc;
                }
            }
            leaf input-secret {
                type string;
            }
            leaf max-wait-time {
                type uint32;
                description "Maximum time in milliseconds before process is forcibly exited. Zero or null cancels this functionality.";
            }
            leaf reason {
                type string;
            }
        }
    }
}
