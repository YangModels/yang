module batch-common {
    namespace "urn:opendaylight:service:batch:common";
    prefix batch-common;

    description "Openflow batch services - common groupings.";

    revision "2016-03-22" {
        description "Initial revision of batch common groupings.";
    }

    grouping batch-order-grouping {
        description "provide unified batch order value";
        leaf batch-order {
            type uint16;
        }
    }
}
