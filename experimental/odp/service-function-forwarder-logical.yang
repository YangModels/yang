module service-function-forwarder-logical {

  yang-version 1;

  namespace "urn:ericsson:params:xml:ns:yang:sfc-sff-logical";

  prefix sfc-sff-logical;

  import ietf-yang-types { prefix yang; revision-date 2013-07-15; }
  import yang-ext { prefix ext; revision-date 2013-07-09; }
  import sfc-common { prefix sfc-common; revision-date 2015-10-17; }
  import service-function { prefix sfc-sf; revision-date 2014-07-01; }
  import service-function-forwarder { prefix sfc-sff; revision-date 2014-07-01; }
  import rendered-service-path { prefix rsp; revision-date 2014-07-01; }

  organization "Ericsson, Inc.";
  contact "Diego Granados <diego.jesus.granados.lopez@ericsson.com>";

  description "This module contains a collection of YANG definitions used to
        augment Service Function Forwarder operational information to
        contain logical-SFF specific information. Also, minor changes
        (augmentations) in the rendered service path and in the service
        function elements, in order to use the new logical interface
        locator";

  revision 2016-06-20 {
    description
      "Augmentations in sf, sff-state, rendered service paths to include support for
      logical SFFs (based on Genius project support)";
  }

  grouping logical-interface-locator {
    description "Interface name of the VM on which the SF is running";
    leaf interface-name {
      type string;
      description "Name of the interface";
    }
  }

  //typedefs for dpn identifiers
  typedef dpn-id-type  {
    type uint64;
    description "Data-plane node id";
  }

  grouping dpn-grouping {
    description
      "Data plane id: dpn-id";
    leaf dpn-id {
      type dpn-id-type;
    }
  }

  grouping dpnid-rsps {
    description "";
    container dpn-rsps {
      description "For each DPN id, the list contains all RSPs that
                   are using the data plane node";
      // uses dpn-grouping;
      list dpn {
        description
          "List of all dpn ids part of this logical sff";
        uses dpn-grouping;
        key dpn-id;
        container rsps-for-dpnid {
          list rsps {
            key "name";
            leaf name {
              type sfc-common:sfp-name;
              description "The name of the Service Path";
            }
          }
        }
      }
    }
  }

  augment "/sfc-sf:service-functions/"
        + "sfc-sf:service-function/"
        + "sfc-sf:sf-data-plane-locator/"
        + "sfc-sf:locator-type/" {
    description "augment the Service Function to allow the use of logical interface
                locators";
    ext:augment-identifier "sf-logical-sff-augmentation";
    case logical-interface {
      uses logical-interface-locator;
    }
  }

  augment "/sfc-sff:service-function-forwarders/"
        + "sfc-sff:service-function-forwarder/"
        + "sfc-sff:sff-data-plane-locator/"
        + "sfc-sff:data-plane-locator/"
        + "sfc-sff:locator-type/" {
    description "Augments the Service Function Forwarder to allow the use of logical
                interface locators";
    case logical-interface {
      uses logical-interface-locator;
    }
  }

  augment "/sfc-sff:service-function-forwarders-state/"
        + "sfc-sff:service-function-forwarder-state/" {
    description "Augments the SFF state to hold logical SFF specific information";
    ext:augment-identifier "sff-logical-sff-augmentation";
    uses dpnid-rsps;
  }

  augment "/rsp:rendered-service-paths/"
      + "rsp:rendered-service-path/"
      + "rsp:rendered-service-path-hop/" {
    description "Augments the RSP hop information to allow to use dpn locators
                instead of sff locators";
    ext:augment-identifier "rsp-logical-sff-augmentation";
    uses dpn-grouping;
  }
}
