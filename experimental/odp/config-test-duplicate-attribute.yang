// vi: set smarttab et sw=4 tabstop=4:
module config-test-duplicate-attribute {
    yang-version 1;
    namespace "urn:opendaylight:params:xml:ns:yang:controller:jmx:generator:it:duplicate";
    prefix "it-duplicate";

    import config { prefix config; revision-date 2013-04-05; }
    import ietf-inet-types { prefix inet; revision-date 2010-09-24;}

    description
        "Testing IMPL";

    revision "2013-04-03" {
        description
            "Initial revision";
    }

    identity implementation {
        base config:module-type;
        config:java-name-prefix TestImpl;
    }

    identity netconf {
        base config:module-type;
        config:java-name-prefix NetconfTestImpl;
    }

    augment "/config:modules/config:module/config:configuration" {
        case implementation {
            when "/config:modules/config:module/config:type = 'implementation'";

           container dto-a {
                leaf simple-arg {
                    type uint32;
                }

                leaf port {
                    type inet:port-number;
                }

            }
        }
    }

    augment "/config:modules/config:module/config:state" {
        case implementation {
            when "/config:modules/config:module/config:type = 'implementation'";
            // root runtime bean
            leaf created-sessions {
                type uint32;
            }
        }
    }

    augment "/config:modules/config:module/config:configuration" {
        case netconf {
            when "/config:modules/config:module/config:type = 'netconf'";

           container dto-a {
                leaf simple-arg {
                       type uint32;
                   }

                   leaf port {
                       type inet:port-number;
                   }
            }
        }
    }

    augment "/config:modules/config:module/config:state" {
        case netconf {
            when "/config:modules/config:module/config:type = 'netconf'";
            // root runtime bean
            leaf created-sessions {
                type uint32;
            }

        }
    }
}
