module augment-leaf {
  namespace "ns:augment:leaf";  
  prefix "auglf";

  
  import yang {prefix yng; revision-date 2013-11-26;}	


  revision "2013-11-26" {    
  }
  
	augment "/yng:cont" {
		leaf lf2 {
			type string;
		}
	}
	
}
