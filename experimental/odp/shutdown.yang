module shutdown {
    yang-version 1;
    namespace "urn:opendaylight:params:xml:ns:yang:controller:shutdown";
    prefix "shutdown";

    import config { prefix config; revision-date 2013-04-05; }

    description
        "This module contains the base YANG definitions for
         shutdown service.

        Copyright (c)2013 Cisco Systems, Inc. All rights reserved.;

        This program and the accompanying materials are made available
        under the terms of the Eclipse Public License v1.0 which
        accompanies this distribution, and is available at
        http://www.eclipse.org/legal/epl-v10.html";

    revision "2013-12-18" {
        description
            "Initial revision.";
    }

    identity shutdown {
        base "config:service-type";
        config:java-class "org.opendaylight.controller.config.shutdown.ShutdownService";
    }

}
