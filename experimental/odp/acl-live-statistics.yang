module acl-live-statistics {
    namespace "urn:opendaylight:netvirt:acl:live:statistics";
    prefix "acl-stats";

    import ietf-interfaces {prefix if;}
    import aclservice {prefix aclservice; revision-date "2016-06-08";}

    description "YANG model describes RPC to retrieve ACL live statistics.";

    revision "2016-11-29" {
        description "Initial revision of ACL live statistics";
    }

    typedef direction {
        type enumeration {
            enum ingress;
            enum egress;
            enum both;
        }
    }

    grouping acl-drop-counts {
        leaf drop-count {
            type uint64;
        }
        leaf invalid-drop-count {
            type uint64;
        }
        leaf anti-spoof-drop-count {
            type uint64;
        }
        leaf total-drop-count {
            type uint64;
        }
    }

    grouping acl-stats-output {
        description "Output for ACL port statistics";
        list acl-port-stats {
            key "interface-name";
            leaf interface-name {
                type leafref {
                    path "/if:interfaces/if:interface/if:name";
                }
            }
            list acl-drop-stats {
                max-elements "2";
                min-elements "0";
                leaf direction {
                    type direction;
                }
                container packets {
                    uses acl-drop-counts;
                }
                container bytes {
                    uses acl-drop-counts;
                }
            }
            container error {
                leaf error-message {
                    type string;
                }
            }
        }
    }

    grouping acl-stats-input {
        description "Input parameters for ACL port statistics";

        leaf direction {
            type direction;
            mandatory "true";
        }
        leaf-list interface-names {
            type leafref {
                path "/if:interfaces/if:interface/if:name";
            }
            max-elements "unbounded";
            min-elements "1";
        }
    }

    rpc get-acl-port-statistics {
        description "Get ACL statistics for given list of ports";

        input {
            uses acl-stats-input;
        }
        output {
            uses acl-stats-output;
        }
    }

}
