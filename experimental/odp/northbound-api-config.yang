module neutron-northbound-api-config {

    namespace "urn:opendaylight:neutron:northbound-api:config";

    prefix neutron-northbound-api-config;

    import ietf-yang-types {
        prefix yang;
    }

    description "This YANG module defines neutron northbound-api configuration.";
    revision "2018-10-24";

    container neutron-northbound-api-config {
        config true;
        leaf pre-register-port-status-websocket {
           type boolean;
           default true;
           description "Pre-register the port status update websocket";
        }
    }
}
