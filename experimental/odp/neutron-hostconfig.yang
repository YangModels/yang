/*
 * Copyright (c) 2016 Intel Corporation.  All rights reserved.
 *
 * This program and the accompanying materials are made available under the
 * terms of the Eclipse Public License v1.0 which accompanies this distribution,
 * and is available at http://www.eclipse.org/legal/epl-v10.html
 */

module neutron-hostconfig {

    yang-version 1;

    namespace "urn:opendaylight:neutron-hostconfig";

    prefix neutron-hostconfig;

    organization "OpenDaylight Neutron Group";

    contact "Ritu Sood <ritu.sood@intel.com>";

    description "This YANG module defines host configurations that is used
        in specifying the physical node type (network node, compute node) for
        a host system. This information is used by Openstack Neutron scheduler.
        For example for L3 centralized SNAT support this will be used to inform
        Neutron which node is Network node. This information will be read and
        populated by networking-odl in Neutron agent_db. This model corresponds
        to openstack neutron agent API";

    revision "2015-07-12" {
        description
                "OpenDaylight Boron release";
    }

    grouping hostconfig-entry-attributes {
        description "These values will be populated by the Cloud Operator and
        will be stored in the Open_vSwitch configuration data in the
        external_ids field as a key value pair.";

        leaf host-id {
            type string;
            config false;
            description "Host identification string. This string will be
            stored with the key as odl_os_hostconfig_hostid.";
        }
        leaf host-type {
            type string;
            config false;
            description "The string is for type of the node. For example L3
            Agent,DHCP Agent etc. This string will be stored with the key as
            odl_os_hostconfig_hosttype.";
        }
        leaf config {
            type string;
            config false;
            description "This is the configuration data for the host type to
            be used to configure that host type by Openstack. This string
            will be stored with the key as odl_os_hostconfig_config.";
        }
    }

    grouping hostconfig-attributes {
        container hostconfigs {
            config false;
            list hostconfig {
                description "List of Host with types and configurations.";
                key "host-id host-type";
                uses hostconfig-entry-attributes;
            }
        }
    }
}
