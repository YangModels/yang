module service-function-forwarder-ofs {
  yang-version 1;

  namespace "urn:ericsson:params:xml:ns:yang:sfc-sff-ofs";

  prefix sfc-sff-ofs;

  import service-function-forwarder {
      prefix sfc-sff;
      revision-date 2014-07-01;
  }
  import ietf-yang-types {
      prefix yang;
      revision-date 2013-07-15;
  }

  organization "Ericsson, Inc.";
  contact "Brady Johnson <brady.allen.johnson@ericsson.com>";

  revision 2015-04-08 {
    description "Augmentation of SFF for OFS";
  }

  grouping port-details {
    container ofs-port {
      leaf port-id {
        description "Open Flow Switch port ID.";
        type string;
      }
      leaf mac-address {
        description "MAC address to use on this OFS port";
        type yang:mac-address;
      }
    }
  }

  augment "/sfc-sff:service-function-forwarders/"
        + "sfc-sff:service-function-forwarder/"
        + "sfc-sff:sff-data-plane-locator" {

    uses port-details;
  }

}
