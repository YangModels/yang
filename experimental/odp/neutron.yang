/*
 * Copyright (c) 2014 Cisco Systems, Inc. and others.  All rights reserved.
 *
 * This program and the accompanying materials are made available under the
 * terms of the Eclipse Public License v1.0 which accompanies this distribution,
 * and is available at http://www.eclipse.org/legal/epl-v10.html
 */

module neutron {

    yang-version 1;

    namespace "urn:opendaylight:neutron";

    prefix neutron;

    import neutron-extensions { prefix "extensions"; }
    import neutron-networks { prefix "networks"; }
    import neutron-ports { prefix "ports"; }
    import neutron-subnets { prefix "subnets"; }
    import neutron-secgroups { prefix "secgroups"; }
    import neutron-L3 { prefix "l3"; }
    import neutron-metering { prefix "metering"; }
    import neutron-lbaasv2 { prefix "lbaasv2"; }
    import neutron-l2gateways { prefix "l2gateways"; }
    import neutron-vpnaas { prefix "vpnaas"; }
    import neutron-fwaas { prefix "fwaas"; }
    import neutron-bgpvpns { prefix "bgpvpns"; }
    import neutron-hostconfig { prefix "hostconfig"; }
    import neutron-qos { prefix "qos"; }
    import neutron-sfc-flow-classifier { prefix "sfc-flow-classifier"; }
    import neutron-sfc { prefix "sfc"; }
    import neutron-trunks { prefix "trunks"; }
    import neutron-tapaas { prefix "tapaas"; }

    organization "OpenDaylight Neutron Group";

    contact "Ed Warnicke <eaw@cisco.com>";

    description "This YANG module defines a top level for the neutron models in opendaylight.";

    revision "2015-07-12" {
        description
                "OpenDaylight Beryllium release";
    }

    container neutron {
        uses extensions:extensions-attributes;
        uses extensions:service-provider-features-attributes;
        uses networks:networks-attributes;
        uses subnets:subnets-attributes;
        uses ports:ports-attributes;
        uses l3:routers-attributes;
        uses l3:floatingips-attributes;
        uses metering:metering-labels-attributes;
        uses metering:metering-rules-attributes;
        uses secgroups:security-groups-attributes;
        uses secgroups:security-rules-attributes;
        uses fwaas:firewalls-attributes;
        uses fwaas:policies-attributes;
        uses fwaas:rules-attributes;
        uses lbaasv2:lbaas-attributes;
        uses vpnaas:vpnservices-attributes;
        uses vpnaas:ikepolicies-attributes;
        uses vpnaas:ipsecpolicies-attributes;
        uses vpnaas:ipsecconnections-attributes;
        uses bgpvpns:bgpvpns-attributes;
        uses l2gateways:l2gateways-attributes;
        uses l2gateways:l2gateway-connections-attributes;
        uses hostconfig:hostconfig-attributes;
        uses qos:qos-attributes;
        uses sfc-flow-classifier:sfc-flow-classifiers-attributes;
        uses sfc:sfc-attributes;
        uses trunks:trunks-attributes;
        uses tapaas:tap-services-attributes;
    }
}
