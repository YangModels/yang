module pod-meta {
    namespace "urn:opendaylight:netvirt:coe:meta";
    prefix "coemeta";

    import ietf-yang-types {
        prefix yang;
        revision-date "2013-07-15";
    }

    revision "2018-01-18" {
        description "Coe Meta Information";
    }

    container podidentifier-info {
        description "Contains the list of podnames to poduuid mapping";

        list pod-identifier {
            key pod-name;
            leaf pod-name {
                type string;
            }

            leaf pod-uuid {
                type instance-identifier;
                description "reference to a pod";
            }
        }
    }
}
