module service-function-forwarder-metadata-features {

  namespace "urn:cisco:params:xml:ns:yang:sfc-sff-md-features";

  prefix sfc-sff-md-features;

  import ietf-inet-types {
      prefix inet;
      revision-date 2013-07-15;
  }

  import yang-ext {
      prefix ext;
      revision-date 2013-07-09;
  }

  import service-function-forwarder {
      prefix "sfc-sff";
      revision-date 2014-07-01;
  }

  organization "Cisco Systems, Inc.";
  contact "Reinaldo Penno <repenno@cisco.com>";


  description
    "This module contains a collection of YANG definitions for
     service function forwarder features.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2015-10-10 {
      description
      "Initial revision based on Opendaylight list discussions";
      reference "https://lists.opendaylight.org/pipermail/" +
        "sfc-dev/2015-September/001886.html";
  }

  feature vxlan-classifier-type-1 {
    description "Feature definition for C1: IPv4 tunnel dest and" +
     "C2: VNID";
  }

  augment "/sfc-sff:service-function-forwarders"  {
    description
      "Augments SFF module with definition of" +
       "VXLAN overlay classifier feature";
    ext:augment-identifier "sff-vxlan-classifier-type-1-feature";
  }

  feature mobility-allocation-type-1 {
    description "Feature definition for https://tools.ietf.org/html/" +
      "draft-napper-sfc-nsh-mobility-allocation-01";
  }

  augment "/sfc-sff:service-function-forwarders"  {
    description
      "Augments SFF module with definition of" +
       "Mobility allocation feature";
    ext:augment-identifier "sff-mobility-allocation-type-1-feature";
  }

  feature dc-allocation-type-1 {
    description "Feature definition for https://tools.ietf.org/" +
      "html/draft-guichard-sfc-nsh-dc-allocation-02";
  }

  augment "/sfc-sff:service-function-forwarders"  {
    description
      "Augments SFF module with definition of" +
       "DC allocation feature";
    ext:augment-identifier "sff-dc-allocation-type-1-feature";
  }

  augment "/sfc-sff:service-function-forwarders/"
          + "sfc-sff:service-function-forwarder" {
    description
      "Augments SFF definition with new vxlan overlay classifier " +
      "configuration";
    container vxlan-classifier-type-1 {
       if-feature "vxlan-classifier-type-1";
       presence "Enables VXLAN overlay classifier support";
       description
         "Container holding VXLAN overlay classifier configuration";
    }
    ext:augment-identifier "sff-vxlan-classifier-type-1";
  }
}
