module sfc-ioam-nb-pot {

  yang-version 1;

  namespace "urn:cisco:params:xml:ns:yang:sfc-ioam-nb-pot";

  prefix sfc-ioam-nb-pot;

  import yang-ext { prefix ext; }

  import rendered-service-path { prefix sfc-rsp; }
  import sfc-common { prefix sfc-co; }

  organization "Cisco Systems, Inc.";
  contact
     "Srihari Raghavan <srihari@cisco.com>";

  description
    "This module contains a collection of YANG definitions for
     managing service function chain proof of transit related
     configuration parameters (RPC) at the north-bound side towards
     the controller and some internal configuration parameters.";

  revision 2016-11-22 {
    description
      "Initial revision.";
    reference
      "";
  }

  identity time-resolution{
    description
      "Time interval resolution";
  } //base identity

  identity hours {
    base time-resolution;
    description
      "Hours";
  }

  identity minutes {
    base time-resolution;
    description
      "Minutes";
  }

  identity seconds {
    base time-resolution;
    description
      "Seconds";
  }

  identity milliseconds {
    base time-resolution;
    description
      "Milli-seconds";
  }

  identity microseconds {
    base time-resolution;
    description
      "Micro-seconds";
  }

  identity nanoseconds {
    base time-resolution;
    description
      "Nano-seconds";
  }

  grouping refresh-period-interval {
    description
      "Refresh period interval.";
    leaf refresh-period-time-units {
      type identityref {
        base time-resolution;
      }
      description "Time units.";
    }

    leaf refresh-period-value {
      type uint32;
      description "Time value.";
    }
  }

  typedef bit-mask-options {
    type enumeration {
      enum bits16 {
        value 0;
        description
          "16-bits used for individual proof of transit metadata.";
      }
      enum bits32 {
        value 1;
        description
          "32-bits used for individual proof of transit metadata.";
      }
      enum bits64 {
        value 2;
        description
          "64-bits used for individual proof of transit metadata.";
      }
      enum bits128 {
        value 3;
        description
          "128-bits used for individual proof of transit metadata.";
      }
      enum bits256 {
        value 4;
        description
          "256-bits used for individual proof of transit metadata.";
      }
      enum bits512 {
        value 5;
        description
          "512-bits used for individual proof of transit metadata.";
      }
      enum bits1024 {
        value 6;
        description
          "1024-bits used for individual proof of transit metadata.";
      }
    }
    description
      "Defines the max number of bits used for individual
       proof of transit metadata fields. For now, the max is 64-bits.
       This handles the current scope of the proof of transit
       domain.";
  }

  grouping ioam-pot-params {
    description "In-band OAM Proof of transit related parameters.";

    leaf ioam-pot-enable {
      type boolean;
      default false;
      description
        "Flag to enable iOAM Proof of Transit for this SFC.";
    }

    leaf ioam-pot-num-profiles {
      type uint32 {
        range "2..16";
      }
      default 2;
      description
        "Default number of profiles to be sent to nodes.
         Currently, it defaults to two to handle an odd and
         even profile per node.";
    }

    leaf ioam-pot-bit-mask {
      type bit-mask-options;
      default bits64;
      description "Default bit mask value for proof of transit
                   calculations.";
    }

    uses refresh-period-interval;
  }

  augment "/sfc-rsp:rendered-service-paths"
        + "/sfc-rsp:rendered-service-path" {
    description "Rendered service path's proof of transit
                 related augmentation.";
    ext:augment-identifier "rsp-ioam-pot-augmentation";
    uses ioam-pot-params;
  }


  /*** RPCs ***/
  rpc enable-sfc-ioam-pot-rendered-path {
    description
      "Enable and Configure service function chain proof
       of transit for a rendered service path.";
    input {
      leaf sfc-ioam-pot-rsp-name {
        type sfc-co:rsp-name;
        description
          "Name of the Rendered Service Path to enable
           proof of transit on. This should be an existing
           rendered service path such as one created from
           rendered-service-path:create-rendered-path RPC.
           NOTE: by default, the last node of the SFC is
           taken as the decap node for proof of transit.";
      }

      uses ioam-pot-params;
    }

    output {
      leaf result {
        type boolean;
        description
          "True if SFC proof of transit of the chosen
           Rendered Service Path is enabled, otherwise false";
      }
    }
  }

  rpc disable-sfc-ioam-pot-rendered-path {
    description
      "Disable service function chain proof of transit
       for a rendered service path.";
    input {
      leaf sfc-ioam-pot-rsp-name {
        type sfc-co:rsp-name;
        description
          "Name of the Rendered Service Path to disable
           proof of transit on. This should be an existing
           rendered service path such as one created from
           rendered-service-path:create-rendered-path RPC.";
      }
    }

    output {
      leaf result {
        type boolean;
        description
          "True if SFC proof of transit of the chosen
           Rendered Service Path is disabled, otherwise false.";
      }
    }
  }
}
