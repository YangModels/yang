module netvirt-sfc {
    yang-version 1;
    namespace "urn:opendaylight:params:xml:ns:yang:netvirt:sfc";
    prefix "netvirt-sfc";

    revision "2015-01-05" {
        description "Initial revision of the netvirt sfc model";
    }

    container sfc {
        leaf name {
            type string;
        }
    }
}
