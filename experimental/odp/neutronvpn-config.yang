module neutronvpn-config {
    yang-version 1;
    namespace "urn:opendaylight:netvirt:neutronvpn:config";
    prefix "neutronvpn-config";
    description
        "Configuration for neutronvpn-impl.";

    revision "2016-08-06" {
        description
                "Initial revision.";
    }

    container neutronvpn-config {
        config true;

        leaf opendaylight-vni-ranges {
            type string;
            default "70000:99999";
        }
    }
}
