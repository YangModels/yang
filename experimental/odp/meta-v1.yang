module meta-v1 {
    yang-version 1;
    namespace "urn:opendaylight:k8s:meta-v1";
    prefix "meta-v1";

    description
        "This YANG module defines the kubernetes meta-v1 API.";

    revision "2018-12-05" {
        description "Initial revision.";
    }

    organization "OpenDaylight COE Group";

    contact "COE Developers <coe-dev@lists.opendaylight.org>";

    grouping label-selector {
        list match-labels {
            leaf key {
                type string;
            }
            leaf value {
                type string;
            }
        }
    }
}
