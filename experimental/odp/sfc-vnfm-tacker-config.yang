module sfc-vnfm-tacker-config {
    yang-version 1;
    namespace "urn:opendaylight:sfc:vnfm:tacker:config";
    prefix "vnfm-tacker-config";

    description
      "This module contains the YANG configuration definitions for the SFC VNF MANAGER TACKER module.";

    revision "2017-07-24" {
        description "Initial revision";
    }

    container vnfm-tacker-config {
        description
            "Configuration for SFC Vnfm Tacker setup";

        leaf sfc-vnfm-tacker-name {
            description
                "This is the username used for authentication with tacker service.";
            type string;
        }
        leaf sfc-vnfm-tacker-password {
            description
                "This is the password used for authentication with tacker service.";
            type string;
        }
        leaf sfc-vnfm-uri {
            description
                "This is the URI used for communication with services.";
            type string;
        }
        leaf sfc-vnfm-tacker-port {
            description
                "This is the port that Tacker uses for communication.";
            type int32;
        }
        leaf sfc-vnfm-keystone-port {
            description
                "This is the port that Keystone uses for communication.";
            type int32;
        }
        leaf sfc-vnfm-tacker-tenant {
            description
                "This is the tenant name used for tacker.";
            type string;
        }
    }
}
