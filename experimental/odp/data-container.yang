module data-container-yang {
  namespace "data:container:yang";  

  prefix "dtconyg";
  revision 2013-11-19 {    
  }
  
  container cont {	
	  list lst1 {
	  	leaf lf11 {
	  		type string;
	  	}
	  	leaf-list lflst11 {
	  		type string;
	  	}
	  	list lst11 {
	  		leaf lf111 {
	  			type string;
	  		} 
	  	}
	  	container cont11 {
	  		leaf lf111 {
	  			type uint8;
	  		}
	  	}
	  }  
  }
}
