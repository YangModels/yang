module network-config {
    yang-version 1;
    namespace "urn:opendaylight:genius:networkutils:config";
    prefix "network-config";
    description
        "Configuration for network parameters";

    revision "2018-11-29" {
        description
                "Initial revision.";
    }

    container network-config {
        config true;

        leaf opendaylight-vni-ranges {
            type string;
            default "70000:99999";
        }

        leaf opendaylight-rd-start-value {
            type         string;
            description  "start value of auto generated RD";
            default      "100:1";
        }

        leaf opendaylight-rd-count {
            type         uint32;
            description  "number of RD values to be autogenarated";
            default      65535;
        }
    }
}
