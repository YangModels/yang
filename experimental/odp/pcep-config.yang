// vi: set smarttab et sw=4 tabstop=4:
module pcep-config {
    yang-version 1.1;
    namespace "urn:opendaylight:params:xml:ns:yang:pcep:config";
    prefix pd-config;

    import ietf-inet-types { prefix inet; revision-date 2013-07-15; }
    import rfc2385 { prefix rfc2385; revision-date 2016-03-24; }

    organization "AT&T Services, Inc.";
    contact "Claudio D. Gasparini <claudio.gasparini@pantheon.sk>";

    description
        "This module contains the base YANG definitions for
         PCEP Dispatcher service config.
         Copyright (c)2017 AT&T Services, Inc. All rights reserved.;

         This program and the accompanying materials are made available
         under the terms of the Eclipse Public License v1.0 which
         accompanies this distribution, and is available at
         http://www.eclipse.org/legal/epl-v10.html";

    revision "2017-10-25" {
        description
            "Initial revision.";
    }

    grouping pcep-config {
        container session-config {
            description "PCEP topology config";

            leaf rpc-timeout {
                type int16;
                default 30;
                units seconds;
            }

            leaf listen-address {
                type inet:ip-address;
                default "0.0.0.0";
            }

            leaf listen-port {
                type inet:port-number;
                default 4189;
            }

            leaf dead-timer-value {
                type uint16;
                default 120;
                units seconds;
            }

            leaf keep-alive-timer-value {
                type uint16;
                default 30;
                units seconds;
            }
        }
    }

    grouping pcep-node-config {
        description "PCEP node config";

        container session-config {
            leaf password {
                type rfc2385:rfc2385-key;
                description "RFC2385 shared secret";
            }
        }
    }
}
