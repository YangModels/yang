module test-types {
    yang-version 1;
    namespace "urn:opendaylight:params:xml:ns:yang:controller:config:test:types";
    prefix "tt";

    description
        "Types generated for testing";

    revision "2013-11-27";

    typedef extend-once {
        type uint16;
    }

    typedef extend-twice {
        type extend-once;
    }

    typedef extend-enum {
        type enumeration {
            enum "ONE";
            enum "TWO";
        }
    }

      typedef unionTest {
        type union {
          type string;
          type uint32;
          type extend-twice;
        }
      }



    identity test-identity1 {

    }

    identity test-identity2 {
        base test-identity1;
    }
}
