module sal-remote {

    yang-version 1;
    namespace "urn:opendaylight:params:xml:ns:yang:controller:md:sal:remote";
    prefix "sal-remote";

    organization "Cisco Systems, Inc.";
    contact "Martin Bobak <mbobak@cisco.com>";

    description
          "This module contains the definition of methods related to
           sal remote model.

           Copyright (c)2013 Cisco Systems, Inc. All rights reserved.

           This program and the accompanying materials are made available
           under the terms of the Eclipse Public License v1.0 which
           accompanies this distribution, and is available at
           http://www.eclipse.org/legal/epl-v10.html";

    revision "2014-01-14" {
        description
            "Initial revision";
    }


     typedef q-name {
       type string;
       reference
         "http://www.w3.org/TR/2004/REC-xmlschema-2-20041028/#QName";
     }

    rpc create-data-change-event-subscription {
        input {
            leaf path {
                type instance-identifier;
                description "Subtree path. ";
            }
         }
         output {
            leaf stream-name {
                type string;
                description "Notification stream name.";
            }
         }
    }

    notification data-changed-notification {
        description "Data change notification.";
        list data-change-event {
            key path;
            leaf path {
                type instance-identifier;
            }
            leaf store {
                type enumeration {
                    enum config;
                    enum operation;
                }
            }
            leaf operation {
                type enumeration {
                    enum created;
                    enum updated;
                    enum deleted;
                }
            }
            anyxml data{
                description "DataObject ";
            }
         }
    }

    rpc create-notification-stream {
        input {
            leaf-list notifications {
                type q-name;
                description "Notification QNames";
            }
         }
        output {
            leaf notification-stream-identifier {
                type string;
                description "Unique notification stream identifier, in which notifications will be propagated";
            }
        }
    }

    rpc begin-transaction {
        output {
            anyxml data-modification-transaction{
                description "DataModificationTransaction xml";
            }
        }
    }

}
