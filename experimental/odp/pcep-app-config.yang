module pcep-app-config {
    yang-version 1;
    namespace "urn:opendaylight:params:xml:ns:yang:controller:pcep:app-config";
    prefix "pcep-app-config";

    description
      "Configuration for the PCEP implementation.";

    revision "2016-07-07" {
        description
            "Initial revision.

            Copyright (c) 2016 Brocade Communications Systems, Inc. All rights reserved.

            This program and the accompanying materials are made available
            under the terms of the Eclipse Public License v1.0 which
            accompanies this distribution, and is available at
            http://www.eclipse.org/legal/epl-v10.html";
    }

    container pcep-session-config {
        leaf dead-timer-value {
            type uint16;
            default 120;
        }

        leaf keep-alive-timer-value {
            type uint16;
            default 30;
        }
    }

    typedef path-type {
        type enumeration {
            enum "PATH";
            enum "CLASSPATH";
        }
    }

    typedef store-type {
        type enumeration {
            enum "JKS";
            enum "PKCS12";
        }
    }

    container pcep-dispatcher-config {
        leaf max-unknown-messages {
            type uint16 {
                range "1..max";
            }
            default 5;
        }

        container tls {
            presence true;
            leaf keystore {
                description "keystore location";
                type string;
                mandatory true;
            }
            leaf keystore-type {
                description "keystore type (JKS or PKCS12)";
                type store-type;
                mandatory true;
            }
            leaf keystore-path-type {
                description "keystore path type (CLASSPATH or PATH)";
                type path-type;
                mandatory true;
            }
            leaf keystore-password {
                description "password protecting keystore";
                type string;
                mandatory true;
            }
            leaf certificate-password {
                description "password protecting certificate";
                type string;
                mandatory true;
            }
            leaf truststore {
                description "truststore location";
                type string;
                mandatory true;
            }
            leaf truststore-type {
                description "truststore type (JKS or PKCS12)";
                type store-type;
                mandatory true;
            }
            leaf truststore-path-type {
                description "truststore path type (CLASSPATH or PATH)";
                type path-type;
                mandatory true;
            }
            leaf truststore-password {
                description "password protecting truststore";
                type string;
                mandatory true;
            }
        }
    }
}
