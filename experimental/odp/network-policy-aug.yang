module network-policy-aug {
    yang-version 1;
    namespace "urn:opendaylight:k8s:network-policy-aug";
    prefix "network-policy-aug";

    description
        "This YANG module defines the kubernetes network policy API
         augmentations.";

    revision "2018-12-05" {
        description "Initial revision.";
    }

    import yang-ext { prefix "ext"; }
    import k8s { prefix k8s; revision-date "2018-12-05"; }
    import meta-v1 { prefix meta-v1; revision-date "2018-12-05"; }
    import network-policy { prefix network-policy; revision-date "2018-12-05"; }
    import pod { prefix pod; revision-date "2017-06-11"; }

    organization "OpenDaylight COE Group";

    contact "COE Developers <coe-dev@lists.opendaylight.org>";

    grouping pods {
        list pods {
            key "uid";

                description
                    "List of all configured pods in the network.";

                uses pod:pod_attributes;
            }
        }
    }

    augment "/k8s:k8s/k8s:network-policies/k8s:network-policy/k8s:pod-selector" {
        description "Augment the network-policy container with pods information.";
        ext:augment-identifier "spec-pod-selector-aug";
        uses pods;
    }

    augment "/k8s:k8s/k8s:network-policies/k8s:network-policy/k8s:ingress/k8s:from/k8s:peer-pod-selector" {
        description "Augment the container with pods information.";
        ext:augment-identifier "from-peer-pod-selector-aug";
        uses pods;
    }

    augment "/k8s:k8s/k8s:network-policies/k8s:network-policy/k8s:egress/k8s:to/k8s:peer-pod-selector" {
        description "Augment the container with pods information.";
        ext:augment-identifier "to-peer-pod-selector-aug";
        uses pods;
    }

    augment "/k8s:k8s/k8s:network-policies/k8s:network-policy/k8s:ingress/k8s:from/k8s:peer-namespace-selector" {
        description "Augment the container with pods information.";
        ext:augment-identifier "from-peer-namespace-selector-aug";
        uses pods;
    }

    augment "/k8s:k8s/k8s:network-policies/k8s:network-policy/k8s:egress/k8s:to/k8s:peer-namespace-selector" {
        description "Augment the container with pods information.";
        ext:augment-identifier "to-peer-namespace-selector-aug";
        uses pods;
    }
}
