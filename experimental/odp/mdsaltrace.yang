module mdsaltrace {
    yang-version 1;
    namespace "urn:opendaylight:params:xml:ns:yang:mdsaltrace";
    prefix "mdsaltrace";

    organization
        "Red Hat, Inc.";

    description
        "Copyright (c) 2016 Red Hat, Inc. and others.  All rights reserved.

        This program and the accompanying materials are made available under the
        terms of the Eclipse Public License v1.0 which accompanies this distribution,
        and is available at http://www.eclipse.org/legal/epl-v10.html";

    revision "2016-09-08" {
        description "Initial revision of mdsaltrace model";
    }

    container config {
        leaf-list registration-watches {
            type string;
        }
        leaf-list write-watches {
            type string;
        }
        leaf transaction-debug-context-enabled {
            default false;
            type boolean;
            description "Enable or disable transaction context debug. This will preserve the call site trace for
                         transactions, so that the original caller of un-close'd() transaction can be identified.
                         NB: This is a different property from the equally named one in etc/org.opendaylight.controller.cluster.datastore.cfg;
                         that one does something somewhat similar, but serves to include the stack trace on failed transaction submit,
                         whereas this one is specific to odl-mdsal-trace's trace:transaction leak troubleshooting command.";
            // This ^^^ description is also copy/pasted in mdsaltrace_config.xml, and should be kept in line.]
        }
    }
}
