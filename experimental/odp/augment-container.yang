module augment-container {
  namespace "ns:augment:container";  
  prefix "augcont";

  
  import yang {prefix yng; revision-date 2013-11-26;}	


  revision "2013-11-26" {    
  }
  
	augment "/yng:cont" {
		container cont1 {
			leaf lf11 {
				type string;
			}
		}
	}
	

	  
}
