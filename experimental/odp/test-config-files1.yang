module test-config-files1 {
    yang-version 1;
    namespace "urn:opendaylight:params:xml:ns:yang:controller:config:test:files1";
    prefix "it-duplicate";

    import config { prefix config; revision-date 2013-04-05; }
    import ietf-inet-types { prefix inet; revision-date 2010-09-24;}


    description
        "Testing IMPL";

    revision "2013-04-03" {
        description
            "Initial revision";
    }

    identity implementation1 {
        base config:module-type;
        config:java-name-prefix TestFiles1Impl;
    }

    identity netconf1 {
        base config:module-type;
        config:java-name-prefix NetconfTestFiles1Impl;
    }

    augment "/config:modules/config:module/config:configuration" {
        case implementation1 {
            when "/config:modules/config:module/config:type = 'implementation1'";

           container dto-a {
                leaf simple-arg {
                    type uint32;
                }

                leaf port {
                    type inet:port-number;
                }

            }
        }
    }

    augment "/config:modules/config:module/config:state" {
        case implementation1 {
            when "/config:modules/config:module/config:type = 'implementation1'";
            // root runtime bean
            leaf created-sessions {
                type uint32;
            }
        }
    }

    augment "/config:modules/config:module/config:configuration" {
        case netconf1 {
            when "/config:modules/config:module/config:type = 'netconf1'";
        }
    }

    augment "/config:modules/config:module/config:state" {
        case netconf1 {
            when "/config:modules/config:module/config:type = 'netconf1'";
            // root runtime bean
            leaf created-sessions {
                type uint32;
            }

        }
    }
}
