module service-function-forwarder-ovs {
  yang-version 1;

  namespace "urn:cisco:params:xml:ns:yang:sfc-sff-ovs";

  prefix sfc-sff-ovs;

  import service-function-forwarder {
      prefix sfc-sff;
      revision-date 2014-07-01;
  }
  import sfc-common {
      prefix sfc-common;
      revision-date 2015-10-17;
  }
  import yang-ext {
      prefix ext;
      revision-date 2013-07-09;
  }
  import ietf-yang-types {
      prefix yang;
      revision-date 2013-07-15;
  }
  import ovsdb {
    prefix ovsdb;
    revision-date 2015-01-05;
  }
  import overlay {
    prefix ovsdb-overlay;
    revision-date 2015-01-05;
  }

  organization "Cisco Systems, Inc.";
  contact "Reinaldo Penno <repenno@cisco.com>";

  description
    "This module contains a collection of YANG definitions used
     to augment Service Function Forwarder configuration with
     OpenvSwitch specific information.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2014-07-01 {
    description "Augmentation of SFF for OVS";
    reference "https://tools.ietf.org/html/draft-penno-sfc-yang";
  }

  grouping node {
    description
      "Groups that holds OVS node information";
    container ovs-node {
      description
        "This container holds OVS node information";
      leaf node-id {
        type ovsdb:ovsdb-node-ref;
        description "Open vSwitch node id.";
      }
    }
  }

  grouping bridge {
    description
      "Groups OVS bridge information that is reused throughout
       SFF augmentations";
    container ovs-bridge {
      description
        "This container holds OVS bridge information";
      leaf bridge-name {
        type string;
        description
          "Open vSwitch bridge name. In Openstack it is usually"
          + " br-tun or br-int depending if it is used in the"
          + " overlay or facing virtual machines respectively";
      }
      leaf uuid {
        type yang:uuid;
        description "Open vSwitch bridge UUID";
      }
      leaf openflow-node-id {
        type string;
        description "Openflow node ID";
      }
      list external-ids {
        key "name";
        description
          "The list of external ids associated with this
           bridge";
        leaf name {
          type string;
          description
            "A unique string that represents this external-id such
             as attached-mac";
        }
        leaf value {
          type string;
          description
            "A unique string that represents the value of the
             external-id such as fa:16:3e:56:47:10";
        }
      }
    }
  }

  container sff-ovs-mappings {

    description "Container for keeping lists of mappings needed"
      + "by the SFC-OVS renderer";

    list ovs-node-to-sff-mapping {
      key "uuid bridge-name";
      config false;
      description "List to keep mappings of OVS UUIDs + Bridge Name"
        + "to Service Function Fowarders (SFFs). This is used to"
        + "correlate OVS bridge events to SFFs";
      leaf uuid {
        type yang:uuid;
        description "Open vSwitch bridge UUID";
      }
      leaf bridge-name {
        type string;
        description
          "Open vSwitch bridge name. In Openstack it is usually"
          + " br-tun or br-int depending if it is used in the"
          + " overlay or facing virtual machines respectively";
      }
      leaf name {
        type sfc-common:sff-name;
        description
          "The unique name of this service function forwarder, such
           as SFF1";
      }
    }
  }

  grouping options {
    description
      "Groups all OVS specific configuration options that are reused
       throughout many SFF augmentations";
    container ovs-options {
      description "Port/Interface related optional input values";
      leaf local-ip {
        type string;
        description "Local interface IP address";
      }
      leaf remote-ip {
        type string;
        description
          "Remote IP address, e.g. the remote Vxlan tunnel endpoint
           IP";
      }
      leaf dst-port {
        type string;
        description
          "Remote port, e.g. the remote Vxlan tunnel endpoint port";
      }
      leaf nsp {
        type string;
        description "NSH Service Path ID";
      }
      leaf nsi {
        type string;
        description "NSH Starting Index";
      }
      leaf exts {
        type string;
        description "VxLAN extension type";
      }
      leaf in-nsp {
        type string;
        description "Ingress NSH Service Path ID";
      }
      leaf in-nsi {
        type string;
        description "Ingress NSH Service Index";
      }
      leaf out-nsp {
        type string;
        description "Egress NSH Service Path ID";
      }
      leaf out-nsi {
        type string;
        description "Egress NSH Service Index";
      }
      leaf nshc1 {
        type string;
        description "NSH Context Header 1";
      }
      leaf nshc2 {
        type string;
        description "NSH Context Header 2";
      }
      leaf nshc3 {
        type string;
        description "NSH Context Header 3";
      }
      leaf nshc4 {
        type string;
        description "NSH Context Header 4";
      }
      leaf key {
        type string;
        description "Vxlan tunnel ID";
      }
    }
  }

  augment "/sfc-sff:service-function-forwarders/"
        + "sfc-sff:service-function-forwarder" {
    description
      "Augments the SFF definition with
       OVS node specific information";
    ext:augment-identifier "sff-ovs-node-augmentation";
    uses node;
  }

  augment "/sfc-sff:service-function-forwarders/"
          + "sfc-sff:service-function-forwarder" {
    description
      "Augments the SFF definition with
       bridge specific information";
    ext:augment-identifier "sff-ovs-bridge-augmentation";
    uses bridge;
  }

  augment "/sfc-sff:service-function-forwarders/"
        + "sfc-sff:service-function-forwarder/"
        + "sfc-sff:sff-data-plane-locator" {
    description
      "Augments the SFF data plane locator with
       bridge specific information";
    ext:augment-identifier "sff-ovs-locator-bridge-augmentation";
    uses bridge;
  }

  augment "/sfc-sff:service-function-forwarders/"
        + "sfc-sff:service-function-forwarder/"
        + "sfc-sff:sff-data-plane-locator" {
    description
      "Augments the SFF data plane locator with
       options specific to OVS such as context headers";
    ext:augment-identifier "sff-ovs-locator-options-augmentation";
    uses options;
  }

  rpc create-ovs-bridge {
    description
      "Creates OVS Bridge on specified OVS Node";
    input {
      leaf name {
        type string;
        description
          "The name of OVS Bridge to be created";
      }

      container ovs-node {
        description
        "Contains ip:port locator of the OVS Node,
        on which OVS Bridge is going to be created";

        uses ovsdb-overlay:ip-port-locator;
      }
    }
    output {
      leaf result {
        type boolean;
        description
          "True if the OVS bridge was created, otherwise
           false";
      }
    }
  }
}
