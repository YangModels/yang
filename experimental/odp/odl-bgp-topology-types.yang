module odl-bgp-topology-types {
    namespace "urn:opendaylight:params:xml:ns:yang:odl-bgp-topology-types";
    prefix "topology-types";

    import network-topology { prefix nt; revision-date 2013-10-21; }

    organization "Brocade Communications Systems, Inc.";
    contact "Ajay Lele <alele@brocade.com>";

    description
        "This module contains augmentations to ODL network topology
        types for various BGP topologies.

        Copyright (c) 2016 Brocade Communications Systems, Inc. All rights reserved.

        This program and the accompanying materials are made available
        under the terms of the Eclipse Public License v1.0 which
        accompanies this distribution, and is available at
        http://www.eclipse.org/legal/epl-v10.html";

    revision 2016-05-24 {
        description "Initial revision";
    }

    grouping bgp-ipv4-reachability-topology-type {
        container bgp-ipv4-reachability-topology {
            presence "Indicates a BGP IPv4 reachability aware topology";
        }
    }

    grouping bgp-ipv6-reachability-topology-type {
        container bgp-ipv6-reachability-topology {
            presence "Indicates a BGP IPv6 reachability aware topology";
        }
    }

    grouping bgp-linkstate-topology-type {
        container bgp-linkstate-topology {
            presence "Indicates a BGP linkstate aware topology";
        }
    }

    augment "/nt:network-topology/nt:topology/nt:topology-types" {
        uses bgp-ipv4-reachability-topology-type;
        uses bgp-ipv6-reachability-topology-type;
        uses bgp-linkstate-topology-type;
    }
}
