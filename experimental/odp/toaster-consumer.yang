// vi: set smarttab et sw=4 tabstop=4:
module toaster-consumer {

    yang-version 1;
    namespace "urn:opendaylight:params:xml:ns:yang:controller:config:toaster-consumer";
    prefix "toaster-consumer";

    import config { prefix config; revision-date 2013-04-05; }

    description
        "This module contains the base YANG definitions for
        toaster-consumer services.";

    revision "2014-01-31" {
        description
            "Initial revision.";
    }

    // This is the definition of a service
    identity toaster-consumer {

        base "config:service-type";

        config:java-class "org.opendaylight.controller.sample.toaster.provider.api.ToastConsumer";
    }
}
