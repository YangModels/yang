module ipv6service-config {
    yang-version 1;
    namespace "urn:opendaylight:netvirt:ipv6service-config";
    prefix "ipv6service-config";

    description
        "Configuration for IPv6 service.";

    revision "2018-10-10" {
        description
                "Initial revision.";
    }

    container ipv6service-config {
        config true;

        leaf router-discovery-punt-timeout {
            description "Hard timeout value for learnt flows for router discovery punts (unit - seconds).
                To turn off the rate limiting and installation of learnt flows, it should be set to 0";
            type uint16;
            default 10;
        }

        leaf neighbor-discovery-punt-timeout {
            description "Hard timeout value for learnt flows for neighbor discovery punts (unit - seconds).
                To turn off the rate limiting and installation of learnt flows, it should be set to 0";
            type uint16;
            default 10;
        }
    }
}
