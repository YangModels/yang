module reconciliation {

    namespace "urn:opendaylight:params:xml:ns:yang:openflowplugin:app:reconciliation:service";
    prefix reconciliation;

    import ietf-yang-types {prefix yang; revision-date "2013-07-15";}
    revision "2018-02-27" {
        description "Initial revision for reconciliation";
    }

    container reconciliation-counter {
        description "Number of reconciliation triggered for openflow nodes";
        config false;
        list reconcile-counter {
            key node-id;
            leaf node-id {
                type uint64;
            }
            uses counter;
        }
    }

    grouping counter {
        leaf success-count {
            type uint32;
            default 0;
        }
        leaf failure-count {
            type uint32;
            default 0;
        }
        leaf last-request-time {
             description "Timestamp when reconciliation was last requested";
             type yang:date-and-time;
        }
    }

    container reconciliation-state {
         description "Reconciliation state for the given openflow nodes";
         config false;
         list reconciliation-state-list {
              key node-id;
              leaf node-id {
                   type uint64;
              }
              uses node-reconcile-state;
         }
    }

    grouping node-reconcile-state {
         leaf state {
              description "Current state of the node reconciliation";
              type enumeration {
                   enum IN_PROGRESS;
                   enum COMPLETED;
                   enum FAILED;
              }
         }
    }

    rpc reconcile {
        description "Request the reconciliation for given device or set of devices to the controller.";
        input {
            leaf-list nodes {
                description "List of nodes to be reconciled";
                type uint64;
            }

            leaf reconcile-all-nodes {
                description "Flag to indicate that all nodes to be reconciled";
                type boolean;
                mandatory false;
                default false;
            }
        }

        output {
             leaf result {
                 type boolean;
             }

             leaf-list inprogress-nodes {
                 description "List of nodes currently reconciliation mode";
                 type uint64;
             }
        }
    }
}
