module service-function-ovs {
  yang-version 1;

  namespace "urn:ericsson:params:xml:ns:yang:sfc-sf-ovs";

  prefix sfc-sf-ovs;

  import service-function {
      prefix sfc-sf;
      revision-date 2014-07-01;
  }
  import yang-ext {
      prefix ext;
      revision-date 2013-07-09;
  }

  organization "Ericsson, Inc.";
  contact "Brady Johnson <brady.allen.johnson@ericsson.com>";

  description
    "This module contains a collection of YANG definitions used
     to augment Service Function configuration with OpenvSwitch
     specific information.";

  revision 2016-01-07 {
    description
      "Augment SF to include OVS tap port in DPL.";
    reference
     "https://tools.ietf.org/html/draft-penno-sfc-yang-14";
  }

  grouping connected-port {
    description
      "Groups OVS connected port information";
    container ovs-port {
      description
        "Holds OVS port information";
      leaf port-id {
        type string;
        description "OVS port ID this SF is connected on";
      }
    }
  }

  augment "/sfc-sf:service-functions/"
        + "sfc-sf:service-function/"
        + "sfc-sf:sf-data-plane-locator" {
    description
      "Augments the SF Data Plane Locator definition
       with OVS specific information";
    ext:augment-identifier "sf-dpl-ovs-augmentation";
    uses connected-port;
  }

}
