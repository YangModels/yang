module simple-yang-types {
  namespace "simple:yang:types";  

  prefix "smptp";
   revision 2013-11-5 {
    description  "Initial revision.";
  }
  
  container cont1 {
	  leaf lf11 {
	  	type string;
	  }
	  leaf-list lflst11 {
	  	type int32;
	  }
	  leaf-list lflst12 {
	  	type string;
	  }
	  list lst11 {
	  	key lf111;
	  	leaf lf111 {
	  		type uint8;
	  	}
	  	leaf lf112 {
	  		type string;
	  	}	  	
	  	container cont111 {
	  		leaf lf1111 {
	  			type string;
	  		}
	  		leaf-list lflst1111 {
	  			type int32;
	  		}
	  		list lst1111 {
	  			leaf lf1111A {
	  				type string;
	  			}
	  			leaf lf1111B {
	  				type uint8;
	  			}
	  		}
	  	}
	  	list lst111 {
	  		leaf lf1111 {
	  			type int32;
	  		}
	  	}
	  	list lst112 {
	  		leaf lf1121 {
	  			type string;
	  		}
	  	}	  	
	  }
	  
  }

}
