module network-topology-programming {
    yang-version 1;
    namespace "urn:opendaylight:params:xml:ns:yang:topology:programming";
    prefix "tp";

    import network-topology { prefix nt; revision-date 2013-10-21; }
    import odl-network-topology { prefix ont; revision-date 2014-01-13; }
    import programming { prefix pgm; revision-date 2015-07-20; }

    organization "Cisco Systems, Inc.";
    contact "Robert Varga <rovarga@cisco.com>";

    description
        "This module contains the programming extensions for tunnel
        topologies.

        Copyright (c)2013 Cisco Systems, Inc. All rights reserved.

        This program and the accompanying materials are made available
        under the terms of the Eclipse Public License v1.0 which
        accompanies this distribution, and is available at
        http://www.eclipse.org/legal/epl-v10.html";

    revision "2013-11-02" {
        description
            "Initial revision.";
        reference "";
    }

    grouping topology-instruction-input {
        uses pgm:submit-instruction-input;
        uses ont:network-topology-reference;
    }

    grouping topology-instruction-output {
        uses pgm:submit-instruction-output;
    }
}
