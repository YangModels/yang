module odl-pcep-auto-bandwidth {
    namespace "urn:opendaylight:params:xml:ns:yang:controller:pcep:auto:bandwidth";
    prefix "auto-bw";

    import pcep-types { prefix pcep; revision-date 2018-11-09; }
    import pcep-message { prefix msg; revision-date 2018-11-09; }
    import network-topology { prefix nt; revision-date 2013-10-21; }
    import network-topology-pcep { prefix topo; revision-date 2018-11-09; }
    import odl-pcep-ietf-stateful07 { prefix stateful; revision-date 2018-11-09; }
    import network-concepts { prefix netc; revision-date 2013-11-25; }

    organization "Cisco Systems, Inc.";
    contact "Milos Fabian <milfabia@cisco.com>";

    description
        "This module contains the data model of PCEP extensions defined
        in draft-dhody-pce-stateful-pce-auto-bandwidth-06.

        Copyright (c)2016 Cisco Systems, Inc. All rights reserved.

        This program and the accompanying materials are made available
        under the terms of the Eclipse Public License v1.0 which
        accompanies this distribution, and is available at
        http://www.eclipse.org/legal/epl-v10.html";

    revision "2018-11-09" {
        description
            "P2MP extension.";
        reference "RFC8306";
    }

    revision 2017-10-25 {
        description "Update network-topology-pcep revision";
    }

    revision 2016-01-09 {
        description "Initial revision";
        reference "https://tools.ietf.org/html/draft-dhody-pce-stateful-pce-auto-bandwidth-06";
    }

    grouping bw-samples {
        leaf-list bw-sample {
            type netc:bandwidth;
            ordered-by user;
        }
    }

    grouping bandwidth-usage-object {
        description "Bandwidth-Usage Report Object";
        reference "https://tools.ietf.org/html/draft-dhody-pce-stateful-pce-auto-bandwidth-06#section-8.4";
        container bandwidth-usage {
            uses pcep:object;
            uses bw-samples;
        }
    }

    augment "/stateful:pcrpt/stateful:pcrpt-message/stateful:reports/stateful:path/stateful:bandwidth" {
        uses bw-samples;
    }

    augment "/nt:network-topology/nt:topology/nt:node/topo:path-computation-client/topo:reported-lsp/topo:path/topo:bandwidth" {
        uses bw-samples;
    }

}
