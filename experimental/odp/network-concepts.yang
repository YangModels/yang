module network-concepts {
    yang-version 1;
    namespace "urn:opendaylight:params:xml:ns:yang:network:concepts";
    prefix "netc";

    import ieee754 { prefix ieee754; revision-date 2013-08-19; }

    organization "Cisco Systems, Inc.";
    contact "Dana Kutenicsova <dkutenic@cisco.com>";

    description
        "This module contains the base data model of used general
        concepts.

        Copyright (c)2013 Cisco Systems, Inc. All rights reserved.

        This program and the accompanying materials are made available
        under the terms of the Eclipse Public License v1.0 which
        accompanies this distribution, and is available at
        http://www.eclipse.org/legal/epl-v10.html";

    revision "2013-11-25" {
        description
            "Rename to network concepts";
    }

    revision "2013-09-30" {
        description
            "Initial revision.";
    }

    typedef iso-system-identifier {
        reference "https://tools.ietf.org/html/draft-ietf-idr-ls-distribution-03#section-3.2.1.4";
        type binary {
            length "6";
        }
    }

    typedef igp-metric {
        reference "http://tools.ietf.org/html/draft-ietf-idr-ls-distribution-03#section-3.3.2.3";
        type uint32 {
            range "0..16777215";
        }
    }

    typedef te-metric {
        reference "http://tools.ietf.org/html/draft-ietf-idr-ls-distribution-03#section-3.3.2.3";
        type uint32;
    }

    typedef bandwidth {
        type ieee754:float32;
    }

    typedef metric {
        reference "http://tools.ietf.org/html/draft-ietf-idr-ls-distribution-03#section-3.3.3.4";
        type uint32;
    }

    typedef accumulated-igp-metric {
        reference "https://tools.ietf.org/html/rfc7311#section-3";
        type uint64;
    }

    typedef mpls-label {
        reference "https://tools.ietf.org/html/rfc3032#section-2.1";
        type uint32 {
            range "0..1048575";
        }
    }
}
