module sfc-ioam-sb-pot-hop-params {

  yang-version 1;

  namespace "urn:cisco:params:xml:ns:yang:sfc-ioam-sb-pot-hop-params";

  prefix sfc-ioam-sb-pot-hop-params;

  organization "Cisco Systems, Inc.";
  contact
     "Srihari Raghavan <srihari@cisco.com>";

  description
    "This module contains a collection of YANG definitions for
     generated OAM proof of transit per-hop configuration
     parameters.";

  revision 2016-12-05 {
    description
      "Initial revision.";
    reference
      "";
  }

  container poly-secrets {
    description "Proof of transit algorithm per-hop parameters.";
    list poly-secret {
      key "pindex";
      ordered-by system;
      description
        "List of parameters ordered by the profile name
         for a node to use.";

      leaf pindex {
        type uint32;
        description
          "Profile index being referred to.";
      }

      leaf secret-share {
        type int64;
        description
          "Per-hop secret share of the profile.";
      }

      leaf secret {
        type int64;
        description
          "The overall secret of the profile being referred to.
           Meant for the proof of transit verifier node.";
      }
    }
  }
}
