module natservice-config {
    yang-version 1;
    namespace "urn:opendaylight:netvirt:natservice:config";
    prefix "natservice-config";

    description
        "Configuration for nat-serviceImpl.";

    revision "2017-02-06" {
        description
                "Initial revision.";
    }

    container natservice-config {
        config true;
        leaf nat-mode {
            type enumeration {
                enum "controller";
                enum "conntrack";
            }
            default "controller";
        }
        leaf snat-punt-timeout {
            description "hard timeout value for learnt flows for snat punts in seconds.
                To turn off the rate limiting and installation of learnt flows, it should be set to 0,";
            type uint32;
            default 5;
        }
   }
}
