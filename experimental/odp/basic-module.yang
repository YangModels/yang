module basic-module {
  namespace "basic:module";  

  prefix "basmod";
  
  import referenced-module {prefix refmo; revision-date 2013-12-2;}
   
  revision 2013-12-2 {    
  }
  
	container cont {
	   container cont1 {
    		leaf lf11 {
    			type identityref {
    				base "refmo:iden";
    			}
    		}
		}
		leaf lfStr {
		  type string;
		}
		leaf lfInt8 {
		  type int8;
		}
		
		leaf lfInt16 {
		  type int16;
		}
		
		leaf lfInt32 {
		  type int32;
		}
		
		leaf lfInt64 {
		  type int64;
		}
		
		leaf lfUint8 {
		  type uint8;
		}
		
		leaf lfUint16 {
		  type uint16;
		}
		
		leaf lfUint32 {
		  type uint32;
		}
		
		leaf lfUint64 {
		  type uint64;
		}
		
		leaf lfBinary {
		  type binary;
		}
		
		leaf lfBits {
		  type bits {
		      bit one;
		      bit two;
		      bit three;
		  }
		}
		
		leaf lfEnumeration {
		  type enumeration {
		      enum enum1;
		      enum enum2;
		      enum enum3;
		  }
		}
		
		leaf lfEmpty {
		  type empty;
		}
		
		leaf lfBoolean {
		  type boolean;
		}
		
		leaf lfUnion {
		  type union {
		      type int8;
		      type string;
		      type bits {
		          bit first;
		          bit second;
		      }
		      type boolean;
		  }
		}
		
		leaf lfLfref {
		  type leafref {
		      path "/cont/lfBoolean";
		  }    
		}
		
		leaf lfInIdentifier {
		  type instance-identifier;
		}
		
	}
	  
}
