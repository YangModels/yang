module odl-bmp-monitor-config {
    yang-version 1;
    namespace "urn:opendaylight:params:xml:ns:yang:bmp-monitor-config";
    prefix bmp-monitor-config;

    import ietf-inet-types { prefix inet; revision-date 2013-07-15; }
    import rfc2385 { prefix rfc2385; revision-date 2016-03-24; }
    import bmp-monitor { prefix bmp-monitor; revision-date 2018-03-29; }

    description
        "This module contains the base YANG definitions for
         BMP Monitor Configuration.
         Copyright (c) 2017 Pantheon Technologies s.r.o. and others.  All rights reserved.

         This program and the accompanying materials are made available
         under the terms of the Eclipse Public License v1.0 which
         accompanies this distribution, and is available at
         http://www.eclipse.org/legal/epl-v10.html";

    revision "2018-03-29" {
        description "Add support for add-path for all afi/safi.";
    }

    revision "2017-12-07" {
        description "Add support for add-path in base BGP NLRI.";
    }

    revision "2017-05-17" {
        description
            "Initial revision.";
    }

    grouping server-config {
        container server {
            leaf binding-address {
                type inet:ip-address;
                default "0.0.0.0";
            }

            leaf binding-port {
                type inet:port-number;
                mandatory true;
            }
        }
    }

    container odl-bmp-monitors {
        list bmp-monitor-config {

            key "monitor-id";
            leaf monitor-id {
                type bmp-monitor:monitor-id;
            }

            uses server-config;

            list monitored-router {
                leaf address {
                    type inet:ip-address;
                    mandatory true;
                }

                key "address";

                leaf active {
                    type boolean;
                }

                leaf port {
                    when "../active = 'true'";
                    type inet:port-number;
                }

                leaf password {
                    type rfc2385:rfc2385-key;
                    description "RFC2385 shared secret";
                }
            }
        }
    }

}
