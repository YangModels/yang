module core {
    yang-version 1;
    namespace "urn:opendaylight:k8s:core";
    prefix "core";

    description
        "This YANG module defines the kubernetes api core API.";

    revision "2018-12-05" {
        description "Initial revision.";
    }

    organization "OpenDaylight COE Group";

    contact "COE Developers <coe-dev@lists.opendaylight.org>";

    typedef protocol {
        description
            "The protocol (TCP, UDP, or SCTP) which traffic must match.
             If not specified, this field defaults to TCP.";
        type enumeration {
            enum "TCP";
            enum "UDP";
            enum "SCTP";
        }
    }
}
