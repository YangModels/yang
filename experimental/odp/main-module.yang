module main-module {
  namespace "main:module";  

  prefix "mainmod";
  revision 2013-12-2 {    
  }
  
	container cont {
		leaf lf1 {
			type uint32;
		}
		
		container cont1 {
			leaf lf11 {
				type boolean;
			}
		}
		
		leaf lf2 {
			type leafref {
				path "../lf1";
			}
		}
		
		leaf lf3 {
			type leafref {
				path "/cont/cont1/lf11";
			}
		}
		
		/* reference to nonexisting leaf */
		leaf lf5 {
			type leafref {
				path "/cont/lf";
			}
		}
		
		
	}
	

	  
}
