module k8s-cluster {
    namespace "urn:opendaylight:coe:northbound:k8s-cluster";
    prefix "coe";

    revision 2018-11-27 {
        description "Initial revision";
    }

    import ietf-yang-types {
        prefix yang;
        revision-date "2013-07-15";
    }

    organization "OpenDaylight COE Group";

    contact "COE Developers <coe-dev@lists.opendaylight.org>";

    container k8s-clusters-info {
        description
            "Kubernetes Cluster information";

        list k8s-clusters {
            description "List of Kubernetes cluster.";

            key "cluster-id";

            leaf cluster-id {
                type yang:uuid;
                description "UUID representing the K8s cluster.";
            }
        }
    }
}
