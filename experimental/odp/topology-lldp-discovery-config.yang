module topology-lldp-discovery-config {
    yang-version 1;
    namespace "urn:opendaylight:params:xml:ns:yang:topology-lldp-discovery:config";
    prefix "topology-lldp-discovery-config";

    description
        "Configuration for Topology LLDP discovery application.";

    revision "2016-05-11" {
        description
            "Initial revision.";
    }

    typedef non-zero-uint32-type {
        type uint32 {
             range "1..max";
        }
    }

    container topology-lldp-discovery-config {
        leaf lldp-secure-key {
            description "Provided key will be used to generate LLDP custom security hash";
            type string;
            mandatory true;
        }

       leaf topology-lldp-interval {
            description "Periodic interval for sending LLDP packet for link discovery";
            type non-zero-uint32-type;
            default 5000;
        }

       leaf topology-lldp-expiration-interval {
            description "Timeout duration for LLDP response message";
            type non-zero-uint32-type;
            default 60000;
       }

    }
}
