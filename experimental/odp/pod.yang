module pod {
    yang-version 1;
    namespace "urn:opendaylight:coe:northbound:pod";
    prefix "coe";

    description
        "This YANG module defines the generic configuration data for Container Orchestration Engine.";

    revision "2017-06-11" {
        description "Initial revision.";
    }

    import ietf-inet-types {
        prefix inet;
        revision-date "2013-07-15";
    }

    import ietf-yang-types {
        prefix yang;
        revision-date "2013-07-15";
    }

    organization "OpenDaylight COE Group";

    contact "COE Developers <coe-dev@lists.opendaylight.org>";

    container coe {
        description
            "Container Configuration Parameters.";

        list pods {
            key "uid";

            description
                "List of all configured pods in the network.";

            uses pod_attributes;
        }
    }

    grouping pod_attributes {
        description "Kubernetes pod attributes needed by ODL Northbound.";

        leaf uid {
            type yang:uuid;
            description "UUID representing the pod.";
        }

        leaf name {
            type string;
            description "The pod name as reported by Kubernetes.";
        }

        leaf host-ip-address {
            type inet:ip-address;
            description "IP address of k8s node.";
        }

        leaf cluster-id {
            type yang:uuid;
            description "UUID representing the K8s cluster.";
        }

        leaf network-NS {
            type string;
            description "Network namespace defines the space for the pod. The empty namespace is
                equivalent to the default namespace.";
            status deprecated;
        }

        leaf port-mac-address {
            type string;
            description "MAC address of the associated port.";
        }

        list interface {
            key uid;

            leaf uid {
                type    yang:uuid;
                description "UUID representing the interface within a pod.";
            }

            leaf ip-address {
                type inet:ip-address;
                description "IP address assigned by IPAM module.";
            }

            uses network-attributes;
        }
    }

    grouping network-attributes {
        leaf network-id {
            type    yang:uuid;
            description "UUID representing the network.";
        }

        leaf network-type {
            type enumeration {
                enum "FLAT";
                enum "VLAN";
                enum "VXLAN";
                enum "GRE";
            }
        }
    }
}
