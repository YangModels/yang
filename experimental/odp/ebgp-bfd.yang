module bfd {

    yang-version "1";
    namespace "urn:ericsson:params:xml:ns:yang:ebfd";
    prefix "ericsson-bfd";
    organization
        "Ericsson Bangalore";
    contact
        "Ericsson Bangalore";
    description
        "BFD configuration model for monitoring DC-Gwy control path,
         Ericsson's implementation of Opendaylight inter-DC communication";
    revision "2019-02-19" {
    }

    container bfd-config {
        config        "true";

        leaf bfd-enabled {
            description  "is BFD enabled";
            type         boolean;
            default      false;
        }
        leaf detect-mult {
            type        uint32;
            default     3;
            description "The number of packets that have to be missed
                         in a row to declare the session to be down.";
        }
        leaf min-rx {
            type        uint32 {
    	        range "50..50000";
        	}
            default     500;
            description "The shortest interval, in milli-seconds, at
                         which this BFD session offers to receive
                         BFD control messages. Defaults to 500";
        }
        leaf min-tx {
            type        uint32 {
      	    	range "1000 .. 60000";
      	    }
            default     6000;
            description "The shortest interval, in milli-seconds,
                         at which this BFD session is willing to
                         transmit BFD control messages. Defaults
                         to 6000";
        }
        leaf multihop {
            type        boolean;
            default     true;
            description "Value of True indicates suppport for BFD multihop";
        }
    }
}
