module port-management {
    namespace "urn:opendaylight:port:config";
    prefix port-cfg;

    import opendaylight-inventory {prefix inv;revision-date "2013-08-19";}    
    import opendaylight-port-types {prefix port;}

    revision "2013-10-24" {
        description "Initial revision of port service";
    }

    grouping port-entry {
        leaf node {
            type inv:node-ref;
        }
        uses port:port-mod;
    }   
     
    container ports {
        list port {
            key "id node"; 
                        
            leaf id {
                type uint32;
            }                       
            
            uses port-entry;
        }
    }    
}
