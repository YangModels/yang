module module-with-choice {
  namespace "module:with:choice";  

  prefix "mowicho";
  
  revision 2013-12-18 {    
  }
  

  container cont {
    choice choA {
        case caA1 {
            leaf lf1 {
                type string;
            }
        }
        case caA2 {
            leaf lf2 {
                type string;
            }
        } 
    }
  }    
	  
}
