module instance-identifier-module {
  namespace "instance:identifier:module";  

  prefix "inidmod";
   
  revision 2013-12-3 {    
  }
  
	container cont {
		leaf lf1 {
			type instance-identifier {				
			}
		}
	}
	  
}
