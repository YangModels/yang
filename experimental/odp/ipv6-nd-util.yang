module ipv6-nd-util {
    yang-version 1;
    namespace "urn:opendaylight:genius:ipv6:nd:util";
    prefix "ipv6-nd-util";

    import ietf-interfaces {
        prefix if;
    }

    import ietf-inet-types {
        prefix inet; revision-date 2013-07-15;
    }

    import ietf-yang-types {
        prefix yang;
    }

    import yang-ext {
        prefix ext;
        revision-date "2013-07-09";
    }

    import ipv6-neighbor-discovery {
        prefix nd;
        revision-date "2016-06-20";
    }

    revision "2017-02-10" {
        description "IPv6 Neighbor Discovery Util module";
    }

    grouping interfaces {
        list interface-address {
           key interface;
           leaf interface {
                type leafref {
                    path "/if:interfaces/if:interface/if:name";
                }
           }
           leaf src-ip-address {
                type inet:ipv6-address;
           }
           leaf src-mac-address {
                type yang:phys-address;
            }
        }
    }

    grouping packet-metadata-info {
        leaf of-table-id {
            type uint32;
        }
        leaf metadata {
            type uint64;
        }
        leaf interface {
            type leafref {
                path "/if:interfaces/if:interface/if:name";
            }
        }
    }

    augment "/nd:neighbor-advertise-packet" {
        ext:augment-identifier "packet-metadata";
        uses packet-metadata-info;
    }

    rpc send-neighbor-solicitation {
        input {
            leaf target-ip-address {
                type inet:ipv6-address;
            }
            uses interfaces;
        }
    }

    rpc send-neighbor-solicitation-to-of-group {
        input {
            leaf source-ipv6 {
                type inet:ipv6-address;
                mandatory "true";
            }
            leaf target-ip-address {
                type inet:ipv6-address;
                mandatory "true";
            }
            leaf source-ll-address {
               type yang:mac-address;
               mandatory "true";
            }
            leaf dp-id {
               type uint64;
               mandatory "true";
            }
            leaf of-group-id {
               type uint32;
               mandatory "true";
               description "NS will be sent to the specified OpenFlow group ID.";
            }
        }
    }
}
