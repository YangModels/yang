module iana-if-type {
  namespace "urn:ietf:params:xml:ns:yang:iana-if-type";
  prefix ianaift;

  organization "IANA";
  contact
    "        Internet Assigned Numbers Authority

     Postal: ICANN
             4676 Admiralty Way, Suite 330
             Marina del Rey, CA 90292

     Tel:    +1 310 823 9358
     E-Mail: iana&iana.org";
  description
    "This YANG module defines the iana-if-type typedef, which
     contains YANG definitions for IANA-registered interface types.

     This YANG module is maintained by IANA, and reflects the
     'ifType definitions' registry.

     The latest revision of this YANG module can be obtained from
     the IANA web site.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";
  // RFC Ed.: replace XXXX with actual RFC number and remove this
  // note.

  // RFC Ed.: update the date below with the date of RFC publication
  // and remove this note.
  revision 2013-07-04 {
    description
      "Initial revision.";
    reference
      "RFC XXXX: IANA Interface Type YANG Module";
  }

  typedef iana-if-type {
    type enumeration {
      enum "other" {
        value 1;
        description
          "None of the following";
      }
      enum "regular1822" {
        value 2;
      }
      enum "hdh1822" {
        value 3;
      }
      enum "ddnX25" {
        value 4;
      }
      enum "rfc877x25" {
        value 5;
        reference
          "RFC 1382 - SNMP MIB Extension for the X.25 Packet Layer";
      }
      enum "ethernetCsmacd" {
        value 6;
        description
          "For all ethernet-like interfaces, regardless of speed,
           as per RFC3635.";
        reference
          "RFC 3635 - Definitions of Managed Objects for the
                      Ethernet-like Interface Types.";
      }
      enum "iso88023Csmacd" {
        value 7;
        status deprecated;
        description
          "Deprecated via RFC3635.
           Use ethernetCsmacd(6) instead.";
        reference
          "RFC 3635 - Definitions of Managed Objects for the
                      Ethernet-like Interface Types.";
      }
      enum "iso88024TokenBus" {
        value 8;
      }
      enum "iso88025TokenRing" {
        value 9;
      }
      enum "iso88026Man" {
        value 10;
      }
      enum "starLan" {
        value 11;
        status deprecated;
        description
          "Deprecated via RFC3635.
           Use ethernetCsmacd(6) instead.";
        reference
          "RFC 3635 - Definitions of Managed Objects for the
                      Ethernet-like Interface Types.";
      }
      enum "proteon10Mbit" {
        value 12;
      }
      enum "proteon80Mbit" {
        value 13;
      }
      enum "hyperchannel" {
        value 14;
      }
      enum "fddi" {
        value 15;
        reference
          "RFC 1512 - FDDI Management Information Base";
      }
      enum "lapb" {
        value 16;
        reference
          "RFC 1381 - SNMP MIB Extension for X.25 LAPB";
      }
      enum "sdlc" {
        value 17;
      }
      enum "ds1" {
        value 18;
        description
          "DS1-MIB";
        reference
          "RFC 4805 - Definitions of Managed Objects for the
                      DS1, J1, E1, DS2, and E2 Interface Types";
      }
      enum "e1" {
        value 19;
        status obsolete;
        description
          "Obsolete see DS1-MIB";
        reference
          "RFC 4805 - Definitions of Managed Objects for the
                      DS1, J1, E1, DS2, and E2 Interface Types";
      }
      enum "basicISDN" {
        value 20;
        description
          "see also RFC2127";
      }
      enum "primaryISDN" {
        value 21;
      }
      enum "propPointToPointSerial" {
        value 22;
        description
          "proprietary serial";
      }
      enum "ppp" {
        value 23;
      }
      enum "softwareLoopback" {
        value 24;
      }
      enum "eon" {
        value 25;
        description
          "CLNP over IP";
      }
      enum "ethernet3Mbit" {
        value 26;
      }
      enum "nsip" {
        value 27;
        description
          "XNS over IP";
      }
      enum "slip" {
        value 28;
        description
          "generic SLIP";
      }
      enum "ultra" {
        value 29;
        description
          "ULTRA technologies";
      }
      enum "ds3" {
        value 30;
        description
          "DS3-MIB";
        reference
          "RFC 3896 - Definitions of Managed Objects for the
                      DS3/E3 Interface Type";
      }
      enum "sip" {
        value 31;
        description
          "SMDS, coffee";
        reference
          "RFC 1694 - Definitions of Managed Objects for SMDS
                      Interfaces using SMIv2";
      }
      enum "frameRelay" {
        value 32;
        description
          "DTE only.";
        reference
          "RFC 2115 - Management Information Base for Frame Relay
                      DTEs Using SMIv2";
      }
      enum "rs232" {
        value 33;
        reference
          "RFC 1659 - Definitions of Managed Objects for RS-232-like
                      Hardware Devices using SMIv2";
      }
      enum "para" {
        value 34;
        description
          "parallel-port";
        reference
          "RFC 1660 - Definitions of Managed Objects for
                      Parallel-printer-like Hardware Devices using
                      SMIv2";
      }
      enum "arcnet" {
        value 35;
        description
          "arcnet";
      }
      enum "arcnetPlus" {
        value 36;
        description
          "arcnet plus";
      }
      enum "atm" {
        value 37;
        description
          "ATM cells";
      }
      enum "miox25" {
        value 38;
        reference
          "RFC 1461 - SNMP MIB extension for Multiprotocol
                      Interconnect over X.25";
      }
      enum "sonet" {
        value 39;
        description
          "SONET or SDH";
      }
      enum "x25ple" {
        value 40;
        reference
          "RFC 2127 - ISDN Management Information Base using SMIv2";
      }
      enum "iso88022llc" {
        value 41;
      }
      enum "localTalk" {
        value 42;
      }
      enum "smdsDxi" {
        value 43;
      }
      enum "frameRelayService" {
        value 44;
        description
          "FRNETSERV-MIB";
        reference
          "RFC 2954 - Definitions of Managed Objects for Frame
                      Relay Service";
      }
      enum "v35" {
        value 45;
      }
      enum "hssi" {
        value 46;
      }
      enum "hippi" {
        value 47;
      }
      enum "modem" {
        value 48;
        description
          "Generic modem";
      }
      enum "aal5" {
        value 49;
        description
          "AAL5 over ATM";
      }
      enum "sonetPath" {
        value 50;
      }
      enum "sonetVT" {
        value 51;
      }
      enum "smdsIcip" {
        value 52;
        description
          "SMDS InterCarrier Interface";
      }
      enum "propVirtual" {
        value 53;
        description
          "proprietary virtual/internal";
        reference
          "RFC 2863 - The Interfaces Group MIB";
      }
      enum "propMultiplexor" {
        value 54;
        description
          "proprietary multiplexing";
        reference
          "RFC 2863 - The Interfaces Group MIB";
      }
      enum "ieee80212" {
        value 55;
        description
          "100BaseVG";
      }
      enum "fibreChannel" {
        value 56;
        description
          "Fibre Channel";
      }
      enum "hippiInterface" {
        value 57;
        description
          "HIPPI interfaces";
      }
      enum "frameRelayInterconnect" {
        value 58;
        status obsolete;
        description
          "Obsolete use either
           frameRelay(32) or frameRelayService(44).";
      }
      enum "aflane8023" {
        value 59;
        description
          "ATM Emulated LAN for 802.3";
      }
      enum "aflane8025" {
        value 60;
        description
          "ATM Emulated LAN for 802.5";
      }
      enum "cctEmul" {
        value 61;
        description
         "ATM Emulated circuit";
      }
      enum "fastEther" {
        value 62;
        status deprecated;
        description
          "Obsoleted via RFC3635.
          ethernetCsmacd(6) should be used instead";
        reference
          "RFC 3635 - Definitions of Managed Objects for the
                      Ethernet-like Interface Types.";
      }
      enum "isdn" {
        value 63;
        description
          "ISDN and X.25";
        reference
          "RFC 1356 - Multiprotocol Interconnect on X.25 and ISDN
                      in the Packet Mode";
      }
      enum "v11" {
        value 64;
        description
         "CCITT V.11/X.21";
      }
      enum "v36" {
        value 65;
        description
          "CCITT V.36";
      }
      enum "g703at64k" {
        value 66;
        description
          "CCITT G703 at 64Kbps";
      }
      enum "g703at2mb" {
        value 67;
        status obsolete;
        description
          "Obsolete see DS1-MIB";
      }
      enum "qllc" {
        value 68;
        description
          "SNA QLLC";
      }
      enum "fastEtherFX" {
        value 69;
        status deprecated;
        description
          "Obsoleted via RFC3635
          ethernetCsmacd(6) should be used instead";
        reference
          "RFC 3635 - Definitions of Managed Objects for the
                      Ethernet-like Interface Types.";
      }
      enum "channel" {
        value 70;
        description
          "channel";
      }
      enum "ieee80211" {
        value 71;
        description
          "radio spread spectrum";
      }
      enum "ibm370parChan" {
        value 72;
        description
          "IBM System 360/370 OEMI Channel";
      }
      enum "escon" {
        value 73;
        description
          "IBM Enterprise Systems Connection";
      }
      enum "dlsw" {
        value 74;
        description
          "Data Link Switching";
      }
      enum "isdns" {
        value 75;
        description
          "ISDN S/T interface";
      }
      enum "isdnu" {
        value 76;
        description
          "ISDN U interface";
      }
      enum "lapd" {
        value 77;
        description
          "Link Access Protocol D";
      }
      enum "ipSwitch" {
        value 78;
        description
          "IP Switching Objects";
      }
      enum "rsrb" {
        value 79;
        description
          "Remote Source Route Bridging";
      }
      enum "atmLogical" {
        value 80;
        description
          "ATM Logical Port";
        reference
          "RFC 3606 - Definitions of Supplemental Managed Objects
                      for ATM Interface";
      }
      enum "ds0" {
        value 81;
        description
          "Digital Signal Level 0";
        reference
          "RFC 2494 - Definitions of Managed Objects for the DS0
                      and DS0 Bundle Interface Type";
      }
      enum "ds0Bundle" {
        value 82;
        description
          "group of ds0s on the same ds1";
        reference
          "RFC 2494 - Definitions of Managed Objects for the DS0
                      and DS0 Bundle Interface Type";
      }
      enum "bsc" {
        value 83;
        description
          "Bisynchronous Protocol";
      }
      enum "async" {
        value 84;
        description
          "Asynchronous Protocol";
      }
      enum "cnr" {
        value 85;
        description
          "Combat Net Radio";
      }
      enum "iso88025Dtr" {
        value 86;
        description
          "ISO 802.5r DTR";
      }
      enum "eplrs" {
        value 87;
        description
          "Ext Pos Loc Report Sys";
      }
      enum "arap" {
        value 88;
        description
          "Appletalk Remote Access Protocol";
      }
      enum "propCnls" {
        value 89;
        description
          "Proprietary Connectionless Protocol";
      }
      enum "hostPad" {
        value 90;
        description
          "CCITT-ITU X.29 PAD Protocol";
      }
      enum "termPad" {
        value 91;
        description
          "CCITT-ITU X.3 PAD Facility";
      }
      enum "frameRelayMPI" {
        value 92;
        description
          "Multiproto Interconnect over FR";
      }
      enum "x213" {
        value 93;
        description
          "CCITT-ITU X213";
      }
      enum "adsl" {
        value 94;
        description
          "Asymmetric Digital Subscriber Loop";
      }
      enum "radsl" {
        value 95;
        description
          "Rate-Adapt. Digital Subscriber Loop";
      }
      enum "sdsl" {
        value 96;
        description
          "Symmetric Digital Subscriber Loop";
      }
      enum "vdsl" {
        value 97;
        description
          "Very H-Speed Digital Subscrib. Loop";
      }
      enum "iso88025CRFPInt" {
        value 98;
        description
          "ISO 802.5 CRFP";
      }
      enum "myrinet" {
        value 99;
        description
          "Myricom Myrinet";
      }
      enum "voiceEM" {
        value 100;
        description
          "voice recEive and transMit";
      }
      enum "voiceFXO" {
        value 101;
        description
          "voice Foreign Exchange Office";
      }
      enum "voiceFXS" {
        value 102;
        description
          "voice Foreign Exchange Station";
      }
      enum "voiceEncap" {
        value 103;
        description
          "voice encapsulation";
      }
      enum "voiceOverIp" {
        value 104;
        description
          "voice over IP encapsulation";
      }
      enum "atmDxi" {
        value 105;
        description
          "ATM DXI";
      }
      enum "atmFuni" {
        value 106;
        description
          "ATM FUNI";
      }
      enum "atmIma" {
        value 107;
        description
          "ATM IMA";
      }
      enum "pppMultilinkBundle" {
        value 108;
        description
          "PPP Multilink Bundle";
      }
      enum "ipOverCdlc" {
        value 109;
        description
          "IBM ipOverCdlc";
      }
      enum "ipOverClaw" {
        value 110;
        description
          "IBM Common Link Access to Workstn";
      }
      enum "stackToStack" {
        value 111;
        description
          "IBM stackToStack";
      }
      enum "virtualIpAddress" {
        value 112;
        description
          "IBM VIPA";
      }
      enum "mpc" {
        value 113;
        description
          "IBM multi-protocol channel support";
      }
      enum "ipOverAtm" {
        value 114;
        description
          "IBM ipOverAtm";
        reference
          "RFC 2320 - Definitions of Managed Objects for Classical IP
                      and ARP Over ATM Using SMIv2 (IPOA-MIB)";
      }
      enum "iso88025Fiber" {
        value 115;
        description
          "ISO 802.5j Fiber Token Ring";
      }
      enum "tdlc" {
        value 116;
        description
          "IBM twinaxial data link control";
      }
      enum "gigabitEthernet" {
        value 117;
        status deprecated;
        description
          "Obsoleted via RFC3635
           ethernetCsmacd(6) should be used instead";
        reference
          "RFC 3635 - Definitions of Managed Objects for the
                      Ethernet-like Interface Types.";
      }
      enum "hdlc" {
        value 118;
        description
          "HDLC";
      }
      enum "lapf" {
        value 119;
        description
          "LAP F";
      }
      enum "v37" {
        value 120;
        description
          "V.37";
      }
      enum "x25mlp" {
        value 121;
        description
          "Multi-Link Protocol";
      }
      enum "x25huntGroup" {
        value 122;
        description
          "X25 Hunt Group";
      }
      enum "transpHdlc" {
        value 123;
        description
          "Transp HDLC";
      }
      enum "interleave" {
        value 124;
        description
          "Interleave channel";
      }
      enum "fast" {
        value 125;
        description
          "Fast channel";
      }
      enum "ip" {
        value 126;
        description
          "IP (for APPN HPR in IP networks)";
      }
      enum "docsCableMaclayer" {
        value 127;
        description
          "CATV Mac Layer";
      }
      enum "docsCableDownstream" {
        value 128;
        description
          "CATV Downstream interface";
      }
      enum "docsCableUpstream" {
        value 129;
        description
          "CATV Upstream interface";
      }
      enum "a12MppSwitch" {
        value 130;
        description
          "Avalon Parallel Processor";
      }
      enum "tunnel" {
        value 131;
        description
          "Encapsulation interface";
      }
      enum "coffee" {
        value 132;
        description
          "coffee pot";
        reference
          "RFC 2325 - Coffee MIB";
      }
      enum "ces" {
        value 133;
        description
          "Circuit Emulation Service";
      }
      enum "atmSubInterface" {
        value 134;
        description
          "ATM Sub Interface";
      }
      enum "l2vlan" {
        value 135;
        description
          "Layer 2 Virtual LAN using 802.1Q";
      }
      enum "l3ipvlan" {
        value 136;
        description
          "Layer 3 Virtual LAN using IP";
      }
      enum "l3ipxvlan" {
        value 137;
        description
          "Layer 3 Virtual LAN using IPX";
      }
      enum "digitalPowerline" {
        value 138;
        description
          "IP over Power Lines";
      }
      enum "mediaMailOverIp" {
        value 139;
        description
          "Multimedia Mail over IP";
      }
      enum "dtm" {
        value 140;
        description
          "Dynamic syncronous Transfer Mode";
      }
      enum "dcn" {
        value 141;
        description
          "Data Communications Network";
      }
      enum "ipForward" {
        value 142;
        description
          "IP Forwarding Interface";
      }
      enum "msdsl" {
        value 143;
        description
          "Multi-rate Symmetric DSL";
      }
      enum "ieee1394" {
        value 144;
        description
          "IEEE1394 High Performance Serial Bus";
      }
      enum "if-gsn" {
        value 145;
        description
          "HIPPI-6400";
      }
      enum "dvbRccMacLayer" {
        value 146;
        description
          "DVB-RCC MAC Layer";
      }
      enum "dvbRccDownstream" {
        value 147;
        description
          "DVB-RCC Downstream Channel";
      }
      enum "dvbRccUpstream" {
        value 148;
        description
          "DVB-RCC Upstream Channel";
      }
      enum "atmVirtual" {
        value 149;
        description
          "ATM Virtual Interface";
      }
      enum "mplsTunnel" {
        value 150;
        description
          "MPLS Tunnel Virtual Interface";
      }
      enum "srp" {
        value 151;
        description
          "Spatial Reuse Protocol";
      }
      enum "voiceOverAtm" {
        value 152;
        description
          "Voice Over ATM";
      }
      enum "voiceOverFrameRelay" {
        value 153;
        description
          "Voice Over Frame Relay";
      }
      enum "idsl" {
        value 154;
        description
          "Digital Subscriber Loop over ISDN";
      }
      enum "compositeLink" {
        value 155;
        description
          "Avici Composite Link Interface";
      }
      enum "ss7SigLink" {
        value 156;
        description
          "SS7 Signaling Link";
      }
      enum "propWirelessP2P" {
        value 157;
        description
          "Prop. P2P wireless interface";
      }
      enum "frForward" {
        value 158;
        description
          "Frame Forward Interface";
      }
      enum "rfc1483" {
        value 159;
        description
          "Multiprotocol over ATM AAL5";
        reference
          "RFC 1483 - Multiprotocol Encapsulation over ATM
                      Adaptation Layer 5";
      }
      enum "usb" {
        value 160;
        description
          "USB Interface";
      }
      enum "ieee8023adLag" {
        value 161;
        description
          "IEEE 802.3ad Link Aggregate";
      }
      enum "bgppolicyaccounting" {
        value 162;
        description
          "BGP Policy Accounting";
      }
      enum "frf16MfrBundle" {
        value 163;
        description
          "FRF .16 Multilink Frame Relay";
      }
      enum "h323Gatekeeper" {
        value 164;
        description
          "H323 Gatekeeper";
      }
      enum "h323Proxy" {
        value 165;
        description
          "H323 Voice and Video Proxy";
      }
      enum "mpls" {
        value 166;
        description
          "MPLS";
      }
      enum "mfSigLink" {
        value 167;
        description
          "Multi-frequency signaling link";
      }
      enum "hdsl2" {
        value 168;
        description
          "High Bit-Rate DSL - 2nd generation";
      }
      enum "shdsl" {
        value 169;
        description
          "Multirate HDSL2";
      }
      enum "ds1FDL" {
        value 170;
        description
          "Facility Data Link 4Kbps on a DS1";
      }
      enum "pos" {
        value 171;
        description
          "Packet over SONET/SDH Interface";
      }
      enum "dvbAsiIn" {
        value 172;
        description
          "DVB-ASI Input";
      }
      enum "dvbAsiOut" {
        value 173;
        description
          "DVB-ASI Output";
      }
      enum "plc" {
        value 174;
        description
          "Power Line Communtications";
      }
      enum "nfas" {
        value 175;
        description
          "Non Facility Associated Signaling";
      }
      enum "tr008" {
        value 176;
        description
          "TR008";
      }
      enum "gr303RDT" {
        value 177;
        description
          "Remote Digital Terminal";
      }
      enum "gr303IDT" {
        value 178;
        description
          "Integrated Digital Terminal";
      }
      enum "isup" {
        value 179;
        description
          "ISUP";
      }
      enum "propDocsWirelessMaclayer" {
        value 180;
        description
          "Cisco proprietary Maclayer";
      }
      enum "propDocsWirelessDownstream" {
        value 181;
        description
          "Cisco proprietary Downstream";
      }
      enum "propDocsWirelessUpstream" {
        value 182;
        description
          "Cisco proprietary Upstream";
      }
      enum "hiperlan2" {
        value 183;
        description
          "HIPERLAN Type 2 Radio Interface";
      }
      enum "propBWAp2Mp" {
        value 184;
        description
          "PropBroadbandWirelessAccesspt2multipt use of this value
           for IEEE 802.16 WMAN interfaces as per IEEE Std 802.16f
           is deprecated and ieee80216WMAN(237) should be used
           instead.";
      }
      enum "sonetOverheadChannel" {
        value 185;
        description
          "SONET Overhead Channel";
      }
      enum "digitalWrapperOverheadChannel" {
        value 186;
        description
          "Digital Wrapper";
      }
      enum "aal2" {
        value 187;
        description
          "ATM adaptation layer 2";
      }
      enum "radioMAC" {
        value 188;
        description
          "MAC layer over radio links";
      }
      enum "atmRadio" {
        value 189;
        description
          "ATM over radio links";
      }
      enum "imt" {
        value 190;
        description
          "Inter Machine Trunks";
      }
      enum "mvl" {
        value 191;
        description
          "Multiple Virtual Lines DSL";
      }
      enum "reachDSL" {
        value 192;
        description
          "Long Reach DSL";
      }
      enum "frDlciEndPt" {
        value 193;
        description
          "Frame Relay DLCI End Point";
      }
      enum "atmVciEndPt" {
        value 194;
        description
          "ATM VCI End Point";
      }
      enum "opticalChannel" {
        value 195;
        description
          "Optical Channel";
      }
      enum "opticalTransport" {
        value 196;
        description
          "Optical Transport";
      }
      enum "propAtm" {
        value 197;
        description
          "Proprietary ATM";
      }
      enum "voiceOverCable" {
        value 198;
        description
          "Voice Over Cable Interface";
      }
      enum "infiniband" {
        value 199;
        description
          "Infiniband";
      }
      enum "teLink" {
        value 200;
        description
          "TE Link";
      }
      enum "q2931" {
        value 201;
        description
          "Q.2931";
      }
      enum "virtualTg" {
        value 202;
        description
          "Virtual Trunk Group";
      }
      enum "sipTg" {
        value 203;
        description
          "SIP Trunk Group";
      }
      enum "sipSig" {
        value 204;
        description
          "SIP Signaling";
      }
      enum "docsCableUpstreamChannel" {
        value 205;
        description
          "CATV Upstream Channel";
      }
      enum "econet" {
        value 206;
        description
          "Acorn Econet";
      }
      enum "pon155" {
        value 207;
        description
          "FSAN 155Mb Symetrical PON interface";
      }
      enum "pon622" {
        value 208;
        description
          "FSAN622Mb Symetrical PON interface";
      }
      enum "bridge" {
        value 209;
        description
          "Transparent bridge interface";
      }
      enum "linegroup" {
        value 210;
        description
          "Interface common to multiple lines";
      }
      enum "voiceEMFGD" {
        value 211;
        description
          "voice E&M Feature Group D";
      }
      enum "voiceFGDEANA" {
        value 212;
        description
          "voice FGD Exchange Access North American";
      }
      enum "voiceDID" {
        value 213;
        description
          "voice Direct Inward Dialing";
      }
      enum "mpegTransport" {
        value 214;
        description
          "MPEG transport interface";
      }
      enum "sixToFour" {
        value 215;
        status deprecated;
        description
          "6to4 interface (DEPRECATED)";
        reference
          "RFC 4087 - IP Tunnel MIB";
      }
      enum "gtp" {
        value 216;
        description
          "GTP (GPRS Tunneling Protocol)";
      }
      enum "pdnEtherLoop1" {
        value 217;
        description
          "Paradyne EtherLoop 1";
      }
      enum "pdnEtherLoop2" {
        value 218;
        description
          "Paradyne EtherLoop 2";
      }
      enum "opticalChannelGroup" {
        value 219;
        description
          "Optical Channel Group";
      }
      enum "homepna" {
        value 220;
        description
          "HomePNA ITU-T G.989";
      }
      enum "gfp" {
        value 221;
        description
          "Generic Framing Procedure (GFP)";
      }
      enum "ciscoISLvlan" {
        value 222;
        description
          "Layer 2 Virtual LAN using Cisco ISL";
      }
      enum "actelisMetaLOOP" {
        value 223;
        description
          "Acteleis proprietary MetaLOOP High Speed Link";
      }
      enum "fcipLink" {
        value 224;
        description
          "FCIP Link";
      }
      enum "rpr" {
        value 225;
        description
          "Resilient Packet Ring Interface Type";
      }
      enum "qam" {
        value 226;
        description
          "RF Qam Interface";
      }
      enum "lmp" {
        value 227;
        description
          "Link Management Protocol";
        reference
          "RFC 4327 - Link Management Protocol (LMP) Management
                      Information Base (MIB)";
      }
      enum "cblVectaStar" {
        value 228;
        description
          "Cambridge Broadband Networks Limited VectaStar";
      }
      enum "docsCableMCmtsDownstream" {
        value 229;
        description
          "CATV Modular CMTS Downstream Interface";
      }
      enum "adsl2" {
        value 230;
        status deprecated;
        description
          "Asymmetric Digital Subscriber Loop Version 2
           (DEPRECATED/OBSOLETED - please use adsl2plus(238)
           instead)";
        reference
          "RFC 4706 - Definitions of Managed Objects for Asymmetric
                      Digital Subscriber Line 2 (ADSL2)";
      }
      enum "macSecControlledIF" {
        value 231;
        description
          "MACSecControlled";
      }
      enum "macSecUncontrolledIF" {
        value 232;
        description
          "MACSecUncontrolled";
      }
      enum "aviciOpticalEther" {
        value 233;
        description
         "Avici Optical Ethernet Aggregate";
      }
      enum "atmbond" {
        value 234;
        description
          "atmbond";
      }
      enum "voiceFGDOS" {
        value 235;
        description
          "voice FGD Operator Services";
      }
      enum "mocaVersion1" {
        value 236;
        description
          "MultiMedia over Coax Alliance (MoCA) Interface
           as documented in information provided privately to IANA";
      }
      enum "ieee80216WMAN" {
        value 237;
        description
          "IEEE 802.16 WMAN interface";
      }
      enum "adsl2plus" {
        value 238;
        description
          "Asymmetric Digital Subscriber Loop Version 2,
           Version 2 Plus and all variants";
      }
      enum "dvbRcsMacLayer" {
        value 239;
        description
          "DVB-RCS MAC Layer";
        reference
          "RFC 5728 - The SatLabs Group DVB-RCS MIB";
      }
      enum "dvbTdm" {
        value 240;
        description
          "DVB Satellite TDM";
        reference
          "RFC 5728 - The SatLabs Group DVB-RCS MIB";
      }
      enum "dvbRcsTdma" {
        value 241;
        description
          "DVB-RCS TDMA";
        reference
          "RFC 5728 - The SatLabs Group DVB-RCS MIB";
      }
      enum "x86Laps" {
        value 242;
        description
          "LAPS based on ITU-T X.86/Y.1323";
      }
      enum "wwanPP" {
        value 243;
        description
          "3GPP WWAN";
      }
      enum "wwanPP2" {
        value 244;
        description
          "3GPP2 WWAN";
      }
      enum "voiceEBS" {
        value 245;
        description
          "voice P-phone EBS physical interface";
      }
      enum "ifPwType" {
        value 246;
        description
          "Pseudowire interface type";
        reference
          "RFC 5601 - Pseudowire (PW) Management Information Base";
      }
      enum "ilan" {
        value 247;
        description
          "Internal LAN on a bridge per IEEE 802.1ap";
      }
      enum "pip" {
        value 248;
        description
          "Provider Instance Port on a bridge per IEEE 802.1ah PBB";
      }
      enum "aluELP" {
        value 249;
        description
          "Alcatel-Lucent Ethernet Link Protection";
      }
      enum "gpon" {
        value 250;
        description
          "Gigabit-capable passive optical networks (G-PON) as per
           ITU-T G.948";
      }
      enum "vdsl2" {
        value 251;
        description
          "Very high speed digital subscriber line Version 2
           (as per ITU-T Recommendation G.993.2)";
        reference
          "RFC 5650 - Definitions of Managed Objects for Very High
                      Speed Digital Subscriber Line 2 (VDSL2)";
      }
      enum "capwapDot11Profile" {
        value 252;
        description
          "WLAN Profile Interface";
        reference
          "RFC 5834 - Control and Provisioning of Wireless Access
                      Points (CAPWAP) Protocol Binding MIB for
                      IEEE 802.11";
      }
      enum "capwapDot11Bss" {
        value 253;
        description
          "WLAN BSS Interface";
        reference
          "RFC 5834 - Control and Provisioning of Wireless Access
                      Points (CAPWAP) Protocol Binding MIB for
                      IEEE 802.11";
      }
      enum "capwapWtpVirtualRadio" {
        value 254;
        description
          "WTP Virtual Radio Interface";
        reference
          "RFC 5833 - Control and Provisioning of Wireless Access
                      Points (CAPWAP) Protocol Base MIB";
      }
      enum "bits" {
        value 255;
        description
          "bitsport";
      }
      enum "docsCableUpstreamRfPort" {
        value 256;
        description
          "DOCSIS CATV Upstream RF Port";
      }
      enum "cableDownstreamRfPort" {
        value 257;
        description
          "CATV downstream RF port";
      }
      enum "vmwareVirtualNic" {
        value 258;
        description
          "VMware Virtual Network Interface";
      }
      enum "ieee802154" {
        value 259;
        description
          "IEEE 802.15.4 WPAN interface";
        reference
          "IEEE 802.15.4-2006";
      }
      enum "otnOdu" {
        value 260;
        description
          "OTN Optical Data Unit";
      }
      enum "otnOtu" {
        value 261;
        description
          "OTN Optical channel Transport Unit";
      }
      enum "ifVfiType" {
        value 262;
        description
          "VPLS Forwarding Instance Interface Type";
      }
      enum "g9981" {
        value 263;
        description
          "G.998.1 bonded interface";
      }
      enum "g9982" {
        value 264;
        description
          "G.998.2 bonded interface";
      }
      enum "g9983" {
        value 265;
        description
          "G.998.3 bonded interface";
      }
      enum "aluEpon" {
        value 266;
        description
          "Ethernet Passive Optical Networks (E-PON)";
      }
      enum "aluEponOnu" {
        value 267;
        description
          "EPON Optical Network Unit";
      }
      enum "aluEponPhysicalUni" {
        value 268;
        description
          "EPON physical User to Network interface";
      }
      enum "aluEponLogicalLink" {
        value 269;
        description
          "The emulation of a point-to-point link over the EPON
           layer";
      }
      enum "aluGponOnu" {
        value 270;
        description
          "GPON Optical Network Unit";
        reference
          "ITU-T G.984.2";
      }
      enum "aluGponPhysicalUni" {
        value 271;
        description
          "GPON physical User to Network interface";
        reference
          "ITU-T G.984.2";
      }
      enum "vmwareNicTeam" {
        value 272;
        description
          "VMware NIC Team";
      }
      // value 273 reserved by IANA
    }
    description
      "This data type is used as the syntax of the 'type'
       leaf in the 'interface' list in the YANG module
       ietf-interface.

       The definition of this typedef with the
       addition of newly assigned values is published
       periodically by the IANA, in either the Assigned
       Numbers RFC, or some derivative of it specific to
       Internet Network Management number assignments.  (The
       latest arrangements can be obtained by contacting the
       IANA.)

       Requests for new values should be made to IANA via
       email (iana&iana.org).";
    reference
      "IANA ifType definitions registry.
       <http://www.iana.org/assignments/smi-numbers>";
  }
}
