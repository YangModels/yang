module statistics-manager-control {
	yang-version 1;
    namespace "urn:opendaylight:params:xml:ns:yang:openflowplugin:sm:control";
    prefix "sm-control";

    description
        "Statistics manager control API";

    revision "2015-08-12" {
        description
            "Initial proposal.";
    }


    typedef statistics-work-mode {
        description "Statistics manager work modes.";
        type enumeration {
            enum COLLECT_ALL {
                description "Default mode - all available statistics are being polled and processed";
            }
            enum FULLY_DISABLED {
                description "No statistics are being polled at all";
            }
        }
    }

    rpc change-statistics-work-mode {
        description "Set statistics manager work mode";
        input {
            leaf mode {
                type statistics-work-mode;
            }
        }
    }

    rpc get-statistics-work-mode {
        description "Get statistics manager work mode";
        output {
            leaf mode {
                type statistics-work-mode;
            }
        }
    }
}
