// vi: set smarttab et sw=4 tabstop=4:
module toaster-provider {

    yang-version 1;
    namespace "urn:opendaylight:params:xml:ns:yang:controller:config:toaster-provider";
    prefix "toaster-provider";

    import config { prefix config; revision-date 2013-04-05; }

    description
        "This module contains the base YANG definitions for
        toaster-provider services.";

    revision "2014-01-31" {
        description
            "Initial revision.";
    }

    // This is the definition of a service
    identity toaster-provider {

        base "config:service-type";

        config:java-class "org.opendaylight.yang.gen.v1.http.netconfcentral.org.ns.toaster.rev091120.ToasterData";
    }
}
