module augment-main-a {
  namespace "ns:augment:main:a";  
  prefix "aumaa";

  
  import main {prefix mn; revision-date 2014-01-21;}   


  revision "2014-01-21" {    
  }
  
  augment "/mn:cont" {
    container cont1 {
        leaf lf11 {
            type string;
        }
    }
  }
  
}
