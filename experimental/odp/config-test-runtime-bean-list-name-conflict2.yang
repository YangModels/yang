// vi: set smarttab et sw=4 tabstop=4:
module config-test-runtime-bean-list-name-conflict2 {
     yang-version 1;
        namespace "urn:opendaylight:params:xml:ns:yang:controller:jmx:duplicate:runtime:bean";
        prefix "th-java";

        import config { prefix config; revision-date 2013-04-05; }
        import ietf-inet-types { prefix inet; revision-date 2010-09-24;}

        description
            "This module contains the base YANG definitions of
             thread services pure Java implementation.";

        revision "2013-04-05" {
            description
                "Updated to work with new anchors.";
        }

        revision "2013-04-03" {
            description
                "Initial revision";
        }

       identity async-eventbus {
            base config:module-type;
            config:java-name-prefix AsyncEventBus;
        }

        augment "/config:modules/config:module/config:configuration" {
            case async-eventbus {
                when "/config:modules/config:module/config:type = 'async-eventbus'";
                    leaf port {
                        type string;
                    }

                    list state-a-runtime-mX-bean {
                       leaf port {
                           type string;
                       }
                    }
                }
            }

        augment "/config:modules/config:module/config:state" {
            case async-eventbus {
                when "/config:modules/config:module/config:type = 'async-eventbus'";

                list state-a {
                   config:inner-state-bean;

                   leaf port {
                       type string;
                   }
                }
            }
        }
}
