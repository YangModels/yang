module bgp-linkstate-app-config {
    yang-version 1;
    namespace "urn:opendaylight:params:xml:ns:yang:controller:bgp:linkstate-app-config";
    prefix "bgp-linkstate-app-config";

    description
      "Configuration for the BGP linkstate application.";

    revision "2016-06-14" {
        description
            "Initial revision.

            Copyright (c)2016 Brocade Communications Systems, Inc. and others.  All rights reserved.

            This program and the accompanying materials are made available
            under the terms of the Eclipse Public License v1.0 which
            accompanies this distribution, and is available at
            http://www.eclipse.org/legal/epl-v10.html";
    }

    container bgp-linkstate-app-config {
        leaf iana-linkstate-attribute-type {
            description "If true (default) linkstate attribute type (=29) allocated by IANA is used,
                         else type (=99) is used for parsing/serialization";
            type boolean;
            default true;
        }
    }
}
