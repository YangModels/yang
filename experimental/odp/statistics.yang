module statistics {
    yang-version 1;
    namespace "urn:opendaylight:netvirt:statistics";
    prefix "statistics";

    revision "2017-01-20" {
        description "Initial revision of statistics model";
    }

    grouping result {
        list counterResult {
            key id;
            leaf id {
                type string;
            }
            list groups {
                key name;
                leaf name {
                    type string;
                }
                list counters {
                    key name;
                    leaf name {
                        type string;
                    }
                    leaf value {
                        type uint64;
                    }
                }
            }
        }
    }

    grouping filters {
        leaf-list groupFilters {
            type string;
        }
        leaf-list counterFilter {
            type string;
        }
    }

    grouping elementRequestData {
        container filters {

            container tcpFilter {
                leaf on {
                    type boolean;
                }
                leaf srcPort {
                    type int32;
                    default -1;
                }
                leaf dstPort {
                    type int32;
                    default -1;
                }
            }

            container udpFilter {
                leaf on {
                    type boolean;
                }
                leaf dstPort {
                    type int32;
                    default -1;
                }
                leaf srcPort {
                    type int32;
                    default -1;
                }
            }

            container ipFilter {
                leaf ip {
                    type string;
                    default "";
                }
            }
        }
    }

    grouping counterRequestsConfig {
        list counterRequests {
            key "requestId";
            leaf requestId {
                type string;
            }
            leaf portId {
                type string;
            }
            leaf lportTag {
                type int32;
            }
            leaf dpn {
                type uint64;
            }
            leaf trafficDirection {
                type string;
            }
            leaf generatedUniqueId {
                type string;
            }
            uses elementRequestData;
        }
    }

    container ingressElementCountersRequestConfig {
        uses counterRequestsConfig;
    }

    container egressElementCountersRequestConfig {
        uses counterRequestsConfig;
    }

    rpc getNodeConnectorCounters {
        input {
            leaf portId {
                type string;
            }
            uses filters;
        }
        output {
            uses result;
        }
    }

    rpc getNodeCounters {
        input {
            leaf nodeId {
                type uint64;
            }
        }
        output {
            uses result;
        }
    }

    rpc getNodeAggregatedCounters {
        input {
            leaf nodeId {
                type uint64;
            }
            uses filters;
        }
        output {
            uses result;
        }
    }

    rpc acquireElementCountersRequestHandler {
        input {
            leaf portId {
                type string;
            }
            container incomingTraffic {
                uses elementRequestData;
            }
            container outgoingTraffic {
                uses elementRequestData;
            }
            uses filters;
        }
        output {
            leaf incomingTrafficHandler {
                type string;
            }
            leaf outcoingTrafficHandler {
                type string;
            }
        }
    }

    rpc releaseElementCountersRequestHandler {
        input {
            leaf handler {
                type string;
            }
        }
        output {
        }
    }

    rpc getElementCountersByHandler {
        input {
            leaf handler {
                type string;
            }
        }
        output {
            uses result;
        }
    }

    rpc cleanAllElementCounterRequests {
        input {
            leaf portId {
                type string;
                default "";
            }
        }
        output {
        }
    }
}
