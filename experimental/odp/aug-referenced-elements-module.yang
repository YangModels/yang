module aug-referenced-elements-module {
  namespace "aug:referenced:elements:module";  

  prefix "augrefelmo";
  
  import referenced-elements-module {prefix refelmo; revision-date 2013-12-3;}
   
  revision 2013-12-3 {    
  }
  
  augment "/refelmo:cont" {
    leaf lf2 {
        type boolean;
    }
  }
  
	  
}
