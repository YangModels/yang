module topology-tunnel-p2p {
    yang-version 1;
    namespace "urn:opendaylight:params:xml:ns:yang:topology:tunnel:p2p";
    prefix "p2p";

    import network-topology { prefix nt; revision-date 2013-10-21; }
    import topology-tunnel { prefix tt; revision-date 2013-08-19; }

    organization "Cisco Systems, Inc.";
    contact "Robert Varga <rovarga@cisco.com>";

    description
        "This module contains the point-to-point extensions to the
        base tunnel topology model.

        Copyright (c)2013 Cisco Systems, Inc. All rights reserved.

        This program and the accompanying materials are made available
        under the terms of the Eclipse Public License v1.0 which
        accompanies this distribution, and is available at
        http://www.eclipse.org/legal/epl-v10.html";

    revision "2013-08-19" {
        description
            "Initial revision.";
        reference "";
    }

    grouping tunnel-p2p-type {
        container p2p-tunnel {
            presence "indicates a link is a point-to-point tunnel";
        }
    }

    augment "/nt:network-topology/nt:topology/nt:link/tt:tunnel-types" {
        uses tunnel-p2p-type;
    }

    grouping tunnel-p2p-path-hops {
        leaf order {
            type uint32;
            mandatory true;
        }
    }

    grouping tunnel-p2p-path-cfg-attributes {
        list explicit-hops {
            uses tunnel-p2p-path-hops;
            key order;

            leaf loose {
                type boolean;
                mandatory true;
            }
        }
    }

    grouping tunnel-p2p-path-oper-attributes {
        list reported-hops {
            config false;
            uses tunnel-p2p-path-hops;
            key order;
        }
    }

    augment "/nt:network-topology/nt:topology/tt:paths" {
        when "../path-types/p2p-tunnel";
        uses tunnel-p2p-path-cfg-attributes;
        uses tunnel-p2p-path-oper-attributes;
    }
}
