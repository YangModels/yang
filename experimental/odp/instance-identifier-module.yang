module instance-identifier-module {
  namespace "instance:identifier:module";  

  prefix "iimodule";
  revision 2014-01-17 {    
  }

    container cont {
        container cont1 {
        }
    }
  
}
