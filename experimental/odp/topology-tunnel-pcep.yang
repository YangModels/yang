module topology-tunnel-pcep {
    // vi: set et smarttab sw=4 tabstop=4:
    yang-version 1;
    namespace "urn:opendaylight:params:xml:ns:yang:topology:tunnel:pcep";
    prefix "pceptun";

    import network-topology { prefix nt; revision-date 2013-10-21; }
    import network-concepts { prefix netc; revision-date 2013-11-25; }
    import pcep-types { prefix pcep; revision-date 2018-11-09; }
    import rsvp { prefix rsvp; revision-date 2015-08-20; }
    import topology-tunnel { prefix tt; revision-date 2013-08-19; }
    import topology-tunnel-p2p { prefix p2p; revision-date 2013-08-19; }

    organization "Cisco Systems, Inc.";
    contact "Robert Varga <rovarga@cisco.com>";

    description
        "This module contains the PCEP extensions to base tunnel
        topology model.

        Copyright (c)2013 Cisco Systems, Inc. All rights reserved.

        This program and the accompanying materials are made available
        under the terms of the Eclipse Public License v1.0 which
        accompanies this distribution, and is available at
        http://www.eclipse.org/legal/epl-v10.html";

    revision "2018-11-09" {
        description
            "P2MP extension.";
        reference "RFC8306";
    }

    revision "2013-08-20" {
        description
            "Initial revision.";
        reference "";
    }

    grouping topology-tunnel-pcep-type {
        container topology-tunnel-pcep {
            presence "indicates a PCEP tunnel-aware topology";
        }
    }

    augment "/nt:network-topology/nt:topology/nt:topology-types" {
        uses topology-tunnel-pcep-type;
    }

    grouping tunnel-pcep-supporting-node-attributes {
        container path-computation-client {
            leaf controlling {
                type boolean;
                default false;
            }
        }
    }

    augment "/nt:network-topology/nt:topology/nt:node/nt:supporting-node" {
        when "../../../nt:topology-types/topology-tunnel-pcep";

        uses tunnel-pcep-supporting-node-attributes;
    }

    grouping tunnel-pcep-type {
        container pcep-tunnel {
            presence "indicates a link is a PCEP tunnel";
        }
    }

    augment "/nt:network-topology/nt:topology/nt:link/tt:tunnel-types" {
        uses tunnel-pcep-type;
    }

    grouping tunnel-pcep-link-cfg-attributes {
        leaf symbolic-path-name {
            type string;
        }

        leaf class-type {
            type pcep:class-type;
        }

        leaf bandwidth {
            type netc:bandwidth;
        }

        uses rsvp:tunnel-attributes;
    }

    grouping tunnel-pcep-link-oper-attributes {

    }

    grouping tunnel-pcep-path-attributes {

    }

    augment "/nt:network-topology/nt:topology/nt:link" {
        when "../../tunnel-types/pcep-tunnel";
        uses tunnel-pcep-link-cfg-attributes;
        uses tunnel-pcep-link-oper-attributes;
    }

    augment "/nt:network-topology/nt:topology/tt:paths" {
        when "../../tunnel-types/pcep-tunnel";
        uses tunnel-pcep-path-attributes;
    }

    augment "/nt:network-topology/nt:topology/tt:paths/p2p:explicit-hops" {
        when "../../tunnel-types/pcep-tunnel";
        uses rsvp:explicit-route-subobjects;
    }

    augment "/nt:network-topology/nt:topology/tt:paths/p2p:reported-hops" {
        when "../../tunnel-types/pcep-tunnel";
        uses rsvp:record-route-subobjects;
    }
}
