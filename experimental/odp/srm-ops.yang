module odl-srm-ops {
    namespace "urn:opendaylight:serviceutils:srm:ops";
    prefix "srmops";

    import odl-srm-types {
        prefix srmtype;
    }

    revision "2018-06-26" {
        description "ODL Services Recovery Manager Operations Model";
    }

    /* Operations  */

    container service-ops {
        config false;
        list services {
            key service-name;
            leaf service-name {
                type identityref {
                    base srmtype:entity-name-base;
                }
            }
            list operations {
                key entity-name;
                leaf entity-name {
                    type identityref {
                        base srmtype:entity-name-base;
                    }
                }
                leaf entity-type {
                    type identityref {
                        base srmtype:entity-type-base;
                    }
                }
                leaf entity-id {
                    description "Optional when entity-type is service. Actual
                                 id depends on entity-type and entity-name";
                    type string;
                }
                leaf trigger-operation {
                    type identityref {
                        base srmtype:service-op-base;
                    }
                }
            }
        }
    }

}
