module odl-network-topology {
    yang-version 1;
    namespace "urn:opendaylight:params:xml:ns:yang:network:topology";
    prefix "ont";

    import network-topology { prefix nt; revision-date 2013-10-21; }
    import yang-ext {prefix ext; revision-date "2013-07-09"; }

    organization "Cisco Systems, Inc.";
    contact "Robert Varga <rovarga@cisco.com>";

    description
        "Augments IETF network topology model to define routing RPC
        extensions.

        Copyright (c)2013 Cisco Systems, Inc. All rights reserved.

        This program and the accompanying materials are made available
        under the terms of the Eclipse Public License v1.0 which
        accompanies this distribution, and is available at
        http://www.eclipse.org/legal/epl-v10.html";

    revision "2014-01-13" {
        description
            "Initial revision.";
        reference "";
    }

    identity network-topology-context {
        description
            "Identity used to mark the network topology context.
            This is useful for example binding RPCs to a particular
            network topology instance.";
    }

    typedef network-topology-ref {
        type instance-identifier;
        ext:context-reference "network-topology-context";
    }

    grouping network-topology-reference {
        leaf network-topology-ref {
            type network-topology-ref;
            mandatory true;
            // Workaround for yangtools
            ext:context-reference "network-topology-context";
        }
    }

    augment "/nt:network-topology/nt:topology" {
        ext:context-instance "network-topology-context";
    }
}
