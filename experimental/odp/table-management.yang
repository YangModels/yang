module table-management {
    namespace "urn:opendaylight:table:config";
    prefix table-cfg;
    
    import opendaylight-inventory {prefix inv;revision-date "2013-08-19";}
    import opendaylight-table-types {prefix table;}

    revision "2013-10-24" {
        description "Initial revision of table service";
    }

    grouping table-entry {
    
        leaf node {
            type inv:node-ref;
        }
        
        uses table:table-features;
    }   
     
    container tables {
        list table {
            key "id node"; 
                        
            leaf id {
                type uint32;
            }                    
            
            uses table-entry;
        }
    }    
}
