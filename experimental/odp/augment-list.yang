module augment-list {
  namespace "ns:augment:list";  
  prefix "auglst";

  
  import yang {prefix yng; revision-date 2013-11-26;}	


  revision "2013-11-26" {    
  }
  
	augment "/yng:cont" {
		list lst1 {
			leaf lf11 {
				type string;
			}
		}
	}
	

	  
}
