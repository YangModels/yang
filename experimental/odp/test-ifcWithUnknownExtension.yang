// vi: set smarttab et sw=4 tabstop=4:
module config-threads {
    yang-version 1;
    namespace "urn:opendaylight:params:xml:ns:yang:controller:threads";
    prefix "th";

    import config { prefix config; revision-date 2013-04-05; }

    revision "2013-05-02" {
        description
            "Add test";
    }

    extension java-class2 {
        description
            "YANG language extension carrying the fully-qualified name of
             a Java class. Code generation tools use the provided reference
             to tie a specific construct to its Java representation.";

        argument "name";
    }

    identity eventbus {
        description
            "Service representing an event bus. The service acts as message
             router between event producers and event consumers";

        base "config:service-type";
        config:java-class2 "com.google.common.eventbus.EventBus";
    }

}
