module openflow-approved-extensions {
    namespace "urn:opendaylight:openflow:approved:extensions";
    prefix "ofext";

    import yang-ext {prefix ext;}
    import openflow-extensible-match {prefix oxm;}
    import openflow-augments {prefix aug;}

    revision "2016-08-02" {
        description "Openflow approved extensions definition";
    }

    //ONF Approved OpenFlow Extensions
    // Extension 109 - TCP FLAGS
    identity tcp_flags {
        base oxm:match-field;
        description "TCP flags from the TCP header";
    }

    augment "/oxm:oxm-container/oxm:match-entry-value/aug:experimenter-id-case" {
        ext:augment-identifier "tcp-flags-container";
        container tcp-flags {
            leaf flags {
                type uint16;
            }
            leaf mask {
                type binary;
            }
        }
    }

}
