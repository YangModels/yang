module threadpool-impl-flexible {
    yang-version 1;
    namespace "urn:opendaylight:params:xml:ns:yang:controller:threadpool:impl:flexible";
    prefix "th-java-flexible";

    import threadpool { prefix th; revision-date 2013-04-09; }
    import config { prefix config; revision-date 2013-04-05; }
    import rpc-context { prefix rpcx; revision-date 2013-06-17; }

    organization "Cisco Systems, Inc.";

    contact "Robert Varga <rovarga@cisco.com>";

    description
        "This module contains the base YANG definitions for
        thread services pure Java implementation.

        Copyright (c)2013 Cisco Systems, Inc. All rights reserved.;

        This program and the accompanying materials are made available
        under the terms of the Eclipse Public License v1.0 which
        accompanies this distribution, and is available at
        http://www.eclipse.org/legal/epl-v10.html";

    revision "2013-12-01" {
        description
            "Initial revision";
    }

    identity threadpool-flexible {
        base config:module-type;
        config:provided-service th:threadpool;
        config:java-name-prefix FlexibleThreadPool;
    }

    augment "/config:modules/config:module/config:configuration" {
        case threadpool-flexible {
            when "/config:modules/config:module/config:type = 'threadpool-flexible'";
            leaf max-thread-count {
                type uint16;
            }
            leaf minThreadCount {
                type uint16;
            }
            leaf keepAliveMillis {
                type uint32;
            }

            container threadFactory {
                uses config:service-ref {
                    refine type {
                       // mandatory true;
                        config:required-identity th:threadfactory;
                    }
                }
            }
        }
    }
}
