/*
 * Copyright (c) 2018 Redhat Inc. and others.  All rights reserved.
 *
 * This program and the accompanying materials are made available under the
 * terms of the Eclipse Public License v1.0 which accompanies this distribution,
 * and is available at http://www.eclipse.org/legal/epl-v10.html
 */
module neutron-mtu {

    yang-version 1;

    namespace "urn:opendaylight:neutron-mtu";

    prefix neutron-mtu;

    import neutron-networks { prefix "networks"; }

    organization "OpenDaylight Neutron Group";

    description "This YANG module defines Openstack Neutron mtu extension attributes";

    revision "2018-11-14";

    grouping mtu-attributes {
        leaf mtu {
            type uint16;
            description "The maximum transmission unit (MTU) value to address fragmentation.
             Minimum value is 68 for IPv4, and 1280 for IPv6.";
        }
    }
}
