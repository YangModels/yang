module threadpool-impl-fixed {
    yang-version 1;
    namespace "urn:opendaylight:params:xml:ns:yang:controller:threadpool:impl:fixed";
    prefix "th-java-fixed";

    import threadpool { prefix th; revision-date 2013-04-09; }
    import config { prefix config; revision-date 2013-04-05; }
    import rpc-context { prefix rpcx; revision-date 2013-06-17; }

    organization "Cisco Systems, Inc.";

    contact "Robert Varga <rovarga@cisco.com>";

    description
        "This module contains the base YANG definitions for
         thread services pure Java implementation.

        Copyright (c)2013 Cisco Systems, Inc. All rights reserved.;

        This program and the accompanying materials are made available
        under the terms of the Eclipse Public License v1.0 which
        accompanies this distribution, and is available at
        http://www.eclipse.org/legal/epl-v10.html";

    revision "2013-12-01" {
        description
            "Initial revision";
    }


    identity threadpool-fixed {
        base config:module-type;
        config:provided-service th:threadpool;
        config:java-name-prefix FixedThreadPool;
    }

    augment "/config:modules/config:module/config:configuration" {
        case threadpool-fixed {
            when "/config:modules/config:module/config:type = 'threadpool-fixed'";
            leaf max-thread-count {
                type uint16;
            }

            container threadFactory {
                uses config:service-ref {
                    refine type {
                        //mandatory true;
                        config:required-identity th:threadfactory;
                    }
                }
            }
        }
    }
}
