module scalein-rpc {
    namespace "urn:opendaylight:netvirt:scalein:rpcs";
    prefix "scaleinrpcs";

    revision "2017-12-20" {
        description "ODL Specific Scalein Rpcs Module";
    }

    rpc scalein-computes-start {
        description "To trigger start of scale in the given dpns";
        input {
            leaf-list scalein-node-ids {
                type string;
            }
        }
    }

    rpc scalein-computes-end {
        description "To end the scale in of the given dpns";
        input {
            leaf-list scalein-node-ids {
                type string;
            }
        }
    }

    rpc scalein-computes-recover {
        description "To recover the dpns which are marked for scale in";
        input {
            leaf-list recover-node-ids {
                type string;
            }
        }
    }
}
