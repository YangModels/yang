/*
Copyright (c) 2018 Red Hat Inc. and others.  All rights reserved.

This program and the accompanying materials are made available under the
terms of the Eclipse Public License v1.0 which accompanies this distribution,
and is available at http://www.eclipse.org/legal/epl-v10.html
*/

module odl-serviceutils-upgrade {
    yang-version 1.1;
    namespace "urn:opendaylight:serviceutils:upgrade";
    prefix 'srv-upgrade';

    revision "2018-07-02" {
        description "Serviceutils upgrade config models";
    }

    container upgrade-config {
        leaf upgradeInProgress {
            type boolean;
            default false;
        }
    }
}
