module model-structure {

  yang-version "1";

  // namespace
  namespace "http://openconfig.net/yang/structure";

  prefix "struct";

  // import some basic types


  // meta
  organization "OpenConfig working group";

  contact
    "OpenConfig working group
    netopenconfig@googlegroups.com";

  description
    "This module describes a model structure for YANG
    configuration and operational state data models. Its intent is to
    describe how individual device protocol and feature models fit
    together and interact.";

  revision "2015-03-06" {
    description
      "Initial revision";
    reference "TBD";
  }

  // extension statements

  // feature statements

  // identity statements

  // typedef statements

  // grouping statements

  grouping info {
    description
      "base system information";

    container info {
      description
        "This container is for base system information, including
        device type (e.g., physcal or virtual), model, serial no.,
        location, etc.";

      leaf device-type {
        //TODO: consider changing to an identity if finer grained
        // device type classification is envisioned
        type enumeration {
          enum PHYSICAL {
            description "physical or hardware device";
          }
          enum VIRTUAL {
            description "virtual or software device";
          }
        }
        description
          "Type of the device, e.g., physical or virtual.  This node
          may be used to activate other containers in the model";
      }

    }
  }

  grouping hardware {
    description
      "hardware / vendor -specific data relevant to the platform";

    container hardware {
      description
        "This container is an anchor point for platform-specific
        configuration and operational state data.  It may be further
        organized into chassis, linecards, ports, etc.  It is
        expected that vendor or platform-specific augmentations
        would be used to populate this part of the device model";
    }
  }

  grouping l2-protocol-members {
    description "containers for each layer 2 protocol model";

    container vsi {
      description "virtual switch instance (or virtual forwarding
      instance) for use in PWE3 / VPLS services";

    }

    container ipv6-ndp {
      description "IPv6 neighbor discovery";
      reference "RFC 4861 - Neighbor Discovery for IP version 6
      (IPv6)";
    }

    container arp {
      description "Address resolution protocol";
      reference "STD 37 - An Ethernet Address Resolution Protocol";
    }

    container rstp {
      description "rapid spanning tree protocol";
      reference "IEEE 802.1D-2004";
    }

    container lldp {
      description "link layer discovery protocol";
      reference "IEEE 802.1AB";
    }

    container ptp {
      description
        "precision time protocol for time synchronization services.
        PTP also typically requires per-interface configuration";
      reference "IEEE 1588-2008";
    }
  }

  grouping l2-protocols {
    description "Layer 2 protocol models";

    container layer-2-protocols {
      description "layer 2 protocols and features";

      uses l2-protocol-members;

    }

  }

  grouping igp-protocol-members {
    description "containers for IGPs";

    container is-is {
      description "IS-IS IGP routing protocol";
      reference "RFC 1195 - Use of OSI IS-IS for Routing in TCP/IP
      and Dual Environments";
    }

    container ospf {
      description "OSPF IGP routing protocols";

      container ospf2 {
        description "OSPF v2";
        reference "RFC 2328 - OSPF Version 2";
      }

      container ospf3 {
        description "OSPF v3";
        reference "RFC 5340 - OSPF for IPv6";
      }
    }

    container igp-common {
      description "Common parameters for IGP protocols";
    }
  }

  grouping l3-protocol-members-vrf {
    description "containers for layer 3 protocol that are supported
    in a VRF instance";

    container bgp {
      description "BGP 4";
      reference "RFC 4271 - A Border Gateway Protocol 4 (BGP-4)";
    }

    container igp {
      description "interior gateway protocols";

      uses igp-protocol-members;
    }

    container bfd {
      description "bidirectional forwarding detection";
      reference "RFC 5880 - Bidirectional Forwarding Detection
      (BFD)";
    }

    container pim {
      description "protocol independent multicast";
      reference "RFC 4601 - Protocol Independent Multicast -
      Sparse Mode (PIM-SM): Protocol Specification (Revised)";
    }

    container igmp {
      description "Internet group management protocol";
      reference "RFC 3376 - Internet Group Management Protocol,
      Version 3";
    }

    container static-routes {
      description "static route that are manually created";
    }

  }

  grouping l3-protocols-misc {
    description "containers for other features operating at the
    network layer";

  }

  grouping l3-protocols-mpls {
    description "models related to MPLS and TE";

    container mpls-te {
      description "MPLS and traffic engineering";

      container global {
        description "global MPLS configuration";
      }

      container signaling {
        description "MPLS signaling protocols";

        container rsvp {
          description "RSVP signaling";
          reference "RFC 3209 - RSVP-TE: Extensions to RSVP for LSP
          Tunnels";
        }

        container segment-routing {
          description "SR signaling";
          reference "Segment Routing Architecture -
          draft-filsfils-spring-segment-routing-04";
        }

        container ldp {
          description "label distribution protocol";
          reference "RFC 5036 - LDP Specification";
        }
      }

      container label-switched-paths {
        description "models for different types of LSPs";

        container constrained-path {
          description "traffic-engineered, or constrained path LSPs";
        }

        container igp-congruent {
          description "LSPs that follow the IGP-computed path";
        }

        container static {
          description "statically configured LSPs";
        }
      }
    }
  }

  grouping l3-protocol-members {
    description "containers for all layer 3 protocols";

    uses l3-protocol-members-vrf;
    uses l3-protocols-misc;
    uses l3-protocols-mpls;

  }

  grouping l3-routing-policy {
    description "containers for routing policy models";

    container common {
      description "generic routing policy framework and
      configuration parameters";
    }

    container bgp-policy {
      description "BGP-specific routing policy parameters";
    }

    container igp-policy {
      description "IGP routing policy knobs -- may include
      policy parameters for specific IGPs";
    }

    container vrf-policy {
      description "import/export policies for VRFs";
    }
  }

  grouping l3-protocols {
    description "Layer 3 protocol models";

    container layer-3-protocols {
      description "layer 3 protocols and features";

      container global {
        description "router-wide instance of each routing protocol";

        uses l3-protocol-members;

      }

      list vrf {
        key vrf-name;
        description "list of VRF instances";

        leaf vrf-name {
          type string;
          description "name or id of the routing instance / VRF";
        }

        uses l3-protocol-members-vrf;
      }

      container routing-policy {
        description "models related to routing policy across
        protocols and VRFs";

        uses l3-routing-policy;

      }
    }
  }

  grouping interface-ip-common {
    description
      "interface-specific configuration for IP interfaces, IPv4 and
      IPv6";

    container vrrp {
      description "virtual router redundancy protocol";
      reference "RFC 5798 - Virtual Router Redundancy Protocol
      (VRRP) Version 3 for IPv4 and IPv6";
    }
  }

  grouping interface-addr-families {
    description
      "containers for addr family-specific data attached
      to interfaces";

    container ipv4 {
      description "IPv4 interfaces";

      uses interface-ip-common;
    }

    container ipv6 {
      description "IPv6 interfaces";

      uses interface-ip-common;
    }
  }

  grouping interfaces {
    description "interface-related models";

    container interfaces {
      description "various interface models";

      container ethernet {
        description "Ethernet interface config, e.g., 10, 40,
        100GBE";

        container aggregates {
          description "LAGs, LACP, etc. for Ethernet interfaces";
          reference "IEEE 802.1ad, 802.1AX";
        }

        container vlans {
          description "VLANs, 802.1q, q-in-q, etc.";
          reference "IEEE 802.1Q";
        }

        container lfm {
          description
            "Link-layer fault management for Ethernet interfaces";
          reference "IEEE 802.3ah";
        }
      }

      container sonet-sdh {
        description "SONET/SDH interfaces";
        reference
          "SDH: ITU standards G.707, G.783, G.784, and G.803
          SONET: ANSI standard T1.105";

      }

      container addressing {
        description "addressing and other interface-specific data,
        e.g., data plane protocols";

        uses interface-addr-families;
      }

      container tunnels {
        description
          "logical tunnel interfaces incl. GRE, VxLAN, L2TP etc.";
      }

    }
  }

  grouping oam {
    description "containers for features related to operations,
    administration, and management";

    container oam {
      description "commonly use OAM functions on devices";

      container snmp {
        description "SNMP server information, e.g., allowed clients";
      }

      container cfm {
        description
          "Ethernet connectivity fault management.  Also includes
          options that are associated with specific interfaces, such
          as maintenance endpoint domains.";
        reference "IEEE 802.1ag";
      }

      container twamp {
        description
          "Two-way active measurement protocol for measuring
          round-trip IP layer performance.";
        reference "RFC 5357 A Two-Way Active Measurement Protocol
        (TWAMP)";
      }
    }
  }

  grouping system-services {
    description "containers for system service models";

    container dns {
      description "domain name service and resolver configurration";
    }

    container ntp {
      description "network time protocol configuration";
    }

    container dhcp {
      description "dhcp and relay services";
    }

    container syslog {
      description "syslog configuration";
    }

    container ssh {
      description "ssh server configuration";
    }

    container stat-coll {
      description
        "mechanisms for data collection from devices, including
        packet and flow-level sampling";
    }

    uses oam;
  }

  grouping system-aaa {
    description "AAA-related services";

    container aaa {
      description "authentication, authorization, and accounting";

      container tacacs {
        description "TACACS+ configuration";
      }

      container radius {
        description "RADIUS";
        reference "RFC 2865 - Remote Authentication Dial In User
        Service (RADIUS)";
      }
    }
  }

  grouping system {
    description "system-wide services";

    container system {
      description "system services";

      uses system-services;
      uses system-aaa;

      container users {
        description "local user configuration";
      }
    }
  }

  grouping acl {
    description "forwarding rules";

    container acl {
      description "ACLs and packet forwarding rules";
    }
  }

  grouping qos {
    description "QoS features";

    container qos {
      description "QoS, including policing, shaping, etc.";
    }
  }

  // data definition statements

  container device {
    description "top-level anchor point for models.  Device is a
    generic L2/L3 network element";

    uses info;
    uses hardware;
    uses system;
    uses interfaces;
    uses acl;
    uses qos;

    container logical-routers {
      description "devices may support multiple logical router
      instances";

      list logical-router {

        key router-id;
        description "list of logical router instances";

        leaf router-id {
          type uint8; // expect a small number of logical routers
          description "identifier of the logical router instance";
        }

        leaf router-name {
          type string; // expect a small number of logical routers
          description "identifier of the logical router instance";
        }

        uses l2-protocols;
        uses l3-protocols;

      }
    }

  }

  // augment statements

  // rpc statements

  // notification statements

}
