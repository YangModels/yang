module openconfig-transport-types {

  yang-version "1";

  // namespace
  namespace "http://openconfig.net/yang/transport-types";

  prefix "opt-types";

  // import some basic types


  // meta
  organization "OpenConfig working group";

  contact
    "OpenConfig working group
    www.openconfig.net";

  description
    "This ";

  revision "2015-08-17" {
    description
      "Initial revision";
    reference "TBD";
  }

  // extension statements

  // feature statements

  // identity statements

  identity tributary-protocol-type {
    description
      "Base identity for protocol framing used by tributary
      signals.";
  }

  identity prot-1GE {
    base tributary-protocol-type;
    description "1G Ethernet protocol";
  }

  identity prot-OC48 {
    base tributary-protocol-type;
    description "OC48 protocol";
  }

  identity prot-STM16 {
    base tributary-protocol-type;
    description "STM 16 protocol";
  }

  identity prot-10GE_LAN {
    base tributary-protocol-type;
    description "10G Ethernet LAN protocol";
  }

  identity prot-10GE_WAN {
    base tributary-protocol-type;
    description "10G Ethernet WAN protocol";
  }

  identity prot-OC192 {
    base tributary-protocol-type;
    description "OC 192 (9.6GB) port protocol";
  }

  identity prot-STM64 {
    base tributary-protocol-type;
    description "STM 64 protocol";
  }

  identity prot-OTU2 {
    base tributary-protocol-type;
    description "OTU 2 protocol";
  }

  identity prot-OTU2e {
    base tributary-protocol-type;
    description "OTU 2e protocol";
  }

  identity prot-OTU1e {
    base tributary-protocol-type;
    description "OTU 1e protocol";
  }

  identity prot-ODU2 {
    base tributary-protocol-type;
    description "ODU 2 protocol";
  }

  identity prot-ODU2e {
    base tributary-protocol-type;
    description "ODU 2e protocol";
  }

  identity prot-40GE {
    base tributary-protocol-type;
    description "40G Ethernet port protocol";
  }

  identity prot-OC768 {
    base tributary-protocol-type;
    description "OC 768 protocol";
  }

  identity prot-STM256 {
    base tributary-protocol-type;
    description "STM 256 protocol";
  }

  identity prot-OTU3 {
    base tributary-protocol-type;
    description "OTU 3 protocol";
  }

  identity prot-ODU3 {
    base tributary-protocol-type;
    description "ODU 3 protocol";
  }

  identity prot-100GE {
    base tributary-protocol-type;
    description "100G Ethernet protocol";
  }

  identity prot-100G_MLG {
    base tributary-protocol-type;
    description "100G MLG protocol";
  }

  identity prot-OTU4 {
    base tributary-protocol-type;
    description "OTU4 signal protocol (112G) for transporting
    100GE signal";
  }

  identity prot-OTUCn {
    base tributary-protocol-type;
    description "OTU Cn protocol";
  }

  identity prot-ODU4 {
    base tributary-protocol-type;
    description "ODU 4 protocol";
  }

  identity transceiver-form-factor-type {
    description
      "Base identity for identifying the type of pluggable optic
      transceiver (i.e,. form factor) used in a port.";
  }

  identity CFP {
    base transceiver-form-factor-type;
    description
      "C form-factor pluggable, that can support up to a
      100 Gb/s signal with 10x10G or 4x25G physical channels";
  }

  identity CFP2 {
    base transceiver-form-factor-type;
    description
      "1/2 C form-factor pluggable, that can support up to a
      200 Gb/s signal with 10x10G, 4x25G, or 8x25G physical
      channels";
  }

  identity CFP4 {
    base transceiver-form-factor-type;
    description
      "1/4 C form-factor pluggable, that can support up to a
      100 Gb/s signal with 10x10G or 4x25G physical channels";
  }

  identity QSFP {
    base transceiver-form-factor-type;
    description
      "Quad Small Form-factor Pluggable transceiver that can support
      up to 4x10G physical channels";
  }

  identity QSFP28 {
    base transceiver-form-factor-type;
    description
      "QSFP pluggable optic with support for up to 4x28G physical
      channels";
  }

  identity SFP {
    base transceiver-form-factor-type;
    description
      "Small form-factor pluggable transceiver supporting up to
      10 Gb/s signal";
  }

  identity SFP_plus {
    base transceiver-form-factor-type;
    description
      "Enhanced small form-factor pluggable transceiver supporting
      up to 16 Gb/s signals, including 10 GbE and OTU2";
  }

  identity XFP {
    base transceiver-form-factor-type;
    description
      "10 Gigabit small form factor pluggable transceiver supporting
      10 GbE and OTU2";
  }

  identity X2 {
    base transceiver-form-factor-type;
    description
      "10 Gigabit small form factor pluggable transceiver supporting
      10 GbE using a XAUI inerface and 4 data channels.";
  }

  identity non-pluggable {
    base transceiver-form-factor-type;
    description
      "Represents a port that does not require a pluggable optic,
      e.g., with on-board optics like COBO";
  }

  identity other {
    base transceiver-form-factor-type;
    description
      "Represents a transceiver form factor not otherwise listed";
  }

  identity fiber-connector-type {
    description
      "Type of optical fiber connector";
  }

  identity sc-connector {
    base fiber-connector-type;
    description
      "SC type fiber connector";
  }

  identity lc-connector {
    base fiber-connector-type;
    description
      "LC type fiber connector";
  }

  identity mpo-connector {
    base fiber-connector-type;
    description
      "MPO (multi-fiber push-on/pull-off) type fiber connector
      1x12 fibers";
  }

  identity ethernet-pmd-type {
    description
      "Ethernet compliance codes (PMD) supported by transceivers";
  }

  identity eth-10GBASE-LRM {
    base ethernet-pmd-type;
    description "Ethernet compliance code: 10GBASE-LRM";
  }

  identity eth-10GBASE-LR {
    base ethernet-pmd-type;
    description "Ethernet compliance code: 10GBASE-LR";
  }

  identity eth-10GBASE-ZR {
    base ethernet-pmd-type;
    description "Ethernet compliance code: 10GBASE-ZR";
  }

  identity eth-10GBASE-ER {
    base ethernet-pmd-type;
    description "Ethernet compliance code: 10GBASE-ER";
  }

  identity eth-10GBASE-SR {
    base ethernet-pmd-type;
    description "Ethernet compliance code: 10GBASE-SR";
  }

  identity eth-40GBASE-CR4 {
    base ethernet-pmd-type;
    description "Ethernet compliance code: 40GBASE-CR4";
  }

  identity eth-40GBASE-SR4 {
    base ethernet-pmd-type;
    description "Ethernet compliance code: 40GBASE-SR4";
  }

  identity eth-40GBASE-LR4 {
    base ethernet-pmd-type;
    description "Ethernet compliance code: 40GBASE-LR4";
  }

  identity eth-40GBASE-ER4 {
    base ethernet-pmd-type;
    description "Ethernet compliance code: 40GBASE-ER4";
  }

  identity eth-40GBASE-PSM4 {
    base ethernet-pmd-type;
    description "Ethernet compliance code: 40GBASE-PSM4";
  }

  identity eth-4x10GBASE-LR {
    base ethernet-pmd-type;
    description "Ethernet compliance code: 4x10GBASE-LR";
  }

  identity eth-4x10GBASE-SR {
    base ethernet-pmd-type;
    description "Ethernet compliance code: 4x10GBASE-SR";
  }

  identity eth-100G_AOC {
    base ethernet-pmd-type;
    description "Ethernet compliance code: 100G_AOC";
  }

  identity eth-100G_ACC {
    base ethernet-pmd-type;
    description "Ethernet compliance code: 100G_ACC";
  }

  identity eth-100GBASE-SR10 {
    base ethernet-pmd-type;
    description "Ethernet compliance code: 100GBASE-SR10";
  }

  identity eth-100GBASE-SR4 {
    base ethernet-pmd-type;
    description "Ethernet compliance code: 100GBASE-SR4";
  }

  identity eth-100GBASE-LR4 {
    base ethernet-pmd-type;
    description "Ethernet compliance code: 100GBASE-LR4";
  }

  identity eth-100GBASE-ER4 {
    base ethernet-pmd-type;
    description "Ethernet compliance code: 100GBASE-ER4";
  }

  identity eth-100GBASE-CWDM4 {
    base ethernet-pmd-type;
    description "Ethernet compliance code: 100GBASE-CWDM4";
  }

  identity eth-100GBASE-CLR4 {
    base ethernet-pmd-type;
    description "Ethernet compliance code: 100GBASE-CLR4";
  }

  identity eth-100GBASE-PSM4 {
    base ethernet-pmd-type;
    description "Ethernet compliance code: 100GBASE-PSM4";
  }

  identity eth-100GBASE-CR4 {
    base ethernet-pmd-type;
    description "Ethernet compliance code: 100GBASE-CR4";
  }

  identity eth-undefined {
    base ethernet-pmd-type;
    description "Ethernet compliance code: undefined";
  }

  identity sonet-application-code {
    description
      "Supported SONET/SDH application codes";
  }

  identity VSR2000-3R2 {
    base sonet-application-code;
    description
      "SONET/SDH application code: VSR2000-3R2";
  }

  identity VSR2000-3R3 {
    base sonet-application-code;
    description
      "SONET/SDH application code: VSR2000-3R3";
  }

  identity VSR2000-3R5 {
    base sonet-application-code;
    description
      "SONET/SDH application code: VSR2000-3R5";
  }

  identity sonet-undefined {
    base sonet-application-code;
    description
      "SONET/SDH application code: undefined";
  }

  identity otn-application-code {
    description
      "Supported OTN application codes";
  }

  identity P1L1-2D1 {
    base otn-application-code;
    description
      "OTN application code: P1L1-2D1";
  }

  identity P1S1-2D2 {
    base otn-application-code;
    description
      "OTN application code: P1S1-2D2";
  }

  identity P1L1-2D2 {
    base otn-application-code;
    description
      "OTN application code: P1L1-2D2";
  }

  identity otn-undefined {
    base otn-application-code;
    description
      "OTN application code: undefined";
  }

  identity tributary-rate-class-type {
    description
      "Rate of tributary signal -- identities will typically reflect
      rounded bit rate.";
  }

  identity trib-rate-1G {
    base tributary-rate-class-type;
    description
      "1G tributary signal rate";
  }

  identity trib-rate-2.5G {
    base tributary-rate-class-type;
    description
      "2.5G tributary signal rate";
  }

  identity trib-rate-10G {
    base tributary-rate-class-type;
    description
      "10G tributary signal rate";
  }

  identity trib-rate-40G {
    base tributary-rate-class-type;
    description
      "40G tributary signal rate";
  }

  identity trib-rate-100G {
    base tributary-rate-class-type;
    description
      "100G tributary signal rate";
  }

  identity logical-element-protocol-type {
    description
      "Type of protocol framing used on the logical channel or
      tributary";
  }

  identity prot-ethernet {
    base logical-element-protocol-type;
    description
      "Ethernet protocol framing";
  }

  identity prot-otn {
    base logical-element-protocol-type;
    description
      "OTN protocol framing";
  }

  // typedef statements

  // grouping statements

  // data definition statements

  // augment statements

  // rpc statements

  // notification statements

}
