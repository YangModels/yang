module openconfig-rib-bgp-ext {

  yang-version "1";

  // namespace
  namespace "http://openconfig.net/yang/rib/bgp-ext";

  prefix "bgprib-ext";

  import openconfig-rib-bgp { prefix bgprib; }

  organization "OpenConfig working group";

  contact
    "OpenConfig working group
    www.openconfig.net";

  description
    "Defines additional data nodes for the OpenConfig BGP RIB model.
    These items reflect extensions that are desirable features but are
    not currently supported in a majority of BGP implementations.";

  revision "2015-04-15" {
    description
      "Initial revision";
    reference "TBD";
  }

  identity bgp-not-selected-bestpath {
    description
      "Base identity for indicating reason a route was was not
      selected by BGP route selection algorithm";
    reference
      "RFC 4271 - Section 9.1";
  }

  identity local-pref-lower {
    base bgp-not-selected-bestpath;
    description
      "Route has a lower localpref attribute than current best path";
    reference
      "RFC 4271 - Section 9.1.2";
  }

  identity as-path-longer {
    base bgp-not-selected-bestpath;
    description
      "Route has a longer AS path attribute than current best path";
    reference
      "RFC 4271 - Section 9.1.2.2 (a)";
  }

  identity origin-type-higher {
    base bgp-not-selected-bestpath;
    description
      "Route has a higher origin type, i.e., IGP origin is preferred
      over EGP or incomplete";
    reference
      "RFC 4271 - Section 9.1.2.2 (b)";
  }

  identity med-higher {
    base bgp-not-selected-bestpath;
    description
      "Route has a higher MED, or metric, attribute than the current
      best path";
    reference
      "RFC 4271 - Section 9.1.2.2 (c)";
  }

  identity prefer-external {
    base bgp-not-selected-bestpath;
    description
      "Route source is via IGP, rather than EGP.";
    reference
      "RFC 4271 - Section 9.1.2.2 (d)";
  }

  identity nexthop-cost-higher {
    base bgp-not-selected-bestpath;
    description
      "Route has a higher interior cost to the next hop.";
    reference
      "RFC 4271 - Section 9.1.2.2 (e)";
  }

  identity higher-router-id {
    base bgp-not-selected-bestpath;
    description
      "Route was sent by a peer with a higher BGP Identifier value,
      or router id";
    reference
      "RFC 4271 - Section 9.1.2.2 (f)";
  }

  identity higher-peer-address {
    base bgp-not-selected-bestpath;
    description
      "Route was sent by a peer with a higher IP address";
    reference
      "RFC 4271 - Section 9.1.2.2 (g)";
  }

  identity bgp-not-selected-policy {
    description
      "Base identity for reason code for routes that are rejected
      due to policy";
  }

  identity rejected-import-policy {
    base bgp-not-selected-policy;
    description
      "Route was rejected after apply import policies";
  }


  grouping rib-ext-route-annotations {
    description
      "Extended annotations for routes in the routing tables";

    leaf reject-reason {
      type union {
        type identityref {
          base bgp-not-selected-bestpath;
        }
        type identityref {
          base bgp-not-selected-policy;
        }
      }
      description
        "Indicates the reason the route is not used, either due to
        policy filtering or bestpath selection";
    }
  }

  augment "/bgprib:bgp-rib/bgprib:afi-safis/bgprib:afi-safi/" +
    "bgprib:ipv4-unicast/bgprib:loc-rib/bgprib:routes/" +
    "bgprib:route" {
      description
        "Add extended annotations to the Loc-RIB for IPv4";

      uses rib-ext-route-annotations;
  }

  augment "/bgprib:bgp-rib/bgprib:afi-safis/bgprib:afi-safi/" +
    "bgprib:ipv6-unicast/bgprib:loc-rib/bgprib:routes/" +
    "bgprib:route" {
      description
        "Add extended annotations to the Loc-RIB for IPv6";

      uses rib-ext-route-annotations;
  }

  augment "/bgprib:bgp-rib/bgprib:afi-safis/bgprib:afi-safi/" +
    "bgprib:ipv4-unicast/bgprib:neighbors/bgprib:neighbor/" +
    "bgprib:adj-rib-in-pre/bgprib:routes/bgprib:route" {
      description
        "Add extended annotations to Adj-RIB for IPv4";

      uses rib-ext-route-annotations;
  }

  augment "/bgprib:bgp-rib/bgprib:afi-safis/bgprib:afi-safi/" +
    "bgprib:ipv4-unicast/bgprib:neighbors/bgprib:neighbor/" +
    "bgprib:adj-rib-in-post/bgprib:routes/bgprib:route" {
      description
        "Add extended annotations to Adj-RIB for IPv4";

      uses rib-ext-route-annotations;
  }

  augment "/bgprib:bgp-rib/bgprib:afi-safis/bgprib:afi-safi/" +
    "bgprib:ipv4-unicast/bgprib:neighbors/bgprib:neighbor/" +
    "bgprib:adj-rib-out-pre/bgprib:routes/bgprib:route" {
      description
        "Add extended annotations to Adj-RIB for IPv4";

      uses rib-ext-route-annotations;
  }

  augment "/bgprib:bgp-rib/bgprib:afi-safis/bgprib:afi-safi/" +
    "bgprib:ipv4-unicast/bgprib:neighbors/bgprib:neighbor/" +
    "bgprib:adj-rib-out-post/bgprib:routes/bgprib:route" {
      description
        "Add extended annotations to Adj-RIB for IPv4";

      uses rib-ext-route-annotations;
  }

  augment "/bgprib:bgp-rib/bgprib:afi-safis/bgprib:afi-safi/" +
    "bgprib:ipv6-unicast/bgprib:neighbors/bgprib:neighbor/" +
    "bgprib:adj-rib-in-pre/bgprib:routes/bgprib:route" {
      description
        "Add extended annotations to Adj-RIB for IPv6";

      uses rib-ext-route-annotations;
  }

  augment "/bgprib:bgp-rib/bgprib:afi-safis/bgprib:afi-safi/" +
    "bgprib:ipv6-unicast/bgprib:neighbors/bgprib:neighbor/" +
    "bgprib:adj-rib-in-post/bgprib:routes/bgprib:route" {
      description
        "Add extended annotations to Adj-RIB for IPv6";

      uses rib-ext-route-annotations;
  }

  augment "/bgprib:bgp-rib/bgprib:afi-safis/bgprib:afi-safi/" +
    "bgprib:ipv6-unicast/bgprib:neighbors/bgprib:neighbor/" +
    "bgprib:adj-rib-out-pre/bgprib:routes/bgprib:route" {
      description
        "Add extended annotations to Adj-RIB for IPv6";

      uses rib-ext-route-annotations;
  }

  augment "/bgprib:bgp-rib/bgprib:afi-safis/bgprib:afi-safi/" +
    "bgprib:ipv6-unicast/bgprib:neighbors/bgprib:neighbor/" +
    "bgprib:adj-rib-out-post/bgprib:routes/bgprib:route" {
      description
        "Add extended annotations to Adj-RIB for IPv6";

      uses rib-ext-route-annotations;
  }

}
