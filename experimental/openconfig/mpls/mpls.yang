module mpls {

  yang-version "1";

  // namespace
  namespace "http://openconfig.net/yang/mpls";

  prefix "mpls";


  // import some basic types
  import mpls-types { prefix mplst; }
  import mpls-rsvp { prefix rsvp; }
  import mpls-sr { prefix sr; }
  import mpls-ldp { prefix ldp; }
  import openconfig-types { prefix oc-types; }

  // include submodules
  include mpls-te;
  include mpls-igp;
  include mpls-static;


  // meta
  organization "OpenConfig working group";

  contact
    "OpenConfig working group
    netopenconfig@googlegroups.com";

  description
    "This module provides data definitions for configuration of
    Multiprotocol Label Switching (MPLS) and associated protocols for
    signaling and traffic engineering.

    RFC 3031: Multiprotocol Label Switching Architecture

    The MPLS / TE data model consists of several modules and
    submodules as shown below.  The top-level MPLS module describes
    the overall framework.  Three types of LSPs are supported:

    i) traffic-engineered (or constrained-path)

    ii) IGP-congruent (LSPs that follow the IGP path)

    iii) static LSPs which are not signaled

    The structure of each of these LSP configurations is defined in
    corresponding submodules.  Companion modules define the relevant
    configuration and operational data specific to key signaling
    protocols used in operational practice.


                              +-------+
            +---------------->| MPLS  |<--------------+
            |                 +-------+               |
            |                     ^                   |
            |                     |                   |
       +----+-----+      +--------+-------+     +-----+-----+
       | TE LSPs  |      | IGP-based LSPs |     |static LSPs|
       |          |      |                |     |           |
       +----------+      +----------------+     +-----------+
           ^  ^                    ^  ^
           |  +----------------+   |  +--------+
           |                   |   |           |
           |   +------+      +-+---+-+      +--+--+
           +---+ RSVP |      |SEGMENT|      | LDP |
               +------+      |ROUTING|      +-----+
                             +-------+
    ";

  revision "2015-07-04" {
    description
      "Initial revision";
    reference "TBD";
  }

  // extension statements

  // feature statements

  // identity statements


  // grouping statements

  grouping path-setup-common {
    description "common definitions for all signaling protocols";

    // TODO: not clear we really need this
    leaf path-setup-type {
      type identityref {
        base mplst:path-setup-protocol;
      }
      description "path setup protocol to use with the LSP";
    }
  }

  grouping mpls-administrative-groups {
    description
      "global level definitions for MPLS link admin groups";

    list mpls-admin-groups {

      key admin-group-name;
      description "configuration of value to name mapping for mpls
      affinities/admin-groups";

      leaf admin-group-name {
        type string;
        description "name for mpls admin-group";
      }

      leaf admin-group-value {
        type uint32;
        description "value for mpls admin-group";
      }

    }
  }

 grouping mpls-ted-update-threshold_config {
    description "Configuration options for traffic
    engineering database update thresholds.";
    leaf-list ted-update-threshold {
      type oc-types:percentage;
      max-elements 16;
      description "stepped percentages of interface bandwidth change
        which trigger update events into the IGP
        traffic engineering database (TED)";
    }
  }
  grouping mpls-ted-update-threshold {
    description "Top level group for traffic engineering
    database flooding options";
    container ted-update-threshold {
      description "Interface bandwidth change percentages
      that trigger update events into the IGP traffic
      engineering database (TED)";
      container config {
        description "Configuration parameters for TED
        update threshold ";
        uses mpls-ted-update-threshold_config;
      }
      container state {
	config false;
	description "State parameters for TED update threshold ";
	uses mpls-ted-update-threshold_config;
      }
    }
  }


  grouping te_lsp_delay_config {
    description "Group for the timers goerning the delay
    in installation and cleanup of TE LSPs";
    leaf te-lsp-install-delay {
      type uint16 {
        range 0..3600;
      }
      units seconds;
      description "delay the use of newly installed te lsp for a
      specified amount of time.";
    }

    leaf te-lsp-cleanup-delay {
      type uint16;
      units seconds;
      description "delay the removal of old te lsp for a specified
      amount of time";
    }
  }

  grouping te-interfaces {
    description "global level definitions for interfaces
    on which TE is run";

    // TODO: this should be made a reference to an interface in the
    // interfaces model
    // TODO - should probably have as key the interface name, also
    // need an easy way to specify all interfaces and to exclude
    // interfaces.
    list te-interfaces {

      key interface-name;
      description "interfaces for which MPLS is enabled";

      leaf interface-name {
        type string;
        description "reference to interface name";
        // TODO: add ref to interface model
      }

      leaf-list interface-admin-groups {
        type leafref {
          path "/mpls:mpls/mpls:te-global-attributes/" +
	  "mpls:mpls-admin-groups/"+ "mpls:admin-group-name";
        }
        description
          "list of configured admin-groups on the interface";
      }

      leaf interface-ted-update-threshold {
      	type leafref {
      	  path "/mpls/te-global-attributes/ted-update-threshold/" +
	    "config/ted-update-threshold";
      	}
	description
	  "ted update threshold on the interface";
      }


    }

    container te_lsp_timers {
      description "definition for delays associated with setup
      and cleanup of TE LSPs";
      container config {
	description "Configuration parameters related
        to timers for TE LSPs";
	uses te_lsp_delay_config;
	uses te_lsp_reoptimize_config;
      }
      container state {
	config false;
	description "State related to timers for TE LSPs";
	uses te_lsp_delay_config;
	uses te_lsp_reoptimize_config;
      }
    }

  }

container mpls {
    presence "top-level container for MPLS config and operational
    state";

    description "Anchor point for mpls configuration and operational
    data";

    container global {
      // entropy label support, label ranges will be added here.
     description "general mpls configuration applicable to any type
     of LSP and signaling protocol";
    }

    container te-global-attributes {
      description "traffic-engineering global attributes";

      uses mpls-ted-update-threshold;
      uses te-interfaces;
      uses mpls-administrative-groups;

    }

    container signaling-protocols {
      description "top-level signaling protocol configuration";

      uses rsvp:rsvp-global;
      uses sr:sr-global;
      uses ldp:ldp-global;
    }

    container lsps {
      description "LSP definitions and configuration";

      container constrained-path {
        description "traffic-engineered LSPs supporting different
        path computation and signaling methods";

        uses mpls-te-global;
	uses path-definitions;

        list label-switched-path {
          key signaled-name;
          description "list of defined TE LSPs";

	  leaf signaled-name {
	    type leafref {
	      path "../config/signaled-name";
	    }

	    description "LSP name, also carried in signaling messages
            when appropriate";
	  }

          uses te-lsp-common;
          uses te-lsp-setup;
        }
      }

      container unconstrained-path {
        description "LSPs that use the IGP-determined path, i.e., non
        traffic-engineered, or non constrained-path";

        uses igp-lsp-common;
        uses igp-lsp-setup;

      }

      container static-lsps {
      description "statically configured LSPs, without dynamic
        signaling";

        uses static-lsp-main;
      }
    }
  }

  // augment statements

  // rpc statements

  // notification statements
}
