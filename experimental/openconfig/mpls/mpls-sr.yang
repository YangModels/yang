module mpls-sr {

  yang-version "1";

  // namespace
  namespace "http://openconfig.net/yang/sr";

  prefix "sr";


  // import some basic types
  import ietf-inet-types { prefix inet; }
  import mpls-types { prefix mplst; }

  // meta
  organization "OpenConfig working group";

  contact
    "OpenConfig working group
    netopenconfig@googlegroups.com";

  description
    "Configuration for MPLS with segment routing-based LSPs,
    including global parameters, and LSP-specific configuration for
    both constrained-path and IGP-congruent LSPs";

  revision "2015-07-04" {
    description
      "Initial revision";
    reference "TBD";
  }

  // extension statements

  // feature statements

  // identity statements

  // typedef statements

  grouping srgb_config {

    // Matches the "global" configuration options in
    // draft-litkowski-spring-yang...
    // TODO: request to Stéphane for this to be a separate
    // grouping such that it can be included.

    leaf lower-bound {
      type uint32;
      description
        "Lower value in the block.";
    }
    leaf upper-bound {
      type uint32;
      description
        "Upper value in the block.";
    }
    description
      "List of global blocks to be advertised.";
  }

  grouping srgb_state {
    description
      "State parameters relating to the SRGB";

    leaf size {
      type uint32;
      description
        "Number of indexes in the SRGB block";
    }
    leaf free {
      type uint32;
      description
        "Number of SRGB indexes that have not yet been allocated";
    }
    leaf used {
      type uint32;
      description
        "Number of SRGB indexes that are currently allocated";
    }

    // TODO: where do we put LFIB entries?

  }

  grouping adjacency-sid_config {
    description
      "Configuration related to an Adjacency Segment Identifier
      (SID)";

    // tuned from draft-litkowski-spring-yang
    // TODO: need to send a patch to Stéphane

    leaf-list advertise {
      type enumeration {
        enum "PROTECTED" {
          description
            "Advertise an Adjacency-SID for this interface, which is
            eligible to be protected using a local protection
            mechanism on the local LSR. The local protection
            mechanism selected is dependent upon the configuration
            of RSVP-TE FRR or LFA elsewhere on the system";
        }
        enum UNPROTECTED {
          description
            "Advertise an Adajcency-SID for this interface, which is
            explicitly excluded from being protected by any local
            protection mechanism";
        }
      }
      description
        "Specifies the type of adjacency SID which should be
        advertised for the specified entity.";
    }

    leaf-list groups {
      type uint32;
      description
        "Specifies the groups to which this interface belongs.
        Setting a value in this list results in an additional AdjSID
        being advertised, with the S-bit set to 1. The AdjSID is
        assumed to be protected";
    }
  }

  grouping interface_config {
    description
      "Configuration parameters relating to a Segment Routing
      enabled interface";

    leaf interface {
      type string;
      // TODO: this should be changed to a leafref.
      description
        "Reference to the interface for which segment routing
        configuration is to be applied.";
    }
  }

  // grouping statements

  grouping sr-global {
    description "global segment routing signaling configuration";

    container segment-routing {
      description "SR global signaling config";

      list srgb {
        key "lower-bound upper-bound";
        uses srgb_config;
        container config {
          description
            "Configuration parameters relating to the Segment Routing
            Global Block (SRGB)";
          uses srgb_config;
        }
        container state {
          config false;
          description
            "State parameters relating to the Segment Routing Global
            Block (SRGB)";
          uses srgb_config;
          uses srgb_state;
        }
        description
          "List of Segment Routing Global Block (SRGB) entries. These
          label blocks are reserved to be allocated as domain-wide
          entries.";
      }

      list interfaces {
        key "interface";
        uses interface_config;
        container config {
          description
            "Interface configuration parameters for Segment Routing
            relating to the specified interface";
          uses interface_config;
        }
        container state {
          config false;
          description
            "State parameters for Segment Routing features relating
            to the specified interface";
          uses interface_config;
        }
        container adjacency-sid {
          description
            "Configuration for Adjacency SIDs that are related to
            the specified interface";
          container config {
            description
              "Configuration parameters for the Adjacency-SIDs
              that are related to this interface";
            uses adjacency-sid_config;
          }
          container state {
            config false;
            description
              "State parameters for the Adjacency-SIDs that are
              related to this interface";
            uses adjacency-sid_config;
          }
        }
        description
          "List of interfaces with associated segment routing
          configuration";
      }
    }
  }

  grouping te-tunnel-sr_config {
    description
      "Configuration parameters relating to all SR-TE LSPs";

    leaf tunnel-type {
      type mplst:tunnel-type;
      description "specifies the type of LSP, e.g., P2P or P2MP";
    }

    leaf sid-selection-mode {
      type enumeration {
        enum "ADJ-SID-ONLY" {
          description
            "The SR-TE tunnel should only use adjacency SIDs
            to build the SID stack to be pushed for the LSP";
        }
        enum "MIXED-MODE" {
          description
            "The SR-TE tunnel can use a mix of adjacency
            and prefix SIDs to build the SID stack to be pushed
            to the LSP";
        }
      }
      default "MIXED-MODE";
      description
        "The restrictions placed on the SIDs to be selected by the
        calculation method for the SR-TE LSP";
    }

    leaf sid-protection-required {
      type boolean;
      default "false";
      description
        "When this value is set to true, only SIDs that are
        protected are to be selected by the calculating method
        for the SR-TE LSP.";
    }
  }

  grouping te-tunnel-sr_state {
    description
      "State parameters relating to an SR-TE tunnel";
    // placeholder
    // TODO: selected SID stack
  }

  grouping te-sr_config {
    description
      "Configuration parameters relating to an SR-TE LSP";

    leaf destination {
      type inet:ip-address;
      description
        "The destination IP for the SR-TE LSP";
    }
  }

  grouping te-sr_state {
    description
      "State parameters relating to SR-TE for the LSP";
    // placeholder
  }

  grouping te-tunnel-sr {
    description "defintiions for SR-signaled LSP tunnel types,
    .e.g., applicable to point-to-point LSPs";

    container config {
      description
        "Configuration parameters relating to SR-TE";
      uses te-sr_config;
    }
    container state {
      config false;
      description
        "State parameters relating to SR-TE";
      uses te-sr_config;
      uses te-sr_state;
    }

    container tunnel {
      description "contains configuration stanzas for different LSP
      tunnel types (P2P, P2MP, etc.)";

      container config {
        description
          "Configuration parameters relating to SR-TE for the
          tunnel";
        uses te-tunnel-sr_config;
      }
      container state {
        config false;
        description
          "State information relating to SR-TE for the tunnel";
        uses te-tunnel-sr_config;
        uses te-tunnel-sr_state;
      }

      container p2p-lsp {
        when "tunnel-type = 'P2P'" {
          description "container active when LSP tunnel type is
          point to point";
        }
        description "Config for point-to-point tunnels";

        // fill out the configuration details per segment
        // routing requrements
      }
    }
  }


  grouping te-lsp-sr-setup {
    description "data definitions for SR signaling";

    container segment-routing {

      presence "Presence of this container sets the LSP to use
      SR signaling";

      description "Configuration for signaling SR-based TE LSPs";

      uses te-tunnel-sr;
    }
  }

  grouping sr_fec-address_config {
    description
      "Configuration parameters relating to a FEC that is to be
      advertised by Segment Routing";

    leaf fec-address {
      type inet:ip-prefix;
      description
        "FEC that is to be advertised as part of the Prefix-SID";
    }
  }

  grouping sr_fec-prefix-sid_config {
    description
      "Configuration parameters relating to the nature of the
      Prefix-SID that is to be advertised for a particular FEC";

    leaf type {
      type enumeration {
        enum "INDEX" {
          description
            "Set when the value of the prefix SID should be specified
            as an off-set from the SRGB's zero-value. When multiple
            SRGBs are specified, the zero-value is the minimum
            of their lower bounds";
        }
        enum "ABSOLUTE" {
          description
            "Set when the value of a prefix SID is specified as the
            absolute value within an SRGB. It is an error to specify
            an absolute value outside of a specified SRGB";
        }
      }
      default "INDEX";
      description
        "Specifies how the value of the Prefix-SID should be
        interpreted - whether as an offset to the SRGB, or as an
        absolute value";
    }

    leaf node-flag {
      type boolean;
      description
        "Specifies that the Prefix-SID is to be treated as a Node-SID
        by setting the N-flag in the advertised Prefix-SID TLV in the
        IGP";
    }

    leaf last-hop-behavior {
      type enumeration {
        enum "EXPLICIT-NULL" {
          description
            "Specifies that the explicit null label is to be used
            when the penultimate hop forwards a labelled packet to
            this Prefix-SID";
        }
        enum "UNCHANGED" {
          description
            "Specicies that the Prefix-SID's label value is to be
            left in place when the penultimate hop forwards to this
            Prefix-SID";
        }
        enum "PHP" {
          description
            "Specicies that the penultimate hop should pop the
            Prefix-SID label before forwarding to the eLER";
        }
      }
      description
        "Configuration relating to the LFIB actions for the
        Prefix-SID to be used by the penultimate-hop";
    }
  }


  grouping igp-tunnel-sr {
    description "defintiions for SR-signaled, IGP-based LSP tunnel
    types";

    container tunnel {
      description "contains configuration stanzas for different LSP
      tunnel types (P2P, P2MP, etc.)";

      leaf tunnel-type {
        type mplst:tunnel-type;
        description "specifies the type of LSP, e.g., P2P or P2MP";
      }

      container p2p-lsp {
        when "tunnel-type = 'P2P'" {
          description "container active when LSP tunnel type is
          point to point";
        }
        description "properties of point-to-point tunnels";

        list fec {
          key "fec-address";
          uses sr_fec-address_config;

          description
            "List of FECs that are to be originated as SR LSPs";

          container config {
            description
              "Configuration parameters relating to the FEC to be
              advertised by SR";
            uses sr_fec-address_config;
          }
          container state {
            config false;
            description
              "Operational state relating to a FEC advertised by SR";
            uses sr_fec-address_config;
          }
          container prefix-sid {
            description
              "Parameters relating to the Prefix-SID
              used for the originated FEC";

            container config {
              description
                "Configuration parameters relating to the Prefix-SID
                used for the originated FEC";
              uses sr_fec-prefix-sid_config;
            }
            container state {
              config false;
              description
                "Operational state parameters relating to the
                Prefix-SID used for the originated FEC";
              uses sr_fec-prefix-sid_config;
            }
          }
        }
      }
    }
  }

  grouping igp-lsp-sr-setup {
    description "grouping for SR-IGP path setup for IGP-congruent
    LSPs";

    container segment-routing {

      presence "Presence of this container sets the LSP to use
      SR signaling";

      description "segment routing signaling extensions for
      IGP-confgruent LSPs";

      uses igp-tunnel-sr;

    }
  }

  // data definition statements

  // augment statements

  // rpc statements

  // notification statements

}
