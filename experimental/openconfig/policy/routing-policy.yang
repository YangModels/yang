module routing-policy {

  yang-version "1";

  // namespace
  namespace "http://openconfig.net/yang/routing-policy";

  prefix "rpol";

  // import some basic types
  import ietf-inet-types { prefix inet; }
  import policy-types {prefix pt; }


  // meta
  organization
    "OpenConfig working group";

  contact
    "OpenConfig working group
    netopenconfig@googlegroups.com";

  description
    "This module describes a YANG model for routing policy
    configuration. It is a limited subset of all of the policy
    configuration parameters available in the variety of vendor
    implementations, but supports widely used constructs for managing
    how routes are imported, exported, and modified across different
    routing protocols.  This module is intended to be used in
    conjunction with routing protocol configuration models (e.g.,
    BGP) defined in other modules.

    Route policy expression:

    Policies are expressed as a set of top-level policy definitions,
    each of which consists of a sequence of policy statements. Policy
    statements consist of simple condition-action tuples. Conditions
    may include mutiple match or comparison operations, and similarly
    actions may be multitude of changes to route attributes or a
    final disposition of accepting or rejecting the route.

    Route policy evaluation:

    Policy definitions are referenced in routing protocol
    configurations using import and export configuration statements.
    The arguments are members of an ordered list of named policy
    definitions which comprise a policy chain, and optionally, an
    explicit default policy action (i.e., reject or accept).

    Evaluation of each policy definition proceeds by evaluating its
    corresponding individual policy statements in order.  When a
    condition statement in a policy statement is satisfied, the
    corresponding action statement is executed.  If the action
    statement has either accept-route or reject-route actions, policy
    evaluation of the current policy definition stops, and no further
    policy definitions in the chain are evaluated.

    If the condition is not satisfied, then evaluation proceeds to
    the next policy statement.  If none of the policy statement
    conditions are satisfied, then evaluation of the current policy
    definition stops, and the next policy definition in the chain is
    evaluated.  When the end of the policy chain is reached, the
    default route disposition action is performed (i.e., reject-route
    unless an an alternate default action is specified for the
    chain).

    Policy 'subroutines' (or nested policies) are supported by
    allowing policy statement conditions to reference another policy
    definition which applies conditions and actions from the
    referenced policy before returning to the calling policy 
    statement and resuming evaluation.  If the called policy
    results in an accept-route (either explicit or by default), then
    the subroutine returns an effective true value to the calling
    policy.  Similarly, a reject-route action returns false.  If the
    subroutine returns true, the calling policy continues to evaluate
    the remaining conditions (using a modified route if the 
    subroutine performed any changes to the route).";

  revision "2014-11-30" {
    description
      "Initial revision";
    reference "TBD";
  }


  // typedef statements

  typedef default-policy-type {
    type enumeration {
      enum ACCEPT-ROUTE {
        description "default policy to accept the route";
      }
      enum REJECT-ROUTE {
        description "default policy to reject the route";
      }
    }
    description "type used to specify default route disposition in
    a policy chain";
  }

  identity install-protocol-type {
    description
      "Base type for protocols which can install prefixes into the
      RIB";
  }

  identity BGP {
    base install-protocol-type;
    description "BGP";
    reference "RFC 4271";
  }

  identity ISIS {
    base install-protocol-type;
    description "IS-IS";
    reference "ISO/IEC 10589";
  }

  identity OSPF {
    base install-protocol-type;
    description "OSPFv2";
    reference "RFC 2328";
  }

  identity OSPF3 {
    base install-protocol-type;
    description "OSPFv3";
    reference "RFC 5340";
  }

  identity STATIC {
    base install-protocol-type;
    description "Locally-installed static route";
  }

  identity DIRECTLY-CONNECTED {
    base install-protocol-type;
    description "A directly connected route";
  }


  // grouping statements

  grouping generic-defined-sets {
    description
      "Data definitions for pre-defined sets of attributes used in
      policy match conditions.  These sets are generic and can
      be used in matching conditions in different routing
      protocols.";

    list prefix-set {
      key prefix-set-name;
      description
        "Definitions for prefix sets";

      leaf prefix-set-name {
        type string;
        description
          "name / label of the prefix set -- this is used to
          reference the set in match conditions";
      }

      list prefix {
        key "address masklength masklength-range";
        description
          "list of prefix expressions that are part of the set";

        leaf address {
          type inet:ip-address;
          mandatory true;
          description
            "address portion of the prefix";
        }

        leaf masklength {
          type uint8 {
            // simple range covers both ipv4 and ipv6 --
            // could separate this into different types
            // for IPv4 and IPv6 prefixes
            range 0..128;
          }
          mandatory true;
          description
            "masklength for the prefix specification";
        }

        leaf masklength-range {
          type string {
            // pattern modeled after ietf-inet-types
            pattern '(([0-9])|([1-9][0-9])|(1[0-1][0-9])|'
              + '(12[0-8]))\.\.'
              + '(([0-9])|([1-9][0-9])|(1[0-1][0-9])|'
              + '(12[0-8]))';
          }
          description
            "Defines an optional range for the masklength.  Absence
            of the masklength-length implies that the prefix has an
            exact masklength given by the masklength parameter.
            Example: 10.3.192.0/21 through 10.3.192.0/24 would be
            expressed as address: 10.3.192.0, masklength: 21,
            masklength-range: 21..24";
        }
      }
    }

    list neighbor-set {
      key neighbor-set-name;
      description
          "Definitions for neighbor sets";

      leaf neighbor-set-name {
        type string;
        description
            "name / label of the neighbor set -- this is used to
            reference the set in match conditions";
      }

      list neighbor {
        key "address";
        description
            "list of addresses that are part of the neighbor set";

        leaf address {
          type inet:ip-address;
          description
              "IP address of the neighbor set member";
        }
      }
    }

    list tag-set {
      key tag-set-name;
      description
        "Definitions for tag sets";

      leaf tag-set-name {
        type string;
        description
          "name / label of the tag set -- this is used to reference
          the set in match conditions";
      }

      list tag {
        key "value";
        description
          "list of tags that are part of the tag set";

        leaf value {
          type pt:tag-type;
          description
            "Value of the tag set member";
        }
      }
    }
  }

  grouping local-generic-conditions {
    description
        "Condition statement definitions for consideration of a local
        characteristic of a route";

    leaf install-protocol-eq {
      type identityref {
        base install-protocol-type;
      }
      description
        "Condition to check the protocol / method used to install
        which installed the route into the local routing table";
    }
  }

  grouping match-set-options-group {
    description
      "Grouping containing options relating to how a particular set
      should be matched";

    leaf match-set-options {
      type pt:match-set-options-type;
      description
        "Optional parameter that governs the behaviour of the
        match operation";
    }
  }

  grouping generic-conditions {
    description "Condition statement definitions for checking
    membership in a generic defined set";

    container match-prefix-set {
      presence
        "The presence of this container indicates that the routes
        should match the prefix-set referenced.";

      description
        "Match a referenced prefix-set according to the logic
        defined in the match-set-options leaf";

      leaf prefix-set {
        type leafref {
          path "/routing-policy/defined-sets/prefix-set" +
          "/prefix-set-name";
          require-instance true;
        }
        description "References a defined prefix set";
      }
      uses match-set-options-group;
    }

    container match-neighbor-set {
      presence
        "The presence of this container indicates that the routes
        should match the neighbour set referenced";

      description
        "Match a referenced neighbor set according to the logic
        defined in the match-set-options-leaf";

      leaf neighbor-set {
        type leafref {
          path "/routing-policy/defined-sets/neighbor-set" +
          "/neighbor-set-name";
          require-instance true;
        }
        description "References a defined neighbor set";
      }
      uses match-set-options-group;
    }

    container match-tag-set {
      presence
        "The presence of this container indicates that the routes
        should match the tag-set referenced";

      description
        "Match a referenced tag set according to the logic defined
        in the match-options-set leaf";

      leaf tag-set {
        type leafref {
          path "/routing-policy/defined-sets/tag-set" +
          "/tag-set-name";
          require-instance true;
        }
        description "References a defined tag set";
      }
      uses match-set-options-group;
    }

    uses local-generic-conditions;
  }

  grouping igp-generic-conditions {
    description "grouping for IGP policy conditions";

  }


  grouping igp-conditions {
    description "grouping for IGP-specific policy conditions";

    container igp-conditions {
      description "Policy conditions for IGP attributes";

      uses igp-generic-conditions;

    }
  }

  grouping generic-actions {
    description
      "Definitions for common set of policy action statements that
      manage the disposition or control flow of the policy";

    leaf accept-route {
      type empty;
      description "accepts the route into the routing table";
    }

    leaf reject-route {
      type empty;
      description "rejects the route";
    }
  }


  grouping igp-actions {
    description "grouping for IGP-specific policy actions";

    container igp-actions {
      description "Actions to set IGP route attributes; these actions
      apply to multiple IGPs";

      leaf set-tag {
        type pt:tag-type;
        description "set the tag value for OSPF or IS-IS routes";
      }
    }
  }

  container routing-policy {
    description
      "top-level container for all routing policy configuration";

    container defined-sets {
      presence "Container for sets defined for matching in policy
        statements";
      description
          "Predefined sets of attributes used in policy match
          statements";

      uses generic-defined-sets;
      // uses bgp-defined-sets;
      // don't see a need for IGP-specific defined sets at this point
      // e.g., for OSPF, IS-IS, etc.
    }

    list policy-definition {

      key name;
      description
        "List of top-level policy definitions, keyed by unique
        name.  These policy definitions are expected to be
        referenced (by name) in policy chains specified in import/
        export configuration statements.";


      leaf name {
        type string;
        description
            "Name of the top-level policy definition -- this name
              is used in references to the current policy";
      }


      list statement {
        key name;
        // TODO: names of policy statements within a policy defn
        // should be optional, however, YANG requires a unique id
        // for lists; not sure that a compound key works either;
        // need to investigate further.
        ordered-by user;
        description
          "Policy statements group conditions and actions within
          a policy definition.  They are evaluated in the order
          specified (see the description of policy evaluation
          at the top of this module.";

        leaf name {
          type string;
          description "name of the policy statement";
        }

        container conditions {
          presence "conditions";
          description "Condition statements for this
            policy statement";

          leaf call-policy {
            type leafref {
              path "/rpol:routing-policy/rpol:policy-definition/" +
                  "rpol:name";
              require-instance true;
            }
            description
             "Applies the statements from the specified policy
             definition and then returns control the current policy
             statement.  Note that the called policy may itself call
             other policies (subject to implementation limitations).
             This is intended to provide a policy 'subroutine'
             capability.  The called policy should contain an
             explicit or a default route disposition that returns an
             effective true (accept-route) or false (reject-route),
             otherwise the behavior may be ambiguous and
             implementation dependent";
          }
          uses generic-conditions;
          uses igp-conditions;
        }

        container actions {
          presence "actions";
          description "Action statements for this policy
                statement";

          uses generic-actions;
          uses igp-actions;
        }
      }
    }
  }

  grouping apply-policy-group {
    description
      "configuration for applying policies";

    container apply-policy {
      description
        "Anchor point for routing policies in the configuration.
        Import and export policies are with respect to the local
        routing table, i.e., export (send) and import (receive),
        depending on the context.";

      leaf-list import-policies {
        type leafref {
          path "/rpol:routing-policy/rpol:policy-definition" +
              "/rpol:name";
          require-instance true;
        }
        ordered-by user;
        description
          "list of policy names in sequence to be applied on
          receiving a routing update in the current context, e.g.,
          for the current peer group, neighbor, address family,
          etc.";
      }

      leaf default-import-policy {
        type default-policy-type;
        default REJECT-ROUTE;
        description
          "explicitly set a default policy if no policy definition
          in the import policy chain is satisfied.";
      }

      leaf-list export-policies {
        type leafref {
          path "/rpol:routing-policy/rpol:policy-definition" +
              "/rpol:name";
          require-instance true;
        }
        ordered-by user;
        description
          "list of policy names in sequence to be applied on
          sending a routing update in the current context, e.g.,
          for the current peer group, neighbor, address family,
          etc.";
      }

      leaf default-export-policy {
        type default-policy-type;
        default REJECT-ROUTE;
        description
          "explicitly set a default policy if no policy definition
          in the export policy chain is satisfied.";
      }
    }
  }
}
