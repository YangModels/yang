module telemetry {

  yang-version "1";

  // namespace
  namespace "http://openconfig.net/yang/telemetry";

  prefix "oc-telemetry";

  // import some basic types
  import ietf-inet-types { prefix inet; }
  import openconfig-types { prefix oc-types; }


  // meta
  organization "OpenConfig working group";

  contact
    "OpenConfig working group www.openconfig.net";

  description
    "Data model which creates the configuration for the telemetry
     systems and functions on the device.";

  revision "2015-07-28" {
    description
    "Initial revision";
    reference "TBD";
  }

  container telemetry-system {
    description
      "Top level configuration and state for the
       device's telemetry system.";

    list telemetry-sensor-groups {
      key sensor-group-identifier;
      description
        "List of telemetry sensory groups on the local
         system, where a sensor grouping represents a resuable
         grouping of multiple paths and exclude filters.";

      leaf sensor-group-identifier {
        type leafref {
          path "../config/sensor-group-identifier";
        }
        description
          "Reference to the name or identifier of the
           sensor grouping";
      }
      container config {
        description
          "Configuration parameters relating to the
           telemetry sensor grouping";
        uses telemetry-sensor-group-config;
      }
      container state {
        config false;
        description
          "State information relating to the telemetry
           sensor group";
        uses telemetry-sensor-group-config;
      }

      container sensor-paths {
        description
          "Top level container to hold a set of sensor
           paths grouped together";

        list telemetry-sensor-paths {
          key telemetry-sensor-path;
          description
            "List of paths in the model which together
             comprise a sensor grouping. Filters for each path
             to exclude items are also provided.";

          leaf telemetry-sensor-path {
            type leafref {
              path "../config/telemetry-sensor-path";
            }
            description
              "Reference to the path of interest";
          }
          container config {
            description
              "Configuration parameters to configure a set
               of data model paths as a sensor grouping";
            uses telemetry-sensor-path-config;
          }
          container state {
            config false;
            description
              "Configuration parameters to configure a set
               of data model paths as a sensor grouping";
            uses telemetry-sensor-path-config;
          }
        }
      }
    }

    list telemetry-subscriptions {
      key subscription-identifier;
      description
        "List of telemetry subscriptions. A telemetry subscription
         consists of a set of collection destinations, stream
         attributes, and associated paths to state information
         in the model (sensor data)";

      leaf subscription-identifier {
        type leafref {
          path "../config/subscription-identifier";
        }
        description
          "Reference to the identifier of the subscription itself.
           The id will be the handle to refer to the subscription
           once created";
      }

      container config {
        description
          "Config parameters relating to the telemetry subscriptions
           on the local device";

        uses telemetry-subscription-config;
        uses telemetry-heartbeat-config;
        uses telemetry-suppress-redundant-config;
        uses telemetry-local-source-address-config;
        uses telemetry-stream-frequency-config;
      }

      container state {
        config false;
        description
          "State parameters relating to the telemetry subscriptions
           on the local device";

        uses telemetry-subscription-config;
        uses telemetry-subscription-state;
        uses telemetry-heartbeat-config;
        uses telemetry-suppress-redundant-config;
        uses telemetry-local-source-address-config;
        uses telemetry-stream-frequency-config;
      }

      container stream-destinations {
        description
          "Individual destinations for a telemetry stream.
           A telemetry subscription may send to multiple parallel
           destinations";
        list stream-destinations {
          key "stream-destination-address stream-destination-port";
          description
            "List of telemetry stream destinations";

          leaf stream-destination-address {
            type leafref {
              path "../config/stream-destination-address";
            }
            description
              "Reference to the destination address of the
               telemetry stream";
          }

          leaf stream-destination-port {
            type leafref {
              path "../config/stream-destination-port";
            }
            description
              "Reference to the port number of the stream
               destination";
          }

          container config {
            description
              "Configuration parameters relating to
               telemetry destinations";
            uses telemetry-stream-destination-config;
          }

          container state {
            config false;
            description
              "State information associated with
               telemetry destinations";
            uses telemetry-stream-destination-config;
          }
        }
      }
      container sensor-profile {
        description
          "A sensor profile is a set of sensor groups or
           individual sensor paths which are associated with a
           telemetry subscription. This is the source of the
           telemetry data for the subscription to send to the
           defined collectors.";
        list telemetry-sensor-profile {
          key telemetry-sensor-group;
          description
            "List of telemetry sensor groups used
             in the subscription";

          leaf telemetry-sensor-group {
            type leafref {
              path "../config/telemetry-sensor-group";
            }
            description
              "Reference to the telemetry sensor group name";
          }

          container config {
            description
              "Configuration parameters related to the sensor
               profile for a subscription";
            uses telemetry-sensor-profile-config;
          }

          container state {
            config false;
            description
              "State information relating to the sensor profile
               for a subscription";
            uses telemetry-sensor-profile-config;
          }
        }
      }
    }
  }

  // extension statements

  // feature statements

  // identity statements

  // typedef statements

  typedef telemetry-stream-protocol {
    type enumeration {
      enum tcp {
        description
          "TCP protocol transport for the stream";
      }
      enum udp {
        description
          "UDP protocol transport for the stream";
      }
    }
    description
      "Selectable protocols for transport
       of the telemetry stream";
  }

  // grouping statements

  grouping telemetry-sensor-path-config {
    description
      "Configuration parameters relating to the
       grouping of data model paths comprising a
       sensor grouping";
      leaf telemetry-sensor-path {
        type string;
        description
          "Path to a section of operational state of interest
           (the sensor).";
      }

      leaf sensor-exclude-filter {
        type string;
        description
          "Filter to exclude certain values out of the state
           values";
          //May not be necessary. Could remove.
      }
  }

  grouping telemetry-heartbeat-config {
    description
      "Configuration parameters relating to the
       heartbeat of the telemetry subscription";
    leaf heartbeat-interval {
      type inet:port-number;
      description
        "Maximum time interval in seconds that may pass
         between updates from a device to a telemetry collector.
         If this interval expires, but there is no updated data to
         send (such as if suppress_updates has been configured), the
         device must send a telemetry message to the collector.";
    }
  }

  grouping telemetry-suppress-redundant-config {
    description
      "Configuration parameters relating to suppression of
       redundant upstream updates";
    leaf suppress-redundant {
      type boolean;
      description
        "Boolean flag to control suppression of redundant
         telemetry updates to the collector platform. If this flag is
         set to TRUE, then the collector will only send an update at
         the configured interval if a subscribed data value has
         changed. Otherwise, the device will not send an update to
         the collector until expiration of the heartbeat interval.";
    }
  }

  grouping telemetry-sensor-profile-config {
    description
      "Configuration parameters relating to the sensor groups
       used in the sensor profile";
    leaf telemetry-sensor-group {
      type leafref {
        path "/telemetry-system/telemetry-sensor-groups/config"
        + "/sensor-group-identifier";
      }
      description
        "Reference to the sensor group which is used in the profile";
    }
  }

  grouping telemetry-sensor-group-config {
    description
      "Config parameters related to the sensor groups
       on the device";
    leaf sensor-group-identifier {
      type string;
      description
        "Name or identifier for the sensor group itself.
         Will be referenced by other configuration specifying a
         sensor group";
    }
  }

  grouping telemetry-subscription-config {
    description
      "Configuration parameters relating to the telemetry
       subscription";
    leaf subscription-identifier {
      type string;
      description
        "Identifer of the telemetry subscription.
         Will be used by configuration operations needing
         to modify or delete the telemetry subscription";
    }
  }

  grouping telemetry-subscription-state {
    description
      "State values for the telemetry subscription";
    //TODO add values
  }

  grouping telemetry-stream-destination-config {
    description
      "Configuration parameters for the stream destinations";
      leaf stream-destination-address {
        type inet:ip-address;
        description
          "IP address of the telemetry stream destination";
      }
      leaf stream-destination-port {
        type uint16;
        description
          "Protocol (udp or tcp) port number for the telemetry
           stream destination";
      }

      leaf stream-destination-protocol {
        type telemetry-stream-protocol;
        description
          "Protocol used to transmit telemetry data to the
           collector";
      }
  }

  grouping telemetry-stream-frequency-config {
    description
      "Config parameters for the frequency of updates to
        the collector";
    leaf sample-interval {
      type uint64;
      description
        "Time in milliseconds between the device's sample of a
         telemetry data source. For example, setting this to 100
         would require the local device to collect the telemetry
         data every 100 milliseconds. There can be latency or jitter
         in transmitting the data, but the sample must occur at
         the specified interval.

         The timestamp must reflect the actual time when the data
         was sampled, not simply the previous sample timestamp +
         sample-interval.

         If suppress_redundant is set to FALSE, then the device will
         send this collected value upstream immediately.
         If suppress_redundant is set to TRUE, then the collector
         will compare the previously reported telemetry value with
         the current value at each interval. Only if the values
         differ, will the update be transmitted to the collector.";
    }
  }

  grouping telemetry-stream-qos-config {
    description
      "Config parameters relating to quality of service markings
       for telemetry updates";
    leaf export-dscp-marking {
      type string;
      description
        "The DSCP code point value to be set on telemetry messages
         to the collector platform.";
    }
  }

  grouping telemetry-sensor-specification {
    description
      "Config related to creating telemetry sensor groups. A sensor
       group is a related set of sensor paths and/or filters to
       exclude items. A group is assigned a reusable identifer, so
       it can be used in multiple telemetry subscriptions.";
    list telemetry-sensor-group {
      key telemetry-sensor-group-identifier;
      description
        "List of telemetry sensor groups";

      leaf telemetry-sensor-group-identifier{
        type string;
        description
          "The sensor group identifer is a reusable handle which
           identifies a single sensor group. It is referenced from
           the subscription configuration.";
      }

      list telemetry-sensor-paths {
        key telemetry-sensor-path;
        description
          "A list of sensor paths and exclude filters which comprise
           a sensor grouping";

        leaf telemetry-sensor-path {
          type string;
          description
            "The sensor path is a path to a portion of operational
             state of interest in the data model";
        }
        // This may not be needed. Decide on removal.
        leaf sensor-exclude-filter {
          type string;
          description
            "The exclude filter allows certain values of state to be
             filtered out of the telemetry stream";
        }
      }
    }
  }

  grouping telemetry-sensor-profile {
    description
      "Config relating to sensor profiles. A sensor profile is the
       set of sensor information, ether a grouping or individual
       paths, which is relevant for a specific subscription.";
    list telemetry-sensor-profile {
      key telemetry-sensor-group;
      description
        "List of sensor groupings which are used in a subscription";

      leaf telemetry-sensor-group {
        type leafref {
          path "/telemetry-system/telemetry-subscriptions"
          + "/telemetry-sensor-specification/telemetry-sensor-group"
          + "/telemetry-sensor-group-identifier";
          require-instance true;
        }
        description
          "Reference to a telemetry sensor grouping
           to be used in the subscription";
      }
    }
  }

  grouping telemetry-local-source-address-config {
    description
      "Config relating to the local source address for telemetry
       messages";
    // TODO: Make this a reference to an interface.
    leaf local-source-address {
      type inet:ip-address;
      description
        "The IP address which will be the source of packets from
         the device to a telemetry collector destination.";
    }
  }

  // data definition statements

  // augment statements

  // rpc statements

  // notification statements

}
