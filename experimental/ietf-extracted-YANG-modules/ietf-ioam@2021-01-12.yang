module ietf-ioam {
  yang-version 1.1;
  namespace "urn:ietf:params:xml:ns:yang:ietf-ioam";
  prefix "ioam";

  import ietf-pot-profile {
    prefix "pot";
    reference "draft-ietf-sfc-proof-of-transit";
  }

  import ietf-access-control-list {
    prefix "acl";
    reference
      "RFC 8519: YANG Data Model for Network Access Control
       Lists (ACLs)";
  }

  organization
    "IETF IPPM (IP Performance Metrics) Working Group";

  contact
    "WG Web: <http://tools.ietf.org/wg/ippm>
     WG List: <ippm@ietf.org>
     Editor: zhoutianran@huawei.com
     Editor: james.n.guichard@futurewei.com
     Editor: fbrockne@cisco.com
     Editor: srihari@cisco.com";

  description
    "This YANG module specifies a vendor-independent data
     model for the In Situ OAM (IOAM).

    Copyright (c) 2020 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX; see the
    RFC itself for full legal notices.";

  revision 2021-01-12 {
    description "Initial revision.";
    reference "draft-ietf-ippm-ioam-yang";
  }

 /*
  * FEATURES
  */
  feature incremental-trace
  {
    description
      "This feature indicated that the incremental tracing option is
       supported";
    reference "draft-ietf-ippm-ioam-data";
  }

  feature preallocated-trace
  {
    description
      "This feature indicated that the preallocated tracing option is
       supported";
    reference "draft-ietf-ippm-ioam-data";
  }

  feature direct-export
  {
    description
      "This feature indicated that the direct export option is
       supported";
    reference "ietf-ippm-ioam-direct-export";
  }

  feature proof-of-transit
  {
    description
      "This feature indicated that the proof of transit option is
       supported";
    reference "draft-ietf-ippm-ioam-data";
  }

  feature edge-to-edge
  {
    description
      "This feature indicated that the edge to edge option is
       supported";
    reference "draft-ietf-ippm-ioam-data";
  }

 /*
  * IDENTITIES
  */
  identity base-filter {
    description
      "Base identity to represent a filter. A filter is used to
      specify the flow to apply the IOAM profile. ";
  }
  identity acl-filter {
    base base-filter;
    description
      "Apply ACL rules to specify the flow.";
  }

  identity base-protocol {
    description
      "Base identity to represent the carrier protocol. It's used to
       indicate what layer and protocol the IOAM data is embedded.";
  }

  identity ipv6-protocol {
    base base-protocol;
    description
      "The described IOAM data is embedded in IPv6 protocol.";
    reference "ietf-ippm-ioam-ipv6-options";
  }

  identity nsh-protocol  {
    base base-protocol;
    description
      "The described IOAM data is embedded in NSH.";
    reference "ietf-sfc-ioam-nsh";
  }

  identity base-node-action {
    description
      "Base identity to represent the node actions. It's used to
       indicate what action the node will take.";
  }

  identity action-encapsulate {
    base base-node-action;
    description
      "indicate the node is to encapsulate the IOAM packet";
  }

  identity action-decapsulate {
    base base-node-action;
    description
      "indicate the node is to decapsulate the IOAM packet";
  }

  identity base-trace-type {
    description
      "Base identity to represent trace types";
  }
  identity trace-hop-lim-node-id {
    base base-trace-type;
    description
      "indicates presence of Hop_Lim and node_id in the
       node data.";
  }

  identity trace-if-id {
    base base-trace-type;
    description
      "indicates presence of ingress_if_id and egress_if_id in the
       node data.";
  }

  identity trace-timestamp-seconds {
    base base-trace-type;
    description
      "indicates presence of time stamp seconds in the node data.";
  }

  identity trace-timestamp-nanoseconds {
    base base-trace-type;
    description
      "indicates presence of time stamp nanoseconds in the node data.";
  }

  identity trace-transit-delay {
    base base-trace-type;
    description
      "indicates presence of transit delay in the node data.";
  }

  identity trace-namespace-data {
    base base-trace-type;
    description
      "indicates presence of namespace specific data (short format)
       in the node data.";
  }

  identity trace-queue-depth {
    base base-trace-type;
    description
      "indicates presence of queue depth in the node data.";
  }

  identity trace-opaque-state-snapshot {
    base base-trace-type;
    description
      "indicates presence of variable length Opaque State Snapshot
       field.";
  }

  identity trace-hop-lim-node-id-wide {
    base base-trace-type;
    description
      "indicates presence of Hop_Lim and node_id wide in the
       node data.";
  }

  identity trace-if-id-wide {
    base base-trace-type;
    description
      "indicates presence of ingress_if_id and egress_if_id wide in
       the node data.";
  }

  identity trace-namespace-data-wide {
    base base-trace-type;
    description
      "indicates presence of namespace specific data in wide format
       in the node data.";
  }

  identity trace-buffer-occupancy {
    base base-trace-type;
    description
      "indicates presence of buffer occupancy in the node data.";
  }

  identity trace-checksum-complement {
    base base-trace-type;
    description
      "indicates presence of the Checksum Complement node data.";
  }

  identity base-pot-type {
    description
      "Base identity to represent Proof of Transit(PoT) types";
  }

  identity pot-bytes-16 {
    base base-pot-type;
    description
      "POT data is a 16 Octet field.";
  }

  identity base-e2e-type {
    description
      "Base identity to represent e2e types";
  }

  identity e2e-seq-num-64 {
    base base-e2e-type;
    description
      "indicates presence of a 64-bit sequence number";
  }

  identity e2e-seq-num-32 {
    base base-e2e-type;
    description
      "indicates presence of a 32-bit sequence number";
  }

  identity e2e-timestamp-seconds {
    base base-e2e-type;
    description
      "indicates presence of timestamp seconds for the
       transmission of the frame";
  }

  identity e2e-timestamp-subseconds {
    base base-e2e-type;
    description
      "indicates presence of timestamp subseconds for the
       transmission of the frame";
  }

  identity base-namespace {
    description
      "Base identity to represent the namespace";
  }

  identity namespace-ietf {
    base base-namespace;
    description
      "namespace that specified in IETF.";
  }

 /*
  * TYPE DEFINITIONS
  */

  typedef ioam-filter-type {
    type identityref {
      base base-filter;
    }
    description
      "Specifies a known type of filter.";
  }

  typedef ioam-protocol-type {
    type identityref {
      base base-protocol;
    }
    description
      "Specifies a known type of carrier protocol for the IOAM data.";
  }

  typedef ioam-node-action {
    type identityref {
      base base-node-action;
    }
    description
      "Specifies a known type of node action.";
  }

  typedef ioam-trace-type {
    type identityref {
      base base-trace-type;
    }
    description
      "Specifies a known trace type.";
  }

  typedef ioam-pot-type {
    type identityref {
      base base-pot-type;
    }
    description
      "Specifies a known pot type.";
  }

  typedef ioam-e2e-type {
    type identityref {
      base base-e2e-type;
    }
    description
      "Specifies a known e2e type.";
  }

  typedef ioam-namespace {
    type identityref {
      base base-namespace;
    }
    description
      "Specifies the supported namespace.";
  }

 /*
  * GROUP DEFINITIONS
  */

  grouping ioam-filter {
    description "A grouping for IOAM filter definition";

    leaf filter-type {
      type ioam-filter-type;
      description "filter type";
    }

    leaf ace-name {
      when "../filter-type = 'ioam:acl-filter'";
      type leafref {
        path "/acl:acls/acl:acl/acl:aces/acl:ace/acl:name";
      }
      description "Access Control Entry name.";
    }
  }

  grouping encap-tracing {
    description
      "A grouping for the generic configuration for
       tracing profile.";

    container trace-types {
      description
        "the list of trace types for encapsulate";

      leaf use-namespace {
        type ioam-namespace;
        description
          "the namespace used for the encapsulation";
      }

      leaf-list trace-type {
        type ioam-trace-type;
        description
          "The trace type is only defined at the encapsulation node.";
      }
    }
    leaf enable-loopback-mode {
      type boolean;
      default false;
      description
        "Loopback mode is used to send a copy of a packet back towards
        the source. The loopback mode is only defined at the
        encapsulation node.";
    }

    leaf enable-active-mode {
      type boolean;
      default false;
      description
        "Active mode indicates that a packet is used for active
         measurement. An IOAM decapsulating node that receives a
         packet with the Active flag set in one of its Trace options
         must terminate the packet.";
    }
  }

  grouping ioam-incremental-tracing-profile {
    description
      "A grouping for incremental tracing profile.";

    leaf node-action {
      type ioam-node-action;
      description "node action";
    }

    uses encap-tracing {
      when "node-action = 'ioam:action-encapsulate'";
    }

    leaf max-length {
      when "../node-action = 'ioam:action-encapsulate'";
      type uint32;
      units bytes;
      description
        "This field specifies the maximum length of the node data list
        in octets. The max-length is only defined at the
        encapsulation node. And it's only used for the incremental
        tracing mode.";
    }
  }

  grouping ioam-preallocated-tracing-profile {
    description
      "A grouping for incremental tracing profile.";
    leaf node-action {
      type ioam-node-action;
      description "node action";
    }

    uses encap-tracing {
      when "node-action = 'ioam:action-encapsulate'";
    }
  }

  grouping ioam-direct-export-profile {
    description
      "A grouping for direct export profile.";

    leaf node-action {
      type ioam-node-action;
      description "node action";
    }

    uses encap-tracing {
      when "node-action = 'ioam:action-encapsulate'";
    }

    leaf flow-id {
      when "../node-action = 'ioam:action-encapsulate'";
      type uint32;
      description
        "A 32-bit flow identifier. The field is set at the
         encapsulating node. The Flow ID can be uniformly assigned
         by a central controller or algorithmically generated by the
         encapsulating node. The latter approach cannot guarantee
         the uniqueness of Flow ID, yet the conflict probability is
         small due to the large Flow ID space.flow-id is used to
         correlate the exported data of the same flow from multiple
         nodes and from multiple packets.";
    }
  }

  grouping ioam-e2e-profile {
    description
      "A grouping for end to end profile.";

    leaf node-action {
      type ioam-node-action;
      description
        "indicate how the node act for this profile";
    }

    container e2e-types {
      when "../node-action = 'ioam:action-encapsulate'";
      description
        "the list of e2e types for encapsulate";

      leaf use-namespace {
        type ioam-namespace;
        description
          "the namespace used for the encapsulation";
      }

      leaf-list e2e-type {
        type ioam-e2e-type;
        description
          "The e2e type is only defined at the encapsulation node.";
      }
    }
  }

  grouping ioam-admin-config {
    description
      "IOAM top-level administrative configuration.";

    leaf enabled {
      type boolean;
      default false;
      description
        "When true, IOAM configuration is enabled for the system.
         Meanwhile, the IOAM data-plane functionality is enabled.";
    }
  }

 /*
  * DATA NODES
  */

  container ioam {
    description "IOAM top level container";

    container ioam-info {
      config false;
      description
        "Describes assistant information such as units or timestamp
         format. So that monitoring systems can interpret the IOAM
         data.";

    }

    container ioam-profiles {
      description
        "Contains a list of IOAM profiles.";

      container admin-config {
        description
          "Contains all the administrative configurations related to
           the IOAM functionalities and all the IOAM profiles.";

        uses ioam-admin-config;
      }

      list ioam-profile {
        key "profile-name";
        ordered-by user;
        description
          "A list of IOAM profiles that configured on the node.";

        leaf profile-name {
          type string;
          mandatory true;
          description
            "Unique identifier for each IOAM profile";
        }

        container filter {
          uses ioam-filter;
          description
            "The filter which is used to indicate the flow to apply
            IOAM.";
        }

        leaf protocol-type {
          type ioam-protocol-type;
          description
            "This item is used to indicate the carrier protocol where
            the IOAM is applied.";
        }

        container incremental-tracing-profile {
          if-feature incremental-trace;
          description
            "describe the profile for incremental tracing option";

          leaf enabled {
            type boolean;
            default false;
            description
              "When true, apply incremental tracing option to the
               specified flow identified by the filter.";
          }

          uses ioam-incremental-tracing-profile;
        }

        container preallocated-tracing-profile {
          if-feature preallocated-trace;
          description
            "describe the profile for preallocated tracing option";

          leaf enabled {
            type boolean;
            default false;
            description
              "When true, apply preallocated tracing option to the
               specified flow identified by the following filter.";
          }

          uses ioam-preallocated-tracing-profile;
        }

        container direct-export-profile {
          if-feature direct-export;
          description
            "describe the profile for direct-export option";

          leaf enabled {
            type boolean;
            default false;
            description
              "When true, apply direct-export option to the
               specified flow identified by the following filter.";
          }

          uses ioam-direct-export-profile;
        }

        container pot-profile {
          if-feature proof-of-transit;
          description
            "describe the profile for PoT option";

          leaf enabled {
            type boolean;
            default false;
            description
              "When true, apply Proof of Transit option to the
               specified flow identified by the following filter.";
          }

          leaf active-profile-index {
            type pot:profile-index-range;
            description
              "Proof of transit profile index that is currently
               active. Will be set in the first hop of the path
               or chain. Other nodes will not use this field.";
          }

          uses pot:pot-profile;
        }

        container e2e-profile {
          if-feature edge-to-edge;
          description
            "describe the profile for e2e option";

          leaf enabled {
            type boolean;
            default false;
            description
              "When true, apply End to end option to the
               specified flow identified by the following filter.";
          }

          uses ioam-e2e-profile;
        }
      }
    }
  }
}
