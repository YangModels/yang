module i2rs-rib {
  namespace "urn:TBD1:params:xml:ns:yang:rt:i2rs:rib";
    // replace with iana namespace when assigned
    prefix "i2rs-rib";

  import ietf-inet-types {
    prefix inet;
    //rfc6991
  }

  import ietf-interfaces {
    prefix "if";
  }

  import ietf-routing {
    prefix "rt";
  }

  organization
    "TBD2";
  contact
     "email: wang_little_star@sina.com
      email: hari@packetdesign.com
      email: mach.chen@huawei.com
      email: amit.dass@ericsson.com
      email: sriganesh.kini@ericsson.com
      email: nitin_bahadur@yahoo.com";

  description
    "This module defines a YANG data model for
     Routing Information Base (RIB) that aligns
     with the I2RS RIB information model.
     ";

  revision "2015-04-03" {
    description "initial revision";
    reference "draft-ietf-i2rs-rib-info-model-06";
  }

  container nexthop-capacity{
    leaf support-tunnel{
      type boolean;
    }
    leaf support-chains{
      type boolean;
    }
    leaf support-list-of-list{
      type boolean;
    }
    leaf support-replication{
      type boolean;
    }
    leaf support-weighted{
      type boolean;
    }
    leaf support-protection{
      type boolean;
    }
    leaf lookup-limit{
      type uint8;
    }
  }

  container nexthop-tunnel-encap-capacity{
    leaf support-ipv4{
      type boolean;
    }
    leaf support-ipv6{
      type boolean;
    }
    leaf support-mpls{
      type boolean;
    }
    leaf support-gre{
      type boolean;
    }
    leaf support-vxlan{
      type boolean;
    }
    leaf support-nvgre{
      type boolean;
    }
  }

  // Identities and Type Definitions
  identity mpls-action {
    description
      "The mpls-action. ";
  }

  identity push {
    base "mpls-action";
  }

  identity pop {
    base "mpls-action";
  }

  identity swap {
    base "mpls-action";
  }

  typedef mpls-action-def {
    type identityref {
      base "mpls-action";
    }
  }

  identity special-nexthop {
    description
      "special-nexthop. ";
  }

  identity discard {
    base "special-nexthop";
  }

  identity discard-with-error {
    base "special-nexthop";
  }

  identity receive {
    base "special-nexthop";
  }

  identity cos-value {
    base "special-nexthop";
  }

  typedef special-nexthop-def {
    type identityref {
      base "special-nexthop";
    }
  }

  identity ip-route-type {
    description
      "The ip route type. ";
  }

  identity src {
    base "ip-route-type";
  }

  identity dest {
    base "ip-route-type";
  }

  identity dest-src {
    base "ip-route-type";
  }

  typedef ip-route-type-def {
    type identityref {
      base "ip-route-type";
    }
  }

  identity rib-family {
    description
      "The rib-family.";
  }

  identity ipv4-rib-family {
    base "rib-family";
  }

  identity ipv6-rib-family {
    base "rib-family";
  }

  identity mpls-rib-family {
    base "rib-family";
  }
  identity ieee-mac-rib-family {
    base "rib-family";
  }

  typedef rib-family-def {
    type identityref {
      base "rib-family";
    }
  }

  identity route-type {
    description "The route type. ";
  }

  identity ipv4-route {
    base "route-type";
  }

  identity ipv6-route {
    base "route-type";
  }

  identity mpls-route {
    base "route-type";
  }

  identity ieee-mac {
    base "route-type";
  }

  identity interface {
    base "route-type";
  }

  typedef route-type-def {
    type identityref {
      base "route-type";
    }
  }

  identity tunnel-type {
    description
      "The tunnel type.";
  }

  identity ipv4-tunnel {
    base "tunnel-type";
    description
      "IPv4 tunnel type";
  }

  identity ipv6-tunnel {
    base "tunnel-type";
    description
      "IPv6 Tunnel type";
  }

  identity mpls-tunnel {
    base "tunnel-type";
    description
      "MPLS tunnel type";
  }

  identity gre-tunnel {
    base "tunnel-type";
    description
      "GRE tunnel type";
  }

  identity vxlan-tunnel {
    base "tunnel-type";
    description
      "VxLAN tunnel type";
  }

  identity nvgre-tunnel {
    base "tunnel-type";
    description
      "NVGRE tunnel type";
  }

  typedef tunnel-type-def {
    type identityref {
      base "tunnel-type";
    }
  }

  identity route-state {
    description
      "The route state.";
  }

  identity active {
    base "route-state";
  }

  identity inactive {
    base "route-state";
  }

  typedef route-state-def {
    type identityref {
      base "route-state";
    }
  }

  identity nexthop-state {
    description
      "The nexthop state.";
  }

  identity resolved {
    base "nexthop-state";
  }

  identity unresolved {
    base "nexthop-state";
  }

  typedef nexthop-state-def {
    type identityref {
      base "nexthop-state";
    }
  }

  identity route-installed-state {
    description
      "The route installed state. ";
  }

  identity uninstalled {
    base "route-installed-state";
  }

  identity Installed {
    base "route-installed-state";
  }

  typedef route-installed-state-def {
    type identityref {
      base "route-installed-state";
    }
  }

  identity route-reason {
    description
      "The reason of invalid route. ";
  }

  identity low-preference {
    base "route-reason";
    description
      "Low preference";
  }

  identity unresolved-nexthop {
    base "route-reason";
    description
      "Unresolved nexthop";
  }

  identity higher-metric {
    base "route-reason";
    description
      "Higher metric";
  }

  typedef route-reason-def {
    type identityref {
      base "route-reason";
    }
  }

  typedef nexthop-preference-def {
    description
      "Nexthop-preference is used for protection schemes.
       It is an integer value between 1 and 99.  A lower
       value indicates higher preference.  To download a
       primary/standby/tertiary group to the FIB, the
       nexthops that are resolved and have two highest
       preferences are selected.";
    type uint8 {
      range "1..99";
    }
  }
  typedef nhop-lb-weight-def {
    description
      "Nhop-lb-weight is a number between 1 and 99.";
    type uint8 {
      range "1..99";
    }
  }
  typedef nexthop-ref {
    type leafref {
      path  "/i2rs-rib:routing-instance/i2rs-rib:rib-list" +
            "/i2rs-rib:route-list/i2rs-rib:nexthop/i2rs-rib:nexthop-id";
    }
  }

  //Groupings

  grouping route-prefix{
    description
      "The common attributes used for all routes";
    leaf route-index {
      type uint64 ;
      mandatory true;
    }
    leaf route-type {
      type route-type-def ;
      mandatory true;
    }
    container match {
      choice rib-route-type {
        case ipv4 {
          description
            "Match on destination IP address in the IPv4 header";
          container ipv4{
            leaf ipv4-route-type {
              type ip-route-type-def ;
              mandatory true;
            }
            choice ip-route-type {
              case destination-ipv4-address {
                leaf destination-ipv4-prefix {
                  type inet:ipv4-prefix;
                  mandatory true;
                }
              }
              case source-ipv4-address {
                leaf source-ipv4-prefix {
                  type inet:ipv4-prefix;
                  mandatory true;
                }
              }
              case destination-source-ipv4-address {
                container destination-source-ipv4-address {
                  leaf destination-ipv4-prefix {
                    type inet:ipv4-prefix;
                    mandatory true;
                  }
                  leaf source-ipv4-prefix {
                    type inet:ipv4-prefix;
                    mandatory true;
                  }
                }
              }
            }
          }
        }
        case ipv6 {
          description
            "Match on destination IP address in the IPv6 header";
          container ipv6 {
            leaf ipv6-route-type {
              type ip-route-type-def ;
              mandatory true;
            }
            choice ip-route-type {
              case destination-ipv6-address {
                leaf destination-ipv6-prefix {
                  type inet:ipv6-prefix;
                  mandatory true;
                }
              }
              case source-ipv6-address {
                leaf source-ipv6-prefix {
                  type inet:ipv6-prefix;
                  mandatory true;
                }
              }
              case destination-source-ipv6-address {
                container destination-source-ipv6-address {
                  leaf destination-ipv6-prefix {
                    type inet:ipv6-prefix;
                    mandatory true;
                  }
                  leaf source-ipv6-prefix {
                    type inet:ipv6-prefix;
                    mandatory true;
                  }
                }
              }
            }
          }
        }
        case mpls-route {
          description
            "Match on a MPLS label at the top of the MPLS label stack";
          leaf mpls-label {
            type uint32 ;
            mandatory true;
          }
        }
        case mac-route {
          description
            "Match on MAC destination addresses in the ethernet header";
          leaf mac-address {
            type uint32 ;
            mandatory true;
          }
        }
        case interface-route {
          description
            "Match on incoming interface of the packet";
          leaf interface-identifier {
            type if:interface-ref;
            mandatory true;
          }
        }
      }
    }
  }

  grouping route{
    description
      "The common attributes usesd for all routes";
    uses route-prefix;
    container nexthop{
      uses nexthop;
    }
    container route-statistic{
      leaf route-state {
        type route-state-def ;
        config false;
      }
      leaf route-installed-state {
        type route-installed-state-def ;
        config false;
      }
      leaf route-reason {
        type route-reason-def ;
        config false;
      }
    }
    container route-attributes{
      uses route-attributes;
    }
    container route-vendor-attributes{
      uses route-vendor-attributes;
    }
  }

  grouping nexthop {
    leaf nexthop-id {
      mandatory true;
      type uint32;
    }
    choice nexthop-type {
      case nexthop-base {
        container nexthop-base {
          list nexthop-chain {
            key "nexthop-chain-id";
            uses nexthop-chain-member;
          }
        }
      }

       case nexthop-protection {
        list nexthop-protection-list {
            key "nexthop-protection-id";
            leaf nexthop-protection-id {
              mandatory true;
              type uint32;
            }
           leaf nexthop-preference {
             description
             "Nexthop-preference is used for protection schemes.
              It is an integer value between 1 and 99.  A lower
              value indicates higher preference.  To download a
              primary/standby/tertiary group to the FIB, the
              nexthops that are resolved and have two highest
              preferences are selected.";
             mandatory true;
             type nexthop-preference-def;
           }
           leaf nexthop {
             mandatory true;
             type nexthop-ref;
           }
        }
      }

      case nexthop-load-balance {
        container nexthop-lb {
          list nexthop-lbs {
            key "nexthop-lbs-id";
            leaf nexthop-lbs-id {
              mandatory true;
              type uint32;
            }
            leaf nhop-lb-weight {
              mandatory true;
              type nhop-lb-weight-def;
            }
            leaf nexthop-lb-member {
              mandatory true;
              type nexthop-ref;
            }
          }
        }
      }

      case nexthop-replicate {
        container nexthop-replicate {
          list nexthop-replicates{
            key "nexthop-replicates-id";
            leaf nexthop-replicates-id {
              mandatory true;
              type uint32;
            }
            leaf nexthop-replicate {
              type nexthop-ref;
            }
          }
        }
      }
    }
  }

  grouping nexthop-chain-member {
    description
      "One nexthop content for a route.";
    leaf nexthop-chain-id{
      type uint32;
      mandatory true;
    }
    choice nexthop-chain-type {
      case nexthop-chain-member-special {
        container nexthop-chain-member-special {
          leaf nexthop-chain-member-special{
            type special-nexthop-def;
          }
        }
      }

      case nexthop-chain-member-identifier{
        uses nexthop-chain-member-identifier;
      }

      case egress-interface-next-hop {
         description
           "Simple next-hop is specified as an outgoing interface,
            next-hop address or both.";
         leaf outgoing-interface {
           type if:interface-ref;
           mandatory true;
           description
             "Name of the outgoing interface.";
         }
      }

      case ipv4-address-next-hop {
        leaf next-hop-ipv4-address {
          type inet:ipv4-address;
          mandatory true;
          description
            "The nexthop is an IPv4 address.";
        }
      }

      case ipv6-address-next-hop {
        leaf next-hop-ipv6-address {
          type inet:ipv6-address;
          mandatory true;
          description
            "The nexthop is an IPv6 address.";
        }
      }

      case egress-interface-ipv4-next-hop {
        container next-hop-egress-interface-ipv4-address{
          leaf outgoing-interface {
            type if:interface-ref;
            mandatory true;
            description
              "Name of the outgoing interface.";
          }
          leaf next-hop-egress-ipv4-address {
            type inet:ipv4-address;
            mandatory true;
            description
              "The nexthop points to an interface with
               an IPv4 address.";
          }
          description
            "Egress-interface and ip address: This can be usesd
             in cases e.g.where the ip address is a link-local
             address.";
        }
      }

      case egress-interface-ipv6-next-hop {
        container next-hop-egress-interface-ipv6-address{
          leaf outgoing-interface {
            type if:interface-ref;
            mandatory true;
            description
              "Name of the outgoing interface.";
          }
          leaf next-hop-egress-ipv6-address {
            type inet:ipv6-address;
            mandatory true;
            description
              "The nexthop points to an interface with
               an IPv6 address.";
          }
          description
            "Egress-interface and ip address: This can be usesd
             in cases e.g.where the ip address is a link-local
             address.";
        }
      }

      case egress-interface-mac-next-hop {
        container next-hop-egress-interface-mac-address{
          leaf outgoing-interface {
            type if:interface-ref;
            mandatory true;
            description
              "Name of the outgoing interface.";
          }
          leaf ieee-mac-address {
            type uint32;
            mandatory true;
            description
              "The nexthop points to an interface with
               a specific mac-address.";
          }
          description
            "The egress interface must be an ethernet
             interface.Address resolution is not required
             for this nexthop."

        }
      }

      case tunnel-encap-next-hop {
        container tunnel-encap {
          uses tunnel-encap;
            leaf outgoing-interface {
              type string;
          }
          description
            "This can be an encap representing an ip tunnel or
             mpls tunnel or others as defined in this document.
             An optional egress interface can be specified to
             indicate which interface to send The packet out on.
             The egress interface is usesful when the network
             device contains eThernet interfaces and one needs
             to perform address resolution for The ip packet.";
        }
      }

      case logical-tunnel-next-hop {
        container logical-tunnel {
          uses logical-tunnel;
          description
            "This can be a MPLS LSP or a GRE tunnel (or others
             as defined in This document), that is represented
             by a unique identifier (e.g. name).";
        }
      }

      case rib-name {
        leaf rib-name {
          type string;
            description
              "A nexthop pointing to a rib indicates that the
               route lookup needs to continue in The specified
               rib.  This is a way to perform chained lookups.";
        }
      }
    }
  }

  grouping nexthop-chain-member-identifier{
    choice nexthop-identifier-type{
      case nexthop-chain-name {
        leaf nexthop-chain-name {
          type string;
          mandatory true;
        }
      }
      case nexthop-chain-id {
        leaf nexthop-chain-id {
          type uint32;
          mandatory true;
        }
      }
    }
  }

  grouping route-vendor-attributes{
  }

  grouping logical-tunnel{
    leaf tunnel-type {
      type tunnel-type-def ;
      mandatory true;
    }
    leaf tunnel-name {
      type string ;
      mandatory true;
    }
  }

  grouping ipv4-header{
    leaf source-ipv4-address {
      type inet:ipv4-address;
      mandatory true;
    }
    leaf destination-ipv4-address {
      type inet:ipv4-address;
      mandatory true;
    }
    leaf protocol {
      type uint8;
      mandatory true;
    }
    leaf ttl {
      type uint8;
    }
    leaf dscp {
      type uint8;
    }
  }

  grouping ipv6-header{
    leaf source-ipv6-address {
      type inet:ipv6-address;
      mandatory true;
    }
    leaf destination-ipv6-address {
      type inet:ipv6-address;
      mandatory true;
    }
    leaf next-header {
      type uint8;
      mandatory true;
    }
    leaf traffic-class {
      type uint8;
    }
    leaf flow-label {
      type uint16;
    }
    leaf hop-limit {
      type uint8;
    }
  }

  grouping nvgre-header{
    choice nvgre-type {
      description
        "nvgre-header.";
      case ipv4 {
        uses ipv4-header;
      }
      case ipv6 {
        uses ipv6-header;
      }
    }
    leaf virtual-subnet-id {
      type uint32;
      mandatory true;
    }
    leaf flow-id {
      type uint16;
    }
  }

  grouping vxlan-header{
    choice vxlan-type {
      description
        "vxlan-header.";
      case ipv4 {
        uses ipv4-header;
      }
      case ipv6 {
        uses ipv6-header;
      }
    }
    leaf vxlan-identifier {
      type uint32;
    }
  }

  grouping gre-header{
    leaf gre-ip-destination {
      type inet:ipv4-address;
      mandatory true;
    }
    leaf gre-protocol-type {
      type inet:ipv4-address;
      mandatory true;
    }
    leaf gre-key {
      type uint64;
    }
  }

  grouping mpls-header{
    choice mpls-action-type {
      description
        "mpls-header.";
      case mpls-push {
        leaf mpls-push {
          type boolean;
          mandatory true;
        }
        leaf mpls-label {
          type uint32;
          mandatory true;
        }
        leaf s-bit {
          type boolean;
        }
        leaf tos-value {
          type uint8;
        }
        leaf ttl-value {
          type uint8;
        }
          }
      case mpls-pop {
        leaf mpls-pop {
          type boolean;
          mandatory true;
        }
        leaf ttl-action {
          type uint8;
        }
      }
    }
  }

  grouping tunnel-encap{
    choice tunnel-type {
      description
        "options for next-hops.";
      case ipv4 {
        uses ipv4-header;
      }
      case ipv6 {
        uses ipv6-header;
      }
      case mpls {
        uses mpls-header;
      }
      case gre {
        uses gre-header;
      }
      case nvgre {
        uses nvgre-header;
      }
    }
  }

  grouping route-attributes{
    leaf route-preference {
      description
        "ROUTE_PREFERENCE: This is a numerical value that
         allows for comparing routes from different
         protocols.  Static configuration is also
         considered a protocol for the purpose of this
         field.  It iss also known as administrative-distance.
         The lower the value, the higher the preference.";
        type uint32 ;
      mandatory true;
    }
    leaf local-only {
      type boolean ;
      mandatory true;
    }
    container address-family-route-attributes{
      choice route-type {
        case ip-route-attributes {
        }
        case mpls-route-attributes {
        }
        case ethernet-route-attributes {
        }
      }
    }
  }

  container routing-instance {
    description
      "Configuration of an 'i2rs' pseudo-protocol instance
       consists of a list of ribs.";

    leaf name {
      description
        "A routing instance is identified by its name,
        INSTANCE_name.  This MUST be unique across all routing
        instances in a given network device.";
      type string ;
      mandatory true;
    }
    list interface-list {
      description
        "This represents the list of interfaces associated
         with this routing instance.  The interface list helps
         constrain the boundaries of packet forwarding.
         Packets coming on these interfaces are directly
         associated with the given routing instance.  The
         interface list contains a list of identifiers, with
         each identifier uniquely identifying an interface.";
      key "name";
      leaf name {
        type if:interface-ref;
        description
         "A reference to the name of a configured network layer
         interface.";
      }
    }
    uses rt:router-id ;
    list rib-list {
      description
        "This is the list of RIBs associated with this routing
         instance.  Each routing instance can have multiple RIBs
         to represent routes of different types.";
      key "name";
      leaf name {
        description
         "A reference to the name of a rib.";
       type string;
        mandatory true;
      }
      leaf rib-family {
        type rib-family-def;
        mandatory true;
      }
      leaf enable-ip-rpf-check {
        description
          "Each RIB can be optionally associated with a
           ENABLE_IP_RPF_CHECK attribute that enables Reverse
           path forwarding (RPF) checks on all IP routes in that
           RIB.  Reverse path forwarding (RPF) check is used to
           prevent spoofing and limit malicious traffic.";
        type boolean;
      }
      list route-list{
        key "route-index";
        uses route;
      }
    }
  }

  notification nexthop-resolution-status-change {
    description
        "Nexthop resolution status (resolved/unresolved)
         notification.";
    container nexthop{
      uses nexthop;
    }
    leaf nexthop-state {
      description
       "Nexthop resolution status (resolved/unresolved)
        notification.";
      type nexthop-state-def;
      mandatory true;
    }
  }

  notification route-change {
    description
        "Route change notification.";
    leaf instance-name {
      description
        "A routing instance is identified by its name,
        INSTANCE_name.  This MUST be unique across all
        routing instances in a given network device.";
      type string ;
      mandatory true;
    }
    leaf rib-name {
      description
       "A reference to the name of a rib.";
      type string;
      mandatory true;
    }
    leaf rib-family {
      type rib-family-def;
      mandatory true;
    }
    uses route-prefix;
    leaf route-installed-state {
      description
       "Indicates whether the route got installed in the FIB.";
      type route-installed-state-def;
      mandatory true;
    }
    leaf route-state {
      description
       "Indicates whether a route is fully resolved and
        is a candidate for selection.";
      type route-state-def;
      mandatory true;
    }
    leaf route-reason {
      description
       "Need to be added.";
      type route-reason-def;
      mandatory true;
    }
  }
}
