module ietf-cats {
   yang-version 1.1;
   namespace "urn:ietf:params:xml:ns:yang:ietf-cats";
   prefix cats;

   import ietf-inet-types {
      prefix inet;
      reference
         "RFC 6991: Common YANG Data Types";
   }

   import ietf-routing-types {
      prefix "rt-types";
      reference
         "RFC 8294: Common YANG Data Types for the Routing Area";
   }

   import ietf-srv6-types {
      prefix "srv6-types";
   }

   import ietf-interfaces {
      prefix if;
   }

   organization "IETF CATS";
   contact
      "WG Web:  <https://datatracker.ietf.org/group/cats/>
       WG List: <mailto:cats@ietf.org>
       Author:  Huijuan Yao
                <mailto:yaohuijuan@chinamobile.com>
       Author:  Changwang Lin
                <mailto:linchangwang.04414@h3c.com>
       Author:  Zhenqiang Li
                <mailto:lizhenqiang@chinamobile.com>
       Author:  Quan Xiong
                <mailto:xiong.quan@zte.com.cn>
       Author:  Luis M. Contreras
                <mailto:luismiguel.contrerasmurillo@telefonica.com>
      ";

   description
        "This module describes a YANG model for CATS.
        This YANG model conforms to the Network Management
        Datastore Architecture (NMDA) as described in RFC 8342.

        Copyright (c) 2024 IETF Trust and the persons identified as
        authors of the code.  All rights reserved.

        Redistribution and use in source and binary forms, with or
        without modification, is permitted pursuant to, and subject
        to the license terms contained in, the Revised BSD License
        set forth in Section 4.c of the IETF Trust's Legal
        Provisions Relating to IETF Documents
        (https://trustee.ietf.org/license-info).

        This version of this YANG module is part of RFC XXXX
        (https://www.rfc-editor.org/info/rfcXXXX);
        see the RFC itself for full legal notices.

        The key words 'MUST', 'MUST NOT', 'REQUIRED', 'SHALL',
        'SHALL NOT', 'SHOULD', 'SHOULD NOT', 'RECOMMENDED', 'NOT
        RECOMMENDED', 'MAY', and 'OPTIONAL' in this document are to
        be interpreted as described in BCP 14 (RFC 2119) (RFC 8174)
        when, and only when, they appear in all capitals, as shown
        here.";

   revision 2024-06-20 {
      description
         "Initial Version";
      reference
         "RFC XXXX: YANG Data Model for CATS";
   }

   typedef cs-id {
      type union {
         type uint32;
         type inet:ipv4-address;
         type inet:ipv6-address;
      }
      description
        "This type is for CATS CS-ID.";
   }

   typedef csci-id {
      type union {
         type uint32;
         type inet:ipv4-address;
         type inet:ipv6-address;
      }
      description
        "This type is for CATS CSCI-ID.";
   }

   grouping service-policy-type {
      description
        "service policy type";
      leaf policy-type {
          type enumeration {
             enum base-on-affinity {
                value 0;
                description "base on affinity";
             }
             enum base-on-sm-only {
                value 1;
                description "base on service metric only";
             }
             enum base-on-sm-nm {
                value 2;
                description "base on service metric and network
                metric";
             }
          }
          description "service policy type";
      }
   }
   container base {
      description
        "CATS base configuration.";
      leaf enable {
          type boolean;
          description
            "enable CATS";
      }
      leaf update-interval {
         type uint32;
         description
           "update-interval of CATS metric";
      }
      leaf entry-limits {
         type uint64;
         description
           "CATS metric entry limit";
      }
      leaf flow-limits {
         type uint64;
         description
           "CATS flow entry limit";
      }
      leaf flow-timeout {
         type uint32;
         description
           "CATS flow timeout when no flow";
      }
      container service-policy {
         description
           "CATS sercice policy";
         leaf cs-id {
            type cs-id;
            description
              "cs-id";
         }
         uses service-policy-type;
      }
   }

   container traffic-classifiers {
      description
        "CATS traffic-classifier feature";
      list traffic-classifier {
         key "cs-id";
         description
           "CATS traffic-classifier feature";
         leaf cs-id {
            type cs-id;
            description
              "CATS CS-ID";
         }
         leaf description {
            type string;
            description
              "description of this service, example: http";
         }
         leaf server-port {
            type uint16;
            description
              "server-port of the service.";
         }
         leaf protocol {
            type uint16;
            description
              "protocol of the service.";
         }
      }
   }

   container service-metrics {
      description
        "CATS service metric entry";
      list service-metric {
         key "cs-id csci-id source-type";
         description
           "CATS service metric entry";
         leaf cs-id {
            type cs-id;
            description
              "CATS cs-id";
         }
         leaf csci-id {
            type csci-id;
            description
              "CATS csci-id";
         }
         leaf source-type {
            type enumeration {
               enum static {
                  value 0;
                  description "static configuration";
               }
               enum bgp {
                  value 1;
                  description "bgp protocol";
               }
            }
            description
              "source-type of the service-metric";
         }
         leaf priority {
            type uint32;
            description
              "server priority";
         }
         leaf affinity {
            type uint32;
            description
              "server affinity";
         }
         leaf location {
            type inet:ip-address;
            description
              "server location";
         }
         container service-metric {
            description
              "service metric";
            list metric {
               key "metric-type";
               description "Different types of service.";
               leaf metric-type {
                  type enumeration {
                     enum delay {
                        value 0;
                        description " Calculate the metric based on
                        transmission delay, where the metric value
                        is the delay time in milliseconds.";
                     }
                     enum service-ratio {
                        value 1;
                        description "Calculate the metric based on
                        business capacity, where the metric value is
                        the current capacity percentage.";
                     }
                     enum memory-ratio {
                        value 2;
                        description " Calculate the metric based on
                        memory utilization percentage,  where the
                        metric value is the current memory
                        utilization percentage";
                     }
                  }
                  description "metric type";
               }
               leaf metric {
                  type uint32;
                  description "metric value";
               }
            }
         }
      }
   }

   grouping mpls-label-stack {
      description
         "Grouping for MPLS label stack";

      list labels {
         key "index";
         description
            "Stack containing MPLS labels";

         leaf index {
            type uint32;
            description "A unique ID of an MPLS label in labels
            list";
         }
         leaf label {
            type rt-types:mpls-label;
            description
              "MPLS label value";
         }
      }
   }

   grouping srv6-sid-stack {
      description
       "Grouping for SRv6 label stack";

      list sids {
        key "index";
        description
          "Stack containing SRv6 SIDs";

        leaf index {
           type uint32;
           description "A unique ID of an SRv6 sid in sid list";
        }
        leaf sid {
           type srv6-types:srv6-sid;
           description
             "SRv6 sid value";
        }
      }
   }
   grouping path-forwarding-info {
      description
       "cats forwarding path information";

      leaf next-hop-address {
         type inet:ip-address;
         description "Nexthop address";
      }
      leaf interface {
         type if:interface-ref;
         description "Outgoing interface handle";
      }
      container sid-list {
         description
           "Outgoing sid stack";
         choice dataplanetype {
            description
              "Outgoing sids dataplane choice";
            case mpls {
              uses mpls-label-stack;
            }
            case srv6 {
               uses srv6-sid-stack;
            }
         }
      }
   }

   container forwarding-paths {
      description
        "Forwarding state of paths";
      list forwarding-path {
         key "cs-id csci-id";
         description "Forwarding state of paths";
         leaf cs-id {
            type cs-id;
            description "CATS cs-id";
         }
         leaf csci-id {
            type csci-id;
            description "CATS csci-id";
         }
         uses service-policy-type;
         leaf weight {
            type uint32;
            description "Path's weight for W-ECMP balancing";
         }
         list forwarding-path-state {
           key "path-id";
           description "CATS Forwarding path state";
           leaf path-id {
               type uint8;
               description "Primary path id";
            }
            uses path-forwarding-info;
         }
      }
  }

  container flow-entrys {
     description "flow entry";
     list flow-entry {
        key "source-address dest-address source-port dest-port
             protocol";
        description "flow entry";
        leaf source-address {
           type inet:ip-address;
           description "source address of flow";
        }
        leaf dest-address {
           type inet:ip-address;
           description "destination address of flow";
        }
        leaf source-port {
           type uint16;
           description "source port of flow";
        }
        leaf dest-port {
           type uint16;
           description "destination port of flow";
        }
        leaf protocol {
           type uint16;
           description "protocol of flow";
        }
        leaf cs-id {
           type cs-id;
           description "CATS cs-id";
        }
        leaf csci-id {
           type csci-id;
           description "CATS csci-id";
        }
        leaf affinity {
           type uint32;
           description "affinity";
        }
        uses path-forwarding-info;
        container flow-statistics {
           description "flow statistics";
           leaf pkts {
              type uint64;
              description "pkts";
           }
           leaf octets {
              type uint64;
              description "octets";
           }
        }
     }
   }

   container notify {
      description "event notify";
      leaf entry-limit-reached {
         type boolean;
         description "entry limit reached";
      }
      leaf flow-limit-reached {
         type boolean;
         description "flow entry limit reached";
      }
   }
}
