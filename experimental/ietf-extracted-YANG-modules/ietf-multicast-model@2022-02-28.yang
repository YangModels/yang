module ietf-multicast-model {

  yang-version 1.1;

  namespace "urn:ietf:params:xml:ns:yang:ietf-multicast-model";
  prefix ietf-multicast-model;

  import ietf-yang-types {
    prefix "yang";
    reference
      "RFC 6991: Common YANG Data Types";
  }

  import ietf-inet-types {
    prefix "inet";
    reference
      "RFC 6991: Common YANG Data Types";
  }
  import ietf-routing-types {
    prefix "rt-types";
    reference
      "RFC 8294: Common YANG Data Types for the Routing Area";
  }
  import ietf-routing {
    prefix "rt";
    reference
      "RFC 8349: A YANG Data Model for Routing Management
                 (NMDA Version)";
  }

  organization " IETF MBONED (MBONE Deployment) Working Group";
  contact
    "WG List:  <mailto:mboned@ietf.org>

     Editor:   Zheng Zhang
               <mailto:zhang.zheng@zte.com.cn>
     Editor:   Cui Wang
               <mailto:lindawangjoy@gmail.com>
     Editor:   Ying Cheng
               <mailto:chengying10@chinaunicom.cn>
     Editor:   Xufeng Liu
               <mailto:xufeng.liu.ietf@gmail.com>
     Editor:   Mahesh Sivakumar
               <mailto:sivakumar.mahesh@gmail.com>
    ";

  // RFC Ed.: replace XXXX with actual RFC number and remove
  // this note

  description
    "The module defines the YANG definitions for multicast service
     management.

     Copyright (c) 2021 IETF Trust and the persons identified as
     authors of the code.  All rights reserved.

     Redistribution and use in source and binary forms, with or
     without modification, is permitted pursuant to, and subject
     to the license terms contained in, the Simplified BSD
     License set forth in Section 4.c of the IETF Trust's Legal
     Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2022-02-28 {
    description
      "Initial revision.";
    reference
      "RFC XXXX: A YANG Data Model for multicast YANG.";
  }

  /*
   *feature
   */
  feature bier {
    description
      "Cooperation with BIER technology.";
    reference
      "RFC 8279:
         Multicast Using Bit Index Explicit Replication (BIER).";
  }

  /*
   *typedef
   */
  typedef ip-multicast-source-address {
    type union {
      type enumeration {
        enum * {
          description
            "Any source address.";
        }
      }
      type inet:ipv4-address;
      type inet:ipv6-address;
    }
    description
      "Multicast source IP address type.";
  }
  typedef tree-sid {
    type union {
      type rt-types:mpls-label;
      type inet:ip-prefix;
    }
    description
      "The type of the Segment Identifier of a Replication segment
       is a SR-MPLS label or a SRv6 SID.";
  }
  typedef virtual-type {
    type enumeration {
      enum vxlan {
        description
          "The VXLAN encapsulation is used for flow encapsulation.";
        reference
          "RFC 7348: Virtual eXtensible Local Area Network (VXLAN):
           A Framework for Overlaying Virtualized Layer 2 Networks
           over Layer 3 Networks.";
      }
      enum nvgre {
        description
          "The NVGRE encapsulation is used for flow encapsulation.";
        reference
          "RFC 7637: NVGRE: Network Virtualization Using Generic
           Routing Encapsulation.";
      }
      enum geneve {
        description
          "The GENEVE encapsulation is used for flow encapsulation.";
        reference
          "RFC 8926: Geneve: Generic Network
           Virtualization Encapsulation.";
      }
    }
    description
      "The encapsulation type used for the flow.
       When this type is set, the associated vni-value
       MUST be set.";
  } // virtual-type

  /*
   * Identities
   */

  identity multicast-model {
    base "rt:control-plane-protocol";
    description "Identity for the multicast model.";
  }
  identity overlay-type {
    description
      "Base identity for the type of multicast overlay technology.";
  }
  identity transport-type {
    description "Identity for the multicast transport technology.";
  }
  identity underlay-type {
    description "Identity for the multicast underlay technology.";
  }
  identity overlay-pim {
    base overlay-type;
    description
      "Using PIM as multicast overlay technology.
       For example, as BIER overlay.";
    reference
      "I-D.ietf-bier-pim-signaling:
         PIM Signaling Through BIER Core.";
  }
  identity mld {
    base overlay-type;
    description
      "Using MLD as multicast overlay technology.
       For example, as BIER overlay.";
    reference
      "I-D.ietf-bier-mld:
         BIER Ingress Multicast Flow Overlay
         using Multicast Listener Discovery Protocols.";
  }
  identity mld-snooping {
    base overlay-type;
    description
      "Using MLD as multicast overlay technology.
       For example, as BIER overlay.";
    reference
      "RFC 4541:
         Considerations for Internet Group Management
         Protocol (IGMP) and Multicast Listener
         Discovery (MLD) Snooping Switches.";
  }
  identity evpn {
    base overlay-type;
    description
      "Using EVPN as multicast overlay technology.";
    reference
      "RFC 7432: BGP MPLS-Based Ethernet VPN.
       I-D.ietf-bess-evpn-bum-procedure-updates:
         Updates on EVPN BUM Procedures.
       I-D.ietf-bier-evpn: EVPN BUM Using BIER.";
  }
  identity mvpn {
    base overlay-type;
    description
      "Using MVPN as multicast overlay technology.";
    reference
      "RFC 6513: Multicast in MPLS/BGP IP VPNs.
       RFC 7716:
         Global Table Multicast with BGP Multicast VPN
         (BGP-MVPN) Procedures.";
  }
  identity bier {
    base transport-type;
    description
      "Using BIER as multicast transport technology.";
    reference
      "RFC 8279:
         Multicast Using Bit Index Explicit Replication (BIER).";
  }
  identity bier-te {
    base transport-type;
    description
      "Using BIER-TE as multicast transport technology.";
    reference
      "I-D.ietf-bier-te-arch:
         Traffic Engineering for Bit Index Explicit Replication
         (BIER-TE)";
  }
  identity mldp {
    base transport-type;
    description
      "Using mLDP as multicast transport technology.";
    reference
      "RFC 6388:
         Label Distribution Protocol Extensions
         for Point-to-Multipoint and Multipoint-to-Multipoint
         Label Switched Paths.
       I-D.ietf-mpls-mldp-yang: YANG Data Model for MPLS mLDP.";
  }
  identity rsvp-te-p2mp {
    base transport-type;
    description
      "Using P2MP TE as multicast transport technology.";
    reference
      "RFC 4875:
         Extensions to Resource Reservation Protocol
         - Traffic Engineering (RSVP-TE) for Point-to-Multipoint
         TE Label Switched Paths (LSPs).";
  }
  identity sr-p2mp {
    base transport-type;
    description
      "Using Segment Routing  as multicast transport technology.";
    reference
      "I-D.ietf-pim-sr-p2mp-policy:
         Segment Routing Point-to-Multipoint Policy.";
  }
  identity cisco-mdt {
    base transport-type;
    description
      "Using cisco MDT for multicast transport technology.";
    reference
      "RFC 6037:
         Cisco Systems' Solution for Multicast in BGP/MPLS IP VPNs";
  }
  identity pim {
    base transport-type;
    base underlay-type;
    description
      "Using PIM as multicast transport technology.";
    reference
      "RFC 7761:
         Protocol Independent Multicast - Sparse Mode
         (PIM-SM): Protocol Specification (Revised).";
  }
  identity bgp {
    base underlay-type;
    description
      "Using BGP as underlay technology to build the multicast
       transport layer. For example, using BGP as BIER underlay.";
    reference
      "I-D.ietf-bier-idr-extensions: BGP Extensions for BIER.";
  }
  identity ospf  {
    base underlay-type;
    description
      "Using OSPF as multicast underlay technology.
       For example, using OSPF as BIER underlay.";
    reference
      "RFC 8444:
         OSPFv2 Extensions for Bit Index Explicit Replication (BIER),
       I-D.ietf-bier-ospfv3-extensions:
         OSPFv3 Extensions for BIER.";
  }
  identity isis {
    base underlay-type;
    description
      "Using ISIS as multicast underlay technology.
       For example, using ISIS as BIER underlay.";
    reference
      "RFC 8401:
         Bit Index Explicit Replication (BIER) Support via IS-IS";
  }
  identity babel {
    base underlay-type;
    description
      "Using BABEL as multicast underlay technology.
       For example, using BABEL as BIER underlay.";
    reference
      "RFC 8966: The Babel Routing Protocol
       I-D.zhang-bier-babel-extensions: BIER in BABEL";
  }
  identity rift {
    base underlay-type;
    description
      "Using RIFT as multicast underlay technology.
       For example, using RIFT as BIER underlay.";
    reference
      "I-D.ietf-rift-rift: RIFT: Routing in Fat Trees.
       I-D.zzhang-bier-rift: Supporting BIER with RIFT";
  }

  grouping general-multicast-key {
    description
      "The general multicast keys. They are used to distinguish
       different multicast service.";
    leaf vpn-rd {
      type rt-types:route-distinguisher;
      description
        "A Route Distinguisher used to distinguish
         routes from different MVPNs.";
      reference
        "RFC 8294: Common YANG Data Types for the Routing Area.
         RFC 6513: Multicast in MPLS/BGP IP VPNs.";
    }
    leaf source-address {
      type ip-multicast-source-address;
      description
        "The IPv4/IPv6 source address of the multicast flow. The
         value set to zero means that the receiver interests
         in all source that relevant to one given group.";
    }
    leaf group-address {
      type rt-types:ip-multicast-group-address;
      description
        "The IPv4/IPv6 group address of multicast flow. This
         type represents a version-neutral IP multicast group
         address. The format of the textual representation
         implies the IP version.";
      reference
        "RFC 8294: Common YANG Data Types for the Routing Area.";
    }
    leaf mac-address {
      type yang:mac-address;
      description
        "The mac address of flow. In the EVPN situation, the L2
         flow that is called
         BUM (Broadcast, Unknown Unicast, Multicast)
         can be sent to the other PEs that
         are in a same broadcast domain.";
      reference
        "RFC 6991: Common YANG Data Types.
         RFC 7432: BGP MPLS-Based Ethernet VPN.";
    }
    leaf vni-value {
      type uint32;
      description
        "The value of Vxlan network identifier, virtual subnet ID
         or virtual net identifier. This value and vni-type is used
         to indicate a specific virtual multicast service.";
    }
  } // general-multicast-key

  grouping encap-type {
    description
      "The encapsulation type used for flow forwarding.
       This encapsulation acts as the inner encapsulation,
       as compare to the outer multicast-transport encapsulation.";
    choice encap-type {
      case mpls {
        description "The BIER forwarding depends on mpls.";
        reference
          "RFC 8296: Encapsulation for Bit Index Explicit
           Replication (BIER) in MPLS and Non-MPLS Networks.";
      }
      case eth {
        description "The BIER forwarding depends on ethernet.";
        reference
          "RFC 8296: Encapsulation for Bit Index Explicit
           Replication (BIER) in MPLS and Non-MPLS Networks.";
      }
      case ipv6 {
        description "The BIER forwarding depends on IPv6.";
        reference
          "I-D.ietf-bier-bierin6: BIER in IPv6 (BIERin6)";
      }
      description "The encapsulation type in BIER.";
    }
  } // encap-type

  grouping bier-key {
    description
      "The key parameters set for BIER/BIER TE forwarding.";
    reference
      "RFC 8279: Multicast Using Bit Index Explicit Replication
       (BIER).";

    leaf sub-domain {
      type uint16;
      description
        "The subdomain id that the multicast flow belongs to.";
    }
    leaf bitstringlength {
      type uint16;
      description
        "The bitstringlength used by BIER forwarding.";
    }
    leaf set-identifier {
      type uint16;
      description
        "The set identifier used by the multicast flow.";
    }
    uses encap-type;
  }

  grouping transport-tech {
    description
      "The transport technology selected for the multicast service.
       For one specific multicast flow, it's better to use only one
       transport technology for forwarding.";

    leaf type {
      type identityref {
        base transport-type;
      }
      description "The type of transport technology";
    }
    container bier {
      when "../type = 'ietf-multicast-model:bier'" {
         description
           "Only when BIER is used as transport technology.";
      }
      description
        "The transport technology is BIER. The BIER technology
         is introduced in RFC8279. The parameters are consistent
         with the definition in BIER YANG data model.";
      reference
        "I-D.ietf-bier-bier-yang:
           YANG Data Model for BIER Protocol.";
      uses bier-key;
    }
    container bier-te {
      when "../type = 'ietf-multicast-model:bier-te'" {
         description
           "Only when BIER-TE is used as transport technology.";
      }
      description
        "The BIER-TE parameter that may need to be set.
         The parameters are consistent with the definition in
         BIER and BIER TE YANG data model.";
      reference
        "I-D.ietf-bier-bier-yang:
           YANG Data Model for BIER Protocol
         I-D.ietf-bier-te-yang:
           A YANG data model for Traffic Engineering for Bit Index
           Explicit Replication (BIER-TE)";

      uses bier-key;

      list bitstring {
        key "name";
        leaf name {
          type string;
          description "The name of the bitstring";
        }
        list bier-te-adj {
          key "adj-id";
          leaf adj-id {
            type uint16;
            description
              "The link adjacency ID used for BIER TE forwarding.";
          }
          description
            "The adjacencies ID used for BIER TE bitstring
             encapsulation.";
        }
        description
          "The bitstring name and detail used for BIER TE
           forwarding encapsulation. One or more bitstring can be
           used for backup path.";
      }
    }
    container cisco-mdt {
      when "../type = 'ietf-multicast-model:cisco-mdt'" {
         description
           "Only when cisco MDT is used as transport technology.";
      }
      description "The MDT parameter that may need to be set.";
      leaf p-group {
        type rt-types:ip-multicast-group-address;
        description
          "The address of p-group. It is used to encapsulate
           and forward flow according to multicast tree from
           ingress node to egress nodes.";
      }
    }
    container rsvp-te-p2mp {
      when "../type = 'ietf-multicast-model:rsvp-te-p2mp'" {
       description
         "Only when RSVP TE P2MP is used as transport technology.";
      }
      description
        "The parameter that may be set. They are consistent with
        the definition in TE data model.";
      reference
        "RFC 8776: Common YANG Data Types for Traffic Engineering";

      leaf template-name {
        type string {
          pattern '/?([a-zA-Z0-9\-_.]+)(/[a-zA-Z0-9\-_.]+)*';
        }
        description
          "A type for the name of a TE node template or TE link
           template.";
      }
    }
    container pim {
      when "../type = 'ietf-multicast-model:pim'" {
         description
           "Only when PIM is used as transport technology.";
      }
      description "The PIM parameter that may need to be set.";
      uses pim;
    }
    container sr-p2mp {
      when "../type = 'ietf-multicast-model:sr-p2mp'" {
         description
           "Only when segment routing P2MP is used as transport
            technology.";
      }
      description "The SR-P2MP parameter that may need to be set.";
      list ir-segment-lists {
        key "name";
        leaf name {
          type string;
          description "Segment-list name";
        }
        description
          "The segment lists used for ingress replication.
           The name refers a segment list.";
      }

      list replication-segment {
        key "replication-id node-id";
        leaf replication-id {
          type tree-sid;
          description
            "The identifier for a Replication segment that is
             unique in context of the Replication Node.
             This is a SR-MPLS label or a SRv6 SID";
        }
        leaf node-id {
          type inet:ip-address;
          description
            "The address of the Replication Node that the
             Replication segment is for.";
        }
        description
          "A Multi-point service delivery could be realized via
           P2MP trees in a Segment Routing domain.
           It may consist of one or more Replication segment";
        reference
          "I-D.ietf-spring-sr-replication-segment:
             SR Replication Segment for Multi-point Service
             Delivery.";
      }
    } // sr-p2mp
  } // transport-tech

  grouping underlay-tech {
    description
      "The underlay technology selected for the transport layer.
       The underlay technology has no straight relationship with
       the multicast overlay, it is used for transport path
       building, for example BIER forwarding path building.";

    leaf type {
      type identityref {
        base underlay-type;
      }
      description "The type of underlay technology";
    }
    container ospf {
      when "../type = 'ietf-multicast-model:ospf'" {
         description
           "Only when OSPF is used as underay technology.";
      }
      description
        "If OSPF protocol supports multiple topology feature,
         the associated topology name may be assigned.
         In case the topology name is assigned, the specific
         OSPF topology is used for underly to building the
         transport layer.";
      reference
        "RFC 4915: Multi-Topology Routing";
      leaf topology {
        type string;
        description
          "The designed topology name of ospf protocol.";
      }
    }
    container isis {
      when "../type = 'ietf-multicast-model:isis'" {
         description
           "Only when ISIS is used as underay technology.";
      }
      description
        "If ISIS protocol supports multiple topology feature,
         the associated topology name may be assigned.
         In case the topology name is assigned, the specific
         ISIS topology is used for underly to building the
         transport layer.";
      reference
        "RFC 5120: M-IS-IS: Multi Topology Routing in IS-IS";
      leaf topology {
        type string;
        description
          "The designed topology name of isis protocol.";
      }
    }
    container pim {
      when "../type = 'ietf-multicast-model:pim'" {
         description
           "Only when PIM is used as underay technology.";
      }
      description "The PIM parameter that may need to be set.";
      uses pim;
    }
  } // underlay-tech

  /*overlay*/

  grouping overlay-tech {
    container dynamic-overlay {
      leaf type {
        type identityref {
          base overlay-type;
        }
        description "The type of overlay technology";
      }
      container mld {
        when "../type = 'ietf-multicast-model:mld'" {
           description
             "Only when MLD is used as overlay technology.";
        }
        description "The MLD parameter that may need to be set.";
        leaf mld-instance-group {
          type rt-types:ip-multicast-group-address;
          description
            "The multicast address used for multiple MLD instance
             support.";
        }
      }
      description
        "The dynamic overlay technologies and associated parameter
         that may be set.";
    }
    description "The overlay technology used for multicast service.";
  } // overlay-tech

  /*transport*/

  grouping pim {
    description
      "The required information of pim transportion.";
    leaf source-address {
      type ip-multicast-source-address;
      description
        "The IPv4/IPv6 source address of the multicast flow. The
         value set to zero means that the receiver interests
         in all source that relevant to one given group.";
    }
    leaf group-address {
      type rt-types:ip-multicast-group-address;
      mandatory true;
      description
        "The IPv4/IPv6 group address of multicast flow. This
         type represents a version-neutral IP multicast group
         address. The format of the textual representation
         implies the IP version.";
    }
    reference
      "RFC 7761: Protocol Independent Multicast - Sparse Mode
                 (PIM-SM): Protocol Specification (Revised).";
  } //pim

  /*underlay*/

  container multicast-model {
    description
      "The model of multicast YANG data. Include keys, overlay,
       transport and underlay.";

    list multicast-keys{
      key "vpn-rd source-address group-address mac-address
           vni-value";
      uses general-multicast-key;

      container multicast-overlay {
        description
          "The overlay information of multicast service.
           Overlay technology is used to exchange multicast
           flows information. Overlay technology may not be
           used in SDN controlled completely situation, but
           it can be used in partial SDN controlled situation
           or non-SDN controlled situation. Different overlay
           technologies can be choosed according to different
           deploy consideration.";

        leaf vni-type {
          type virtual-type;
          description
            "The encapsulated type for the multicast flow,
             it is used to carry the virtual network identifier
             for the multicast service.";
        }

        container ingress-egress {
          description
            "The ingress and egress nodes address collection.
             The ingress node may use the egress nodes set
             directly to encapsulate the multicast flow by
             transport technology.";

          list ingress-nodes {
            key "ingress-node";
            description
              "The egress nodes of multicast flow.";

            leaf ingress-node {
              type inet:ip-address;
              description
                "The ip address of ingress node for one or more
                 multicast flow. Or the ingress node of MVPN and
                 BIER. In MVPN, this is the address of ingress
                 PE; in BIER, this is the BFR-prefix of ingress
                 nodes.
                 Two or more ingress nodes may existed for the
                 redundant ingress node protection.";
            }
          }

          list egress-nodes {
            key "egress-node";
            description
              "The egress multicast nodes of the multicast flow.
               Or the egress node of MVPN and BIER. In MVPN, this
               is the address of egress PE; in BIER, this is the
               BFR-prefix of ingress nodes.";

            leaf egress-node {
              type inet:ip-address;
              description
                "The ip-address set of egress multicast nodes.";
            }
          }
        }

        container bier-ids {
          if-feature bier;
          description
            "The BFR-ids of ingress and egress BIER nodes for
             one or more multicast flows. This overlay is used
             with BIER transport technology. The egress nodes
             set can be used to encapsulate the multicast flow
             directly in the ingress node.";
          reference
            "RFC 8279: Multicast Using Bit Index Explicit
             Replication (BIER)";

          leaf sub-domain {
            type uint16;
            description
              "The sub-domain that this multicast flow belongs to.";
          }
          list ingress-nodes {
            key "ingress-node";
            description
              "The ingress nodes of multicast flow.";
            leaf ingress-node {
              type uint16;
              description
                "The ingress node of multicast flow. This is the
                 BFR-id of ingress nodes.";
            }
          }
          list egress-nodes {
            key "egress-node";
            description
              "The egress nodes of multicast flow.";

            leaf egress-node {
              type uint16;
              description
                "The BFR-ids of egress multicast BIER nodes.";
            }
          }
        }
        uses overlay-tech;
      }

      container multicast-transport {
        description
          "The transportion of multicast service. Transport
           protocol is responsible for delivering multicast
           flows from ingress nodes to egress nodes with or
           without specific encapsulation. Different transport
           technology can be choosed according to different
           deploy consideration. Once a transport technology
           is choosed, associated protocol should be triggered
           to run.";

        uses transport-tech;
      }
      container multicast-underlay {
        description
          "The underlay of multicast service. Underlay protocol
           is used to build transport layer. Underlay protocol
           need not be assigned in ordinary network since
           existed underlay protocol fits well, but it can be
           assigned in particular networks for better
           controll. Once a underlay technology is choosed,
           associated protocol should be triggered to run.";

        uses underlay-tech;
      }
      description
        "The model of multicast YANG data. Include keys,
         overlay, transport and underlay.";
    }
  }

  /*Notifications*/

  notification ingress-egress-event {
    leaf event-type {
      type enumeration {
        enum down {
          description
            "There is something wrong with ingress or egress node,
             and node can't work properlay.";
        }
        enum protocol-enabled {
          description
            "The protocol that is used for multicast
             flows have been enabled.";
        }
        enum protocol-disabled {
          description
            "The protocol that is used by multicast
             flows have been disabled.";
        }
      }
      description "Event type.";
    }
    container multicast-key {
      uses general-multicast-key;
      description
        "The associated multicast keys that are influenced by
         ingress or egress node failer.";
    }
    uses overlay-tech;

    container transport-tech {
      description
        "The modules can be used to forward multicast flows.";
      uses transport-tech;
    }

    container underlay-tech {
      description
        "There is something wrong with the module which is
         used to build multicast transport layer.";
      uses underlay-tech;
    }
    description
      "Notification events for the ingress or egress nodes. Like
       node failer, overlay/ transport/ underlay module
       loading/ unloading. And the potential failer about some
       multicast flows and associated
       overlay/ transport/ underlay technologies.";
  }
}
