module ietf-yang-revisions {
  yang-version 1.1;
  namespace "urn:ietf:params:xml:ns:yang:ietf-yang-revisions";
  prefix rev;

  import ietf-yang-types {
    prefix yang;
    reference
      "XXXX [ietf-netmod-rfc6991-bis]: Common YANG Data Types";
  }

  organization
    "IETF NETMOD (Network Modeling) Working Group";
  contact
    "WG Web:   <https://datatracker.ietf.org/wg/netmod/>
     WG List:  <mailto:netmod@ietf.org>

     Author:   Benoit Claise
               <mailto:bclaise@cisco.com>

     Author:   Joe Clarke
               <mailto:jclarke@cisco.com>

     Author:   Reshad Rahman
               <mailto:rrahman@cisco.com>

     Author:   Robert Wilton
               <mailto:rwilton@cisco.com>

     Author:   Kevin D'Souza
               <mailto:kd6913@att.com>

     Author:   Balazs Lengyel
               <mailto:balazs.lengyel@ericsson.com>

     Author:   Jason Sterne
               <mailto:jason.sterne@nokia.com>";
  description
    "This YANG 1.1 module contains definitions and extensions to
     support updated YANG revision handling.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.
  // RFC Ed.: replace XXXX (inc above) with actual RFC number and
  // remove this note.

  revision 2019-09-18 {
    description
      "Initial version.";
    reference
      "XXXX: Updated YANG Module Revision Handling";
  }

  typedef revision-label {
    type string {
      length "1..255";
      pattern '[^\s@]+';
      pattern '\d{4}-\d{2}-\d{2}' {
        modifier invert-match;
      }
    }
    description
      "A label associated with a YANG revision.

       Excludes spaces and '@'.  MUST NOT match revision-date.

       Revision labels that classify as YANG semantic versions,
       as defined by the ietf-yang-semver:version typedef,
       MUST conform to the versioning behaviour defined in
       XXXX [verdt]: YANG Semantic Versioning.";
    reference
      "XXXX: Updated YANG Module Revision Handling;
       Section 3.3, Revision label";
  }

  typedef revision-date-or-label {
    type union {
      type yang:revision-identifier;
      type revision-label;
    }
    description
      "Represents either a YANG revision date or a revision label";
  }

  extension nbc-changes {
    description
      "This statement is used to indicate YANG module revisions that
       contain non-backwards-compatible changes.

       Each 'revision' statement MAY have a single 'nbc-changes'
       substatement.

       If a revision of a YANG module contains changes, relative to
       the preceding revision in the revision history, that do not
       conform to the module update rules defined in RFC-XXX, then
       the 'nbc-changes' statement MUST be added as a substatement to
       the revision statement.

       Conversely, if a revision of a YANG module only contains
       changes, relative to the preceding revision in the revision
       history, that are classified as 'backwards-compatible' then
       the revision statement MUST NOT contain any 'nbc-changes'
       substatement.";

    reference
      "XXXX: Updated YANG Module Revision Handling;
       Section 3.2, nbc-changes revision extension statement";
  }

  extension revision-label {
    argument revision-label;
    description
      "The revision label can be used to provide an additional
       versioning identifier associated with the revision.  E.g., one
       option for a versioning scheme that could be used is [TODO -
       Reference semver draft].

       The format of the revision-label argument MUST conform to the
       pattern defined for the revision-label typedef.
       Each 'revision' statement MAY have a single 'revision-label'
       substatement.

       Revision labels MUST be unique amongst all revisions of a
       module.";

    reference
      "XXXX: Updated YANG Module Revision Handling;
       Section 3.3, Revision label";
  }

  extension revision-or-derived {
    argument revision-date-or-label;
    description
      "Restricts the revision of the module that may be imported to
       one that matches or is derived from the specified
       revision-date or revision-nlabel.

       The argument value MUST conform to the
       'revision-date-or-label' defined type.

       Each 'import' statement MAY have one or more
       'revision-or-derived' substatements.  If specified multiple
       times, then any module revision that satifies at least one of
       the 'revision-or-derived' statements is an acceptable revision
       for import.

       An 'import' statement MUST NOT contain both a
       'revision-or-derived' extension statement and a
       'revision-date' statement.

       A particular revision of an imported module satisfies an
       import's 'revision-or-derived' extension statement if the
       imported module's revision history contains a revision
       statement with a matching revision date or revision label.

       The 'revision-or-derived' extension statement does not
       gaurantee that all module revisions that satisfy an import
       statement are necessarily compatible, it only gives an
       indication that the revisions are more likely to be
       compatible.";

    reference
      "XXXX: Updated YANG Module Revision Handling;
       Section 4, Import by derived revision";
  }

  extension status-description {
    argument description;

    description
      "Freeform text that describes why a given node has been
       deprecated or made obsolete.  E.g., the description could be
       used to give the reason for removal, or it could point to an
       alternative schema elements that can be used in lieu of the
       given node.

       Each 'status' statement MAY have a single 'status-description'
       substatement.";

    reference
      "XXXX: Updated YANG Module Revision Handling;
       Section 3.4, YANG status description extension statement";
  }
}
