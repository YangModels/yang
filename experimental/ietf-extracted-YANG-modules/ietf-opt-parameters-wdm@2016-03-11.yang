module ietf-opt-parameters-wdm {
   namespace "urn:ietf:params:xml:ns:yang:ietf-opt-parameters-wdm";
   prefix iietf-opt-parameters-wdm;

     import ietf-interfaces {
       prefix if;
     }

     import iana-if-type {
       prefix ianaift;
     }

     organization
       "IETF CCAMP
       Working Group";

     contact
       "WG Web:   <http://tools.ietf.org/wg/ccamp/>
        WG List:  <mailto:ccamp@ietf.org>

        Editor:   Gabriele Galimberti
                  <mailto:ggalimbe@cisco.com>";

     description
       "This module contains a collection of YANG definitions for
        collecting and configuring Optical Parameters
        in Optical Networks and calculate the circuit feasibility.

        Copyright (c) 2016 IETF Trust and the persons identified
        as authors of the code.  All rights reserved.

        Redistribution and use in source and binary forms, with or
        without modification, is permitted pursuant to, and
        subject to the license terms contained in, the Simplified
        BSD License set forth in Section 4.c of the IETF Trust's
        Legal Provisions Relating to IETF Documents
        (http://trustee.ietf.org/license-info).";

    revision "2016-03-11" {
           description
               "Initial revision.";
           reference
               "RFC XXXX: A YANG Data Model for Optical Paramenters
                of DWDM Networks
                ";

    }

 typedef tilt-t {
    type decimal64 {
      fraction-digits 2;
      range "-5..5";
    }
    description "Tilt Type";
  }

  typedef signal-output-power-t {
      type decimal64 {
        fraction-digits 2;
        range "-10..30";
      }
    description "
      Amplifier Power provisioning ";
  }

  typedef active-channel-t {
    type union {
      type uint8 {
        range "0..200";
      }
    }
    description "
      Number of channels active on a span - and on an amplifier ";
  }

  typedef dbm-t {
    type decimal64 {
      fraction-digits 2;
      range "-50..-30 | -10..5 | 10000000";
    }
    description "
      Amplifier Power in dBm ";
  }

  typedef attenuator-t {
    type decimal64 {
      fraction-digits 2;
      range "-15..-5";
    }
    description "
      Attenuation value (attenuator) applied after the Amplifier ";
  }

  grouping channel-ITU {
  description "channel-ITU";
  container channel-t {
        description "wavelength notation according to RFC-6205";
         leaf grid {
           type uint32;
           description "grid type e.g.: 0=reserved, 1=DWDM, 2=CWDM";
         }
         leaf channel-spacing {
           type uint32;
           description "DWDM grid e.g.: 1=100GHz, 2=50GHz, 3=25GHz";
         }
         leaf identifier {
           type uint32;
           description "Channel identifier";
         }
         leaf n {
           type uint32;
           description "N Value (Channel n-m notation)";
         }
       }
     }

  grouping channel-flex {
    description "channel-flex";
    container channel-n-m {
      description "Channel N / M Notation to describe the
                   MEdiachannel";
       leaf grid {
         type uint32;
          description "grid type e.g.: 0=reserved, 1=DWDM, 2=CWDM";
         }
       leaf channel-spacing {
         type uint32;
          description "DWDM grid e.g.: 1=100GHz, 2=50GHz, 3=25GHz";
    }
       leaf n {
          type uint32;
           description "N Value (Channel n-m notation)";
    }
       leaf m {
         type uint32;
            description "M Value (Channel n-m notation)";
      }
    }
  }

  augment "/if:interfaces/if:interface" {
    when "if:type = 'ianaift:opticalTransport'" {
        description "Specific optical-transport Interface Data";
    }
    description "Specific optical-transport Interface Data";
    container optical-transport {
      description "Specific optical-transport Data";

      leaf attenuator-value {
        type attenuator-t;
        description "External attenuator value ";
      }

      leaf offset {
        type decimal64 {
          fraction-digits 2;
          range "-30..30";
        }
        description "Raman and power amplifiers offset";
      }

      leaf channel-power-ref {
        type decimal64 {
          fraction-digits 2;
          range "-10..15";
        }
        description "Optical power per channel";
      }

      leaf tilt-calibration {
        type tilt-t;
        description "Amplifier Tilt tuning";
      }
     }
     uses channel-ITU;
     uses channel-flex;
  }

   grouping opwr-threshold-warning-grp {
    description "
      Minimum Optical Power threshold
       - this is used to rise Power alarm ";
    leaf opwr-min {
      type dbm-t;
      units "dBm";
      default -1;
      description "Minimum Power Value";
    }

    leaf opwr-min-clear {
      type dbm-t;
      units "dBm";
      default -1;
      description "threshold to clear Minimum Power value Alarm";
    }

    leaf opwr-max {
      type dbm-t;
      units "dBm";
      default 1;
      description "
        Maximum Optical Power threshold
         - this is used to rise Power alarm ";
    }
  }

  grouping gain-degrade-alarm-grp {
    description "
      Low Optical Power gain threshold
       - this is used to rise Power alarm ";
    leaf gain-degrade-low {
      type dbm-t;
      units "dBm";
      default -1;
      description "Low Gain Degrade Value";
    }
  }
  leaf gain-degrade-high {
      type dbm-t;
      units "dBm";
      default 1;
      description "
        High Optical Power gain threshold
         - this is used to rise Power alarm ";
    }
  }
