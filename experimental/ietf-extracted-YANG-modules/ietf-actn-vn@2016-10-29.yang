module ietf-actn-vn {

    namespace "urn:ietf:params:xml:ns:yang:ietf-actn-vn";

    prefix "vn";

    /* Import TE generic types */
    import ietf-te-types {
        prefix "te-types";
    }

    import ietf-te-topology {
        prefix "tet";
    }

    import ietf-te {
        prefix "te";
    }

    import ietf-pcep {
       prefix "pcep";
    }

    organization
        "IETF Traffic Engineering Architecture and Signaling (TEAS)
        Working Group";

    contact
        "Editor: Young Lee <leeyoung@huawei.com>";

    description
        "This module contains a YANG module for the ACTN VN. It
        describes a VN operation module that takes place in the
        context of the CNC-MDSC Interface (CMI) of the ACTN
        architecture where the CNC is the actor of a VN Instantiation
        /modification /deletion.";

    revision 2016-10-29 {
        description
            "initial version.";
        reference
            "TBD";
    }

    identity path-metric-delay {
       base te-types:path-metric-type;
       description
         "delay  path metric";
     }

     identity path-metric-delay-variation {
       base te-types:path-metric-type;
       description
         "delay-variation path metric";
     }

     identity path-metric-loss {
       base te-types:path-metric-type;
       description
         "loss path metric";
     }

     identity path-metric-hop {
       base te-types:path-metric-type;
       description
         "hop path metric";
     }

    /*
     * Groupings
     */

    grouping access-point{
        description
            "AP related information";
        leaf access-point-id {
            type uint32;
            description
                "unique identifier for the referred
                access point";
        }
        leaf access-point-name {
            type string;
            description
                "ap name";
        }
        leaf max-bandwidth {
            type decimal64 {

                fraction-digits 2;
                range "0..max";
            }
            description
                "max bandwidth of the AP";
        }
        leaf avl-bandwidth {
            type decimal64 {
                fraction-digits 2;
                range "0..max";
            }
            description
                "available bandwidth of the AP";
        }
        /*add details and any other properties of AP,
        not associated by a VN
        CE port, PE port etc.

        This link may not be in the TE topology model(?)
        thus reference to that model would be incorrect
        */
    }//access-point

    grouping vn-member {
        description
            "vn-member is described by this container";
        leaf vn-member-id {
            type uint32;
            description
                "vn-member identifier";
        }
        container src
        {
            description
                "the source of VN Member";
            leaf src {
                type leafref {
                    path "/actn/ap/access-point-list/access-point-id";
                }
                description
                    "reference to source AP";
            }
            leaf src-vn-ap-id{
                type uint32;
                description

                    "vn-ap-id";
            }
            leaf multi-src {
                type boolean;
                description
                    "Is source part of multi-source, where
                    only one of the source is enabled";
            }
        }
        container dest
        {
            description
                "the destination of VN Member";
            leaf dest {
                type leafref {
                    path "/actn/ap/access-point-list/access-point-id";
                }
                description
                    "reference to destination AP";
            }
            leaf dest-vn-ap-id{
                type uint32;
                description
                    "vn-ap-id";
            }
            leaf multi-dest {
                type boolean;
                description
                    "Is destination part of multi-destination, where
                    only one of the destination is enabled";
            }
        }
    }//vn-member

    grouping policy {
        description
            "policy related to vn-member-id";
        leaf local-reroute {
            type boolean;
            description
                "Policy to state if reroute
                can be done locally";
        }
        leaf push-allowed {
            type boolean;
            description
                "Policy to state if changes
                can be pushed to the customer";
        }
        leaf incremental-update {
            type boolean;
            description
                "Policy to allow only the
                changes to be reported";
        }
    }//policy

    grouping metrics {
        description
            "metric related information";
        list metric{
            key "metric-type";
            description
                "The list of metrics for VN";
            leaf metric-type {
                type identityref {
                    base te-types:path-metric-type;
                }
                description
                    "The VN metric type.";
            }
            container limit {
                description
                    "Limiting contraints";
                leaf enabled{
                    type boolean;
                    description
                        "Limit contraint is enabled";
                }
                leaf value{
                    type uint32;
                    description
                        "The limit value";
                }
            }
            container optimize{
                description
                    "optimizing constraints";
                leaf enabled{
                    type boolean;
                    description
                        "Metric to optimize";
                 }
                 leaf value{
                     type uint32;
                     description
                        "The computed value";
                }
            }
        }

    }

    grouping service-metric {
        description
            "service-metric";
        leaf objective-function {
            type pcep:objective-function;
                description
                    "operational state of the objective function";
        }

        uses metrics;

        leaf bandwidth {
            type decimal64 {
                fraction-digits 2;

                range "0..max";
            }
            description
                "bandwidth requested/required for
                vn-member-id";
        }

        leaf protection {
            type identityref {
                base te-types:lsp-prot-type;
            }
            description "protection type.";
        }

        uses policy;

    }//service-metric

    /*
     * Configuration data nodes
     */
    container actn {
        description
            "actn is described by this container";
        container ap {
            description
                "AP configurations";
         list access-point-list {
                key "access-point-id";
                description
                    "access-point identifier";
                uses access-point{
                    description
                        "access-point information";
                }
         }
        }
        container vn {
            description
                "VN configurations";

            list vn-list {
                key "vn-id";
                description
                    "a virtual network is identified by a vn-id";
                leaf vn-id {
                    type uint32;
                    description
                        "a unique vn identifier";
                }
                leaf vn-name {
                    type string;
                    description "vn name";
                }
                list vn-member-list{
                    key "vn-member-id";
                    description
                        "List of VN-members in a VN";
                    uses vn-member;
                }
                uses service-metric;

                leaf admin-status {
                    type identityref {
                        base te-types:state-type;
                    }
                    default te-types:state-up;
                    description "VN administrative state.";
                }

            }//vn-list
        }//vn
    }//actn

    /*
     * Operational data nodes
     */

    container actn-state{
        config false;

        description
            "actn is described by this container";

        container ap {
            description
                "AP state";
            list access-point-list {
                key "access-point-id";
                description
                    "access-point identifier";
                uses access-point{
                    description
                        "access-point information";
                }
         }
        }
        container vn {
            description
                "VN state";
            list vn-list {
                key "vn-id";
                description
                    "a virtual network is identified by a vn-id";
                leaf vn-id {
                    type uint32;
                    description
                        "a unique vn identifier";
                }
                leaf vn-name {
                    type string;
                    description "vn name";
                }
                list vn-member-list{
                    key "vn-member-id";
                    description
                        "List of VN-members in a VN";
                    uses vn-member;
                    uses metrics;
                    leaf oper-status {
                        type identityref {
                            base te-types:state-type;
                        }
                        description

                            "VN-member operational state.";
                    }
                    leaf tunnel-ref {
                        type te:tunnel-ref;
                        description
                            "A reference to the TE tunnel
                            in the TE model";
                    }
                }
                container multi-src-dest{
                    description
                        "The selected VN Member when multi-src
                        and/or mult-destination is enabled.";
                    leaf selected-vn-member{
                        type leafref {
                            path "/actn-state/vn/vn-list/vn-id";
                        }
                        description
                            "The selected VN Member along the set
                            of source and destination configured
                            with multi-source and/or multi-destination";
                    }
                }
                container vn-topology-ref{
                    description
                        "An optional reference to the TE Topology
                         Model where the abstract nodes and links
                         of the Topology can be found";
                     uses tet:te-topology-ref;
                }

                uses service-metric;

                leaf admin-status {
                    type identityref {
                        base te-types:state-type;
                    }
                    description "VN administrative state.";
                }
                leaf oper-status {
                    type identityref {
                        base te-types:state-type;
                    }
                    description "VN operational state.";
                }

            }//vn-list
        }//vn
    }//actn-state
    /*
    * Notifications - TBD
    */
    /*
    * RPC
    */
    rpc  vn-compute{
        description
            "The VN computation without actual
            instantiation";
        input {
            list vn-member-list{
                key "vn-member-id";
                description
                    "List of VN-members in a VN";
                uses vn-member;
            }
            uses service-metric;
        }
        output {
            list vn-member-list{
                key "vn-member-id";
                description
                    "List of VN-members in a VN";
                uses vn-member;
                uses metrics;
                leaf oper-status {
                    type identityref {
                        base te-types:state-type;
                    }
                    description
                        "VN-member operational state.";
                }
            }
            container multi-src-dest{
                description
                    "The selected VN Member when multi-src
                    and/or mult-destination is enabled.";
                leaf selected-vn-member-id{
                    type uint32;
                    description
                        "The selected VN Member-id from the
                        input";
                }
            }
        }
    }
}
