module ietf-module-tags {
  yang-version "1";
  namespace "urn:ietf:params:xml:ns:yang:ietf-module-tags";
  prefix "mtags";

  import ietf-yang-types {
    prefix yang;
  }

  organization "IETF NetMod Working Group (NetMod)";

  contact
    "NetMod Working Group - <netmod@ietf.org>";

  description
    "This module describes a tagging mechanism for yang module.
     Tags may be IANA assigned or privately defined types.";

  revision "2018-03-06" {
    description
      "Initial revision.";
    reference "TBD";
  }

  list module-tags {
    key "name";

    description
      "A list of modules and their associated tags";

    leaf name {
        type yang:yang-identifier;
        mandatory true;
        description
            "The YANG module or submodule name.";
    }

    leaf-list tag {
        type string;

        description
            "A tag associated with the module. See the IANA 'YANG Module
             Tag Prefix' registry for reserved prefixes and the IANA
             'YANG Module IETF Tag' registry for IETF standard tags.

             The operational view of this list will contain all
             user-configured tags as well as any predefined tags that
             have not been masked by the user using the masked-tag leaf
             list below.";
    }

    leaf-list masked-tag {
        type string;

        description
            "The list of tags that should not be associated with this
             module. This user can remove (mask) predefined tags by
             adding them to this list. It is not an error to add tags to
             this list that are not predefined for the module.";
    }
  }
}
