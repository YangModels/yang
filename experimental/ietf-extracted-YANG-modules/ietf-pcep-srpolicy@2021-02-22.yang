module ietf-pcep-srpolicy {
  yang-version 1.1;
  namespace "urn:ietf:params:xml:ns:yang:ietf-pcep-srpolicy";
  prefix pcep-srp;

  import ietf-pcep {
    prefix pcep;
    reference
      "I-D.ietf-pce-pcep-yang: A YANG Data Model for Path
       Computation Element Communications Protocol (PCEP)";
  }
  import ietf-sr-policy {
    prefix sr-policy;
    reference
      "I-D.ietf-spring-sr-policy-yang: YANG Data Model for
       Segment Routing Policy";
  }
  import ietf-routing {
    prefix rt;
    reference
      "RFC 8349: A YANG Data Model for Routing Management";
  }

  organization
    "IETF PCE (Path Computation Element) Working Group";
  contact
    "WG Web:   <http://tools.ietf.org/wg/pce/>
     WG List:  <mailto:pce@ietf.org>
     Editor:   Cheng Li
               <mailto:c.l@huawei.com>";
  description
    "The YANG module augments the PCEP YANG operational
     model with SRv6.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see the
     RFC itself for full legal notices.";

  revision 2021-02-22 {
    description
      "Initial revision.";
    reference
      "RFC XXXX:  A YANG Data Model for Segment Routing (SR) Policy
       and SRv6 support in Path Computation Element Communications
       Protocol (PCEP)";
  }

  /* Groupings */

  grouping sr-policy {
    description
      "Segment Routing Policy grouping";
    // Editor's Note - headend is missig in SR Policy
    //  Yang mode
    leaf color {
      type leafref {
        path "/rt:routing/sr-policy:segment-routing/"
           + "sr-policy:traffic-engineering/sr-policy:"
           + "policies/sr-policy:policy/sr-policy:"
           + "color";
      }
      description
        "SR Policy Color";
      reference
        "I-D.ietf-spring-segment-routing-policy: Segment
         Routing Policy Architecture";
    }
    leaf endpoint {
      type leafref {
        path "/rt:routing/sr-policy:segment-routing/"
           + "sr-policy:traffic-engineering/sr-policy:"
           + "policies/sr-policy:policy/sr-policy:"
           + "endpoint";
      }
      description
        "SR Policy Endpoint";
      reference
        "I-D.ietf-spring-segment-routing-policy: Segment
         Routing Policy Architecture";
    }
    leaf protocol-origin {
      type leafref {
        path "/rt:routing/sr-policy:segment-routing/"
           + "sr-policy:traffic-engineering/sr-policy:"
           + "policies/sr-policy:policy/sr-policy:"
           + "candidate-paths/sr-policy:"
           + "candidate-path/sr-policy:protocol-origin";
      }
      must '(. = "pcep")' {
        error-message "The protocol origin must be PCEP";
      }
      description
        "SR Policy Candidate Path Protocol";
      reference
        "I-D.ietf-spring-segment-routing-policy: Segment
         Routing Policy Architecture";
    }
    leaf originator {
      type leafref {
        path "/rt:routing/sr-policy:segment-routing/"
           + "sr-policy:traffic-engineering/sr-policy:"
           + "policies/sr-policy:policy/sr-policy:"
           + "candidate-paths/sr-policy:"
           + "candidate-path/sr-policy:originator";
      }
      description
        "SR Policy Candidate Path Originator";
      reference
        "I-D.ietf-spring-segment-routing-policy: Segment
         Routing Policy Architecture";
    }
    leaf discriminator {
      type leafref {
        path "/rt:routing/sr-policy:segment-routing/"
           + "sr-policy:traffic-engineering/sr-policy:"
           + "policies/sr-policy:policy/sr-policy:"
           + "candidate-paths/sr-policy:"
           + "candidate-path/sr-policy:discriminator";
      }
      description
        "SR Policy Candidate Path Discriminator";
      reference
        "I-D.ietf-spring-segment-routing-policy: Segment
         Routing Policy Architecture";
    }
  }

  augment "/pcep:pcep/pcep:entity/pcep:lsp-db/pcep:lsp" {
    description
      "Augmenting SR Policy";
    container sr-policy {
      when
        "derived-from-or-self
         (/pcep:pcep/pcep:entity/pcep:lsp-db/pcep:lsp/pcep:pst,
          'path-setup-sr') or
         derived-from-or-self
         (/pcep:pcep/pcep:entity/pcep:lsp-db/pcep:lsp/pcep:pst,
          'path-setup-srv6')" {
        description
          "Applicable for SR or SRv6";
      }
      uses sr-policy;
      description
        "SR Policy";
    }
  }
}
