module ietf-dhcpv6 {
    namespace "urn:ietf:params:xml:ns:yang:ietf-dhcpv6";
    prefix "dhcpv6";

    import ietf-inet-types {
        prefix inet;
        revision-date "2013-07-15";
    }
    import ietf-yang-types {
        prefix yang;
        revision-date "2013-07-15";
    }

    organization "dhc wg";
    contact "yong@csnet1.cs.tsinghua.edu.cn
            wangh13@mails.tsinghua.edu.cn
            lh.sunlinh@gmail.com
            Ted.Lemon@nominum.com
            ian.farrer@telekom.de";

    description "This model defines a YANG data model that can be
        used to configure and manage DHCPv6 server, DHCPv6 relay and
    DHCPv6 client.";

    revision 2015-09-25 {
        description "version04: Correct duid and grammar errors.";
        reference "I-D: draft-cui-dhc-dhcpv6-yang-04"
    }
    revision 2015-07-01 {
        description "version03: Correct grammar errors.";

        reference "I-D: draft-cui-dhc-dhcpv6-yang-03"
    }
    revision 2015-04-13 {
        description "version02: Correct grammar errors.";

        reference "I-D: draft-cui-dhc-dhcpv6-yang-02"
    }
    revision 2015-04-02 {
        description "version01: Correct grammar errors, Reuse
            groupings, Update 'dhcpv6-realy' feature, Add
                notifications.";

        reference "I-D: draft-cui-dhc-dhcpv6-yang-01"
    }
    revision 2015-03-04 {
        description "version00: Initial revision.";

        reference "I-D: draft-cui-dhc-dhcpv6-yang-00"
    }

/*
 * Features
 */

    feature dhcpv6-server {
        description
            "Server in DHCPv6.";
        reference
            "RFC3315";
    }

    feature dhcpv6-relay {
        description
            "Relay agent in DHCPv6.";
        reference
            "RFC3315";
    }

    feature dhcpv6-client {
        description
             "Client in DHCPv6.";
        reference
               "RFC3315";
    }
/*
 * Typedef
 */

    typedef duidtype {
            type union {
                    type uint16 {
                            description
                                "This uint16 specifies the type of this duid";
                        }
                        type string {
                            pattern '(([0-9a-fA-F]{2}){2,128})';
                            description
                "This should be a variable length value
                no more than 128 octets."
                        }
                }
        }

    typedef threshold {
        description "Threshold value in percent";
        type union {
            type uint16 {
                range 0..100;
                description "threshold value";
            }
            type enumeration {
                enum "disabled" {
                    description "No threshold";
                }
            }
        }
    }
/*
 * Grouping
 */

    grouping vendor-infor {
        container vendor-info {
            description "";
            leaf ent-num {
                type uint32;
                mandatory true;
                description "enterprise number";
            }
            leaf-list data {
                type string;
                description "specific vendor info";
            }
        }
    }

    grouping portset-para {
        container port-parameter {
            leaf offset {
                type uint8;
                mandatory true;
                description "offset in a port set";
            }
            leaf psid-len {
                type uint8;
                mandatory true;
                description "length of a psid";
            }
            leaf psid {
                type uint16;
                mandatory true;
                description "psid value";
            }
        }
    }

/*
 * Data Nodes
 */

    container server {
        if-feature dhcpv6-server;
         description "server portion";
        container serv-attributes {
            description "This container contains basic attributes
            of a DHCPv6 server such as DUID, server name and so
            on. Some optional functions that can be provided by
            the server is also included.";
            leaf name {
                type string;
                mandatory true;
                description "server's name";
            }
            leaf duid {
                            type duidtype;
                mandatory true;
                description "DHCP Unique Identifer";
                        }
            leaf enable {
                type boolean;
                mandatory true;
                description "whether to enable the server";
            }
            leaf ipv6-address {
                type inet:ipv6-address;
                mandatory true;
                description "server's IPv6 address";
            }
            leaf description {
                type string;
                description "description of the server";
            }
            leaf pd-function {
                type boolean;
                mandatory true;
                description "Whether the server can act as a
                delegating router to perform prefix delegation
                                ([RFC3633]).";
            }
            leaf stateless-service {
                type boolean;
                mandatory true;
                description "A boolean value specifies whether
                the server support client-server exchanges
                involving two messages defined in ([RFC3315]).";
            }
            leaf rapid-commit {
                type boolean;
                mandatory true;
                description "A boolean value specifies whether
                the server support client-server exchanges
                involving two messages defined in ([RFC3315]).";
            }
            leaf store-client-link-layer {
                type boolean;
                description "whether to store the clients'
                link-layer addresses";
            }
            uses vendor-infor;
            }
        container option-sets {
            description "*";
            list option-set {
                key option-set-id;
                description "*";
                leaf option-set-id {
                    type uint8;
                    mandatory true;
                    description "the option-set-id key";
                }
                                list new-option {
                    key option-code;
                    description "*";
                    leaf option-code {
                        type uint16;
                        manadatory true;
                        description "the option code key";
                    }
                    leaf option-name {
                        type string;
                        manadatory true;
                        description "the new option's name";
                    }
                    leaf option-description {
                        type string;
                        manadatory true;
                        description "description of new option";
                    }
                    leaf option-reference {
                        type string;
                        description "reference to the
                        specification";
                    }
                    leaf option-value {
                        type string;
                        manadatory true;
                        description "the new option's value";
                    }
                }
                leaf user-class-value {
                    type string;
                    description "use class option's value";
                }
                leaf enterprise-number {
                    type uint32;
                    description "*";
                }
                leaf store-client-link-layer {
                    type boolean;
                    description "*";
                }
                container preference-option {
                    description "*";
                    leaf enable {
                        type boolean;
                        mandatory true;
                        description "*";
                    }
                    leaf preference-value {
                        type uint8;
                        mandatory true;
                        description "*";
                    }
                }
                container sip-server-option {
                    description "*";
                    leaf enable {
                        type boolean;
                        mandatory true;
                        description "*";
                    }
                    list sip-server {
                        key sip-serv-id;
                        leaf sip-serv-id {
                            type uint8;
                            mandatory true;
                            description "*";
                        }
                        leaf sip-serv-domain-name {
                            type string;
                            mandatory true;
                            description "*";
                        }
                        leaf sip-serv-addr {
                            type inet:ipv6-address;
                            mandatory true;
                            description "*";
                        }
                    }
                }
                container dns-config-option {
                    description "*";
                    leaf enable {
                        type boolean;
                        mandatory true;
                        description "*";
                    }
                    list dns-server {
                        key dns-serv-id;
                        leaf dns-serv-id {
                            type uint8;
                            mandatory true;
                            description "*";
                        }
                        leaf dns-serv-addr {
                            type inet:ipv6-address;
                            mandatory true;
                            description "*";
                        }
                    }
                    leaf domain-search-list {
                        type string;
                        mandatory true;
                        description "*";
                    }
                }
                container nis-config-option {
                    description "*";
                    leaf enable {
                        type boolean;
                        mandatory true;
                        description "*";
                    }
                    list nis-server {
                        key nis-serv-id;
                        description "*";
                        leaf nis-serv-id {
                            type uint8;
                            mandatory true;
                            description "*";
                        }
                        leaf nis-serv-addr {
                            type inet:ipv6-address;
                            mandatory true;
                            description "*";
                        }
                    }
                }
                container nis-plus-config-option {
                    description "*";
                    leaf enable {
                        type boolean;
                        mandatory true;
                        description "*";
                    }
                    list nis-plus-server {
                        key nis-plus-serv-id;
                        description "*";
                        leaf nis-plus-serv-id {
                            type uint8;
                            mandatory true;
                            description "*";
                        }
                        leaf nis-plus-serv-addr {
                            type inet:ipv6-address;
                            mandatory true;
                            description "*";
                        }
                    }
                }
                container info-refresh-time-option {
                    description "*";
                    leaf enable {
                        type boolean;
                        mandatory true;
                        description "*";
                    }
                    leaf info-refresh-time {
                        type yang:timeticks;
                        mandatory true;
                        description "*";
                    }
                }
                container cli-fqdn-option {
                    description "*";
                    leaf enable {
                        type boolean;
                        mandatory true;
                        description "*";
                    }
                    leaf server-initiate-update {
                        type boolean;
                        mandatory true;
                        description "*";
                    }
                    leaf client-initiate-update {
                        type boolean;
                        mandatory true;
                        description "*";
                    }
                    leaf modify-name-from-cli {
                        type boolean;
                        mandatory true;
                        description "*";
                    }
                }
                container timezone-option {
                    description "*";
                    leaf enable {
                        type boolean;
                        mandatory true;
                        description "*";
                    }
                    leaf tz-posix {
                        type string;
                        mandatory true;
                        description "*";
                    }
                    leaf tz-database {
                        type string;
                        mandatory true;
                        description "*";
                    }
                }
                container ntp-server-option {
                    description "*";
                    leaf enable {
                        type boolean;
                        mandatory true;
                        description "*";
                    }
                    list ntp-server {
                        key ntp-serv-id;
                        description "*";
                        leaf ntp-serv-id {
                            type uint8;
                            mandatory true;
                            description "*";
                        }
                        leaf ntp-serv-addr {
                            type inet:ipv6-address;
                            mandatory true;
                            description "*";
                        }
                        leaf ntp-serv-mul-addr {
                            type inet:ipv6-address;
                            mandatory true;
                            description "*";
                        }
                        leaf ntp-serv-fqdn {
                            type string;
                            mandatory true;
                            description "*";
                        }
                    }
                }
                container sntp-server-option {
                    description "*";
                    leaf enable {
                        type boolean;
                        mandatory true;
                        description "*";
                    }
                    list sntp-server {
                        key sntp-serv-id;
                        description "*";
                        leaf sntp-serv-id {
                            type uint8;
                            mandatory true;
                            description "*";
                        }
                        leaf sntp-serv-addr {
                            type inet:ipv6-address;
                            mandatory true;
                            description "*";
                        }
                    }
                }
                container network-boot-option {
                    description "*";
                    leaf enable {
                        type boolean;
                        mandatory true;
                        description "*";
                    }
                    list boot-file {
                        key boot-file-id;
                        description "*";
                        leaf boot-file-id {
                            type uint8;
                            mandatory true;
                            description "*";
                        }
                        leaf-list suitable-arch-type {
                            type uint16;
                            description "*";
                        }
                        leaf-list suitable-net-if {
                            type uint32;
                            description "*";
                        }
                        leaf boot-file-url {
                            type string;
                            mandatory true;
                            description "*";
                        }
                        list boot-file-paras {
                            key para-id;
                            description "*";
                            leaf para-id {
                                type uint8;
                                mandatory true;
                                description "*";
                            }
                            leaf parameter {
                                type string;
                                mandatory true;
                                description "*";
                            }
                        }
                    }
                }
                container dslite-option {
                    description "*";
                    leaf enable {
                        type boolean;
                        mandatory true;
                        description "*";
                    }
                    leaf dslite-aftr-name {
                        type string;
                        mandatory true;
                        description "*";
                    }
                }
                container kerberos-option {
                    description "*";
                    leaf enable {
                        type boolean;
                        mandatory true;
                        description "*";
                    }
                    leaf default-realm-name {
                        type string;
                        mandatory true;
                        description "*";
                    }
                    list kdc-info {
                        key kdc-id;
                        description "*";
                        leaf kdc-id {
                            type uint8;
                            mandatory true;
                            description "*";
                        }
                        leaf priority {
                            type uint16;
                            mandatory true;
                            description "*";
                        }
                        leaf weight {
                            type uint16;
                            mandatory true;
                            description "*";
                        }
                        leaf transport-type {
                            type uint8;
                            mandatory true;
                            description "*";
                        }
                        leaf port-number {
                            type uint16;
                            mandatory true;
                            description "*";
                        }
                        leaf kdc-ipv6-addr {
                            type inet:ipv6-address;
                            mandatory true;
                            description "*";
                        }
                        leaf realm-name {
                            type string;
                            mandatory true;
                            description "*";
                        }
                    }
                }
                container addr-selection-option {
                    description "*";
                    leaf enable {
                        type boolean;
                        mandatory true;
                        description "*";
                    }
                    leaf a-bit-set {
                        type boolean;
                        mandatory true;
                        description "*";
                    }
                    leaf p-bit-set {
                        type boolean;
                        mandatory true;
                        description "*";
                    }
                    list policy-table {
                        key policy-id;
                        description "*";
                        leaf policy-id {
                            type uint8;
                            mandatory true;
                            description "*";
                        }
                        leaf label {
                            type uint8;
                            mandatory true;
                            description "*";
                        }
                        leaf precedence {
                            type uint8;
                            mandatory true;
                            description "*";
                        }
                        leaf prefix-len {
                            type uint8;
                            mandatory true;
                            description "*";
                        }
                        leaf prefix {
                            type inet:ipv6-prefix;
                            mandatory true;
                            description "*";
                        }
                    }
                }
                container sol-max-rt-option {
                    description "*";
                    leaf enable {
                        type boolean;
                        mandatory true;
                        description "*";
                    }
                    leaf sol-max-rt-value {
                        type yang:timeticks;
                        mandatory true;
                        description "*";
                    }
                }
                container inf-max-rt-option {
                    description "*";
                    leaf enable {
                        type boolean;
                        mandatory true;
                        description "*";
                    }
                    leaf inf-max-rt-value {
                        type yang:timeticks;
                        mandatory true;
                        description "*";
                    }
                }
                container pcp-server-option {
                    description "*";
                    leaf enable {
                        type boolean;
                        mandatory true;
                        description "*";
                    }
                    list pcp-server {
                        key pcp-serv-id;
                        description "*";
                        leaf pcp-serv-id {
                            type uint8;
                            mandatory true;
                            description "*";
                        }
                        leaf pcp-serv-addr {
                            type inet:ipv6-address;
                            mandatory true;
                            description "*";
                        }
                    }
                }
                container s46-rule-option {
                    description "*";
                    leaf enable {
                        type boolean;
                        mandatory true;
                        description "*";
                    }
                    list s46-rule {
                        key rule-id;
                        description "*";
                        leaf rule-id {
                            type uint8;
                            mandatory true;
                            description "*";
                        }
                        leaf rule-type {
                            type enumeration {
                            enum "BMR";
                            enum "FMR";
                            }
                            mandatory true;
                            description "*";
                        }
                        leaf prefix4-len {
                            type uint8;
                            mandatory true;
                            description "*";
                        }
                        leaf ipv4-prefix {
                            type inet:ipv4-prefix;
                            mandatory true;
                            description "*";
                        }
                        leaf prefix6-len {
                            type uint8;
                            mandatory true;
                            description "*";
                        }
                        leaf ipv6-prefix {
                            type inet:ipv6-prefix;
                            mandatory true;
                            description "*";
                        }
                        uses portset-para;
                    }
                }
                container s46-br-option {
                    description "*";
                    leaf enable {
                        type boolean;
                        mandatory true;
                        description "*";
                    }
                    list br {
                        key br-id;
                        description "*";
                        leaf br-id {
                            type uint8;
                            mandatory true;
                            description "*";
                        }
                        leaf br-ipv6-addr {
                            type inet:ipv6-address;
                            mandatory true;
                            description "*";
                        }
                    }
                }
                container s46-dmr-option {
                    leaf enable {
                        type boolean;
                        mandatory true;
                        description "*";
                    }
                    list dmr {
                        key dmr-id;
                        description "*";
                        leaf dmr-id {
                            type uint8;
                            mandatory true;
                            description "*";
                        }
                        leaf dmr-prefix-len {
                            type uint8;
                            mandatory true;
                            description "*";
                        }
                        leaf dmr-ipv6-prefix {
                            type inet:ipv6-prefix;
                            mandatory true;
                            description "*";
                        }
                    }
                }
                container s46-v4-v6-binding-option {
                    description "*";
                    leaf enable {
                        type boolean;
                        mandatory true;
                        description "*";
                    }
                    list ce {
                        key ce-id;
                        description "*";
                        leaf ce-id {
                            type uint8;
                            mandatory true;
                            description "*";
                        }
                        leaf ipv4-addr {
                            type inet:ipv4-address;
                            mandatory true;
                            description "*";
                        }
                        leaf bind-prefix6-len {
                            type uint8;
                            mandatory true;
                            description "*";
                        }
                        leaf bind-ipv6-prefix {
                            type inet:ipv6-prefix;
                            mandatory true;
                            description "*";
                        }
                        uses portset-para;
                    }
                }
            }
        }
            container network-range {
                description "*";
                leaf-list option-set {
                    type uint8;
                    description "*";
                }
                list network-range {
                    key network-range-id;
                    description "*";
                    leaf network-range-id {
                        type uint8;
                        mandatory true;
                        description "*";
                    }
                    leaf network-description {
                        type string;
                        mandatory true;
                        description "*";
                    }
                    leaf network-prefix {
                        type inet:ipv6-prefix;
                        mandatory true;
                        description "*";
                    }
                    leaf inherit-option-set {
                        type boolean;
                        mandatory true;
                        description "*";
                    }
                    leaf-list option-set {
                        type uint8;
                        description "*";
                    }
                    container address-pools {
                        description "A container describes
                        the DHCPv6 server's address pools.";
                        list address-pool {
                            key pool-id;
                            description "A DHCPv6 server can
                            be configured with several address
                            pools. This list defines such
                            address pools which are distinguish
                            by the key called 'pool-name'.";
                            leaf pool-id {
                                type uint8;
                                mandatory true;
                                description "*";
                            }
                            leaf pool-prefix {
                                type inet:ipv6-prefix;
                                mandatory true;
                                description "*";
                            }
                            leaf start-address {
                                type inet:ipv6-address-no-zone;
                                mandatory true;
                                description "*";
                            }
                            leaf end-address {
                                type inet:ipv6-address-no-zone;
                                mandatory true;
                                description "*";
                            }
                            leaf preferred-lifetime {
                                type yang:timeticks;
                                mandatory true;
                                description "*";
                            }
                            leaf valid-lifetime {
                                type yang:timeticks;
                                mandatory true;
                                description "*";
                            }
                            leaf total-ipv6-count {
                                type uint64;
                                config "false";
                                mandatory true;
                                description "*";
                            }
                            leaf used-ipv6-count {
                                type uint64;
                                config "false";
                                mandatory true;
                                description "*";
                            }
                            leaf utilization-ratio {
                                type threshold;
                                mandatory true;
                                description "*";
                            }
                            leaf inherit-option-set {
                                type boolean;
                                mandatory true;
                                description "*";
                            }
                            leaf-list option-set {
                                type uint8;
                                description "*";
                            }
                            container reserved-addresses {
                                description "*";
                                list static-binding {
                                    key cli-id;
                                    description "*";
                                    leaf cli-id {
                                        type uint32;
                                        mandatory true;
                                        description "*";
                                    }
                                    leaf duid {
                                        type duidtype;
                                        mandatory true;
                                        description "DHCP Unique
                                        Identifer";
                                    }
                                    leaf-list reserv-addr {
                                        type inet:ipv6-address;
                                        description "*";
                                    }
                                }
                                leaf-list other-reserv-addr {
                                    type inet:ipv6-address;
                                    description "*";
                                }
                            }
                        }
                        list binding-info {
                            key cli-id;
                            config "false";
                            description "A list records a binding
                            information for each DHCPv6 client
                            that has already been allocated IPv6
                            addresses.";
                            leaf cli-id {
                                type uint32;
                                mandatory true;
                                description "*";
                            }
                            leaf duid {
                                type duidtype;
                                mandatory true;
                                                                description "DHCP Unique Identifer";
                                                        }
                            list cli-ia {
                                key iaid;
                                description "*";
                                leaf ia-type {
                                    type string;
                                    mandatory true;
                                    description "*";
                                }
                                leaf iaid {
                                    type uint32;
                                    mandatory true;
                                    description "*";
                                }
                                leaf-list cli-addr {
                                    type inet:ipv6-address;
                                    description "*";
                                }
                                leaf pool-id {
                                    type uint8;
                                    mandatory true;
                                    description "*";
                                }
                            }
                        }
                    }
                    container prefix-pools {
                        description "If a server supports prefix
                        delegation function, this container will
                        be used to define the delegating router's
                        refix pools.";
                        list prefix-pool {
                            key pool-id;
                            description "Similar to server's
                            address pools, a delegating router
                            can also be configured with multiple
                            prefix pools specified by a list
                            called 'prefix-pool'.";
                            leaf pool-id {
                                type uint8;
                                mandatory true;
                                description "*";
                            }
                            leaf prefix {
                                type inet:ipv6-prefix;
                                mandatory true;
                                description "*";
                            }
                            leaf prefix-length {
                                type uint8;
                                mandatory true;
                                description "*";
                            }
                            leaf preferred-lifetime {
                                type yang:timeticks;
                                mandatory true;
                                description "*";
                            }
                            leaf valid-lifetime {
                                type yang:timeticks;
                                mandatory true;
                                description "*";
                            }
                            leaf utilization-ratio {
                                type threshold;
                                mandatory true;
                                description "*";
                            }
                            leaf inherit-option-set {
                                type boolean;
                                mandatory true;
                                description "*";
                            }
                            leaf-list option-set {
                                type uint8;
                                description "*";
                            }
                            container reserved-prefixes {
                                description "*";
                                list static-binding {
                                    key cli-id;
                                    description "*";
                                    leaf cli-id {
                                        type uint32;
                                        mandatory true;
                                        description "*";
                                    }
                                    leaf duid {
                                        type duidtype;
                                        mandatory true;
                                        description "DHCP Unique
                                                                                Identifer";
                                    }
                                    leaf reserv-prefix-len {
                                        type uint8;
                                        mandatory true;
                                        description "*";
                                    }
                                    leaf reserv-prefix {
                                        type inet:ipv6-prefix;
                                        mandatory true;
                                        description "*";
                                    }
                                }
                                leaf exclude-prefix-len {
                                    type uint8;
                                    mandatory true;
                                    description "*";
                                }
                                leaf exclude-prefix {
                                    type inet:ipv6-prefix;
                                    mandatory true;
                                    description "*";
                                }
                                list other-reserv-prefix {
                                    key reserv-id;
                                    description "*";
                                    leaf reserv-id {
                                        type uint8;
                                        mandatory true;
                                        description "*";
                                    }
                                    leaf prefix-len {
                                        type uint8;
                                        mandatory true;
                                        description "*";
                                    }
                                    leaf prefix {
                                        type inet:ipv6-prefix;
                                        mandatory true;
                                        description "*";
                                    }
                                }
                            }
                        }
                        list binding-info {
                            key cli-id;
                            config "false";
                            description "A list records a
                            binding information for each
                            DHCPv6 client that has already
                            been allocated IPv6 addresses.";
                            leaf cli-id {
                                type uint32;
                                mandatory true;
                                description "*";
                            }
                            leaf duid {
                                type duidtype;
                                manadatory true;
                                description "DHCP Unique
                                Identifier";
                            }
                            list cli-iapd {
                                key iaid;
                                description "*";
                                leaf iaid {
                                    type uint32;
                                    mandatory true;
                                    description "*";
                                }
                                leaf-list cli-prefix {
                                    type inet:ipv6-prefix;
                                    description "*";
                                }
                                leaf-list cli-prefix-len {
                                    type uint8;
                                    description "*";
                                }
                                leaf pool-id {
                                    type uint8;
                                    mandatory true;
                                    description "*";
                                }
                            }
                        }
                    }
                    container hosts {
                        description "*";
                        list host {
                            key cli-id;
                            description "*";
                            leaf cli-id {
                                type uint32;
                                mandatory true;
                                description "*";
                            }
                            leaf duid {
                                type duidtype;
                                mandatory true;
                                description "DHCP Unique
                                Identifer";
                            }
                            leaf inherit-option-set {
                                type boolean;
                                mandatory true;
                                description "*";
                            }
                            leaf-list option-set {
                                type uint8;
                                description "*";
                            }
                            leaf nis-domain-name {
                                type string;
                                description "*";
                            }
                            leaf nis-plus-domain-name {
                                type string;
                                description "*";
                            }
                        }
                    }
                }
            }
            container relay-opaque-paras {
                description "This container contains some
                opaque values in Relay Agent options that
                need to be configured on the server side
                only for value match. Such Relay Agent
                options include Interface-Id option,
                Remote-Id option and Subscriber-Id option.";
                list relays {
                    key relay-name;
                    description "*";
                    leaf relay-name {
                        type string;
                        mandatory true;
                        description "*";
                    }
                    list interface-info {
                        key if-name;
                        description "*";
                        leaf if-name {
                            type string;
                            mandatory true;
                            description "*";
                        }
                        leaf interface-id {
                            type string;
                            mandatory true;
                            description "*";
                        }
                    }
                    list subscribers {
                        key subscriber;
                        description "*";
                        leaf subscriber {
                            type uint8;
                            mandatory true;
                            description "*";
                        }
                        leaf subscriber-id {
                            type string;
                            mandatory true;
                            description "*";
                        }
                    }
                    list remote-host {
                        key ent-num;
                        description "*";
                        leaf ent-num {
                            type uint32;
                            mandatory true;
                            description "*";
                        }
                        leaf remote-id {
                            type string;
                            mandatory true;
                            description "*";
                        }
                    }
                }
            }
            container rsoo-enabled-options {
                description "*";
                list rsoo-enabled-option{
                    key option-code;
                    description "*";
                    leaf option-code {
                        type uint16;
                        mandatory true;
                        description "*";
                    }
                    leaf description {
                        type string;
                        mandatory true;
                        description "*";
                    }
                }
            }
            container packet-stats {
                config "false";
                description "A container presents
                the packet statistics related to
                the DHCPv6 server.";
                leaf solicit-count {
                    type uint32;
                    mandatory true;
                    description "*";
                }
                leaf request-count {
                    type uint32;
                    mandatory true;
                    description "*";
                }
                leaf renew-count {
                    type uint32;
                    mandatory true;
                    description "*";
                }
                leaf rebind-count {
                    type uint32;
                    mandatory true;
                    description "*";
                }
                leaf decline-count {
                    type uint32;
                    mandatory true;
                    description "*";
                }
                leaf release-count {
                    type uint32;
                    mandatory true;
                    description "*";
                }
                leaf info-req-count {
                    type uint32;
                    mandatory true;
                    description "*";
                }
                leaf advertise-count {
                    type uint32;
                    mandatory true;
                    description "*";
                }
                leaf confirm-count {
                    type uint32;
                    mandatory true;
                    description "*";
                }
                leaf reply-count {
                    type uint32;
                    mandatory true;
                    description "*";
                }
                leaf reconfigure-count {
                    type uint32;
                    mandatory true;
                    description "*";
                }
                leaf relay-forward-count {
                    type uint32;
                    mandatory true;
                    description "*";
                }
                leaf relay-reply-count {
                    type uint32;
                    mandatory true;
                    description "*";
                }
            }
        }
    }
