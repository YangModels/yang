module ietf-msdp {

 namespace "urn:ietf:params:xml:ns:yang:ietf-msdp";

 prefix msdp;

 import ietf-inet-types {
     prefix "inet";
 }

 /*import ietf-bfd {
    prefix "bfd";
 }*/

 organization " IETF PIM( Protocols for IP Multicast ) Working Group";
 contact
     "WG List:  <mailto:pim@ietf.org>
      WG Chair: Stig Venaas
                        <stig@venaas.com>
      WG Chair: Mike McBride
                        <mmcbride7@gmail.com>

      Editor:   Zheng Zhang
                <mailto:zhang.zheng@zte.com.cn>
      Editor:   Benchong Xu
                <mailto:xu.benchong@zte.com.cn>
     ";

 description
     "This module contains a collection of YANG definitions for
      managing msdp protocol.";

 revision 2016-04-23 {
     description
     "Initial version.";
     reference "https://tools.ietf.org/html/draft-zhang-pim-msdp-yang";
 }

 /*feature bfd-protocol-parms {
    description "BFD protocol specific parameters support.";
 }*/

/*SA information*/
    grouping sa-message {
        description "The Source-Active message information.";

        list adv-peer-list {
            key "adv-peer-addr";
            description "The advertisement information of one peer.";
            leaf adv-peer-addr {
                type inet:ip-address;
                mandatory true;
                description "The address of peer that advertises the SA message.
                  When this value is set to zero mearns that the sa message is
                  originated by this node itself.";
            }

            list rp-entry {
                key "rp-addr";
                description "The SA entry information of one RP.";
                leaf rp-addr {
                    type inet:ip-address;
                    mandatory true;
                    description "The address of RP.";
                }
                list sa-cache {
                    key "count";
                    description "The SA cache information.";
                    leaf count {
                        type uint32;
                        mandatory true;
                        description "The sequence number of this SA cache.";
                    }
                    leaf sa-adv-timer {
                        type uint16 {
                            range "1 .. 65535";
                        }
                        units "seconds";
                        default 60;
                        description "The SA-Advertisement-Period of this SA cache.";
                    }
                    leaf sa-cache-timeout {
                        type uint16 {
                            range "1 .. 65535";
                        }
                        units "seconds";
                        description "The timeout interval of this SA cache. The
                          value of this timer MUST NOT be less than
                          [SA-Advertisement-Period] + [SA-Hold-Down-Period].";
                    }
                    leaf source-addr {
                        type inet:ip-address;
                        mandatory true;
                        description "The address of source.";
                    }
                    leaf group-addr {
                        type inet:ip-address;
                        mandatory true;
                        description "The address of group.";
                    }
                }
            }
        }
    }

/*peer information*/
        grouping peer-state {
        description "The collection of msdp peer state.";
        choice peer-state {
            mandatory true;
            case disabled {
                description "The state of this msdp peer is disabled.";
            }
            case inactive {
                description "The tcp connection of this peer is not established yet.";
            }
            case connecting {
                description "The tcp connection of this peer is in process.";
            }
            case listen {
                description "The tcp connection of this peer is in process, and the ip address of this node is higher.";
            }
            case established {
                description "The tcp connection of this peer is established.";
            }
            description "The collection of all possible peer state.";
        }
    }

        grouping peer-timer {
            description "The timer of msdp peer.";
            leaf hold-timer {
            type uint16 {
                range "1 .. 65535";
            }
            units "seconds";
            default 75;
            description "The SA-Hold-Down-Period of this msdp peer.";
        }
        leaf keepalive-timer {
            type uint16 {
                range "1 .. 65535";
            }
            units "seconds";
            default 60;
            description "The keepalive timer of this msdp peer.";
        }
        leaf connectRetry-timer {
            type uint16 {
                range "1 .. 65535";
            }
            units "seconds";
            default 30;
            description "The connect retry timer of this msdp peer.";
        }
    }

    container msdp-configure {
        description "The information of msdp protocol.";
        container peer-information {
            description "The information of msdp peer.";

            list peer-list {
                key "peer-addr";
                description "The information of this msdp peer.";
                leaf peer-addr {
                    type inet:ip-address;
                    mandatory true;
                    description "The address of this msdp peer.";
                }
                leaf mesh-group {
                    type string;
                    description "The mesh-group that the msdp peer belongs to.";
                }
                container bfd {
                    description "BFD operation.";
                    leaf enabled {
                        type boolean;
                        description "True if BFD is enabled for the peer.";
                    }
                    /*uses bfd:bfd-grouping-base-cfg-parms {
                        if-feature bfd-protocol-parms;
                    }*/
                }
                container peer-timer {
                    description "The timer information of this peer.";
                    uses peer-timer;
                }
            }
        }

        container source-active-cache {
            description "The source active cache information.";
            uses sa-message;
        }
    }

    container msdp {
        config false;
        description "The information of msdp protocol.";
        container peer-information {
            description "The information of msdp peer.";

            list peer-list {
                key "peer-addr";
                description "The information of this msdp peer.";
                leaf peer-addr {
                    type inet:ip-address;
                    mandatory true;
                    description "The address of this msdp peer.";
                }
                leaf mesh-group {
                    type string;
                    description "The mesh-group that the msdp peer belongs to.";
                }
                container bfd {
                    description "BFD operation.";
                    leaf enabled {
                        type boolean;
                        description "True if BFD is enabled for the peer.";
                    }
                    /*uses bfd:bfd-grouping-base-cfg-parms {
                        if-feature bfd-protocol-parms;
                    }*/
                }
                container peer-timer {
                    description "The timer information of this peer.";
                    uses peer-timer;
                }
                uses peer-state;
            }
        }

        container source-active-cache {
            description "The source active cache information.";
            uses sa-message;
        }
    }

/*notification*/
        notification msdp-notification {
        description "This notification is sent when a condition changes in msdp.";

        container peer-state-change {
            description "The msdp peer state changes.";
            leaf peer-addr {
                type inet:ip-address;
                mandatory true;
                description "The address of this msdp peer.";
            }
            uses peer-state;
        }

        container tlv-format-error {
            description "The tlv format is error from this peer.";
            leaf peer-addr {
                type inet:ip-address;
                mandatory true;
                description "The address of this msdp peer.";
            }
            container sa-error-message {
                description "The source active message information.";
                uses sa-message;
            }
        }
    }
}
