module ietf-altmark {
  yang-version 1.1;
  namespace "urn:ietf:params:xml:ns:yang:ietf-altmark";
  prefix "altmark";

  import ietf-access-control-list {
    prefix "acl";
    reference
      "RFC 8519: YANG Data Model for Network Access Control
       Lists (ACLs)";
  }

  import ietf-interfaces {
    prefix "if";
    reference
      "RFC 8343: A YANG Data Model for Interface Management";
  }

  organization
    "IETF IPPM (IP Performance Metrics) Working Group";

  contact
    "WG Web: <https://datatracker.ietf.org/wg/ippm>
     WG List: <ippm@ietf.org>
     Author: thomas.graf@swisscom.com
     Author: wangminxue@chinamobile.com
     Author: giuseppe.fioccola@huawei.com
     Author: zhoutianran@huawei.com
     Author: xiao.min2@zte.com.cn";

  description
    "This YANG module specifies a vendor-independent data
     model for the Alternate Marking (AltMark).

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-07-03 {
    description "First revision.";
    reference "RFC XXXX: A YANG Data Model for Alternate-Marking";
  }

 /*
  * FEATURES
  */

  feature altmark {
    description
      "This feature indicated that the Alternate-Marking Method is
      supported.";
    reference
      "RFC 9341: Alternate-Marking Method;
       RFC 9342: Clustered Alternate-Marking Method
       RFC 9343: IPv6 Application of the Alternate-Marking Method
       RFC 9714: Application of the Alternate Marking Method to the
       MPLS Label Stack
       RFC 9947: Application of the Alternate Marking Method to the
       Segment Routing Header";
  }

 /*
  * IDENTITIES
  */

  identity filter {
    description
      "Base identity to represent a filter. A filter is used to
      specify the flow to which the AltMark method is applied.";
  }

  identity acl-filter {
    base filter;
    description
      "Apply ACL rules to specify the flow.";
  }

  identity method {
    description
      "Base identity to represent the method type.";
  }

  identity single-marking {
    base method;
    description
      "The AltMark Single-Marking method.";
  }

  identity double-marking  {
    base method;
    description
      "The AltMark Double-Marking method.";
  }

  identity protocol {
    description
      "Base identity to represent the protocol. It's used to
       indicate the protocol for the application of the AltMark
       method.";
  }

  identity ipv6 {
    base protocol;
    description
      "The AltMark method is applied to IPv6 protocol.";
    reference
      "RFC 9343: IPv6 Application of the Alternate-Marking Method";
  }

  identity srh {
    base protocol;
    description
      "The AltMark method is applied to SRH.";
    reference
      "RFC 9947: Application of the Alternate Marking Method to the
       Segment Routing Header";
  }

  identity mpls {
    base protocol;
    description
      "The AltMark method is applied to MPLS.";
    reference
      "RFC 9714: Application of the Alternate Marking Method
      to the MPLS Label Stack";
  }

  identity interface-action {
    description
      "Base identity to represent the interface actions. It's used to
       indicate what action the node will take on that interface.";
  }

  identity action-marking {
    base interface-action;
    description
      "It indicates that the interface must mark the AltMark data
      field, according to the operations described in RFC 9341 and
      RFC 9342";
  }

  identity action-unmarking {
    base interface-action;
    description
      "It indicates that the interface must unmark the AltMark data
       field, according to the operations described in RFC 9341 and
       RFC 9342";
  }

  identity action-read {
    base interface-action;
    description
      "It indicates that the interface only reads the AltMark data,
       according to the operations described in RFC 9341 and
       RFC 9342";
  }

 /*
  * TYPE DEFINITIONS
  */

  typedef altmark-filter-type {
    type identityref {
      base filter;
    }
    description
      "It specifies a known type of filter.";
  }

  typedef altmark-interface-action {
    type identityref {
      base interface-action;
    }
    description
      "It specifies the action on the interface.";
  }

  typedef altmark-method-type {
    type identityref {
      base method;
    }
    description
      "It specifies the AltMark method used.";
  }

  typedef altmark-protocol-type {
    type identityref {
      base protocol;
    }
    description
      "It specifies a known type of carrier protocol for the AltMark
       data.";
  }

  typedef flow-id {
    type uint32 {
      range 0..1048575;
    }
    description
      "It specifies the 20-bit AltMark flow identifier.";
  }

  typedef flow-direction {
    type enumeration {
      enum "ingress" {
        value 1;
        description
          "Ingress of an AltMark flow.";
      }
      enum "transit" {
        value 2;
        description
          "Transit of an AltMark flow.";
      }
      enum "egress" {
        value 3;
        description
          "Egress of an AltMark flow.";
      }
    }
    description
      "Flow direction.";
  }
  typedef altmark-measurement-mode {
    type enumeration {
      enum "e2e" {
        value 1;
        description
          "It indicates that end-to-end measurements can be enabled.";
      }
      enum "hbh" {
        value 2;
        description
          "It indicates that hop-by-hop measurements can be enabled.";
      }
    }
    description
      "It specifies the measurement mode.";
  }

 /*
  * GROUP DEFINITIONS
  */

  grouping altmark-admin-config {
    description
      "AltMark top-level administrative configuration.";

    leaf enabled {
      type boolean;
      default false;
      description
        "This object is to control the availability of configuration.
         It MUST be true before anything in the
         /altmark/altmark-profile can be edited.
         If false, any configuration in place is not used.";
    }
  }

  grouping altmark-filter {
    description
      "A grouping for AltMark filter definition";

    leaf filter-type {
      type altmark-filter-type;
      description "filter type";
    }

    leaf ace-name {
      when "derived-from-or-self(../filter-type,
      'altmark:acl-filter')";
      type leafref {
        path "/acl:acls/acl:acl/acl:aces/acl:ace/acl:name";
      }
      description
        "The Access Control Entry name is used to refer to an
         ACL specification.";
    }
  }

  grouping altmark-setup {
    description
      "A grouping for AltMark profile.";

    leaf flow-mon-id {
      type flow-id;
      description
        "It specifies the FlowMonID. A 20-bit flow identifier as
         defined in RFC 9343 and RFC 9714. The field is set at the
         marking node. The FlowMonID can be uniformly assigned by
         a central controller or algorithmically generated by the
         marking node. Note that it corresponds to the
         altmarkFlowMonID parameter defined in
         draft-ietf-opsawg-ipfix-alt-mark.";
    }

    leaf method-type {
      type altmark-method-type;
      description
        "This item is used to indicate the AltMark method.";
    }

    leaf measurement-period {
      type uint64;
      description
        "It specifies the AltMark marking period. Its value can be set
         according to RFC 9341, RFC 9342 and
         draft-ietf-ippm-alt-mark-deployment";
    }

    leaf measurement-mode {
      type altmark-measurement-mode;
      default "hbh";
      description
        "It specifies the AltMark measurement mode.";
    }
  }

 /*
  * DATA NODES
  */

  container altmark {
    if-feature altmark;
    description
      "AltMark top level container";

    container admin-config {
      description
        "Contains all the administrative configurations related to
         the AltMark functionalities";

      uses altmark-admin-config;
    }

    container available-interfaces {
      description
        "It contains the list of the interfaces to be activated for
         AltMark";
      list available-interface {
        key "if-name";
        description
          "A list of available interfaces that support
           Alternate-Marking.";
        leaf if-name {
          type if:interface-ref;
          description "This is a reference to the Interface name.";
        }

        container altmark-profiles {
          description
            "Contains the AltMark profiles.";

          list altmark-profile {
            key "altmark-profile-name";
            description
              "It describes the list of the AltMark profiles
               configured on the node. The AltMark feature MUST be
               enabled on the node before anything in the
               altmark-profile can be edited";

            leaf altmark-profile-name {
              type string{
                length "1..300";
              }
              description
                "Unique identifier for each AltMark profile.";
            }

            container filter {
              uses altmark-filter;
              description
                "The filter which is used to indicate the flow where
                 the AltMark is applied.";
           }

            leaf direction {
              type flow-direction;
              description
               "Specify the flow direction.";
            }

            leaf interface-action {
              type altmark-interface-action;
              default action-read;
              description
                "This object indicates the action that the node needs
                 to take, i.e. marking/read/unmarking.";
            }

            leaf protocol-type {
              type altmark-protocol-type;
              description
                "This item is used to indicate the carrier protocol
                 where the AltMark is applied.";
            }

            uses altmark-setup;

            leaf enable-loss-measurement {
              type boolean;
              default false;
              description
                "If true, it indicates that loss measurements are
                 enabled.";
            }

            leaf enable-delay-measurement {
              type boolean;
              default false;
              description
                "If true, it indicates that delay measurements are
                enabled.";
            }
          }
        }
      }
    }
  }
}
