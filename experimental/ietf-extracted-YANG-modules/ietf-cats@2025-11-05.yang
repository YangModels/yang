module ietf-cats {
  yang-version 1.1;
  namespace "urn:ietf:params:xml:ns:yang:ietf-cats";
  prefix cats;

  import ietf-routing {
    prefix rt;
    reference
      "RFC 8349: A YANG Data Model for Routing
       Management (NMDA Version)";
  }

  import ietf-inet-types {
    prefix inet;
    reference
      "RFC 6991: Common YANG Data Types";
  }

  organization
    "IETF Computing-Aware Traffic Steering
     (CATS) Working Group";
  contact
    "WG Web:  <https://datatracker.ietf.org/group/cats/>
     WG List: <mailto:cats@ietf.org>
     Author:  Huijuan Yao
              <mailto:yaohuijuan@chinamobile.com>
     Author:  Changwang Lin
              <mailto:linchangwang.04414@h3c.com>
     Author:  Zhenqiang Li
              <mailto:lizhenqiang@chinamobile.com>
     Author:  Quan Xiong
              <mailto:xiong.quan@zte.com.cn>
     Author:  Luis M. Contreras
              <mailto:luismiguel.contrerasmurillo@telefonica.com>
     ";

  description
    "This module describes a YANG model for CATS.
     This YANG model conforms to the Network Management
     Datastore Architecture (NMDA) as described in RFC 8342.

     Copyright (c) 2025 IETF Trust and the persons identified as
     authors of the code. All rights reserved.
     Redistribution and use in source and binary forms, with or
     without modification, is permitted pursuant to, and subject
     to the license terms contained in, the Revised BSD License
     set forth in Section 4.c of the IETF Trust's Legal
     Provisions Relating to IETF Documents
     (https://trustee.ietf.org/license-info).

     This version of this YANG module is part of RFC XXXX
     (https://www.rfc-editor.org/info/rfcXXXX);
     see the RFC itself for full legal notices.

     The key words 'MUST', 'MUST NOT', 'REQUIRED', 'SHALL',
     'SHALL NOT', 'SHOULD', 'SHOULD NOT', 'RECOMMENDED', 'NOT
     RECOMMENDED', 'MAY', and 'OPTIONAL' in this document are to
     be interpreted as described in BCP 14 (RFC 2119) (RFC 8174)
     when, and only when, they appear in all capitals, as shown
     here.";

  revision 2025-11-05 {
    description
      "Initial Version";
    reference
      "RFC XXXX: YANG Data Model for CATS";
   }

  typedef cs-id {
    type union {
      type uint32;
      type inet:ipv4-address;
      type inet:ipv6-address;
    }
    description
      "This type is for CATS CS-ID.";
    reference
      "RFC XXXX: YANG Data Model for CATS";
  }

  typedef csci-id {
    type union {
      type uint32;
      type inet:ipv4-address;
      type inet:ipv6-address;
    }
    description
      "This type is for CATS CSCI-ID.";
    reference
      "RFC XXXX: YANG Data Model for CATS";
  }
  grouping service-policy-type {
    description
      "service policy type";
    leaf policy-type {
      type enumeration {
        enum base-on-affinity {
          value 0;
          description "base on affinity";
        }
        enum base-on-sm-only {
          value 1;
          description "base on service metric only";
        }
        enum base-on-nm-only {
          value 2;
          description "base on network metric only";
        }
        enum base-on-sm-nm {
          value 3;
          description
            "base on the combination of service metric and network
             metric";
        }
      }
      description "service policy type";
    }
  }

  augment "/rt:routing" {
    description
      "This augments the CATS configuration.";
    container cats {
      description
        "Support for the CATS configuration.";
      container base {
        description
          "CATS base configuration.";
        leaf enable {
          type boolean;
          description
            "enable CATS";
        }
        leaf update-interval {
          type uint32;
          units "seconds";
          default "30";
          description
            "Update interval of CATS metric. A value of 0
             indicates that metrics are sent only when a
             significant change occurs and not on a periodic
             basis.";
        }
        leaf metric-limits {
          type uint32;
          description
            "CATS metric entry limit";
        }
        leaf flow-limits {
          type uint32;
          description
            "CATS flow entry limit";
        }
        leaf flow-timeout {
          type uint32;
          units "seconds";
          default "120";
          description
            "CATS flow timeout when no flow. A value of 0 means
             that the flow does not time out due to inactivity
             (i.e., infinite timeout), and must be terminated
             explicitly (e.g., via signaling or administrative
             action).";
        }
        container service-policy {
          description
            "CATS service policy";
          leaf cs-id {
            type cs-id;
            description
              "cs-id";
          }
          uses service-policy-type;
        }
      }

      container traffic-classifiers {
        description
          "CATS traffic-classifier feature";
        list traffic-classifier {
          key "cs-id";
          description
            "CATS traffic-classifier feature";
          leaf cs-id {
            type cs-id;
            description
              "CATS CS-ID";
          }
          leaf description {
            type string;
            description
              "description of this service, example: http";
          }
          leaf server-port {
            type uint16;
            description
              "server-port of the service, matches the
               destination port in the IP packets of data
               flows destined for the service.";
          }
          leaf protocol {
            type uint8;
            description
              "protocol of the service.";
          }
        }
      }

      container service-metrics {
        description
          "CATS service metric entry";
        list service-metric {
          key "cs-id csci-id source-type";
          description
            "CATS service metric entry";
          leaf cs-id {
            type cs-id;
            description
              "CATS cs-id";
          }
          leaf csci-id {
            type csci-id;
            description
              "CATS csci-id";
          }
          leaf source-type {
            type enumeration {
              enum static {
                value 0;
                description "static configuration";
              }
            }
            description
              "source-type of the service compute-metric";
          }
          leaf priority {
            type uint8;
            description
              "server priority, the smaller the value,
               the higher the priority.";
          }
          leaf affinity {
            type uint8;
            description
              "server affinity, the higher the value,
               the higher the affinity.";
          }
          leaf location {
            type inet:ip-address;
            description
              "server location";
          }
          container metrics {
            description
              "service metric";
            list metric {
              key "metric-type";
              description "Different types of service.";
              leaf metric-type {
                type enumeration {
                  enum delay {
                    value 0;
                    description
                      "Calculate the metric based on transmission
                       delay, where the metric value is the delay
                       time in milliseconds.";
                  }
                  enum service-ratio {
                    value 1;
                    description
                      "Calculate the metric based on business
                       capacity, where the metric value is the
                       current capacity percentage.";
                  }
                  enum memory-ratio {
                    value 2;
                    description
                      "Calculate the metric based on memory
                       utilization percentage, where the metric
                       value is the current memory utilization
                       percentage";
                  }
                }
                description "metric type";
                reference
                  "RFC YYYY: CATS Metrics Definition";
              }
              leaf metric-value {
                type uint32;
                description "metric value";
              }
            }
          }
        }
      }
      container notify {
        description "event notify";
        leaf entry-limit-reached {
          type boolean;
          description "entry limit reached";
        }
        leaf flow-limit-reached {
          type boolean;
          description "flow entry limit reached";
        }
      }
    }
  }
}
