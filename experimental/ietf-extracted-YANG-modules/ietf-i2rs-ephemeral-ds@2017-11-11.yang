module ietf-i2rs-ephemeral-ds {
  yang-version 1.1;
  namespace "urn:ietf:params:xml:ns:yang:ietf-i2rs-ephemeral-ds";
  prefix i2rs;

  import ietf-datastores {
    prefix ds;
  }
  import ietf-origin {
    prefix or;
  }

      organization
             "IETF I2RS (Interface to the Routing System)
              Working Group";

     contact
        "WG WB:  <http://tools.ietf.org/wg/i2rs>
         WG List: <mailto:i2rs@ietf.org>
             Editor:  Susan Hares
                      <mailto: shares@ndzh.com>

             Editor:  Alex Clemm
                      <mailto: ludwig@clemm.org>";

     description
        "This module defines the I2RS ephemeral datastore.
     Deployed copies will augment the

             Copyright (c) 2017 IETF Trust and the persons
             identified as authors of the code.  All rights reserved.

             Redistribution and use in source and binary forms,
             without modification, is permitted pursuant to,
             and subject to the license terms contained in,
             the Simplified BSD License set form in
             Section 4.c of the IETF Trust's Legal Provisions
             related to the IETF documents
             (http://trusee.ietf.org/license-info).

             This version of this YANG Module is part of
             draft-hcww-i2rs-ephemeral-ds-00.txt.
             See the RFC itself for full legal notices.

             Note to RFC Editor: Please replace above reference
             to the draft-hcww-i2rs-ephemeral-ds-00.txt
             with RFC umber when published (i.e. RFC xxx).";

             revision 2017-11-11 {
             description
               "initial revision.
                Note to RFC EDITOR:
                (1) Please replace the following reference with
                to draft-hwcc-i2rs-ephemeral-ds with
                RFC number whe published (i.e. RFC xxx)";

                reference "draft-hcww-i2rs-ephemeral-ds-00.txt";

             }

  // add datastore identity
  identity ds-ephemeral {
    base ds:datastore;
    description
      "The 'ephemeral' datastore.";
  }

  // add origin identity
  identity or-ephemeral {
    base or:dynamic;
    description
      "Denotes data from the ephemeral dynamic datastore.";
  }

  extension data-not-sensitive {
    argument "value";
    description
      "This extension indicates that this
              read-only data node is not sensitive
              and should be allowed to
              access via a non-secure transport.
              The value is either true or false.
              ";
  }

      // modules which can be used this draft are included here
  // topology drafts:
  //ietf-network, ietf-network-topology
      // with state modules (ietf-network-state,
      // ietf-network-topology-state)
  // ietf-l3-unicast-topology
      // with state modules
      // (ietf-l3-unicast-topology-state)
  // ietf-i2rs-rib
  // (additional models can be added here

}
