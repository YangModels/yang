module ietf-pim-dm {
  yang-version 1.1;
  namespace "urn:ietf:params:xml:ns:yang:ietf-pim-dm";
  prefix pim-dm;

  import ietf-routing {
    prefix "rt";
  }

  import ietf-pim-base {
    prefix "pim-base";
  }

  organization
    "IETF PIM Working Group";

  contact
    "WG Web:   <http://tools.ietf.org/wg/pim/>
     WG List:  <mailto:pim@ietf.org>

     Editor:   Xufeng Liu
               <mailto:Xufeng_Liu@jabil.com>

     Editor:   Pete McAllister
               <mailto:pete.mcallister@metaswitch.com>

     Editor:   Anish Peter
               <mailto:anish.ietf@gmail.com>

     Editor:   Mahesh Sivakumar
               <mailto:masivaku@cisco.com>

     Editor:   Yisong Liu
               <mailto:liuyisong@huawei.com>

     Editor:   Fangwei Hu
               <mailto:hu.fangwei@zte.com.cn>";

  description
    "The YANG module defines a PIM (Protocol Independent Multicast)
     DM (Dense Mode) model.";

  revision 2018-01-29 {
    description
      "Initial revision.";
    reference
      "RFC XXXX: A YANG Data Model for PIM.
       RFC 3973: Protocol Independent Multicast - Dense Mode
      (PIM-DM): Protocol Specification (Revised).";
  }

  /*
   * Configuration data nodes
   */

  augment "/rt:routing/rt:control-plane-protocols/"
    + "pim-base:pim/pim-base:address-family" {
    description "PIM DM (Dense Mode) augmentation.";

    container dm {
      presence "Present to enable dense-mode.";
      description
        "PIM DM configuration data.";
    } // Dm
  } // augment

  augment "/rt:routing/rt:control-plane-protocols/"
    + "pim-base:pim/pim-base:interfaces/pim-base:interface/"
    + "pim-base:address-family" {
    description "PIM DM augmentation to PIM base interface.";

    container dm {
      presence "Present to enable dense-mode.";
      description
        "PIM DM configuration data.";
    } // sm
  } // augment
}
