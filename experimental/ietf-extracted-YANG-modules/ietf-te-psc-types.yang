module ietf-te-psc-types {

    namespace "urn:cisco:params:xml:ns:yang:ietf-psc-te-types";

    /* Replace with IANA when assigned */
    prefix "te-psc-types";

    import ietf-inet-types { prefix inet; }

    organization
      "IETF TEAS Working Group";

    description
        "This module contains a collection of generally
         useful TE specific YANG data type defintions.";

    /* Describes egress LSP label allocation */
    typedef egress-label {
        description
            "Describes egress label allocation";
        type enumeration {
            enum "IPv4-EXPLICIT-NULL" {
                description
                    "Use IPv4 explicit-NULL MPLS label at the egress";
            }
            enum "IPv6-EXPLICIT-NULL" {
                description
                    "Use IPv6 explicit-NULL MPLS label at the egress";
            }
            enum "IMPLICIT-NULL" {
                description
                    "Use implicit-NULL MPLS label at the egress";
            }
            enum "NON-NULL";
                description
                    "Use a non NULL MPLS label at the egress";
        }
    }

    identity backup-type {
        description
            "Base identity for backup protection types";
    }

    identity backup-facility {
        base backup-type;
        description
            "Use facility backup to protect LSPs traversing
            protected TE interface";
        reference
            "RFC49090: RSVP-TE Fast Reroute";
    }

    identity backup-detour {
        base backup-type;
        description
            "Use detour or 1-for-1 protection";
        reference
            "RFC49090: RSVP-TE Fast Reroute";
    }

    identity backup-protection-type {
        description
            "Base identity for backup protection type";
    }

    identity backup-protection-link {
        base backup-protection-type;
        description
            "backup provides link protection only";
    }

    identity backup-protection-node-link {
        base backup-protection-type;
        description
            "backup offers node (preferred) or link protection";
    }

    identity bc-model-type {
        description
            "Base identity for Diffserv-TE bandwidth constraint
            model type";
    }

    identity bc-model-rdm {
        base bc-model-type;
        description
            "Russian Doll bandwidth constraint model type.";
    }

    identity bc-model-mam {
        base bc-model-type;
        description
            "Maximum Allocation bandwidth constraint
            model type.";
    }

    identity bc-model-mar {
        base bc-model-type;
        description
            "Maximum Allocation with Reservation
            bandwidth constraint model type.";
    }

    grouping bandwidth-constraint-values {
        choice value-type {
             case percentages {
                 container perc-values {
                     uses bandwidth-psc-constraints;
                 }
             }
             case absolutes {
                 container abs-values {
                     uses bandwidth-psc-constraints;
                 }
             }
        }
    }

    grouping bandwidth-psc-reservable {
        choice bc-model-type {
        description
            "Reservable bandwidth percentage capacity
            values.";
        case bc-model-rdm {
            container bc-model-rdm {
                description
                    "Russian Doll Model Bandwidth Constraints.";
                uses bandwidth-psc-constraints;
            }
        }
        case bc-model-mam {
            container bc-model-mam {
                description
                    "Maximum Allocation Model Bandwidth Constraints.";
                uses bandwidth-psc-constraints;
            }
        }
        case bc-model-mar {
            container bc-model-mar {
                description
                    "Maximum Allocation with Reservation Model
                    Bandwidth Constraints.";
                uses bandwidth-psc-constraints;
            }
        }
        }
    }

    typedef bfd-type {
        type enumeration {
            enum classical {
                description "BFD classical session type.";
            }
            enum seamless {
                description "BFD seamless session type.";
            }
        }
        default "classical";
    }

    typedef bfd-encap-mode-type {
        type enumeration {
            enum gal;
            enum ip;
        }
        default ip;
        description
            "Possible BFD transport modes when running over TE
             LSPs.";
    }

    grouping bandwidth-psc-constraints {
        description "Bandwidth constraints.";
        container bandwidth-psc-constraints {
            leaf maximum-reservable {
                type uint32 {
                     range "0..4294967295";
                }
            }
            leaf-list bc-value {
                type uint32 {
                    range "0..4294967295";
                }
                max-elements 8;
            }
        }
    }

    grouping tunnel-routing-properties {
        choice routing-choice {
            description
                "Announces the tunnel to IGP as either
                 autoroute or forwarding adjacency.";
            case autoroute {
                container autoroute-announce {
                    presence "Enable autoroute announce.";
                    description
                        "Announce the TE tunnel as autoroute to
                         IGP for use as IGP shortcut.";
                    leaf-list routing-afs {
                         type inet:ip-version;
                    }
                    choice metric-type {
                        leaf metric {
                            type uint32 {
                                 range "1..2147483647";
                            }
                        }
                        leaf relative-metric {
                            type int32 {
                                 range "-10..10";
                            }
                        }
                        leaf absolute-metric {
                            type uint32 {
                                 range "1..2147483647";
                            }
                        }
                    }
                }
            }
            case forwarding-adjacency {
                container forwarding-adjacency {
                    presence "Enable forwarding adjacency
                              on the tunnel.";
                    description
                        "Announce the TE tunnel
                         as forwarding adjacency.";
                    leaf holdtime {
                        description
                            "Holdtime in seconds after
                             tunnel becomes UP.";
                        type uint32 {
                             range "0..4294967295";
                        }
                    }
                    leaf-list routing-afs {
                         type inet:ip-version;
                    }
                }
            }
        }
    }
}
