module ietf-flexe {
  yang-version 1.1;
  namespace "urn:ietf:params:xml:ns:yang:ietf-flexe";
  prefix "flexe";

  import iana-if-type {
    prefix ianaift;
  }
  import ietf-interfaces {
    prefix if;
    reference
    "RFC8343: A YANG Data Model for Interface Management";
  }

  organization "IETF CCAMP Working Group";
  contact
   "WG Web:   http://tools.ietf.org/wg/ccamp/
    WG List:  <mailto:ccamp@ietf.org>
    Author:   Minxue Wang
              <mailto: wangminxue@chinamobile.com>
    Author:   Liuyan Han
              <mailto: hanliuyan@chinamobile.com>
    Author:   Fan Yang
              <mailto:shirley.yangfan@huawei.com>
    Author:   Xiaobing Niu
              <mailto: niu.xiaobing@zte.com.cn>
    Author:   Luis M. Contreras
              <mailto:luismiguel.contrerasmurillo@telefonica.com>
    Author:   Xufeng Liu
              <mailto:xufeng.liu.ietf@gmail.com>";
  description
   "This YANG module defines a data model for the configuration
    of a FlexE network.";

  revision "2022-05-16" {
    description "the third version";
    reference
    "draft-wang-ccamp-flexe-yang-cm-03: YANG Data Model for FlexE
     Management";
  }

  typedef negotiation-mode-type {
    type enumeration {
      enum "dynamic" {
        value 1;
        description
          "Dynamic mode.";
      }
      enum "static" {
        value 2;
        description
          "Static mode.";
      }
    }
    description
      "Negotiation mode of a FlexE group.";
  }

  container flexe {
    description
      "Specify FlexE configuration information.";
    container flexe-groups {
      description
        "List of FlexE groups.";
      list flexe-group {
        key "index";
        description
          "Configure FlexE group.";
        leaf index {
          type uint32 {
            range "1..65535";
          }
          description
            "FlexE group index.";
        }
        leaf group-num {
          type uint32 {
            range "1..1048574";
          }
          mandatory true;
          description
            "FlexE group number, as specified in OIF FlexE 2.1.";
        }
        leaf negotiation-mode {
          type negotiation-mode-type;
          mandatory true;
          description
            "FlexE group calendar negotiation mode, the default
             value is 'dynamic'.";
        }
        leaf total-bandwidth {
          type string {
            length "1..9";
          }
          config false;
          mandatory true;
          description
            "FlexE group total bandwidth in Gbit/s, such as 10.";
        }
        leaf free-bandwidth {
          type string {
            length "1..9";
          }
          config false;
          description
            "FlexE group free bandwidth in Gbit/s, such as 100.";
        }
        leaf sync-phy-number {
          type uint32 {
            range "1..254";
          }
          config false;
          mandatory true;
          description
            "The FlexE PHY number used for synchronization management
             channel in a FlexE group, which is one of the PHY number
             value in a FlexE group.";
        }
        container flexe-phys {
          description
            "List of physical port information in a FlexE Group.";
          list flexe-phy {
            key "port-name";
            description
              "FlexE PHY port name.";
            leaf port-name {
              type if:interface-ref;
              description
                "Physical port name. ";
            }
            leaf phy-number {
              type uint32 {
                range "1..254";
              }
              mandatory true;
              description
                "Number of a FlexE physical port. The PHY number of
              a 100G port is an integer ranging from 1 to 254.
              The PHY number of a 50G port is an integer ranging
              from 1 to 126.";
            }
            leaf free-timeslot-list {
              type string {
                length "1..199";
              }
              config false;
              mandatory true;
              description
               "Free timeslots of a FlexE PHY. The string
               consists of one or more numbers separated by
               commas (,) or hyphens (-), e.g.'1-5' indicates
               1,2,3,4,5 timeslots, '0,5,7-10' indicates
               0,5,7,8,9,10 timeslots.";
            }
            leaf used-timeslot-list {
              type string {
                length "1..199";
              }
              config false;
              mandatory true;
              description
               "Used timeslots of a FlexE PHY. The string
               consists of one or more numbers separated by
               commas (,) or hyphens (-), e.g.'1-5' indicates
               1,2,3,4,5 timeslots, '0,5,7-10' indicates
               0,5,7,8,9,10 timeslots.";
            }
          }
        }
      }
    }
  }
}
