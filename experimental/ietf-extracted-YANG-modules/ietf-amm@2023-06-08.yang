module ietf-amm {
  namespace "ari:/ietf-amm";
  prefix amm;
  amm:enum "0";

  organization
    "IETF Delay Tolerant Networking (DTN) Working Group";
  contact
    "WG Web: <http://tools.ietf.org/wg/dtn/>
     WG List: <mailto:dtn@ietf.org>

     Author: Brian Sipos
             <mailto:brian.sipos+ietf@gmail.com>";
  description
    "This module implements the DTN Management Architecture (DTNMA)
     Application Management Model (AMM) extensions within YANG";
  reference
    "draft-birrane-dtn-adm";

  revision 2023-06-08 {
    description
      "Updated for latest AMM contents.";
    reference
      "draft-birrane-dtn-adm";
  }
  revision 2016-04-01 {
    description
      "Updated to fix typos.";
    reference
      "draft-bsipos-dtn-amp-yang";
  }
  revision 2016-03-14 {
    description
      "Initial draft release.";
    reference
      "draft-bsipos-dtn-amp-yang";
  }

  /****
   * This section contains extension for AMM object definitions
   ****/
  // This group of extensions are for common behavior for AMM objects

  extension enum {
    argument value;
    description
      "An enumeration identifies an object within a namespace.
       The argument to this statement is the integer value.";
  }

  extension parameter {
    argument name;
    description
      "The schema for a formal parameter of an object.
       Order of parameters is significant within this statement.";
  }

  extension default {
    argument value;
    description
      "The literal value default for a parameter or result.
       The argument is the text form of the ARI";
  }

  extension init-value {
    argument value;
    description
      "The literal value of a CONST object,
       initial state for a VAR object.
       The argument is the text form of the ARI";
  }

  extension init-expr {
    argument expr;
    description
      "An expression evaluated to initialize a VAR object.
       The argument is the text form of the EXPR AC";
  }

  // This group are AMM object keywords and their parameters

  extension typedef {
    argument name;
    description
      "Definition of a TYPEDEF within an ADM.
       The argument to this statement is the object name.
       One of the type use substatements must be present.";
  }

  extension ident {
    argument name;
    description
      "Definition of an IDENT within an ADM.
       The argument to this statement is the object name.
       An 'base' substatement must be present.";
  }

  extension base {
    argument name;
    description
      "The argument is the base of an IDENT object.";
  }

  extension const {
    argument name;
    description
      "Definition of a CONST within an ADM.
       The argument to this statement is the object name.
       An 'init-value' substatement must be present.";
  }

  extension ctrl {
    argument name;
    description
      "Definition of a CTRL within an ADM.
       The argument to this statement is the object name.";
  }

  extension result {
    argument name;
    description
      "A result value reported as a response to a control.
       The substatement is the result type.
       Each CTRL can have a single optional result.";
  }

  extension edd {
    argument name;
    description
      "Definition of an EDD within an ADM.
       The argument to this statement is the object name.";
  }

  extension oper {
    argument name;
    description
      "Definition of an OPER within an ADM.
       The argument to this statement is the object name.";
  }

  extension operand {
    argument name;
    description
      "An individual operand taken from the expression stack
       during evaluation of the OPER.
       Each substatement is an operand as a leaf (ARI).
       Order of operands is significant within an object definition.";
  }

  extension var {
    argument name;
    description
      "Definition of a VAR within an ADM.
       The argument to this statement is the object name.";
  }

  /****
   * This section contains ARI (literal and object-reference) value types.
   ****/

  extension type {
    argument name;
    description
      "A reference to a built-in type or prefix-qualified typedef.";
  }

  extension int-labels {
    description
      "Type narrowing for an INTEGER to label enum values or bit positions.";
  }

  extension cddl {
    argument text;
    description
      "Type narrowing for a CBOR item in the form of CDDL syntax.
       The argument to this statement is the actual CDDL text.";
  }

  extension ulist {
    description
      "Type for an AC containing a list of uniform-typed values.";
  }

  extension dlist {
    description
      "Type for an AC containing a list of diverse-typed sequences.";
  }

  extension seq {
    description
      "A sequence of uniform-typed values within a 'dlist'.";
  }

  extension tblt {
    description
      "Type for a table of values with a column schema.";
  }

  extension column {
    argument name;
    description
      "Type for a table of values with a column schema.";
  }

  extension key {
    argument columns;
    description
      "Names of columns composing the row key.";
  }

  extension unique {
    argument columns;
    description
      "Names of columns composing a uniqueness constraint.";
  }

  extension union {
    description
      "Type for a union of other types.";
  }

  // Named type unions for literals
  amm:typedef TYPE-REF {
    amm:union {
      amm:type LITTYPE;
      amm:type TYPEDEF-REF;
    }
    description
      "Reference to either a literal type or a typedef.";
  }
  amm:typedef INTEGER {
    amm:union {
      amm:type BYTE;
      amm:type UINT;
      amm:type INT;
      amm:type UVAST;
      amm:type VAST;
    }
    description
      "Any type which represents a discrete integer.";
  }
  amm:typedef FLOAT {
    amm:union {
      amm:type REAL32;
      amm:type REAL64;
    }
    description
      "Any type which represents a floating point number.";
  }
  amm:typedef NUMERIC {
    amm:union {
      amm:type INTEGER;
      amm:type FLOAT;
    }
    description
      "Any type which can be used with numeric expressions.";
  }
  amm:typedef TIME {
    amm:union {
      amm:type TP;
      amm:type TD;
    }
    description
      "Any type which can be used with time expressions.";
  }
  amm:typedef SIMPLE {
    amm:union {
      amm:type NULL;
      amm:type BOOL;
      amm:type NUMERIC;
      amm:type TEXTSTR;
      amm:type BYTESTR;
      amm:type TIME;
      amm:type LABEL;
      amm:type CBOR;
    }
    description
      "Any type which contains a single literal value (not complex).";
  }
  amm:typedef COMPLEX {
    amm:union {
      amm:type AC;
      amm:type AM;
    }
    description
      "A literal type which is not SIMPLE.";
  }
  amm:typedef LITERAL {
    amm:union {
      amm:type TYPE-REF; //FIXME: is typeref a literal or something else?
      amm:type SIMPLE;
      amm:type COMPLEX;
    }
    description
      "Any type which is represented as a literal ARI.";
  }
  amm:typedef ANY {
    amm:union {
      amm:type LITERAL;
      amm:type OBJECT;
    }
    description
      "Any type representable by an ARI.";
  }
  amm:typedef VALUE-OBJ {
    amm:union {
      amm:type CONST;
      amm:type EDD;
      amm:type VAR;
    }
    description
      "A reference to an object which can produce a value.";
  }

  // operational semantic types
  amm:typedef counter32 {
    amm:type UINT;
    description
      "A 32-bit counter with an arbitrary initial value that only increments.
       When the value reaches the upper range it wraps around to zero.
       At least two samples of this value need to be compared over time.";
  }
  amm:typedef counter64 {
    amm:type UVAST;
    description
      "A 64-bit counter with an arbitrary initial value that only increments.
       When the value reaches the upper range it wraps around to zero.
       At least two samples of this value need to be compared over time.";
  }
  amm:typedef gauge32 {
    amm:type INT;
    description
      "A 32-bit value sampling some quantized measurement.
       The value can increase or decrease arbitrarily over time.";
  }
  amm:typedef gauge64 {
    amm:type VAST;
    description
      "A 64-bit value sampling some quantized measurement.
       The value can increase or decrease arbitrarily over time.";
  }
  amm:typedef timestamp {
    amm:type TP;
    description
      "A time point representing the system clock at which a specific
       occurrence happened.
       The specific occurrence must be defined in the description
       of any node defined using this type.";
  }

  // Restrictions on AC item types for specific purposes
  amm:typedef EXPR-item {
    amm:union {
      amm:type SIMPLE;
      amm:type VALUE-OBJ;
      amm:type TYPEDEF;
      amm:type OPER;
    }
    description
      "Each item of an EXPR list.
       The value-object must be typed to contain a SIMPLE.";
  }
  amm:typedef EXPR {
    amm:ulist {
      amm:type EXPR-item;
    }
    description
      "The contents of an EXPR container.";
  }
  amm:typedef EXEC-item {
    amm:union {
      amm:type VALUE-OBJ;
      amm:type CTRL;
    }
    description
      "A reference to an object which can be executed.
       The value-object must be typed to contain a MAC.";
  }
  amm:typedef MAC {
    amm:ulist {
      amm:type EXEC-item;
    }
    description
      "The contents of a MAC container.";
  }
  amm:typedef RPTT-item {
    amm:union {
      amm:type VALUE-OBJ;
      amm:type EXPR;
    }
    description
      "Each item of a RPTT.
       Each item references a value-producing object or contains an
       expression to be evaluated.";
  }
  amm:typedef RPTT {
    amm:ulist {
      amm:type RPTT-item;
    }
    description
      "The contents of a report template, encoded as the sequence of items.";
  }
  amm:typedef RPT {
    amm:dlist {
      amm:type VALUE-OBJ {
        description
          "Reference to the reported object.";
      }
      amm:type timestamp {
        description
          "The generation timestamp.";
      }
      amm:seq {
        amm:type ANY;
        description
          "The sequence of items in the report.";
      }
    }
    description
      "The source and contents of a report, encoded as the sequence
       of values reported.
       The semantics of each item are contained in the associated
       source object (RPTT or CTRL).";
  }
  amm:typedef TBL {
    amm:dlist {
      amm:type UVAST {
        description
          "The number of columns in the table.";
      }
      amm:seq {
        amm:type ANY;
        description
          "All table values listed in row-major order.";
      }
    }
    description
      "The flattened contents of a table.
       The semantics of each column are contained in the associated TBLT.";
  }
}
