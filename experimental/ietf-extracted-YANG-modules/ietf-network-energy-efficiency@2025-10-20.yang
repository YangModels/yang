module ietf-network-energy-efficiency {

  yang-version 1.1;

  namespace "urn:ietf:params:xml:ns:yang:ietf-network-energy-
efficiency";

  prefix ntw-eff;

  import ietf-network {

    prefix nw;

    reference

      "RFC 8345: A YANG Data Model for Network Topologies";

  }

  import ietf-yang-types {
    prefix yang;

    reference

      "RFC 6991: Common YANG Types";

  }

  import iana-hardware {

    prefix ianahw;

    reference

      "https://www.iana.org/assignments/iana-hardware/iana-
hardware.xhtml";

  }

  organization "IETF NETMOD Working Group";

  contact

    "WG Web:   <https://datatracker.ietf.org/wg/netmod/>

     WG List:  <mailto:netmod@ietf.org>";

  description

    "This module augments the ietf-network model to add power

     consumption monitoring capabilities for hardware components.

     Copyright (c) 2025 IETF Trust and the persons identified as

     authors of the code. All rights reserved.";

  revision 2025-10-20 {

    description

      "Initial revision.";

    reference
      "RFC XXXX: Power Consumption Extension for Hardware
Management";

  }

  feature energy-efficiency {

    description

      "Indicates support for energy efficiency monitoring features";

  }

  // ========== Type Definitions ==========

  identity green-type {

    description "Base identity for energy-efficiency types";

  }

  identity average {

    base green-type;

    description "Average energy-efficiency over time";

  }

  identity maximum {

    base green-type;

    description "Maximum energy-efficiency observed";

  }

  identity real-time {

    base green-type;
    description "Real-time energy-efficiency reading";

  }

  grouping green-energy-efficiency {

    description "Energy Efficiency attributes";

    leaf value {

      type decimal64 {

        fraction-digits 4;

      }

      units "watts/GB";

      mandatory true;

      description "Energy Efficiency value";

    }

    leaf timestamp {

      type yang:date-and-time;

      description "Time when measurement was taken";

    }

    leaf update-period {

      type uint32;

      units "seconds";

      description

        "For maximum and real-time values, it indicates the minimum
refresh time when there is a change; if the value remains unchanged,
no refresh occurs. For the average, it represents the sampling
window.";

    }

  } // End of green-energy-efficiency grouping

  // ========== Main Augmentation ==========

  augment "/nw:networks/nw:network/nw:node" {

    if-feature energy-efficiency;

    description

      "Add green consumption to network components";

    list component {

      key name;

      config false;

      description

        "List of components.";

      leaf name {

        type string;

        description

          "The name assigned to this component.

           This name is not required to be the same as

           entPhysicalName.";

      }

      leaf class {
        type identityref {

          base ianahw:hardware-class;

        }

        mandatory true;

        description

          "An indication of the general hardware type of the

           component.";

        reference

          "RFC 6933: Entity MIB (Version 4) - entPhysicalClass";

      }

      uses green-energy-efficiency;

    } // End of component list

  } // End of augment

} // End of module
