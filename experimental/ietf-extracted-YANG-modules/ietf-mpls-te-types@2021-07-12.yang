module ietf-mpls-te-types {
  yang-version 1.1;
  namespace "urn:ietf:params:xml:ns:yang:ietf-mpls-te-types";

  prefix "mte-types";

  import ietf-routing-types {
    prefix "rt-types";
  }

  organization
    "Internet Engineering Task Force (IETF) TEAS WG";
  contact
    "WG Web:   <https://datatracker.ietf.org/wg/teas/>
     WG List:  <mailto:teas@ietf.org>

     Editor: Italo Busi
       <mailto:italo.busi@huawei.com>

     Editor: Haomian Zheng
       <mailto:zhenghaomian@huawei.com>

     Editor: Aihua Guo
       <mailto:aihuaguo.ietf@gmail.com>

     Editor: Xufeng Liu
       <mailto:xufeng.liu.ietf@gmail.com>";

  description
    "This module defines technology-specific MPLS-TE types
     data model.

     Copyright (c) 2021 IETF Trust and the persons identified
     as authors of the code.  All rights reserved.

     Redistribution and use in source and binary forms, with
     or without modification, is permitted pursuant to, and
     subject to the license terms contained in, the Simplified
     BSD License set forth in Section 4.c of the IETF Trust's
     Legal Provisions Relating to IETF Documents
     (http://trustee.ietf.org/license-info).
     This version of this YANG module is part of RFC XXXX; see
     the RFC itself for full legal notices.";

  revision 2021-07-12 {
    description
      "Initial Version";
    reference
      "draft-busizheng-teas-yang-te-mpls-topology";
  }

  /*
  * Typedefs
  */

  typedef load-balancing-type {
    type enumeration {
      enum per-flow {
        description
          "The load-balancing algorithm ensures that packets
           characterized as the same flow (e.g. based on IP 5-tuple)
           that egress on a LAG or a bundled TE link are forwarded
           on the same component link.

           Packets for different flows within the same LSP can be
           forwarded on different component links.";
      }
      enum per-top-label {
        description
          "The load-balancing algorithm ensures incoming MPLS
           packets with the same top MPLS label and that egress on
           on a LAG or bundled TE link are forwarded on the same
           component link.

           Packets for different flows within the same LSP are
           forwarded on the same component link.";
      }
    }
    description
      "The type of load balancing used on bundled links.";
  }  // typedef load-balancing-type

  /*
  * Groupings
  */

  grouping te-mpls-label-hop {
    description
      "MPLS-TE Label Hop.";
    leaf mpls-label {
      type rt-types:mpls-label;
      description
        "MPLS Label.";
    }
  }  // grouping te-mpls-label-hop
}
