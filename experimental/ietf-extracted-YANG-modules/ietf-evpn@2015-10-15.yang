module ietf-evpn {
  namespace "urn:ietf:params:xml:ns:yang:ietf-evpn";
  prefix "evpn";

  import ietf-yang-types {
    prefix "yang";
  }

  organization  "ietf";
  contact       "ietf";
  description   "evpn";

  revision "2015-10-15" {
    description "Initial revision";
    reference   "";
  }

  /* Typedefs */

  typedef bgp-rt-type {
    type enumeration {
      enum import {
        description "For import";
      }
      enum export {
        description "For export";
      }
      enum both {
        description "For both import and export";
      }
    }
    description "BGP route-target type. Import from BGP YANG";
  }

  /* Groupings */

  grouping bgp-parameters-grp {
    description "BGP parameters grouping";
    container bgp-parameters {
      description "BGP parameters";
      container common {
        description "Common BGP parameters";
        leaf route-distinguisher {
          type string;
          description "BGP RD";
        }
        list vpn-targets {
          key rt-value;
          description "Route Targets";
          leaf rt-value {
            type string;
            description "Route-Target value";
          }
          leaf rt-type {
            type bgp-rt-type;
            mandatory true;
            description "Type of RT";
          }
        }
      }
    }
  }

  /* EVPN YANG Model */

  container evpn {
    description "evpn";
    container common {
      description "common epn attributes";
      choice replication-type {
        description "A choice of replication type";
        case ingress-replication {
          leaf ingress-replication {
            type boolean;
            description "ingress-replication";
          }
        }
        case p2mp-replication {
          leaf p2mp-replication {
            type boolean;
            description "p2mp-replication";
          }
        }
      }
    }
    container evpn-instances {
      description "evpn-instances";
      list evpn-instance {
        key "name";
        description "An EVPN instance";
        leaf name {
          type string;
          description "Name of EVPN instance";
        }
        leaf evi {
          type uint32;
          description "evi";
        }
        leaf source-bmac {
          type yang:hex-string;
          description "source-bmac";
        }
        leaf evpn-arp-proxy {
          type boolean;
          description "evpn-arp-proxy";
        }
        leaf nd-arp-proxy {
          type boolean;
          description "nd-arp-proxy";
        }
        uses bgp-parameters-grp;
      }
    }
  }
}
