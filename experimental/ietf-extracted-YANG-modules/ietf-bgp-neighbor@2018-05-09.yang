submodule ietf-bgp-neighbor {
  yang-version "1.1";
  belongs-to ietf-bgp {
    prefix "bgp";
  }

  import ietf-routing-policy {
    prefix rpol;
  }
  import ietf-bgp-types {
    prefix bgp-types;
  }
  import ietf-inet-types {
    prefix inet;
  }
  import ietf-yang-types {
    prefix yang;
  }

  // Include the common submodule
  include ietf-bgp-common;
  include ietf-bgp-common-multiprotocol;
  include ietf-bgp-peer-group;
  include ietf-bgp-common-structure;

  // meta
  organization
    "IETF IDR Working Group";

  contact
    "WG Web:   <http://tools.ietf.org/wg/idr>
     WG List:  <idr@ietf.org>

     Editor:  Mahesh Jethanandani (mjethanandani@gmail.com)
     Authors: Keyur Patel,
              Mahesh Jethanandani,
              Susan Hares";

  description
    "This sub-module contains groupings that are specific to the
     neighbor context of the OpenConfig BGP module.";

  revision "2018-05-09" {
    description
      "Initial Version";
    reference
      "RFC XXX, BGP Model for Service Provider Network.";
  }

  grouping bgp-neighbor-use-multiple-paths {
    description
      "Multi-path configuration and state applicable to a BGP
       neighbor";

    container use-multiple-paths {
      description
        "Parameters related to the use of multiple-paths for the same
         NLRI when they are received only from this neighbor";

      uses bgp-common-use-multiple-paths-config;

      container ebgp {
        description
          "Multi-path configuration for eBGP";
        uses bgp-common-use-multiple-paths-ebgp-as-options-config;
      }
    }
  }

  grouping bgp-neighbor-counters-message-types-state {
    description
      "Grouping of BGP message types, included for re-use across
       counters";

    leaf UPDATE {
      type uint64;
      description
        "Number of BGP UPDATE messages announcing, withdrawing or
         modifying paths exchanged.";
    }

    leaf NOTIFICATION {
      type uint64;
      description
        "Number of BGP NOTIFICATION messages indicating an error
         condition has occurred exchanged.";
    }
  }

  grouping bgp-neighbor-afi-safi-list {
    description
      "List of address-families associated with the BGP neighbor";

    list afi-safi {
      key "afi-safi-name";
      description
        "AFI,SAFI configuration available for the neighbour or
         group";

      uses bgp-common-mp-afi-safi-config;

      leaf active {
        type boolean;
        config false;
        description
          "This value indicates whether a particular AFI-SAFI has
           been succesfully negotiated with the peer. An AFI-SAFI may
           be enabled in the current running configuration, but a
           session restart may be required in order to negotiate the
           new capability.";
      }

      container prefixes {
        config false;
        description "Prefix counters for the BGP session";
        leaf received {
          type uint32;
          description
            "The number of prefixes received from the neighbor";
        }

        leaf sent {
          type uint32;
          description
            "The number of prefixes advertised to the neighbor";
        }

        leaf installed {
          type uint32;
          description
            "The number of advertised prefixes installed in the
             Loc-RIB";
        }
      }

      container graceful-restart {
        description
          "Parameters relating to BGP graceful-restart";

        uses bgp-common-mp-afi-safi-graceful-restart-config;

        leaf received {
          type boolean;
          config false;
          description
            "This leaf indicates whether the neighbor advertised the
             ability to support graceful-restart for this AFI-SAFI";
        }

        leaf advertised {
          type boolean;
          config false;
          description
            "This leaf indicates whether the ability to support
             graceful-restart has been advertised to the peer";
        }
      }

      uses bgp-common-mp-all-afi-safi-list-contents;
      uses bgp-neighbor-use-multiple-paths;
    }
  }

  grouping bgp-neighbor-base {
    description
      "Parameters related to a BGP neighbor";

    leaf peer-group {
      type leafref {
        path "../../../peer-groups/peer-group/peer-group-name";
      }
      description
        "The peer-group with which this neighbor is associated";
    }

    leaf neighbor-address {
      type inet:ip-address;
      description
        "Address of the BGP peer, either in IPv4 or IPv6";
    }

    leaf enabled {
      type boolean;
      default true;
      description
        "Whether the BGP peer is enabled. In cases where the enabled
         leaf is set to false, the local system should not initiate
         connections to the neighbor, and should not respond to TCP
         connections attempts from the neighbor. If the state of the
         BGP session is ESTABLISHED at the time that this leaf is set
         to false, the BGP session should be ceased.";
    }

    uses bgp-common-neighbor-group-config;

    leaf session-state {
      type enumeration {
          enum IDLE {
            description
              "neighbor is down, and in the Idle state of the FSM";
          }
          enum CONNECT {
            description
              "neighbor is down, and the session is waiting for the
               underlying transport session to be established";
          }
          enum ACTIVE {
            description
              "neighbor is down, and the local system is awaiting a
               connection from the remote peer";
          }
          enum OPENSENT {
            description
              "neighbor is in the process of being established.  The
               local system has sent an OPEN message";
          }
          enum OPENCONFIRM {
            description
              "neighbor is in the process of being established.  The
               local system is awaiting a NOTIFICATION or KEEPALIVE
               message";
          }
          enum ESTABLISHED {
            description
              "neighbor is up - the BGP session with the peer is
               established";
          }
        }
      config false;
      description
        "Operational state of the BGP peer";
    }

    leaf last-established {
      // Was oc-types:timeticks64
      type uint64;
      config false;
      description
        "This timestamp indicates the time that the BGP session last
         transitioned in or out of the Established state.  The value
         is the timestamp in seconds relative to the Unix Epoch (Jan
         1, 1970 00:00:00 UTC).

         The BGP session uptime can be computed by clients as the
         difference between this value and the current time in UTC
         (assuming the session is in the ESTABLISHED state, per the
         session-state leaf).";
    }

    leaf established-transitions {
      type yang:counter64;
      config false;
      description
        "Number of transitions to the Established state for the
         neighbor session.  This value is analogous to the
         bgpPeerFsmEstablishedTransitions object from the standard
         BGP-4 MIB";
      reference
        "RFC 4273 - Definitions of Managed Objects for BGP-4";
    }

    leaf-list supported-capabilities {
      type identityref {
        base bgp-types:BGP_CAPABILITY;
      }
      config false;
      description
        "BGP capabilities negotiated as supported with the peer";
    }

    container messages {
      config false;
      description
        "Counters for BGP messages sent and received from the
         neighbor";
      container sent {
        description
          "Counters relating to BGP messages sent to the neighbor";
        uses bgp-neighbor-counters-message-types-state;
        }

      container received {
        description
          "Counters for BGP messages received from the neighbor";
        uses bgp-neighbor-counters-message-types-state;
      }
    }
    container queues {
      config false;
      description
        "Counters related to queued messages associated with the BGP
         neighbor";

      leaf input {
        type uint32;
        description
          "The number of messages received from the peer currently
           queued";
      }

      leaf output {
        type uint32;
        description
          "The number of messages queued to be sent to the peer";
      }
    }

    container timers {
      description
        "Timers related to a BGP neighbor";

      uses bgp-common-neighbor-group-timers-config;

      leaf negotiated-hold-time {
        type decimal64 {
          fraction-digits 2;
        }
        config false;
        description
          "The negotiated hold-time for the BGP session";
      }
    }

    container transport {
      description
        "Transport session parameters for the BGP neighbor";

      uses bgp-common-neighbor-group-transport-config;

      leaf local-port {
        type inet:port-number;
        config false;
        description
          "Local TCP port being used for the TCP session supporting
           the BGP session";
      }

      leaf remote-address {
        type inet:ip-address;
        config false;
        description
          "Remote address to which the BGP session has been
           established";
      }

      leaf remote-port {
        type inet:port-number;
        config false;
        description
          "Remote port being used by the peer for the TCP session
           supporting the BGP session";
      }
    }

    container error-handling {
      description
        "Error handling parameters used for the BGP neighbor or
         group";
      uses bgp-common-neighbor-group-error-handling-config;

      leaf erroneous-update-messages {
        type uint32;
        config false;
        description
          "The number of BGP UPDATE messages for which the
           treat-as-withdraw mechanism has been applied based on
           erroneous message contents";
      }
    }

    container graceful-restart {
      description
        "Parameters relating the graceful restart mechanism for BGP";

      uses bgp-common-graceful-restart-config;

      leaf peer-restart-time {
        type uint16 {
          range 0..4096;
        }
        config false;
        description
          "The period of time (advertised by the peer) that the peer
           expects a restart of a BGP session to take";
      }

      leaf peer-restarting {
        type boolean;
        config false;
        description
          "This flag indicates whether the remote neighbor is
           currently in the process of restarting, and hence received
           routes are currently stale";
      }

      leaf local-restarting {
        type boolean;
        config false;
        description
          "This flag indicates whether the local neighbor is
           currently restarting. The flag is unset after all NLRI
           have been advertised to the peer, and the End-of-RIB (EOR)
           marker has been unset";
      }

      leaf mode {
        type enumeration {
          enum HELPER_ONLY {
            description
              "The local router is operating in helper-only mode, and
               hence will not retain forwarding state during a local
               session restart, but will do so during a restart of
               the remote peer";
          }
          enum BILATERAL {
            description
              "The local router is operating in both helper mode, and
               hence retains forwarding state during a remote
               restart, and also maintains forwarding state during
               local session restart";
          }
          enum REMOTE_HELPER {
            description
              "The local system is able to retain routes during
               restart but the remote system is only able to act as a
               helper";
          }
        }
        config false;
        description
          "This leaf indicates the mode of operation of BGP graceful
           restart with the peer";
      }
    }

    uses bgp-common-structure-neighbor-group-logging-options;
    uses bgp-common-structure-neighbor-group-ebgp-multihop;
    uses bgp-common-structure-neighbor-group-route-reflector;
    uses bgp-common-structure-neighbor-group-as-path-options;
    uses bgp-common-structure-neighbor-group-add-paths;
    uses bgp-neighbor-use-multiple-paths;
    uses rpol:apply-policy-group;

    container afi-safis {
      description
        "Per-address-family configuration parameters associated with
        the neighbor";
      uses bgp-neighbor-afi-safi-list;
    }
  }

  grouping bgp-neighbor-list {
    description
      "The list of BGP neighbors";

    list neighbor {
      key "neighbor-address";
      description
        "List of BGP neighbors configured on the local system,
        uniquely identified by peer IPv[46] address";

      uses bgp-neighbor-base;
    }
  }
}
