module ietf-netconf-ds-diff {
  yang-version 1.1;
  namespace "urn:ietf:params:xml:ns:yang:ietf-netconf-ds-diff";
  prefix dsdiff;

  organization
    "IETF NETCONF (Network Configuration) Working Group";

  contact
      "WG Web:   <http://tools.ietf.org/wg/netconf/>
       WG List:  <mailto:netconf@ietf.org>";

  description
    "This module defines 'datastore-diff' rpc to
    support obtaining datastore differences.

     Copyright (c) 2021 IETF Trust and the persons identified
     as authors of the code. All rights reserved.

     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2021-11-29 {
    description
      "Initial revision.";
    reference
      "RFC XXXX: NETCONF Extension to Support Obtaining
       Datastore Differences";
  }

  rpc datastore-diff {
    description
      "Get datastore differences.";

    input {
      container target {
        description
          "Target datastore to be compared.";

        choice config-target {
          mandatory true;
          description
           "The configuration target to compare the differences.";

          leaf candidate {
            type empty;
            description
              "The candidate configuration is the target.";
          }
          leaf running {
            type empty;
            description
              "The running configuration is the target.";
          }
          leaf startup {
            type empty;
            description
              "The startup configuration is the target.";
          }
        }
      }

      container source {
        description
          "Source datastore to be compared.";

        choice config-source {
          mandatory true;
          description
           "The configuration source to compare the differences.";

          leaf candidate {
            type empty;
            description
              "The candidate configuration is the source.";
          }
          leaf running {
            type empty;
            description
              "The running configuration is the source.";
          }
          leaf startup {
            type empty;
            description
              "The startup configuration is the source.";
          }
        }
      }
    }

    output {
      anyxml data {
        description
         "Copy of the datastore differences subset that matched
         the filter criteria (if any).  An empty data container
         indicates that the request did not produce any results.";
      }
    }
  }
}
