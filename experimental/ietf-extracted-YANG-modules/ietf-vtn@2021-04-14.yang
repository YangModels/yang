module ietf-vtn {
  yang-version 1.1;
  namespace "urn:ietf:params:xml:ns:yang:ietf-vtn";
  prefix "ietf-vtn";

  import ietf-inet-types {
    prefix "inet";
  }

  import ietf-routing {
    prefix "rt";
  }

  import ietf-routing-types {
    prefix "rt-types";
  }

  import ietf-yang-types {
    prefix "yang";
  }

  import ietf-interfaces {
    prefix "if";
  }

  import ietf-network-instance {
    prefix "ni";
  }

  import ietf-sr-policy {
    prefix "sr-policy";
  }

  organization "IETF TEAS Working Group";

  contact
    "
         WG Web: <http://tools.ietf.org/wg/teas/>
         WG List:<mailto:teas@ietf.org>

         Editor: Xuesong Geng
                 <mailto:gengxuesong@huawei.com>
     Editor: Zhibo Hu
                 <mailto:huzhibo@huawei.com>
        ";

  description
    "This YANG module defines a data model for VTN(Virtual Transport Network)";

  revision "2021-04-14" {
    description
      "This is the initial version of VTN yang module";
        reference
          "RFC XXX: YANG Data Model for VTN";
  }

  grouping vtn-instances{
    description
          "VTN instances";
    list vtn-instance {
          key "vtn-id";
      description
        "vtn instance list";
          leaf vtn-id {
            type uint32;
            description
              "vtn-id";
          }
          container vtn-topology {
            description
                  "vtn topology is nt";
                choice vtn-topolgy-type{
                  description
                    "customized topology of VTN";
                  case flex-algo {
                    container flex-algo {
                          description
                            "flex-algo could be used as topology specification for VTN";
                          leaf flex-algo-id {
                            type uint32;
                            description
                              "flex-algo-id for VTN";
                          }
                        }
                  }
                  case multi-topology {
                    description
                          "MT could be used as topology specification for VTN";
                    leaf multi-topology-id{
                          type uint32;
                          description
                            "MT-id for VTN";
                        }
                  }
                }
          }
      container data-plane {
            description
                  "vtn data plane mechanism";
            leaf vtn-data-plane-identifier {
              type uint32;
                  description
                    "VTN identifier of data plane for vtn distinguishment";
            }
          }
          container steering-policy {
            description
                  "Policy set that matches to a VTN";
                leaf vtn-color-id {
                  type uint32;
                  description
                    "VTN color ID for VTN traffic steering";
                }
          }
    }
  }

  grouping interface-configuration-for-vtn{
    description
          "interface configuration for vtn";
    container interface-configuration-for-vtn {
          description
            "interface configuration for vtn";
          choice vtn-interface-binding-type{
        description
                  "vtn interface binding type";
                case layer-2-sub-interface {
                  description
                    "vtn is bound to a layer-2 sub-interface";
                  container layer-2-sub-interface {
                    description
                          "sub-interface configuration";
                        leaf sub-interface-id {
                          type uint32;
                          description
                            "sub-interface id";
                        }
                        leaf vtn-id {
                          type uint32;
                          description
                            "vtn-id";
                        }
                        leaf bandwidth {
                          type uint32;
                          description
                            "bandwidth allocation for the slice";
                        }
                  }
                }
                case queue {
                  description
                    "vtn is bound to a queue in the interface";
              container queue {
                    description
                          "queue configuration";
                        leaf queue-id {
                          type uint32;
                          description
                            "queue id";
                        }
                        leaf vtn-id {
                          type uint32;
                          description
                            "queue id";
                        }
                        leaf bandwidth {
                          type uint32;
                          description
                            "bandwidth allocation for the slice";
                        }
                  }
                }
          }
        }
  }

  grouping sr-policy-traffic-steering{
    container vtn{
          description
            "candidata path is bound to VTN";
          leaf vtn-id{
            type uint32;
                description
                  "vtn";
          }
        }
  }

  grouping vtn-traffic-steering{
    container vtn-traffic-steering {
          leaf color-index {
            type uint32;
                description
                  "color index";
          }
          leaf vtn-id {
            type uint32;
                description
                  "vtn id";
          }
        }
  }

  container vtn-instance {
    description
          "vtn instance configuraiton";
    uses vtn-instances;
  }

  grouping vtn-id-sr-policy {
    description
          "VTN ID for SR policy";
        container vtn-id-sr-policy {
          description
            "VTN ID for SR policy";
          leaf vtn-id {
            type uint32;
                description
                  "vtn id";
          }
        }
  }

  augment "/rt:routing/sr-policy:segment-routing/sr-policy:traffic-engineering/sr-policy:policies/sr-policy:policy/sr-policy:candidate-paths/sr-policy:candidate-path" {
    description
          "VTN ID for candidate path in SR path";
        uses vtn-id-sr-policy;
  }

  augment "/if:interfaces/if:interface" {
    description
          "interface model extension for vtn";
        uses interface-configuration-for-vtn;
  }

  augment /ni:network-instances/ni:network-instance{
    description
          "network instance model extension for vtn";
    uses vtn-traffic-steering;
  }
}
