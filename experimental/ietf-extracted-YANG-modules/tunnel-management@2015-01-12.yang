module tunnel-management {
  namespace "urn:huawei:params:xml:ns:yang:tunnel-management";
  // replace with IANA namespace when assigned
  prefix "tlnm";

  import bgp {
    prefix bgp;
    //draft-zhdankin-netmod-bgp-cfg
  }

  import ietf-interfaces {
    prefix if;
    //rfc7223-YANG Interface Management
  }

  import ietf-inet-types {
    prefix inet;
    //rfc6991-Common YANG Data Types
  }

  description
    "This YANG module defines the tunnel management configuration
     data for tunnel management service.
     ";

  revision 2015-01-12 {
    description
      "Initial revision.";
  }

  grouping matchMode {
    leaf matchMode {
      config "true";
      type enumeration {
        enum "permit" {
          value "0";
          description "permit:
            Specifies the matching mode of the route-policy as permit.
            In permit mode, a route matches all the if-match clauses,
            the route matches the route-policy and the actions defined
            by the apply clause are performed on the route. Otherwise,
            the route continues to match the next entry.";
        }
        enum "deny" {
          value "1";
          description "deny:
            Specifies the matching mode of the route-policy as deny. In
            deny mode, if a route matches all the if-match clauses, the
            route fails to match the route-policy and cannot match the
            next node.";
        }
      }
    }
  }//End of grouping matchMode

  /*
   A tunnel policy determines which type of tunnels can be selected by
   an application module.

   Tunnel policies can be classified into two modes:
   Select-seq: The system selects a tunnel for an application program
   based on the tunnel type priorities defined in the tunnel policy.
   Tunnel binding: The system selects only a specified tunnel for an
   application program.

   The two modes are mutually exclusive.
  */
  container tunnelPolicys {
    list tunnelPolicy {
      min-elements "0";
      max-elements "unbounded";
      key "tunnelPolicyName";

      leaf tunnelPolicyName {
        description
          "Specify tunnel policy name.";
        config "true";
        mandatory "true";
        type "string";
      }

      leaf description {
        description
          "Tunnel policy description(no more than 80 characters).";
        config "true";
        mandatory "false";
        type "string";
      }

      choice tunnelPolicyMode {
        case SpecifyTunnelSelectionSequence { //Tunnel selection sequence
          container tunnelTypeSequences {
            description
              "Specify Tunnel Selection Sequence.";

            leaf-list tunnelType {
              type enumeration {
                enum "gre" {
                  value "0";
                  description "gre:
                    Specifies the GRE tunnel.";
                }
                enum "lsp" {
                  value "1";
                  description "lsp:
                    Specifies the LDP LSP, BGP LSP or static LSP.";
                }
                enum "cr-lsp" {
                  value "2";
                  description "cr-lsp:
                    Specifies the CR-LSP tunnel.";
                }
                //TBD
              }
            }

            leaf loadBalanceNumber {
              description
                "Specify tunnel load balance number.";
              config "true";
              mandatory "true";
              type uint32 {
                range "1..32";
              }
            }
          }
        }

        case BindApplicationToTunnel { //Bind application to tunnel
          container bindingPolicies {
            list bindingPolicy {
              key "nextHopAddress";
              min-elements "0";
              max-elements "unbounded";

              leaf nextHopAddress {
                description
                  "Specifies the destination address of the tunnel.";
                type inet:ip-address;
              }

              leaf-list tunnelInterface {
                description
                  "Specifies the interface number of the bound
                   tunnel interface.";
                config "true";
                type leafref {
                  path "/if:interfaces/if:interface/if:name";
                }
              }

              leaf ignoreDestinationCheck {
                description
                  "Specifies whether to ignore destination consistency
                   check. If this parameter is enabled, a tunnel
                   policy selects a TE tunnel for route iteration even
                   if the destination address of that TE tunnel is
                   different from the destination address specified in
                   the tunnel policy.";

                config "true";
                default "false";
                type "boolean";
              }
              leaf downSwitch {
                description
                  "Indicates that the tunnel switchover is enabled.

                   After this parameter is configured, an available
                   tunnel, with the priority as LSP, CR-LSP, and then
                   GRE, is adopted when the bound TE tunnel fails.";

                config "true";
                default "false";
                type "boolean";
              }
            }

          }
        }

      }

    }

  }//End of container tunnelPolicys

  /*
  The tunnel selector is specific to BGP/MPLS IP VPN services (a
  type of VPN service), selecting a tunnel policy for VPNv4/VPNv6
  routes on the backbone network.

  A tunnel selector selects tunnel policies for routes after
  filtering routes based on some route attributes such as the
  route distinguisher (RD) and next hop. This makes tunnel
  selection more flexible.

  A tunnel selector is often used on the autonomous system boundary
  router (ASBR) in inter-AS VPN Option B or the superstratum
  provider edge (SPE) in hierarchy of VPN (HoVPN).
  */
  container tunnelSelectors {
    list tunnelSelector {
      key "name";
      min-elements "0";
      max-elements "unbounded";

      leaf name {
        description
          "Specifies the name of a tunnel selector.";

        config "true";
        type "string";
      }

      leaf description {

        config "true";
        type "string";
      }

      container tunnelSelectorNodes {
        list tunnelSelectorNode {
          key "nodeSequence";
          min-elements "0";
          max-elements "unbounded";

          leaf nodeSequence {
            description
              "Specifies the index of a node of the tunnel selector.
               When a route-policy is used to filter a route, the
               route first matches the node with the smallest node
               value.";

            config "true";
            type uint32 {
              range "0..65535";
            }
          }

          uses matchMode;

          container matchCondition {
            container matchIPv4NextHop {
              leaf matchType {
                config "true";
                mandatory "true";
                type enumeration {
                  enum "matchNHopPF" {
                    value "0";
                    description "matchNHopPF:";
                  }
                  enum "matchNHopAcl" {
                    value "1";
                    description "matchNHopAcl:";
                  }
                }
              }
              leaf prefixName {
                description
                  "Specifies the name of an IP address prefix list
                   that is used for route filtering.";

                config "true";
                mandatory "true";
                type "string";
              }
              leaf aclNameOrNum {
                description
                  "";

                config "true";
                mandatory "true";
                type "string";
              }
            }//End of container matchIPv4NextHop

            container matchIPv6NextHop {
              leaf ipv6PrefixName {
                description
                  "Specifies the name of an IPv6 address prefix
                   list.";

                config "true";
                mandatory "true";
                type "string";
              }
            }//End of container matchIPv6NextHops

            container matchRdFilter {
              leaf rdIndex {
                config "true";
                mandatory "true";
                type uint32 {
                  range "1..199";
                }
              }
            }//End of container matchRdFilters
          }//End of container matchCondition

          container applyAction {
             leaf tunnelPolicyName {
               config "true";
               mandatory "true";
               type "string";
             }
          }//End of container applyAction

        }
      }//End of container tunnelSelectorNodes

    }
  }//End of container tunnelSelectors

  /*
   * augment some bgp vpn functions in bgp module.
   */
  augment "/bgp:bgp-router/bgp:vpnv4/bgp:unicast" {
    leaf tunnelSelectorName {
      description
        "Specifies the name of a tunnel selector.";

      config "true";
      type "string";
    }
  }

  augment "/bgp:bgp-router/bgp:vpnv6/bgp:unicast" {
    leaf tunnelSelectorName {
      description
        "Specifies the name of a tunnel selector.";

      config "true";
      type "string";
    }
  }

}
