module logical-network-element {

  yang-version "1";

  // namespace
  namespace "urn:ietf:params:xml:ns:yang:logical-network-element";

  prefix "struct";

  // import some basic types
  import ietf-interfaces {
    prefix if;
  }

  // meta
  organization "IETF RTG YANG Design Team Collaboration
                with OpenConfig";

  contact
      "Routing Area YANG Architecture Design Team -
       <rtg-dt-yang-arch@ietf.org>";

  description
    "This module is used to support multiple logical network
     elements on a single physical or virtual system.";

  revision "2016-01-19" {
    description
      "IETF Routing YANG Design Team Meta-Model";
    reference "TBD";
  }

  // extension statements

  // feature statements
  feature bind-network-element-id {
    description
      "Logical network element ID to which an interface is bound";
  }

  // identity statements

  identity logical-network-element-type {
    description
     "Identify type of logical-network-element";
  }

  identity lne-managed {
    base logical-network-element-type;
    description
      "A Logical Network Element that can
       be managed by the host system";
  }

  identity lne-unmanaged {
    base logical-network-element-type;
    description
      "A Logical Network Element that cannot
       be managed by the host system";
  }

  // typedef statements

  // grouping statements

  // top level device definition statements
  container logical-network-inventory {
    description "Allows a network device to support multiple logical
                 network element (device) instances";
    list logical-network-element {
      key lne-id;
      description "List of logical network elements";
      leaf lne-id {
        type uint16; // expect a small number of logical routers
        description "Device-wide unique identifier for the
                     logical network element";
      }
      leaf lne-name {
        type string;
        description "Descriptive name for the logical network
                     element";
      }
      leaf lne-type {
        type identityref {
          base logical-network-element-type;
        }
        description "Type of logical-network-element";
      }
      leaf lne-root {
        type structural-mount;
        description "Root for models supported per logical
                     network element";
      }
    }
  }

  // augment statements
  augment "/if:interfaces/if:interface" {
    description
        "Add a node for the identification of the logical network
        element associated with an interface. Applies to interfaces
        that can be assigned on a per logical network element basis.
        A <TBD> error is returned when the interface type cannot be
        assigned.";

    leaf bind-lne-id {
      type uint16;
      description
        "Logical network element ID to which interface is bound";
    }
  }

  // rpc statements

  // notification statements

}
