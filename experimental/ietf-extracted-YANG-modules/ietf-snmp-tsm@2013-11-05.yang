submodule ietf-snmp-tsm {

  belongs-to ietf-snmp {
    prefix snmp;
  }

  include ietf-snmp-common;
  include ietf-snmp-target;
  include ietf-snmp-proxy;

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";

  description
    "This submodule contains a collection of YANG definitions for
     configuring the Transport Security Model (TSM) of SNMP.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  reference
    "RFC5591: Transport Security Model for the
              Simple Network Management Protocol (SNMP)";

  // RFC Ed.: update the date below with the date of RFC publication
  // and remove this note.

  revision 2013-11-05 {
    description
      "Initial revision.";
    reference
      "RFC XXXX: A YANG Data Model for SNMP Configuration";
  }

  feature tsm {
    description
      "A server implements this feature if it supports the
      Transport Security Model for SNMP.";
    reference
      "RFC5591: Transport Security Model for the
                Simple Network Management Protocol (SNMP)";
  }

  augment /snmp:snmp {
    if-feature tsm;
    container tsm {
      description
        "Configuration of the Transport-based Security Model";

      leaf use-prefix {
        type boolean;
        default false;
        reference
          "SNMP-TSM-MIB.snmpTsmConfigurationUsePrefix";
      }
    }
  }

  grouping tsm-target-params {
    container tsm {
      description
        "Transport based security SNMPv3 parameters type.

         Represents snmpTargetParamsMPModel '3' and
         snmpTargetParamsSecurityModel '4'";
      leaf security-name {
        type snmp:security-name;
        mandatory true;
        reference
          "SNMP-TARGET-MIB.snmpTargetParamsSecurityName";
      }
      leaf security-level {
        type snmp:security-level;
        mandatory true;
        reference
          "SNMP-TARGET-MIB.snmpTargetParamsSecurityLevel";
      }
    }
  }

  augment /snmp:snmp/snmp:target/snmp:params {
    if-feature tsm;
    case tsm {
      uses tsm-target-params;
    }
  }

  augment /snmp:snmp/snmp:proxy/snmp:params-in/snmp:params {
    if-feature tsm;
    case tsm {
      uses tsm-target-params;
    }
  }
}
