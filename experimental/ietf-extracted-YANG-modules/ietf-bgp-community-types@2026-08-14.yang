module ietf-bgp-community-types {
  yang-version 1.1;
  namespace
    "urn:ietf:params:xml:ns:yang:ietf-bgp-community-types";
  prefix ibct;

  import ietf-yang-semver {
    prefix ysv;
    reference
      "I-D.ietf-netmod-yang-semver: YANG Semantic Versioning";
  }

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This module contains common YANG type and feature definitions
     for BGP Communities that are not backed by IANA registries.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-08-14 {
    description
      "Initial Version";
    ysv:version 0.0.9;
    reference
      "RFC XXXX: YANG module for Border Gateway Protocol (BGP-4).";
  }

  /*
   * Features.
   */

  feature send-communities {
    description
      "Enable the propagation of communities.";
    reference
      "RFC 1997: BGP Communities Attribute.
       RFC 4360: BGP Extended Communities Attribute.
       RFC 5668: BGP Extended Community Attribute for Route Target
                 Constraints.
       RFC 8092: BGP Large Communities Attribute.";
  }

  /*
   * Identities.
   */

  identity send-community-feature {
    description
      "Base identity to identify send-community feature.";
  }

  identity none {
    base send-community-feature;
    description
      "Send no communities.  When used, no other community types
       should be present.";
  }

  identity standard {
    base send-community-feature;
    description
      "Send standard communities.";
    reference
      "RFC 1997: BGP Communities Attribute.";
  }
  identity extended {
    base send-community-feature;
    description
      "Send extended communities.";
    reference
      "RFC 4360: BGP Extended Communities Attribute.";
  }

  identity large {
    base send-community-feature;
    description
      "Send large communities.";
    reference
      "RFC 8092: BGP Large Communities Attribute.";
  }

  /*
   * Typedefs.
   */

  typedef bgp-community-regexp-type {
    type string;
    description
      "Type definition for communities specified as regular
       expression patterns.

       A compliant implementation of this type MUST accept a POSIX.2
       Extended Regular Expression excluding the following features:
       - character class expressions (Section 9.3.5)
       - collating symbols (Section 9.3.5)
       - equivalence classes (Section 9.3.5)
       - back-reference expressions (Section 9.3.6)

       Implementations MAY accept additional forms of regular
       expressions as long as the minimally compliant form documented
       above is accepted.";
    reference
      "IEEE Std 1003.1-2017: The Open Group Base Specifications Issue
       7, 2018 edition.";
  }

  typedef bgp-std-community-type {
    type union {
      type uint32;
      type string {
        pattern '([0-9]|[1-9][0-9]{1,3}|[1-5][0-9]{4}|'
              + '6[0-5][0-9]{3}|66[0-4][0-9]{2}|'
              + '665[0-2][0-9]|6653[0-5])'
              + ':'
              + '([0-9]|[1-9][0-9]{1,3}|[1-5][0-9]{4}|'
              + '6[0-5][0-9]{3}|66[0-4][0-9]{2}|'
              + '665[0-2][0-9]|6653[0-5])';
      }
    }
    description
      "Type definition for standard community attributes.";
    reference
      "RFC 1997: BGP Communities Attribute.";
  }

  typedef bgp-large-community-type {
    type string {
      // 4-octets global:4-octets local part-1:4-octets local part-2.
      pattern '([0-9]|[1-9][0-9]{1,8}|[1-3][0-9]{9}|4[01][0-9]{8}|'
            + '42[0-8][0-9]{7}|429[0-3][0-9]{6}|4294[0-8][0-9]{5}|'
            + '42949[0-5][0-9]{4}|429496[0-6][0-9]{3}|'
            + '4294967[01][0-9]{2}|42949672[0-8][0-9]|'
            + '429496729[0-5])'
            + ':'
            + '([0-9]|[1-9][0-9]{1,8}|[1-3][0-9]{9}|4[01][0-9]{8}|'
            + '42[0-8][0-9]{7}|429[0-3][0-9]{6}|4294[0-8][0-9]{5}|'
            + '42949[0-5][0-9]{4}|429496[0-6][0-9]{3}|'
            + '4294967[01][0-9]{2}|42949672[0-8][0-9]|'
            + '429496729[0-5])'
            + ':'
            + '([0-9]|[1-9][0-9]{1,8}|[1-3][0-9]{9}|4[01][0-9]{8}|'
            + '42[0-8][0-9]{7}|429[0-3][0-9]{6}|4294[0-8][0-9]{5}|'
            + '42949[0-5][0-9]{4}|429496[0-6][0-9]{3}|'
            + '4294967[01][0-9]{2}|42949672[0-8][0-9]|'
            + '429496729[0-5])';
    }
    description
      "Type definition for a large BGP community";
    reference
      "RFC 8092: BGP Large Communities Attribute.";
  }

}
