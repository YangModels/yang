module ietf-bgp-lsdb {
  yang-version 1.1;
  namespace "urn:ietf:params:xml:ns:yang:ietf-bgp-lsdb";
  prefix bgp-lsdb;

  import ietf-yang-types {
    prefix yang;
    reference
      "RFC 6991: Common YANG Data Types.";
  }

  import ietf-inet-types {
    prefix inet;
    reference
      "RFC 6991: Common YANG Data Types.";
  }

  organization
    "IETF LSVR Working Group";
  contact
    "WG Web:   <http://tools.ietf.org/wg/lsvr>
     WG List:  <lsvr@ietf.org>

     Authors: Mahesh Jethanandani (mjethanandani at gmail.com),
              Keyur Patel (keyur at arrcus.com)";

  description
    "This module contains contains configuration and management
     information for BGP-LS, BGP-LS-SPF.

     Copyright (c) 2022 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2023-01-12 {
    description
      "Initial Version";
    reference
      "RFC XXXX, BGP Model for Link State Distribution.";
  }

  // Typedefs
  typedef lsdb-proto-id-type {
    type enumeration {
      enum unknown {
        description "Unknown protocol.";
      }
      enum isis-level1 {
        description "IS-IS Level 1.";
      }
      enum isis-level2 {
        description "IS-IS Level 2.";
      }
      enum ospfv2 {
        description "OSPF Version 2.";
      }
      enum direct {
        description "Direct.";
      }
      enum static {
        description "Static";
      }
      enum ospfv3 {
        description "OSPF Version 3.";
      }
      enum bgp {
        description "BGP.";
      }
    }
    description
      "LS database proto id type.";
  }

  typedef lsdb-attr-type {
    type enumeration {
      enum unknown {
        description
        "Unknown attribute.";
      }
      enum node-pdu-auth-info {
        description
          "Node authentication information attribute.";
      }
      enum node-hostname {
        description
          "Node Hostname attribute.";
      }
      enum node-flags {
        description
          "Node Flags attribute.";
      }
      enum node-opaque {
        description
          "Node Opaque attribute.";
      }
      enum node-as {
        description
          "Node AS Number attribute.";
      }
      enum node-isis-node-id {
        description
          "Node ISIS Node-Id attribute.";
      }
      enum node-ipv4-rtr-id {
        description
          "Node IPv4 Router-Id attribute.";
      }
      enum node-ipv6-rtr-id {
        description
          "Node IPv6 Router-Id attribute.";
      }
      enum node-sid-index {
        description
          "Node SID Index attribute.";
      }
      enum node-topo-ids {
        description
          "Node Topology-IDs attribute.";
      }
      enum node-isis-nlpid {
        description
          "Node NLPID attribute.";
      }
      enum node-isis-area-id {
        description
          "Node ISIS Area-Id attribute.";
      }
      enum node-ospf-area-id {
        description
          "Node OSPF Area-Id attribute.";
      }
      enum node-admin-tag {
        description
          "Node Admin-Tags attribute.";
      }
      enum node-srgb-range {
        description
          "Node SRGB Range attribute.";
      }
      enum node-spf-status {
        description
          "Node SPF Status attribute.";
      }
      enum node-spf-algorithm {
        description
          "Node SPF Algorithm Type attribute.";
      }
      enum link-name {
        description
          "Link Name attribute.";
      }
      enum link-proto-id {
        description
          "Link Protocol-Id attribute.";
      }
      enum link-local-id {
        description
          "Link Local-Id attribute.";
      }
      enum link-remote-id {
        description
          "Node Remote-Id attribute.";
      }
      enum link-local-isis-node-id {
        description
          "Link Local ISO Node-Id attribute.";
      }
      enum link-remote-isis-node-id {
        description
          "Link Remote ISO Node-Id attribute.";
      }
      enum link-local-ipv4-rtr-id {
        description
          "Link Local IPv4 Router-Id attribute.";
      }
      enum link-remote-ipv4-rtr-id {
        description
          "Link Remote IPv4 Router-Id attribute.";
      }
      enum link-local-ipv6-rtr-id {
        description
          "Link Local IPv6 Router-Id attribute.";
      }
      enum link-remote-ipv6-rtr-id {
        description
          "Link Remote IPv6 Router-Id attribute.";
      }
      enum link-circuit-id {
        description
          "Link Local Circuit-Id attribute.";
      }
      enum link-igp-metric {
        description
          "Link IGP metric attribute.";
      }
      enum link-mtu {
        description
          "Link MTU attribute.";
      }
      enum link-max-bandwidth {
        description
          "Link Maximum Bandwidth attribute.";
      }
      enum link-max-reserve-bandwidth {
        description
          "Link Maximum Reserved Bandwidth attribute.";
      }
      enum link-unreserve-bandwidth {
        description
          "Link Unreserved Bandwidth attribute.";
      }
      enum link-default-te-metric {
        description
          "Link TE-Default Metric attribute.";
      }
      enum link-protection-type {
        description
          "Link Protection-Type attribute.";
      }
      enum link-opaque {
        description
          "Link Opaque attribute.";
      }
      enum link-mpls-proto-mask {
        description
          "Link MPLS-Protocol-Mask attribute.";
      }
      enum LSDB_LINK_LOCAL_IPV4_ADDR {
        description "Link Local IPv4 Address attribute.";
      }
      enum LSDB_LINK_LOCAL_IPV6_ADDR {
        description "Link Local IPv6 Address attribute.";
      }
      enum LSDB_LINK_REMOTE_IPV4_ADDR {
        description "Link Remote IPv4 Address attribute.";
      }
      enum LSDB_LINK_REMOTE_IPV6_ADDR {
        description "Link Remote IPv6 Address attribute.";
      }
      enum LSDB_LINK_ISIS_LEVEL {
        description "Link ISIS Level attribute.";
      }
      enum LSDB_LINK_ADMIN_TAG {
        description "Link Admin-Tag attribute.";
      }
      enum LSDB_LINK_SRLG {
        description "Link SRLGs attribute.";
      }
      enum LSDB_LINK_SPF_STATUS {
        description "Link SPF Status attribute.";
      }
      enum LSDB_PREFIX_IGP_FLAGS {
        description "Prefix IGP-Flags attribute.";
      }
      enum LSDB_PREFIX_METRIC {
        description "Prefix Metric attribute.";
      }
      enum LSDB_PREFIX_OSPF_FWADDR {
        description "Prefix OSPF-Forwarding-Address attribute.";
      }
      enum LSDB_PREFIX_OSPF_ROUTE_TYPE {
        description "Prefix OSPF-Route-Type attribute.";
      }
      enum LSDB_PREFIX_OPAQUE {
        description "Prefix Opaque attribute.";
      }
      enum LSDB_PREFIX_ROUTE_TAGS {
        description "Prefix Route-Tags attribute.";
      }
      enum LSDB_PREFIX_EXT_ROUTE_TAGS {
        description "Prefix Extended-Route-Tags attribute.";
      }
      enum LSDB_PREFIX_SPF_STATUS {
        description "Prefix SPF Status attribute.";
      }
    }
    description
      "Link-State database attribute type.";
  }

  typedef lsdb-obj-type {
    type enumeration {
      enum LSDB_UNKNOWN_OBJ {
        description "Unknown attribute.";
      }
      enum LSDB_NODE_OBJ {
        description "Node Object.";
      }
      enum LSDB_LINK_OBJ {
        description "Link object.";
      }
      enum LSDB_PREFIX_OBJ {
        description "Prefix object.";
      }
    }
    description
      "Link-State database object type.";
  }

  // Groupings
  grouping lsdb-obj-common {
    description "Common details for all object types.";

    leaf handle {
      type uint64;
      description "Handle of the object.";
    }

    leaf type {
      type lsdb-obj-type;
      description "Type of object.";
    }

    leaf topology-id {
      type uint16;
      description "Id of the topology object belongs to.";
    }

    leaf pdu-id {
      type uint32;
      description
        "Id of the original protocol PDU unit this object belongs
         to.";
    }

    container attributes {
      description
        "List of attributes for a given object.";

      list attribute {
        key "attribute-handle attribute-type";

        leaf attribute-handle {
          type uint64;
          description
            "Handle of the attribute.";
        }

        leaf attribute-type {
          type lsdb-attr-type;
          description
            "Type of attribute.";
        }

        leaf attribute-length {
          type uint16;
          description
            "Length of attribute value in bytes.";
        }

        leaf attribute-value {
          type union {
            type uint8;
            type uint16;
            type uint32;
            type uint64;
            type boolean;
            type string;
            type inet:ip-address;
            type yang:hex-string;
          }
          description
            "Actual value of the attribute.";
        }
        description
          "Details of a single attribute.";
      }
    }
  }

  grouping lsdb-top {
    description
      "Details for all databases under an application instance.";

    container local-databases {
      config false;
      description
        "List of local databases.";

      list database {
        key "vrf-name instance protocol-id area-id";

        description
          "Operational state for a given database.";

        leaf vrf-name {
          type string;
          description
            "Name of the VRF this database belongs to.";
        }

        leaf instance {
          type string;
          description
            "Name of the application instance this database belongs
             to.";
        }

        leaf protocol-id {
          type lsdb-proto-id-type;
          description
            "Id of the aplication protocol this database belongs
             to.";
        }

        leaf area-id {
          type uint32;
          description
            "Id of the protocol area this database belongs to.";
        }

        container nodes {
          description
            "List of node objects for a given database.";

          list node {
            key "handle";

            leaf node-id {
              type string;
              description
                "Id of the node object.";
            }

            uses lsdb-obj-common;
            container links {
              description
                "List of link objects for a given node object.";

              list link {
                key "handle";

                leaf local-id {
                  type uint32;
                  description
                    "Local identifier of the link object.";
                }

                leaf local-address {
                  type string;
                  description
                    "Local address of the link object.";
                }

                leaf local-node-id {
                  type uint32;
                  description
                    "Local Node identifier of the link object.";
                }

                leaf remote-id {
                  type uint32;
                  description
                    "Remote identifier of the link object.";
                }

                leaf remote-address {
                  type string;
                  description
                    "Remote address of the link object.";
                }

                leaf remote-node-id {
                  type uint32;
                  description
                    "Remote Node identifier of the link object.";
                }

                uses lsdb-obj-common;
                description
                  "Details of a single link object.";
              }
            }

            container prefixes {
              description
                "List of prefix objects for a given node object.";

              list prefix {
                key "handle";

                leaf prefix-key {
                  type string;
                  description
                    "Key value for the prefix object.";
                }

                uses lsdb-obj-common;
                description
                  "Details of a single prefix object.";
              }
            }
            description
              "Details of a single node object.";
          }
        }
      }
    }
  }
}
