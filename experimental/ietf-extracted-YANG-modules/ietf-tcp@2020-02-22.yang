module ietf-tcp {
  yang-version "1.1";
  namespace "urn:ietf:params:xml:ns:yang:ietf-tcp";
  prefix "tcp";

  import ietf-yang-types {
    prefix "yang";
    reference
      "RFC 6991: Common YANG Data Types.";
  }
  import ietf-tcp-client {
    prefix "tcpc";
  }
  import ietf-tcp-server {
    prefix "tcps";
  }
  import ietf-tcp-common {
    prefix "tcpcmn";
  }
  import ietf-inet-types {
    prefix "inet";
  }

  organization
    "IETF TCPM Working Group";

  contact
    "WG Web:   <http://tools.ietf.org/wg/tcpm>
     WG List:  <tcpm@ietf.org>

     Authors: Michael Scharf (michael.scharf at hs-esslingen dot de)
              Vishal Murgai (vmurgai at cisco dot com)
              Mahesh Jethanandani (mjethanandani at gmail dot com)";

  description
    "This module focuses on fundamental and standard TCP functions
     that widely implemented. The model can be augmented to address
     more advanced or implementation specific TCP features.";

  revision "2020-02-22" {
    description
      "Initial Version";
    reference
      "RFC XXX, TCP Configuration.";
  }

  // Features
  feature server {
    description
      "TCP Server configuration supported.";
  }

  feature client {
    description
      "TCP Client configuration supported.";
  }

  feature statistics {
    description
      "This implementation supports statistics reporting.";
  }

  // TCP-AO Groupings

  grouping mkt {
    leaf options {
      type binary;
      description
        "This flag indicates whether TCP options other than TCP-AO
         are included in the MAC calculation. When options are
         included, the content of all options, in the order present,
         is included in the MAC, with TCP-AO's MAC field zeroed out.
         When the options are not included, all options other than
         TCP-AO are excluded from all MAC calculations (skipped over,
         not zeroed).

         Note that TCP-AO, with its MAC field zeroed out, is always
         included in the MAC calculation, regardless of the setting
         of this flag; this protects the indication of the MAC length
         as well as the key ID fields (KeyID, RNextKeyID). The option
         flag applies to TCP options in both directions
         (incoming and outgoing segments).";
      reference
        "RFC 5925: The TCP Authentication Option.";
    }

    leaf key-id {
      type uint8;
      description
        "An unsigned 1-byte field indicating the Master Key Tuple
         (MKT) used to generate the traffic keys that were used to
         generate the MAC that authenticates this segment.";
      reference
        "RFC 5925: The TCP Authentication Option.";
    }

    leaf rnext-key-id {
      type uint8;
      description
        "An unsigned 1-byte field indicating the MKT that is
         ready at the sender to be used to authenticate received
         segments, i.e., the desired 'receive next' key ID.";
    }
    description
      "A Master Key Tuple (MKT) describes TCP-AO properties to be
       associated with one or more connections.";
  }

  grouping ao {
    leaf enable-ao {
      type boolean;
      default "false";
      description
        "Enable support of TCP-Authentication Option (TCP-AO).";
    }

    leaf send-id {
      type uint8 {
        range "0..255";
      }
      must "../enable-ao = 'true'";
      description
        "The SendID is inserted as the KeyID of the TCP-AO option
         of outgoing segments.";
      reference
        "RFC 5925: The TCP Authentication Option.";
    }

    leaf recv-id {
      type uint8 {
        range "0..255";
      }
      must "../enable-ao = 'true'";
      description
        "The RecvID is matched against the TCP-AO KeyID of incoming
         segments.";
      reference
        "RFC 5925: The TCP Authentication Option.";
    }

    leaf include-tcp-options {
      type boolean;
      must "../enable-ao = 'true'";
      description
        "Include TCP options in HMAC calculation.";
    }

    leaf accept-ao-mismatch {
      type boolean;
      must "../enable-ao = 'true'";
      description
        "Accept packets with HMAC mismatch.";
    }
    description
      "Authentication Option (AO) for TCP.";
    reference
      "RFC 5925: The TCP Authentication Option.";
  }

  grouping md5 {
    description
      "Grouping for use in authenticating TCP sessions using MD5.";
    reference
      "RFC 2385: Protection of BGP Sessions via the TCP MD5
       Signature.";

    leaf enable-md5 {
      type boolean;
      default "false";
      description
        "Enable support of MD5 to authenticate a TCP session.";
    }
  }

  // Congestion control

  identity congestion-control-algorithm {
    description
      "Base identity from which all congestion control
       algorithms are derived.";
  }

  identity reno {
    base congestion-control-algorithm;
    description
      "Standard TCP congestion control referred to as
       'Reno algorithm'";
    reference
      "RFC 5681: TCP Congestion Control";
  }

  identity new-reno {
    base congestion-control-algorithm;
    description
      "NewReno modification to TCP's fast recovery algorithm";
    reference
      "RFC 6582: The NewReno Modification to TCP's Fast Recovery
       Algorithm";
  }

  identity ledbat {
    base congestion-control-algorithm;
    description
      "Low Extra Delay Background Transport (LEDBAT)
       congestion control";
   reference
      "RFC 6817: Low Extra Delay Background Transport (LEDBAT)";
  }

  identity dctcp {
    base congestion-control-algorithm;
    description
      "TCP Congestion Control for Data Centers (DCTCP)
       congestion control";
    reference
      "RFC 8257: Data Center TCP (DCTCP): TCP Congestion
       Control for Data Centers";
  }

  identity cubic {
    base congestion-control-algorithm;
    description
      "CUBIC congestion control";
    reference
      "RFC 8312: CUBIC for Fast Long-Distance Networks";
  }

  grouping tcp-global {
    description
      "Important global TCP stack parameters.";
    leaf mss-max {
      type uint16;
      description
        "Sets the max segment size for TCP connections.";
      reference
        "RFC 1122: Requirements for Internet Hosts -- Communication
         Layers";
    }

    leaf mtu-discovery-enable {
      type boolean;
      description
        "Turns path mtu discovery for TCP connections on (true) or
         off (false)";
      reference
        "RFC 4821: Packetization Layer Path MTU Discovery";
    }

    leaf sack-enable {
      type boolean;
      description
        "Enable negotiation of Selective Acknowledgements (SACK)";
      reference
        "RFC 2018: TCP Selective Acknowledgment Options";
    }

    leaf timestamps-enable {
      type boolean;
      description
        "Enable negotiation of timestamps";
      reference
        "RFC 7323: TCP Extensions for High Performance";
    }

    leaf window-scale-enable {
      type boolean;
      description
        "Enable negotiation of receive window scaling";
      reference
        "RFC 7323: TCP Extensions for High Performance";
    }

    leaf ecn-enable {
      type enumeration {
        enum disable;
        enum passive;
        enum active;
      }
      description
        "Enabling of Explicit Congestion Notification (ECN).";
      reference
        "RFC 3168: The Addition of Explicit Congestion
         Notification (ECN) to IP";
    }

    leaf fin-timeout {
      type uint16;
      units "seconds";
      description
        "When a connection is closed actively, it must linger in
         TIME-WAIT state for a time 2xMSL (Maximum Segment Lifetime).
         This parameter sets the TIME-WAIT timeout duration in
         seconds.";
      reference
         "RFC 793: Transmission Control Protocol";
    }

    leaf congestion-control-default {
      type identityref {
        base congestion-control-algorithm;
      }
      description
        "This parameter selects the congestion control algorithm that
         is used by default for new TCP connections. The default may
         be overridden per connection by means outside the scope of
         this model (e.g., via the Sockets API).";
       reference
         "RFC 2914: Congestion Control Principles";
    }
  }

  // TCP configuration

  container tcp {
    presence "The container for TCP configuration.";

    description
      "TCP container.";

    container connections {
      list connection {
        key "local-address remote-address local-port remote-port";

        leaf local-address {
          type inet:ip-address;
          description
            "Local address that forms the connection identifier.";
        }

        leaf remote-address {
          type inet:ip-address;
          description
            "Remote address that forms the connection identifier.";
        }

        leaf local-port {
          type inet:port-number;
          description
            "Local TCP port that forms the connection identifier.";
        }

        leaf remote-port {
          type inet:port-number;
          description
            "Remote TCP port that forms the connection identifier.";
        }

        container common {
          uses tcpcmn:tcp-common-grouping;

          leaf congestion-control {
            type identityref {
              base congestion-control-algorithm;
            }
            config false;
            description
              "Type of the actually used TCP congestion control
               algorithm. It may be different from the default
               algorithm, for instance, if an application has
               explicitly selected an algorithm.";
            reference "RFC 2914: Congestion Control Principles";
          }

          choice authentication {
            case ao {
              uses ao;
              description
                "Use TCP-AO to secure the connection.";
            }

            case md5 {
              uses md5;
              description
                "Use TCP-MD5 to secure the connection.";
            }
            description
              "Choice of how to secure the TCP connection.";
          }
          leaf tcp-nodelay {
            type boolean;
            config false;
            description
              "Disabling of the 'Nagle algorithm'.";
          }
          description
            "Common definitions of TCP configuration. This includes
             parameters such as how to secure the connection,
             keepalives and idle time, that can be part of either
             the client or server.";
        }

        container server {
          if-feature server;
          uses tcps:tcp-server-grouping;
          description
            "Definitions of TCP server configuration.";
        }

        container client {
          if-feature client;
          uses tcpc:tcp-client-grouping;
          description
            "Definitions of TCP client configuration.";
        }
        description
          "Connection related parameters.";
      }
      description
        "A container of all TCP connections.";
    }

    container global {
      uses tcp-global;
      description
        "Parameters affecting all TCP connections";
    }
    container statistics {
      if-feature statistics;
      config false;

      leaf active-opens {
        type yang:counter32;
        description
          "The number of times that TCP connections have made a direct
           transition to the SYN-SENT state from the CLOSED state.";
      }

      leaf passive-opens {
        type yang:counter32;
        description
          "The number of times TCP connections have made a direct
           transition to the SYN-RCVD state from the LISTEN state.";
      }

      leaf attempt-fails {
        type yang:counter32;
        description
          "The number of times that TCP connections have made a direct
           transition to the CLOSED state from either the SYN-SENT
           state or the SYN-RCVD state, plus the number of times that
           TCP connections have made a direct transition to the
           LISTEN state from the SYN-RCVD state.";
      }

      leaf establish-resets {
        type yang:counter32;
        description
          "The number of times that TCP connections have made a direct
           transition to the CLOSED state from either the ESTABLISHED
           state or the CLOSE-WAIT state.";
      }

      leaf currently-established {
        type yang:gauge32;
        description
          "The number of TCP connections for which the current state
           is either ESTABLISHED or CLOSE-WAIT.";
      }

      leaf in-segments {
        type yang:counter32;
        description
          "The total number of segments received, including those
           received in error.  This count includes segments received
           on currently established connections.";
      }

      leaf out-segments {
        type yang:counter32;
        description
          "The total number of segments sent, including those on
           current connections but excluding those containing only
           retransmitted octets.";
      }

      leaf retransmitted-segments {
        type yang:counter32;
        description
          "The total number of segments retransmitted; that is, the
           number of TCP segments transmitted containing one or more
           previously transmitted octets.";
      }

      leaf in-errors {
        type yang:counter32;
        description
          "The total number of segments received in error (e.g., bad
           TCP checksums).";
      }

      leaf out-resets {
        type yang:counter32;
        description
          "The number of TCP segments sent containing the RST flag.";
      }

      action reset {
        description
          "Reset statistics action command.";
        input {
          leaf reset-at {
            type yang:date-and-time;
            description
              "Time when the reset action needs to be
               executed.";
          }
        }
        output {
          leaf reset-finished-at {
            type yang:date-and-time;
            description
              "Time when the reset action command completed.";
          }
        }
      }
      description
        "Statistics across all connections.";
    }
  }
}
