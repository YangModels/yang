module ietf-mud-reporter {
  yang-version 1.1;
  namespace "urn:ietf:params:xml:ns:yang:ietf-mud-reporter";
  prefix mud-reporter;

  import ietf-inet-types {
    prefix inet;
  }
  import ietf-yang-types {
    prefix yang;
  }

  organization
    "IETF OPSAWG (Ops Area) Working Group";
  contact
    "WG Web: http://tools.ietf.org/wg/opsawg/
     WG List: opsawg@ietf.org
     Author: Eliot Lear
     lear@cisco.com
    ";
  description
    "This YANG module specifies the reporting format for MUD managers
     to use when they are reporting to manufacturers.

     Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
       (https://trustee.ietf.org/license-info).

     This version of this YANG module is part of RFC XXXX
     (https://www.rfc-editor.org/info/rfcXXXX); see the RFC itself
      for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
    ";

  revision 2019-06-21 {
    description
      "Initial proposed standard.";
    reference
      "RFC XXXX: Extension for MUD Reporting";
  }

  container mud-reporter {
    uses mud-reporter-grouping;
    description "Reporter Information.";
  }

  grouping mud-reporter-grouping   {

    description
      "MUD reporter container.";
    leaf mudurl {
      type inet:uri;
      description
        "The MUD-URL for which the report is being sent.";
    }
    list mud-report {
      key "time";
      description
        "individual records.";
      leaf time {
        type yang:timestamp;
        description
          "when this happened.";
      }
      leaf opaqueidentifier {
        type string;
        description
          "This is an identifier that maps to a particular
           device.  Its value MUST NOT be mappable back to
           any identifying information about the device.  It
           may be a suitable hash, such as SHA256.";
      }
      leaf direction {
        type enumeration {
          enum to-device {
            description
              "packet was traveling toward the device";
          }
          enum from-device {
            description
              "packet was traveling away from the device";
          }
        }
        description
          "which way packet is going";
      }
      leaf mycontrollers {
        type uint32;
        description
          "how many entries for my-controller.";
      }
      list controllers {
        key "uri";
        description
          "list of controllers and how many there were.";
        leaf uri {
          type inet:uri;
          description
            "the class URI of this controller";
        }
        leaf count {
          type uint32;
          description
            "number of devices serving this class.";
        }
        leaf ipaddress {
          type inet:ip-address;
          description
            "IP address of the controller.  Note that the MUD
             reporter MUST NOT transmit this contents of this
             node to the manufacturer.";
        }
      }
      leaf samemanufacturers {
        type uint32;
        description
          "number of devices matching same
           manufacturer.";
      }
      list manufacturers {
        key "authority";
        description
          "list of models and how many there were.";
        leaf authority {
          type inet:host;
          description
            "the manufacturer domain";
        }
        leaf count {
          type uint32;
          description
            "number of devices serving this class.";
        }
        leaf ipaddress {
          type inet:ip-address;
          description
            "IP address of the controller.  Note that the MUD
             reporter MUST NOT transmit this contents of this
             node to the manufacturer.";
        }
      }
      list models {
        key "uri";
        description
          "list of models and how many there were.";
        leaf uri {
          type inet:uri;
          description
            "the URI of this model";
        }
        leaf count {
          type uint32;
          description
            "number of devices serving this class.";
        }
        leaf ipaddress {
          type inet:ip-address;
          description
            "IP address of the controller.  Note that the MUD
             reporter MUST NOT transmit this contents of this
             node to the manufacturer.";
        }
      }
      list domains {
        key "hostname";
        description
          "list of hosts, and ip addresses if known.";
        leaf hostname {
          type inet:host;
          description
            "the host listed";
        }
        leaf-list ip-addresses {
          type inet:ip-address;
          description
            "ipv4 or v6 address mapping for this host if
             known.";
        }
      }
      uses class-drop-count;
    }
  }

  grouping class-drop-count {
    description
      "Destination fields of acl violating  packet are classfied.";
    leaf manufacturer {
      type string;
      description
        "manufacturer name";
    }
    leaf model {
      type string;
      description
        "model name";
    }
    leaf local-networks {
      type boolean;
      description
        "this packet matches the local networks
         classification";
    }
    leaf controller {
      type string;
      description
        "controller name";
    }
    leaf drop-count {
      type uint32;
      description
        "number of packets dropped for this classification";
    }
  }
}
