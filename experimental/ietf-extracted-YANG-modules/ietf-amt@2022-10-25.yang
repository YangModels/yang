module ietf-amt {
  yang-version "1.1";
  namespace "urn:ietf:params:xml:ns:yang:ietf-amt";
  prefix "amt";

  import ietf-inet-types {
    prefix "inet";
    reference
      "RFC 6991: Common YANG Data Types";
  }

  import ietf-routing-types {
       prefix rt-types;
       reference
         "RFC 8294, Common YANG Data Types for the Routing Area.";
  }

  import ietf-interfaces {
       prefix if;
       reference
         "RFC 8343, A YANG Data Model for Interface Management.";
  }

  import ietf-routing {
       prefix rt;
       reference
         "RFC 8349, A YANG Data Model for Routing Management
          (NMDA Version).";
  }

  organization
    "IETF MBONE Working Group";

  contact
    "TBD";

  description
    "This module describes a YANG model for configuring and managing
     AMT Protocol.

     This YANG model conforms to the Network Management
     Datastore Architecture (NMDA) as described in RFC 8342.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2022-10-25 {
    description
      "Initial Version";
    reference
      "RFC XXXX, YANG Data Model for Automatic Multicast Tunneling";
  }

  identity address-family {
    description
      "Base identity from which identities describing address
       families are derived.";
  }

  typedef ip-multicast-source-address {
    type union {
      type rt-types:ipv4-multicast-source-address;
      type rt-types:ipv6-multicast-source-address;
    }
    description
      "This type represents a version-neutral IP multicast source
       address.  The format of the textual representation implies
       the IP version.";
  }

  augment "/rt:routing/rt:control-plane-protocols" {
    description
      "AMT augmentation to the routing instance model.";
    container amt {
      description
        "Configuration parameters for the AMT protocol.";
      container relay {
        description
          "Parameters of AMT Relay service.";
        container relay-addresses {
          description
            "Parameters of AMT Relay addresses.";
          list relay-address {
            key "family";
            description
              "Each entry contains parameters for a AMT relay
               Address identified by the 'family' key.";
            leaf family {
              type identityref {
                base address-family;
              }
              mandatory true;
              description
                "The Address family.";
            }
            leaf anycast-prefix {
              type inet:ip-address;
              description
                "The anycast IP address of AMT Relay Discovery
                 Address.";
            }
            leaf local-address {
              type inet:ip-address;
              description
                "The unicast IP address of AMT Relay Address.";
            }
          }
        }
        leaf tunnel-limit {
          type uint32;
          description
            "The total number of endpoints";
        }
        leaf secret-key-timeout {
          type uint32;
          description
            "The timeout interval of secret key.";
        }
        container amt-tunnels {
          config false;
          description
            "The AMT tunnel information on the relay.";
          list amt-tunnel {
            key "gateway-address gateway-port";
            description
              "An entry of AMT tunnel.";
            leaf gateway-address {
              type inet:ip-address;
              description
                "The IP address of AMT gateway.";
            }
            leaf gateway-port {
              type inet:port-number;
              description
                "The UDP port of AMT gateway.";
            }
            leaf local-address {
              type inet:ip-address;
              description
                "The local IP address of AMT relay.";
            }
            leaf local-port {
              type inet:port-number;
              description
                "The local UDP port of AMT relay.";
            }
            leaf state {
              type enumeration {
                enum up {
                  description
                    "The AMT tunnel has been successfully
                     established.";
                }
                enum establishing {
                  description
                    "The AMT tunnel is being establishing.";
                }
              }
              description
                "The state of AMT tunnel.";
            }
            container multicastflows {
              config false;
              description
                "The multicast flow information in the AMT tunnel.";
              list multicastflow {
                key "source-address group-address";
                description
                  "An entry of multicast flow.";
                leaf source-address {
                  type ip-multicast-source-address;
                  description
                    "The source IP address of multicast flow.";
                }
                leaf group-address {
                  type rt-types:ip-multicast-group-address;
                  description
                    "The group address of multicast flow.";
                }
              }
            }
          }
        }
        container amtrelay-dns-resource-records {
          description
            "The DNS resource records of AMT relay.";
          list amtrelay-dns-resource-record {
            key "source-address";
            description
              "An entry of AMTRELAY resource record.";
            leaf source-address {
              type inet:ip-address;
              description
                "The IP address of multicast sender.";
            }
            leaf precedence {
              type uint32;
              description
                "The precedence of this record.";
            }
            leaf d-flag {
              type boolean;
              default "false";
              description
                "If the D-bit is set to true, the gateway MAY
                 send an AMT Request message directly to the
                 discovered relay address without first
                 sending an AMT Discovery message.
                 If the D-bit is set to false, the gateway MUST
                 receive an AMT Relay Advertisement message
                 for an address before sending an AMT
                 Request message to that address.";
            }
            leaf relay-type {
              type enumeration {
                enum empty {
                  value "0";
                  description
                    "The relay field is empty.";
                }
                enum ipv4-address {
                  value "1";
                  description
                    "The relay field contains a 4-octet IPv4
                     address.";
                }
                enum ipv6-address {
                  value "2";
                  description
                    "The relay field contains a 16-octet IPv6
                     address.";
                }
                enum domain-name {
                  value "3";
                  description
                    "The relay field contains a wire-encoded
                     domain name.";
                }
              }
              description
                "The type of Relay address.";
            }
            leaf discovery-address {
              type inet:ip-address;
              description
                "The IP address of AMT Relay Discovery Address.";
            }
            leaf domain-name {
              type inet:domain-name;
              description
                "The wire-encoded domain name of AMT Relay.";
            }
          }
        }
      } // relay
      container gateway {
        description
          "Parameters of AMT gateway service.";
        container pseudo-interfaces {
          description
            "Parameters of AMT pseudo-interface.";
          list pseudo-interface {
            key ifIndex;
            description
              "An entry of AMT pseudo-interface.";
            leaf ifIndex {
              type if:interface-ref;
              description
                "Index of pseudo interface, which can be ifindex
                 or interface name.";
            }
            leaf discovery-method {
              type enumeration {
                enum by-amt-solicit {
                  description
                    "Find the relay address by sending an AMT
                     Discovery message.";
                }
                enum by-dns-reverse-ip {
                  description
                    "Find the relay address by DNS reverse IP
                     AMT Discovery.";
                }
              }
              description
                "The method of discover relay address.";
            }
            leaf relay-discovery-address {
              type inet:ip-address;
              description
                "The IP address of AMT Relay Discovery Address.";
            }
            leaf relay-address {
              type inet:ip-address;
              description
                "The Ip address of AMT relay Address.";
            }
            leaf upstream-interface {
              type if:interface-ref;
              description
                "The index of upstream interface, which can
                 be ifindex or interface name.";
            }
            leaf discovery-timeout {
              type uint32;
              description
                "Initial time to wait for a response to
                 a Relay Discovery message.";
            }
            leaf discovery-retrans-count {
              type uint32;
              description
                "Maximum number of Relay Discovery retransmissions
                 to allow before terminating relay discovery
                 and reporting an error.";
            }
            leaf request-timeout {
              type uint32;
              description
                "Initial time to wait for a response
                 to a Request message";
            }
            leaf request-retrans-count {
              type uint32;
              description
                "Maximum number of Request retransmissions
                 to allow before abandoning a relay and restarting
                 relay discovery or reporting an error.";
            }
            leaf dest-unreach-retry-count {
              type uint32;
              description
                "The maximum number of times a gateway should
                 attempt to send the same Request or Membership
                 Update message after receiving an ICMP Destination
                 Unreachable message.";
            }
            leaf relay-port {
              type inet:port-number;
              description
                "The UDP port of AMT Relay.";
            }
            leaf local-address {
              type inet:ip-address;
              config false;
              description
                "The local IP address of this AMT tunnel.";
            }
            leaf local-port {
              type inet:port-number;
              config false;
              description
                "The local UDP port of this AMT tunnel.";
            }
            leaf tunnel-state {
              type enumeration {
                enum initial {
                  description
                    "Initial state.";
                }
                enum discoverying {
                  description
                    "The Relay Discovery message has been sent
                     and is waiting for the Advertisement message.";
                }
                enum requesting {
                  description
                    "The Request message has been sent,
                     waiting for the Query message.";
                }
                enum up {
                  description
                    "The AMT tunnel is Established.";
                }
              }
              config false;
              description
                "The tunnel's state.";
            }
          }
        }
      } // gateway
    } // amt
  } // augment
}
