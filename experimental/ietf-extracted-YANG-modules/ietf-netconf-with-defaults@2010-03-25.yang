module ietf-netconf-with-defaults {

   namespace "urn:ietf:params:netconf:capability:with-defaults";

   prefix nwd;

   import ietf-netconf { prefix nc; }

   organization
    "IETF NETCONF (Network Configuration Protocol) Working Group";

   contact
    "WG Web:   <http://tools.ietf.org/wg/netconf/>
     WG List:  <mailto:netconf@ietf.org>

     WG Chair: Bert Wijnen
               <mailto:bertietf@bwijnen.net>

     WG Chair: Mehmet Ersue
               <mailto:mehmet.ersue@nsn.com>

     Editor: Andy Bierman
             <mailto:andyb@iwl.com>

     Editor: Balazs Lengyel
             <mailto:balazs.lengyel@ericsson.com>";

   description
    "This module defines a capability-based extension to the
     NETCONF protocol that allows the NETCONF client to control
     whether default values are part of NETCONF
     <rpc-reply> messages or <copy-config> output to the target URL.

     Copyright (c) 2010 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";
   // RFC Ed.: replace XXXX with actual RFC number and remove this note

   // RFC Ed.: remove this note
   // Note: extracted from draft-ietf-netmod-with-defaults-06.txt

   revision 2010-03-25 {
     description
       "Initial version.";
     reference
      "RFC XXXX: With-defaults capability for NETCONF";
   }
   // RFC Ed.: replace XXXX with actual RFC number and remove this note

   typedef with-defaults-mode {
      description
        "Possible modes to report default data in
         rpc-reply messages.";
      type enumeration {
         enum report-all {
             description
               "All default data is always reported.";
         }
         enum trim {
             description
               "Values are not reported if they match the default.";
         }
         enum explicit {
             description
               "Report values that match the definition of
                explicitly set data.";
         }
     }
   }

   grouping with-defaults-parameters {
     leaf with-defaults {
       description
         "The explicit defaults processing mode requested.";
       type with-defaults-mode;
     }
   }

   // extending the get-config operation
   augment /nc:get-config/nc:input {
       uses with-defaults-parameters;
   }

   // extending the get operation
   augment /nc:get/nc:input {
       uses with-defaults-parameters;
   }

   // extending the copy-config operation
   augment /nc:copy-config/nc:input {
       uses with-defaults-parameters;
   }

}
