module rpki-vrp {

  namespace "urn:ietf:params:xml:ns:yang:rpki-vrp";

  prefix rpki-vrp;
  import "ietf-inet-types" {
    prefix inet;
  }

  typedef asn {
    type string {
      pattern 'AS(0|[1-9][0-9]{0,8}|[1-3][0-9]{1,9}|4([0-1][0-9]{8}|2([0-8][0-9]{7}|9([0-3][0-9]{6}|4([0-8][0-9]{5}|9([0-5][0-9]{4}|6([0-6][0-9]{3}|7([0-1][0-9]{2}|2([0-8][0-9]|9[0-5])))))))))';
    }
    description
      "The Autonomous System Number";
  }

  typedef ta {
    type enumeration {
      enum apic;
      enum arin;
      enum ripe;
      enum lacnic;
      enum afrinic;
    }
  }

  typedef ip-mask {
    type union {
      type ipv4-mask;
      type ipv6-mask;
    }
  }

  typedef ipv4-mask {
    type uint8 {
      range "0 .. 32";
    }
  }

  typedef ipv6-mask {
    type uint8 {
      range "0 .. 128";
    }
  }

  container roas {
    config true;
    list roas {
      key "prefix asn";
      leaf asn {
        type asn;
        mandatory true;
      }
      leaf prefix {
        type inet:ip-prefix;
        mandatory true;
      }
      leaf maxLength {
        type ip-mask;
        mandatory true;
      }
      leaf ta {
        type ta;
        mandatory true;
      }
      must "number(substring-after(prefix,'/')) >= number(maxLength)" {
        error-message "Max prefix Length is larger then prefix";
      }
    }
  }
}
