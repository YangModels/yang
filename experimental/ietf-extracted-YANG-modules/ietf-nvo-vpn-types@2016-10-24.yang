module ietf-nvo-vpn-types {
    namespace "urn:ietf:params:xml:ns:yang:ietf-nvo-vpn-types" ;
    prefix VPNTypes ;

    import ietf-nvo-common-types {
        prefix  CommonTypes;
    }

    organization "";
    contact "";
    description "ietf-nvo-vpn-types";
    revision 2016-10-24 {
        reference "draft-chen-opsawg-composite-vpn-dm-00";
    }

    typedef ProtectionRole {
        type enumeration {
            enum NOP{
                description "NOP";
            }
            enum MAIN{
                description "MAIN";
            }
        }
        description "ProtectionRole";
    }

    grouping VPNBasicInfo {
        description "VPNBasicInfo Grouping.";

        leaf topology {
            type CommonTypes:Topology;
            description "current support for full-mesh and
            point_to_multipoint(hub-spoke), others is reserved for
            future extensions." ;
        }

        leaf serviceType {
            type VPNTypes:ServiceType;
            description "current support for mpls l3vpn/vxlan/L2VPN
            overlay, others is reserved for future extensions." ;
        }

        leaf technology {
            type VPNTypes:VPNTunnelType;
            description "mpls|vxlan overlay l3vpn|eth over sdh|nop";
        }

        leaf adminStatus {
            type CommonTypes:AdminStatus;
            description "administrative status." ;
         }
    }

    typedef VPNTunnelType {
        type enumeration {
            enum NOP{
                description "NOP";
            }
            enum MPLS{
                description "MPLS";
            }
            enum MPLS-TP{
                description "MPLS-TP";
            }
        }
        description "VPNTunnelType";
    }

    typedef ServiceType {
        type enumeration {
            enum l3vpn {
                description "l3vpn" ;
            }
            enum l2vpn {
                description "l2vpn" ;
            }
        }
        description "ServiceType";
    }
}
