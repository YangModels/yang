module ietf-sr-topology-state {
  yang-version 1.1;
  namespace "urn:ietf:params:xml:ns:yang:ietf-sr-topology-state";
  prefix "srt-s";

  import ietf-sr-topology {
    prefix "srt";
  }
  import ietf-network-state {
    prefix "nw-s";
    reference "RFC 8345: A YANG Data Model for Network Topologies";
  }
  import ietf-network-topology-state {
    prefix "nt-s";
    reference "RFC 8345: A YANG Data Model for Network Topologies";
  }
  import ietf-l3-unicast-topology-state {
    prefix "l3t-s";
    reference "RFC 8346: A YANG Data Model for Layer 3 Topologies";
  }
  import ietf-segment-routing-common {
    prefix "sr-cmn";
    reference
      "I-D.ietf-spring-sr-yang: YANG Data Model for Segment Routing";
  }

  organization
    "IETF Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Igor Bryskin
               <mailto:Igor.Bryskin@huawei.com>

     Editor:   Vishnu Pavan Beeram
               <mailto:vbeeram@juniper.net>

     Editor:   Tarek Saad
               <mailto:tsaad@cisco.com>

     Editor:   Himanshu Shah
               <mailto:hshah@ciena.com>

     Editor:   Stephane Litkowski
               <mailto:stephane.litkowski@orange.com>";

  description
    "YANG data model for representing operational state information
     of Segment Routing Topologies, when NMDA is not supported.

     Copyright (c) 2018 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2018-06-22 {
    description "Initial revision";
    reference
      "RFC XXXX: YANG Data Model for SR and SR TE Topologies";
  }

  augment "/nw-s:networks/nw-s:network/nw-s:network-types/"
    + "l3t-s:l3-unicast-topology" {
    description
      "Defines the SR topology type.";
    uses srt:sr-topology-type;
  }

  augment "/nw-s:networks/nw-s:network/"
    + "l3t-s:l3-topology-attributes" {
    when "../nw-s:network-types/l3t-s:l3-unicast-topology/srt-s:sr" {
      description "Augment only for SR topology.";
    }
    description "Augment topology configuration";
    uses srt:sr-topology-attributes;
  }

  augment "/nw-s:networks/nw-s:network/nw-s:node/"
    + "l3t-s:l3-node-attributes" {
    when "../../nw-s:network-types/l3t-s:l3-unicast-topology/"
      + "srt-s:sr" {
      description "Augment only for SR topology.";
    }
    description "Augment node configuration.";
    uses srt:sr-node-attributes;
  }

  augment "/nw-s:networks/nw-s:network/nw-s:node/"
    + "l3t-s:l3-node-attributes/l3t-s:prefix" {
    when "../../../nw-s:network-types/l3t-s:l3-unicast-topology/"
      + "srt-s:sr" {
      description "Augment only for SR topology.";
    }
    description "Augment node prefix.";
    uses srt:sr-node-prefix-attributes;
  }

  augment "/nw-s:networks/nw-s:network/nw-s:node/"
    + "nt-s:termination-point/"
    + "l3t-s:l3-termination-point-attributes" {
    when "../../../nw-s:network-types/l3t-s:l3-unicast-topology/"
      + "srt-s:sr" {
      description "Augment only for SR topology.";
    }
    description "Augment termination point configuration";
    uses srt:sr-tp-attributes;
  }

  grouping sr-topology-attributes {
    description "SR topology scope attributes.";
    container sr {
      description
        "Containing SR attributes.";
      uses sr-cmn:srgb-cfg;
    } // sr
  } // sr-topology-attributes
}
