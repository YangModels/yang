module ietf-vn {
  yang-version 1.1;
  namespace "urn:ietf:params:xml:ns:yang:ietf-vn";
  prefix vn;

  /* Import network */

  import ietf-yang-types {
    prefix yang;
    reference
      "RFC 6991: Common YANG Data Types";
  }
  import ietf-network {
    prefix nw;
    reference
      "RFC 8345: A YANG Data Model for Network Topologies";
  }

  /* Import network topology */

  import ietf-network-topology {
    prefix nt;
    reference
      "RFC 8345: A YANG Data Model for Network Topologies";
  }

  /* Import TE Common types */

  import ietf-te-types {
    prefix te-types;
    reference
      "RFC 8776: Common YANG Data Types for Traffic Engineering";
  }

  /* Import TE Topology */

  import ietf-te-topology {
    prefix tet;
    reference
      "RFC 8795: YANG Data Model for Traffic Engineering (TE)
       Topologies";
  }

  organization
    "IETF Traffic Engineering Architecture and Signaling (TEAS)
     Working Group";
  contact
    "WG Web:  <https://datatracker.ietf.org/wg/teas/>
     WG List:  <mailto:teas@ietf.org>
     Editor: Young Lee <younglee.tx@gmail.com>
           : Dhruv Dhody <dhruv.ietf@gmail.com>";
  description
    "This module contains a YANG module for the Virtual Network
     (VN). It describes a VN operation module that can take place
     in the context of the Customer Network Controller (CNC)-
     Multi-Domain Service Coordinator (MSDC) interface (CMI) of
     the Abstraction and Control of Traffic Engineered Networks
     (ACTN) architecture where the CNC is the actor of a VN
     Instantiation/modification/deletion as per RFC 8453.
     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2023-10-14 {
    description
      "initial version.";
    reference
      "RFC XXXX: A YANG Data Model for Virtual Network (VN)
       Operations";
  }

  /* Features */

  feature multi-src-dest {
    description
      "Support for selection of one src or destination
       among multiple.";
    reference
      "RFC 8453: Framework for Abstraction and Control of TE
       Networks (ACTN)";
  }

  /* Typedef */

  typedef vn-id {
    type string;
    description
      "A type definition for Virtual Network (VN)
       identifier.";
  }

  typedef ap-id {
    type string;
    description
      "A type definition for Access Point (AP) identifier.";
  }

  typedef vnm-id {
    type string;
    description
      "A type definition for VN member identifier.";
  }

  typedef vn-compute-status {
    type te-types:te-common-status;
    description
      "A type definition for representing the VN compute status. Note
       that all status apart from up and down are considered as
       unknown.";
  }

  /* identities */

  identity vn-computation-error-reason {
    description
      "Base identity for VN computation error reasons.";
  }

  identity vn-computation-error-not-ready {
    base vn-computation-error-reason;
    description
      "VN computation has failed because the MDSC is not
       ready";
  }

  identity vn-computation-error-no-cnc {
    base vn-computation-error-reason;
    description
      "VN computation has failed because one or more dependent
       CNC are unavailable.";
  }

  identity vn-computation-error-no-resource {
    base vn-computation-error-reason;
    description
      "VN computation has failed because there is no
       available resource in one or more domains.";
  }

  identity vn-computation-error-path-not-found {
    base vn-computation-error-reason;
    description
      "VN computation failed as no path found.";
  }

  identity vn-computation-ap-unknown {
    base vn-computation-error-reason;
    description
      "VN computation failed as source or destination Access Point
       (AP) not known.";
  }

  /* Groupings */

  grouping vn-ap {
    description
      "Virtual Network Access Points (VNAP) related information";
    leaf vn-ap-id {
      type ap-id;
      description
        "A unique identifier for the referred VNAP";
    }
    leaf vn {
      type leafref {
        path "/virtual-network/vn/vn-id";
      }
      description
        "A reference to the VN";
    }
    leaf abstract-node {
      type leafref {
        path "/nw:networks/nw:network/nw:node/tet:te-node-id";
      }
      description
        "A reference to the abstract node in TE Topology that
         represent the VN";
    }
    leaf ltp {
      type leafref {
        path "/nw:networks/nw:network/nw:node/"
           + "nt:termination-point/tet:te-tp-id";
      }
      description
        "A reference to Link Termination Point (LTP) in the
         TE-topology";
      reference
        "RFC 8795: YANG Data Model for Traffic Engineering (TE)
         Topologies";
    }
    leaf max-bandwidth {
      type te-types:te-bandwidth;
      config false;
      description
        "The max bandwidth of the VNAP";
    }
    reference
      "RFC 8453: Framework for Abstraction and Control of TE
       Networks (ACTN), Section 6";
  }

  grouping access-point {
    description
      "AP related information";
    leaf ap-id {
      type ap-id;
      description
        "A unique identifier for the referred access point";
    }
    leaf pe {
      type leafref {
        path "/nw:networks/nw:network/nw:node/tet:te-node-id";
      }
      description
        "A reference to the PE node in the native TE Topology";
    }
    leaf max-bandwidth {
      type te-types:te-bandwidth;
      description
        "The max bandwidth of the AP";
    }
    leaf avl-bandwidth {
      type te-types:te-bandwidth;
      description
        "The available bandwidth of the AP";
    }
    list vn-ap {
      key "vn-ap-id";
      uses vn-ap;
      description
        "List of VNAP in this AP";
    }
    reference
      "RFC 8453: Framework for Abstraction and Control of TE
       Networks (ACTN), Section 6";
  }

  grouping vn-member {
    description
      "The vn-member is described by this grouping";
    leaf vnm-id {
      type vnm-id;
      description
        "A vn-member identifier";
    }
    container src {
      description
        "The source of VN Member";
      leaf src {
        type leafref {
          path "/access-point/ap/ap-id";
        }
        description
          "A reference to source AP";
      }
      leaf src-vn-ap-id {
        type leafref {
          path "/access-point/ap/vn-ap/vn-ap-id";
        }
        description
          "A reference to source VNAP";
      }
      leaf multi-src {
        if-feature "multi-src-dest";
        type boolean;
        default "false";
        description
          "Is the source part of multi-source, where
           only one of the source is enabled";
      }
    }
    container dest {
      description
        "the destination of VN Member";
      leaf dest {
        type leafref {
          path "/access-point/ap/ap-id";
        }
        description
          "A reference to destination AP";
      }
      leaf dest-vn-ap-id {
        type leafref {
          path "/access-point/ap/vn-ap/vn-ap-id";
        }
        description
          "A reference to dest VNAP";
      }
      leaf multi-dest {
        if-feature "multi-src-dest";
        type boolean;
        default "false";
        description
          "Is destination part of multi-destination, where only one
           of the destination is enabled";
      }
    }
    leaf connectivity-matrix-id {
      type leafref {
        path "/nw:networks/nw:network/nw:node/tet:te/"
           + "tet:te-node-attributes/"
           + "tet:connectivity-matrices/"
           + "tet:connectivity-matrix/tet:id";
      }
      description
        "A reference to connectivity-matrix";
      reference
        "RFC 8795: YANG Data Model for Traffic Engineering (TE)
         Topologies";
    }
    container underlay {
      description
        "An empty container that can be augmented with underlay
         technology information not supported by RFC 8795 (for
         example - Segement Routing (SR). ";
    }
    reference
      "RFC 8454: Information Model for Abstraction and Control of TE
       Networks (ACTN)";
  }

  grouping vn-policy {
    description
      "policy for VN-level diverisity";
    leaf vn-level-diversity {
      type te-types:te-path-disjointness;
      description
        "The type of disjointness on the VN level (i.e., across all
         VN members)";
    }
  }

  /* Configuration data nodes */

  container access-point {
    description
      "AP configurations";
    list ap {
      key "ap-id";
      description
        "access-point identifier";
      uses access-point {
        description
          "The access-point information";
      }
    }
    reference
      "RFC 8453: Framework for Abstraction and Control of TE
       Networks (ACTN), Section 6";
  }
  container virtual-network {
    description
      "VN configurations";
    list vn {
      key "vn-id";
      description
        "A virtual network is identified by a vn-id";
      leaf vn-id {
        type vn-id;
        description
          "A unique VN identifier";
      }
      uses te-types:te-topology-identifier;
      leaf abstract-node {
        type leafref {
          path "/nw:networks/nw:network/nw:node/tet:te-node-id";
        }
        description
          "A reference to the abstract node in TE Topology";
      }
      list vn-member {
        key "vnm-id";
        description
          "List of vn-members in a VN";
        uses vn-member;
        leaf oper-status {
          type te-types:te-oper-status;
          config false;
          description
            "The vn-member operational state.";
        }
        leaf if-selected {
          if-feature "multi-src-dest";
          type boolean;
          default "false";
          config false;
          description
            "Is the vn-member is selected among the multi-src/dest
             options";
        }
      }
      leaf admin-status {
        type te-types:te-admin-status;
        default "up";
        description
          "VN administrative state.";
      }
      leaf oper-status {
        type te-types:te-oper-status;
        config false;
        description
          "VN operational state.";
      }
      uses vn-policy;
    }
    reference
      "RFC 8453: Framework for Abstraction and Control of TE
       Networks (ACTN)";
  }

  /* RPC */

  rpc vn-compute {
    description
      "The VN computation without actual instantiation. This is
       used by the CNC to get the VN results without actually
       creating it in the network.

       The input could include a reference to the single node
       abstract topology. It could optionally also include
       constraints and optimization criteria. The computation
       is done based on the list of VN-members.

       The output includes a reference to the single node
       abstract topology with each VN-member including a
       reference to the connectivity-matrix-id where the
       path properties could be found. Error information is
       also included.";
    input {
      uses te-types:te-topology-identifier;
      leaf abstract-node {
        type leafref {
          path "/nw:networks/nw:network/nw:node/tet:te-node-id";
        }
        description
          "A reference to the abstract node in TE Topology";
      }
      uses te-types:generic-path-constraints;
      leaf cos {
        type te-types:te-ds-class;
        description
          "The class of service";
      }
      uses te-types:generic-path-optimization;
      list vn-member-list {
        key "vnm-id";
        description
          "List of VN-members in a VN";
        uses vn-member;
        uses te-types:generic-path-constraints;
        leaf cos {
          type te-types:te-ds-class;
          description
            "The class of service";
          reference
            "RFC 4124: Protocol Extensions for Support of
             Diffserv-aware MPLS Traffic Engineering,
             Section 4.3.1";
        }
        uses te-types:generic-path-optimization;
      }
      uses vn-policy;
    }
    output {
      uses te-types:te-topology-identifier;
      leaf abstract-node {
        type leafref {
          path "/nw:networks/nw:network/nw:node/tet:te-node-id";
        }
        description
          "A reference to the abstract node in TE Topology";
      }
      list vn-member-list {
        key "vnm-id";
        description
          "List of VN-members in a VN";
        uses vn-member;
        leaf if-selected {
          if-feature "multi-src-dest";
          type boolean;
          default "false";
          description
            "Is the vn-member is selected among the multi-src/dest
             options";
          reference
            "RFC 8453: Framework for Abstraction and Control of TE
             Networks (ACTN), Section 7";
        }
        leaf compute-status {
          type vn-compute-status;
          description
            "The VN-member compute state.";
        }
        container error-info {
          description
            "Error information related to the VN member";
          leaf error-description {
            type string;
            description
              "Textual representation of the error occurred during
               VN compute.";
          }
          leaf error-timestamp {
            type yang:date-and-time;
            description
              "Timestamp of the attempt.";
          }
          leaf error-reason {
            type identityref {
              base vn-computation-error-reason;
            }
            description
              "Reason for the VN computation error.";
          }
        }
      }
    }
  }
}
