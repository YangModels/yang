module netconf-system {

   namespace "urn:ietf:params:xml:ns:yang:netconf-system";

   prefix ncsys;

   import ietf-yang-types { prefix yang; }
   import ietf-inet-types { prefix inet; }
   organization
    "IETF NETCONF (Network Configuration Protocol) Working Group";

   contact
    "WG Web:   <http://tools.ietf.org/wg/netconf/>
     WG List:  <mailto:netconf@ietf.org>

     WG Chair: Bert Wijnen
               <mailto:bertietf@bwijnen.net>

     WG Chair: Mehmet Ersue
               <mailto:mehmet.ersue@nsn.com>

     Editor: Andy Bierman
             <mailto:andyb@iwl.com>";

   description
    "This module defines an YANG data model for use with the
     NETCONF protocol that allows the NETCONF client to monitor
     common system information and receive common system events.

     Copyright (c) 2010 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";
   // RFC Ed.: replace XXXX with actual RFC number and remove this note

   // RFC Ed.: remove this note
   // Note: extracted from draft-bierman-netconf-system-00.txt

   revision 2010-06-10 {
     description
       "Initial version.";
     reference
      "RFC XXXX: NETCONF System Monitoring";
   }
   // RFC Ed.: replace XXXX with actual
   // RFC number and remove this note

  typedef error-type-type {
    description "NETCONF Error Type";
    type enumeration {
      enum transport {
        description "Transport layer error";
      }
      enum rpc {
        description "Operation layer error";
      }
      enum protocol {
        description "Protocol layer error";
      }
      enum application {
        description "Application layer error";
      }
    }
  }

  typedef error-tag-type {
    description "NETCONF Error Tag";
    type enumeration {
      // descriptions TBD; normative text in RFC 4741
      enum in-use;
      enum invalid-value;
      enum too-big;
      enum missing-attribute;
      enum bad-attribute;
      enum unknown-attribute;
      enum missing-element;
      enum bad-element;
      enum unknown-element;
      enum unknown-namespace;
      enum access-denied;
      enum lock-denied;
      enum resource-denied;
      enum rollback-failed;
      enum data-exists;
      enum data-missing;
      enum operation-not-supported;
      enum operation-failed;
      enum partial-operation;
    }
  }

  typedef error-severity-type {
    description "NETCONF Error Severity";
    type enumeration {
      enum error {
        description "Error severity";
      }
      enum warning {
        description "Warning severity";
      }
    }
  }

  typedef edit-operation-type {
    description
      "NETCONF 'operation' Attribute values";
    type enumeration {
      enum merge;
      enum replace;
      enum create;
      enum delete;
    }
    default "merge";
  }

  grouping sys-common-session-parms {

    leaf user-name {
      description
        "Name of the user for the session.";
      type string;
    }

    leaf session-id {
      description "Identifier of the session.";
      type uint32;    // nc:session-id-or-zero-type;
      mandatory true;
    }

    leaf remote-host {
      description
        "Address of the remote host for the session.";
      type inet:ip-address;
    }
  }

  container system {
    description
      "Basic objects for NETCONF system identification.";

    config false;

    leaf sys-name {
      description "The system name.";
      reference "RFC 3418, sysName object";
      type string;
      mandatory true;
    }

    leaf sys-current-date-time {
      description
        "The current system date and time.";
      type yang:date-and-time;
      mandatory true;
    }

    leaf sys-boot-date-time {
      description
        "The system date and time when the system
        last restarted.";
      type yang:date-and-time;
      mandatory true;
    }

    leaf sys-server-id {
      description
        "The vendor-specific name and version ID string
         for the NETCONF server running on this system.";
      type string;
      mandatory true;
    }

    container uname {
      description
        "Contains the broken out fields from the
        output of the 'uname' command on this machine.";
      leaf sysname {
        type string;
        description
          "The name of the operating system in use.";
      }

      leaf release {
        type string;
        description
          "The current release level of the operating
           system in use.";
      }

      leaf version {
        type string;
        description
          "The current version level of the operating
           system in use.";
      }

      leaf machine {
        type string;
        description "A description of the hardware in use.";
      }

      leaf nodename {
        type string;
        description
          "The host name of this system, as reported by
          the uname command.";
      }
    } // container uname
  } // container system

  notification sys-startup {
    description
      "Generated when the system restarts.
      Used for logging purposes, since no
      sessions are actually active when
      the system restarts.";

    leaf startup-source {
      description
        "The system-specific filespec used to load the
         running configuration.  This leaf will only be
         present if there was a startup  configuration file used.";
      type string;
    }

    list boot-error {
      description
        "There will be one entry for each <rpc-error>
        encountered during the load config operation.
        There is no particular order, so no key is defined.
        This list will only be present if the server is configured
        to continue on error during startup, and there were recoverable
        errors encountered during the last restart of the server.";

      leaf error-type {
        description
          "Defines the conceptual layer that the error occurred.";
        type error-type-type;
        mandatory true;
      }

      leaf error-tag {
        description
          "Contains a string identifying the error condition.";
        type error-tag-type;
        mandatory true;
      }

      leaf error-severity {
        description
          "Contains a string identifying the error severity, as
           determined by the device.";
        type error-severity-type;
        mandatory true;
      }

      leaf error-app-tag {
        description
          "Contains a string identifying the data-model-specific
           or implementation-specific error condition, if one exists.";
        type string;
      }

     leaf error-path {
       description
         "Contains the absolute XPath expression identifying
          the element path to the node that is associated with
          the error being reported in a particular <rpc-error>
          element.";
       type yang:xpath1.0;
     }

     leaf error-message {
       description
         "Contains a string suitable for human display that
          describes the error condition.";
        type string;   // LangString;
      }

      anyxml error-info {
        description
          "Contains protocol- or data-model-specific error content.";
      }
    } // list boot-error
  } // notification sys-startup

  notification sys-config-change {
    description
      "Generated when the <running> configuration is changed.";
    uses sys-common-session-parms;

    list edit {
      description
        "An edit record will be present for each distinct
        edit operation on the running config.";
      leaf target {
        type instance-identifier;
        description
          "Topmost node associated with the configuration change.";
      }

      leaf operation {
        type edit-operation-type;
        description "Type of edit operation performed.";
      }
    } // list edit
  } // notification sys-config-change

  notification sys-capability-change {
    description
      "Generated when a <capability> is added, deleted,
       or modified.";
    container changed-by {
      description
        "Indicates who caused this capability change.
        If caused by internal action, then the
        empty leaf 'server' will be present.
        If caused by a management session, then
        the name, remote host address, and session ID
        of the session that made the change will be reported.";
      choice server-or-user {
        leaf server {
          type empty;
          description
            "If present, the capability change was caused
             by the server.";
        }

        case by-user {
          uses sys-common-session-parms;
        } // case by-user
      } // choice server-or-user
    } // container changed-by
    leaf-list added-capability {
      type inet:uri;
      description
        "List of capabilities that have just been added.";
    }

    leaf-list deleted-capability {
      type inet:uri;
      description
        "List of capabilities that have just been deleted.";
    }

    leaf-list modified-capability {
      type inet:uri;
      description
        "List of capabilities that have just been modified.";
    }
  } // notification sys-capability-change

  notification sys-session-start {
    description
      "Generated when a new NETCONF session is started.";
    uses sys-common-session-parms;
  } // notification sys-session-start

  notification sys-session-end {
    description
      "Generated when a NETCONF session is terminated.";
    uses sys-common-session-parms;

    leaf killed-by {
      when "../termination-reason = 'killed'";
      type uint32;    // nc:session-id-type;
      description
        "Session ID that issued the <kill-session>
        if the session was terminated by this operation.";
    }

    leaf termination-reason {
      type enumeration {
        enum "closed" {
          value 0;
          description
            "The session was terminated with
            the <close-session> operation.";
        }
        enum "killed" {
          value 1;
          description
            "The session was terminated with
            the <kill-session> operation.";
        }
        enum "dropped" {
          value 2;
          description
            "The session was terminated because
            the SSH session or TCP connection was
            unexpectedly closed.";
        }
        enum "timeout" {
          value 3;
          description
            "The session was terminated because
            of inactivity, either waiting for
            the <hello> or <rpc> messages.";
        }
        enum "bad-start" {
          value 4;
          description "The session startup sequence failed.";
        }
        enum "bad-hello" {
          value 5;
          description
            "The client's <hello> message was
            bad or never arrived.";
        }
        enum "other" {
          value 6;
          description
            "The session was terminated for
            some other reason.";
        }
      }
      mandatory "true";
      description "Reason the session was terminated.";
    }
  } // notification sys-session-end

  notification sys-confirmed-commit {
    description
      "Generated when a confirmed-commit event occurs.";
    uses sys-common-session-parms;

    leaf confirm-event {
      description
        "Indicates the event that caused the notification.";
      type enumeration {
        enum "start" {
          value 0;
          description
            "The confirm-commit procedure has started.";
        }
        enum "cancel" {
          value 1;
          description
            "The confirm-commit procedure has been canceled,
            due to the session being terminated.";
        }
        enum "timeout" {
          value 2;
          description
            "The confirm-commit procedure has been canceled,
            due to the confirm-timeout interval expiring.
            The common session parameters will not be present
            in this sub-mode.";
        }
        enum "extend" {
          value 3;
          description
            "The confirm-commit timeout has been extended.";
        }
        enum "complete" {
          value 4;
          description
            "The confirm-commit procedure has been completed.";
        }
      }
      mandatory "true";
    }
  } // notification sys-confirmed-commit

}
