module ietf-pcp-iwf {
  yang-version 1.1;

  namespace "urn:ietf:params:xml:ns:yang:ietf-pcp-iwf";
  prefix pcp-iwf;

  import ietf-inet-types { prefix inet; }
  import ietf-pcp-client { prefix pcp-client; }

  organization "xxxx Working Group";
  contact
     "Mohamed Boucadair <mohamed.boucadair@orange.com>
      Christian Jacquenet <christian.jacquenet@orange.com>";

  description
       "This module contains a collection of YANG definitions for
        UPnP IGD/PCP Interworking implementations.

        Copyright (c) 2017 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

  revision 2017-10-17 {
    description "Align with NMDA";
    reference "-05";
  }

  revision 2015-08-05 {
      description "Changes xxxx.";
       reference "xxxx";
   }

// IGD versions

grouping igd-version {
    description
      "UPnp IGD Version";

   leaf igd-version {

      type enumeration {

         enum "igd:1" {
             description
               "UPnP IGD:1";
         }

         enum "igd:2" {
             description
              "UPnP IGD:2";
         }

         enum "both" {
             description
              "UPnP IGD:1 and UPnP IGD:2";
         }
      }
   description
    "UPnP IGD Version";
 }
}

augment "/pcp-client:pcp-client/pcp-client:instances/pcp-client:instance/pcp-client:capabilities" {
           description "Capabilities";

          list igd-supported-version {

            key igd-version;

             description
               "list of supported IGD versions";

             uses igd-version;
           }

}

augment "/pcp-client:pcp-client/pcp-client:instances/pcp-client:instance" {
  description
    "IGD version(s)";

   container igd-version {
     description
       "Configure UPnP IGD version(s).";

     uses igd-version;
   }
}

augment "/pcp-client:pcp-client/pcp-client:instances/pcp-client:instance/pcp-client:mapping-table/pcp-client:mapping-entry" {
  description
    "Mapping table as maintained by a
     UPnP IGD/PCP IWF instance";

  leaf igd-control-point-address {
    type inet:ip-address;

    description
      "IP address of the UPnP Control Point.";
  }

  leaf igd-control-point-port {
    type inet:port-number;

    description
      "Port number of the UPnP Control Point.";
  }
 }
}
