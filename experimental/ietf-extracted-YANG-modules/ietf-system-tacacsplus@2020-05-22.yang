module ietf-system-tacacsplus {
  yang-version 1.1;
  namespace "urn:ietf:params:xml:ns:yang:ietf-system-tacacsplus";
  prefix sys-tcsplus;

  import ietf-inet-types {
    prefix inet;
    reference
      "RFC 6991: Common YANG Data Types";
  }
  import ietf-yang-types {
    prefix yang;
    reference
      "RFC 6991: Common YANG Data Types";
  }
  import ietf-network-instance {
    prefix ni;
    reference
      "RFC 8529: YANG Data Model for Network Instances";
  }
  import ietf-interfaces {
    prefix if;
    reference
      "RFC 8343: A YANG Data Model for Interface Management";
  }
  import ietf-system {
    prefix sys;
    reference
      "RFC 7317: A YANG Data Model for System Management";
  }
  import ietf-netconf-acm {
    prefix nacm;
    reference
      "RFC 8341: Network Configuration Access Control Model";
  }

  organization
    "IETF Opsawg (Operations and Management Area Working Group)";
  contact
    "WG Web:   <http://tools.ietf.org/wg/opsawg/>
     WG List:  <mailto:opsawg@ietf.org>

     Editor: Bo Wu <lana.wubo@huawei.com>
     Editor: Guangying Zheng <zhengguangying@huawei.com>";
  description
    "This module provides configuration of TACACS+ client.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see the
      RFC itself for full legal notices.";

  // RFC Ed.: update the date below with the date of RFC
  // publication and remove this note.
  // RFC Ed.: replace XXXX with actual RFC number and remove
  // this note, and the TACACS+ Protocol refers to
  // draft-ietf-opsawg-tacacs.

  revision 2020-05-22 {
    description
      "Initial revision.";
    reference
      "RFC XXXX: A Yang Data Model for TACACS+";
  }

  typedef tcsplus-server-type {
    type bits {
      bit authentication {
        description
          "When set, the server is an authentication server.";
      }
      bit authorization {
        description
          "When set, the server is an authorization server.";
      }
      bit accounting {
        description
          "When set, the server is an accounting server.";
      }
    }
    description
      "tcsplus-server-type can be set to
       authentication/authorization/accounting
       or any combination of the three types. When all three types are
       supported, all the three bits are set.";
  }

  feature tacacsplus {
    description
      "Indicates that the device can be configured as a TACACS+
       client.";
    reference
      "RFC XXXX : The TACACS+ Protocol ";
  }

  identity tacacsplus {
    base sys:authentication-method;
    description
      "Indicates AAA operation using TACACS+.";
    reference
      "RFC XXXX: The TACACS+ Protocol";
  }

  grouping statistics {
    description
      "Grouping for TACACS+ statistics attributes";
    container statistics {
      config false;
      description
        "A collection of server-related statistics objects";
      leaf connection-opens {
        type yang:counter64;
        description
          "Number of new connection requests sent to the server, e.g.
           socket open";
      }
      leaf connection-closes {
        type yang:counter64;
        description
          "Number of connection close requests sent to the server, e.g.
           socket close";
      }
      leaf connection-aborts {
        type yang:counter64;
        description
          "Number of aborted connections to the server.  These do
           not include connections that are close gracefully.";
      }
      leaf connection-failures {
        type yang:counter64;
        description
          "Number of connection failures to the server";
      }
      leaf connection-timeouts {
        type yang:counter64;
        description
          "Number of connection timeouts to the server";
      }
      leaf messages-sent {
        type yang:counter64;
        description
          "Number of messages sent to the server";
      }
      leaf messages-received {
        type yang:counter64;
        description
          "Number of messages received from the server";
      }
      leaf errors-received {
        type yang:counter64;
        description
          "Number of error messages received from the server";
      }
      leaf sessions {
        type yang:counter64;
        description
          "Number of TACACS+ sessions completed with the server.
           If the Single Connection Mode was NOT enabled, the number of
           sessions is the same as the number of 'connection-closes'.
           If the Mode was enabled, a single TCP connection may contain
           multiple TACACS+ sessions.";
      }
    }
  }

  grouping tacacsplus {
    description
      "Grouping for TACACS+ attributes";
    container tacacsplus {
      if-feature "tacacsplus";
      must "not(derived-from-or-self(../sys:authentication"
         + "/sys:user-authentication-order, 'tacacsplus')) or server" {
        error-message "When 'tacacsplus' is used as a system"
                    + " authentication method, a TACACS+ server"
                    + " must be configured.";
        description
          "When 'tacacsplus' is used as an authentication method,
           a TACACS+ server must be configured.";
      }
      description
        "Container for TACACS+ configurations and operations.";
      list server {
        key "name";
        ordered-by user;
        description
          "List of TACACS+ servers used by the device.";
        leaf name {
          type string;
          description
            "An arbitrary name for the TACACS+ server.";
        }
        leaf server-type {
          type tcsplus-server-type;
          description
            "Server type: authentication/authorization/accounting and
             various combinations.
             When all three types are supported, all the three bits
             are set.";
        }
        leaf address {
          type inet:host;
          mandatory true;
          description
            "The address of the TACACS+ server.";
        }
        leaf port {
          type inet:port-number;
          default "49";
          description
            "The port number of TACACS+ Server port.";
        }
        leaf shared-secret {
          type string {
            length "16..max";
          }
          mandatory true;
          nacm:default-deny-all;
          description
            "The shared secret, which is known to both the
             TACACS+ client and server. TACACS+ server administrators
             should configure shared secret of minimum 16 characters
             length.
             It is highly recommended that shared keys are at least 32
             characters long.";
          reference
            "RFC XXXX: The TACACS+ Protocol";
        }
        choice source-type {
          description
            "The source address type for outbound TACACS+ packets.";
          case source-ip {
            leaf source-ip {
              type inet:ip-address;
              description
                "Specifies source IP address for TACACS+ outbound
                 packets.";
            }
          }
          case source-interface {
            leaf source-interface {
              type if:interface-ref;
              description
                "Specifies the interface from which the IP address is
                 derived for use as the source for the outbound TACACS+
                 packet";
            }
          }
        }
        leaf vrf-instance {
          type leafref {
            path "/ni:network-instances/ni:network-instance/ni:name";
          }
          description
            "Specifies the VPN Routing and Forwarding (VRF) instance to
             use to communicate with the TACACS+ server.";
        }
        leaf single-connection {
          type boolean;
          default "false";
          description
            "Whether the single connection mode is enabled for the
             server. By default, the single connection mode is
             disabled.";
        }
        leaf timeout {
          type uint16 {
            range "1..300";
          }
          units "seconds";
          default "5";
          description
            "The number of seconds the device will wait for a
             response from each TACACS+ server before trying with a
             different server.";
        }
        uses statistics;
      }
    }
  }

  augment "/sys:system" {
    description
      "Augment the system model with the tacacsplus model";
    uses tacacsplus;
  }
}
