module ietf-vn-telemetry {
  yang-version 1.1;
  namespace "urn:ietf:params:xml:ns:yang:ietf-vn-telemetry";
  prefix vn-tel;

  /* Import VN */

  import ietf-vn {
    prefix vn;
    reference
      "I-D.ietf-teas-actn-vn-yang: A YANG Data Model for VN
       Operation";
  }

  /* Import TE */

  import ietf-te {
    prefix te;
    reference
      "I-D.ietf-teas-yang-te: A YANG Data Model for Traffic
       Engineering Tunnels and Interfaces";
  }

  /* Import TE Common types */

  import ietf-te-types {
    prefix te-types;
    reference
      "RFC 8776: Common YANG Data Types for Traffic Engineering";
  }

  /* Import TE Telemetry */

  import ietf-te-telemetry {
    prefix te-tel;
    reference
      "RFC XXXX: YANG models for VN/TE Performance Monitoring
       Telemetry and Scaling Intent Autonomics";
  }

  /* Note: The RFC Editor will replace XXXX with the number
     assigned to this draft.*/

  organization
    "IETF Traffic Engineering Architecture and Signaling (TEAS)
     Working Group";
  contact
    "WG Web:  <https://datatracker.ietf.org/wg/teas/>
     WG List: <mailto:teas@ietf.org>
     Editor:  Young Lee <younglee.tx@gmail.com>
              Dhruv Dhody <dhruv.ietf@gmail.com>";
  description
    "This module describes YANG data models for performance
     monitoring parameters (telemetry data) for Virtual Network
     (VN).

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  /* Note: The RFC Editor will replace XXXX with the number
     assigned to the RFC once draft-lee-teas-pm-telemetry-
     autonomics becomes an RFC.*/

  revision 2024-10-20 {
    description
      "Initial revision.";
    reference
      "RFC XXXX: YANG models for VN/TE Performance Monitoring
       Telemetry and Scaling Intent Autonomics";
  }

  identity grouping-op {
    description
      "Base identity for grouping-operation";
  }

  identity minimum {
    base grouping-op;
    description
      "Select the minimum of the monitored parameters";
  }

  identity maximum {
    base grouping-op;
    description
      "The maximum of the monitored parameters";
  }

  identity mean {
    base grouping-op;
    description
      "The mean of the monitored parameters";
  }

  identity standard-deviation {
    base grouping-op;
    description
      "The standard deviation of the monitored parameters";
  }

  identity sum {
    base grouping-op;
    description
      "The sum of the monitored parameters";
  }

  identity and {
    base grouping-op;
    description
      "Logical AND operation";
  }

  identity or {
    base grouping-op;
    description
      "Logical OR operation";
  }

  grouping grouping-operation {
    list operation {
      key "performance-type";
      leaf performance-type {
        type identityref {
          base te-tel:telemetry-param-type;
        }
        description
          "Reference to the tunnel level telemetry type";
      }
      leaf grouping-operation {
        type identityref {
          base grouping-op;
        }
        description
          "describes the operation to apply to the underlying
           TE tunnels";
      }
      description
        "Grouping operation for each performance-type";
    }
    description
      "Grouping operation for each performance-type";
  }

  augment "/vn:virtual-network/vn:vn" {
    description
      "Augmentation parameters for state TE VN topologies.";
    container vn-scaling-intent {
      description
        "scaling intent";
      container scale-in-intent {
        description
          "VN scale-in";
        uses te-tel:scaling-in-intent;
      }
      container scale-out-intent {
        description
          "VN scale-out";
        uses te-tel:scaling-out-intent;
      }
    }
    container vn-telemetry {
      description
        "VN telemetry params";
      container params {
        config false;
        description
          "Read-only telemetry parameters";
        uses te-types:performance-metrics-attributes;
      }
      uses grouping-operation;
    }
  }

  augment "/vn:virtual-network/vn:vn/vn:vn-member" {
    description
      "Augmentation parameters for state TE vn member topologies.";
    container vn-member-telemetry {
      description
        "VN member telemetry params";
      container params {
        config false;
        description
          "Read-only telemetry parameters";
        uses te-types:performance-metrics-attributes;
        leaf-list te-tunnel-ref {
          type leafref {
            path "/te:te/te:tunnels/te:tunnel/te:name";
          }
          description
            "A list of underlying TE tunnels that form the
             VN-member";
        }
      }
      uses grouping-operation;
    }
  }
}
