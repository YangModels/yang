module ietf-yang-revisions {
  yang-version 1.1;
  namespace "urn:ietf:params:xml:ns:yang:ietf-yang-revisions";
  prefix rev;

  organization
    "IETF NETMOD (Network Modeling) Working Group";
  contact
    "WG Web:   <https://datatracker.ietf.org/wg/netmod/>
     WG List:  <mailto:netmod@ietf.org>

     Author:   Benoit Claise
               <mailto:bclaise@cisco.com>

     Author:   Joe Clarke
               <mailto:jclarke@cisco.com>

     Author:   Reshad Rahman
               <mailto:rrahman@cisco.com>

     Author:   Robert Wilton
               <mailto:rwilton@cisco.com>

     Author:   Kevin D'Souza
               <mailto:kd6913@att.com>

     Author:   Balazs Lengyel
               <mailto:balazs.lengyel@ericsson.com>

     Author:   Jason Sterne
               <mailto:jason.sterne@nokia.com>";
  description
    "This YANG 1.1 module contains definitions and extensions to
     support updated YANG revision handling.";

  revision 2019-05-02 {
    description
      "Initial version.  Derived from ietf-semver.yang@2019-02-17.";
    reference
      "draft-verdt-netmod-module-versioning: Updated YANG Module
       Revision Handling";
  }

  typedef revision-identifier {
    type string {
      pattern '\d{4}-\d{2}-\d{2}';
    }
    description
      "Represents a specific date in YYYY-MM-DD format.
       TODO - Import and reuse type from 6991-bis";
  }

  typedef label-string {
    type string {
      length "1..255";
      pattern '[^\s@]+';
      pattern '\d{4}-\d{2}-\d{2}' {
        modifier invert-match;
      }
    }
    description
      "A label associated with a YANG revision.

       Excludes spaces and '@'.  Cannot match revision-date.";
    reference
      "draft-verdt-netmod-yang-module-versioning: Revision label";
  }

  typedef revision-date-or-label {
    type union {
      type revision-identifier;
      type label-string;
    }
    description
      "Represents either a YANG revision date or a revision label";
  }

  extension nbc-changes {
    description
      "This statement is used to indicate YANG module revisions that
       contain non-backwards-compatible changes.

       Each 'revision' statement MAY have a single 'nbc-changes'
       substatement.

       If a revision of a YANG module contains changes, relative to
       the preceding revision in the revision history, that do not
       conform to the module update rules defined in RFC-XXX, then
       the 'nbc-changes' statement MUST be added as a substatement to
       the revision statement.

       Conversely, if a revision of a YANG module only contains
       changes, relative to the preceding revision in the revision
       history, that are classified as 'backwards-compatible' then
       the revision statement MUST NOT contain any 'nbc-changes'
       substatement.";
    reference
      "draft-verdt-netmod-module-versioning: nbc-changes revision
       extension statement";
  }

  extension revision-label {
    argument label-string;
    description
      "The revision label can be used to provide an additional
       versioning identifier associated with the revision.  E.g., one
       option for a versioning scheme that could be used is [TODO -
       Reference semver draft].

       Each 'revision' statement MAY have a single 'revision-label'
       substatement.

       Revision labels MUST be unique amongst all revisions of a
       module.";
    reference
      "draft-verdt-netmod-module-versioning: Revision label";
  }

  extension revision-or-derived {
    argument revision-date-or-label;
    description
      "Restricts the revision of the module that may be imported to
       one that matches or is derived from the specified
       revision-date or revision-nlabel.

       The argument value MUST conform to the
       'revision-date-or-label' defined type.

       Each 'import' statement MAY have one or more
       'revision-or-derived' substatements.  If specified multiple
       times, then any module revision that satifies at least one of
       the 'revision-or-derived' statements is an acceptable revision
       for import.

       An 'import' statement MUST NOT contain both a
       'revision-or-derived' extension statement and a
       'revision-date' statement.

       A particular revision of an imported module satisfies an
       import's 'revision-or-derived' extension statement if the
       imported module's revision history contains a revision
       statement with a matching revision date or revision label.

       The 'revision-or-derived' extension statement does not
       gaurantee that all module revisions that satisfy an import
       statement are necessarily compatible, it only gives an
       indication that the revisions are more likely to be
       compatible.";

    reference
      "draft-verdt-netmod-yang-module-versioning: Import by derived
       revision";
  }

  extension status-description {
    argument description;

    description
      "Freeform text that describes why a given node has been
       deprecated or made obsolete.  E.g., the description could be
       used to give the reason for removal, or it could point to an
       alternative schema elements that can be used in lieu of the
       given node.

       Each 'status' statement MAY have a single 'status-description'
       substatement.";

    reference
      "draft-verdt-netmod-yang-module-versioning: YANG status
       description extension";
  }
}
