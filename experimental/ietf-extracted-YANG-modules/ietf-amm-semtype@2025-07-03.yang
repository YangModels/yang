module ietf-amm-semtype {
  yang-version 1.1;
  namespace "ari://ietf/amm-semtype/";
  prefix amm-semtype;

  import ietf-amm {
    prefix amm;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module defines base and derived IDENT objects which
     allow introspection of AMM semantic types.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2025-07-03 {
    description
      "Updated for latest ADM document.";
    reference
      "draft-ietf-dtn-adm-yang";
  }
  amm:enum 24;

  // Base IDENT objects
  amm:ident semtype {
    amm:enum 1;
    description
      "The base IDENT for semantic type introspection.
       This object itself provides no type information.";
  }

  // Semantic-type leaf IDENT objects
  amm:ident type-use {
    amm:enum 2;
    description
      "A named type use with possibe annotations and/or
       constraints.";
    amm:base "./IDENT/semtype";
    amm:parameter name {
      description
        "A built-in ARITYPE or reference to TYPEDEF object being
         used.";
      amm:type "//ietf/amm-base/TYPEDEF/type-ref";
    }
    // FIXME include constraints and annotations also?
  }
  amm:ident ulist {
    amm:enum 3;
    description
      "A uniformly-typed list within an AC.";
    amm:base "./IDENT/semtype";
    amm:parameter item-type {
      description
        "The semantic type for all items.";
      amm:type "./TYPEDEF/semtype";
    }
    amm:parameter min-elements {
      description
        "The smallest valid item count for the AC.";
      amm:default "null";
      amm:union {
        amm:type "/ARITYPE/uvast";
        amm:type "/ARITYPE/null";
      }
    }
    amm:parameter max-elements {
      description
        "The largest valid item count for the AC.";
      amm:default "null";
      amm:union {
        amm:type "/ARITYPE/uvast";
        amm:type "/ARITYPE/null";
      }
    }
  }
  amm:ident dlist {
    amm:enum 4;
    description
      "A diverse-typed list within an AC.";
    amm:base "./IDENT/semtype";
    amm:parameter item-types {
      description
        "The list of semantic type for each item in sequence within
         the list.
         The list itself is encoded as an AC in this parameter.";
      amm:ulist {
        amm:type "./TYPEDEF/semtype";
      }
    }
  }
  amm:ident umap {
    amm:enum 5;
    description
      "A uniformly-typed map within an AM.";
    amm:base "./IDENT/semtype";
    amm:parameter key-type {
      description
        "The semantic type for each key.";
      amm:type "./TYPEDEF/semtype";
    }
    amm:parameter value-type {
      description
        "The semantic type for each value.";
      amm:type "./TYPEDEF/semtype";
    }
  }
  amm:ident tblt {
    amm:enum 6;
    description
      "A parameterized table template for data within a TBL.";
    amm:base "./IDENT/semtype";
    amm:parameter columns {
      description
        "The list of column definitions as rows in a table.
         The order of these definitions is significant and correspond
         exactly with the order of columns in the TBL values.";
      amm:tblt {
        amm:key "name";
        amm:column name {
          description
            "The name of this column.
             Each name SHALL be unique within a table template.
             Each name SHALL be restricted to valid label text.";
          amm:type "//ietf/amm-base/typedef/id-text";
        }
        amm:column datatype {
          description
            "The semantic type for values in this column.";
          amm:type "./TYPEDEF/semtype";
        }
      }
    }
    amm:parameter min-elements {
      description
        "The smallest valid row count for the TBL.";
      amm:default "null";
      amm:union {
        amm:type "/ARITYPE/uvast";
        amm:type "/ARITYPE/null";
      }
    }
    amm:parameter max-elements {
      description
        "The largest valid row count for the TBL.";
      amm:default "null";
      amm:union {
        amm:type "/ARITYPE/uvast";
        amm:type "/ARITYPE/null";
      }
    }
    amm:parameter key {
      description
        "The primary key column names tuples in this table,
         space-separated labels.";
      amm:default "null";
      amm:union {
        amm:type "/ARITYPE/textstr";
        amm:type "/ARITYPE/null";
      }
    }
    amm:parameter unique {
      description
        "The set of unique column name tuples in this table, as
         space-separated labels.
         The set itself is encoded as an AC in this parameter.";
      amm:default "/AC/()";
      amm:ulist {
        amm:type "/ARITYPE/textstr";
      }
    }
  }
  amm:ident union {
    amm:enum 8;
    description
      "A list of alternative type choices.";
    amm:base "./IDENT/semtype";
    amm:parameter choices {
      description
        "The semantic type for each choice.
         The list itself is encoded as an AC in this parameter.";
      amm:ulist {
        amm:type "./TYPEDEF/semtype";
      }
    }
  }
  amm:ident seq {
    amm:enum 9;
    description
      "A sequence of similarly-typed items as a sub-sequence of an
       AC value.
       This is only usable in specific contexts, such as within a
       ./IDENT/dlist parameter.";
    amm:base "./IDENT/semtype";
    amm:parameter item-type {
      description
        "The semantic type for all items in the sequence.";
      amm:type "./TYPEDEF/semtype";
    }
    amm:parameter min-elements {
      description
        "The smallest valid item count for the sequence.";
      amm:default "null";
      amm:union {
        amm:type "/ARITYPE/uvast";
        amm:type "/ARITYPE/null";
      }
    }
    amm:parameter max-elements {
      description
        "The largest valid item count for the sequence.";
      amm:default "null";
      amm:union {
        amm:type "/ARITYPE/uvast";
        amm:type "/ARITYPE/null";
      }
    }
  }

  // Named types
  amm:typedef semtype {
    amm:enum 25;
    description
      "A parameterized reference to a semantic type object.
       This is used for introspection of AMM objects.";
    amm:type "/ARITYPE/ident" {
      amm:base "./IDENT/semtype";
    }
  }
}
