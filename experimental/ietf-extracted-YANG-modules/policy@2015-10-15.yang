submodule policy {
  belongs-to sfc-control-planes {
    prefix sfc-p;
  }
  organization "ETRI.";
  contact
  "M-K. Shin mkshin@etri.re.kr
   M-J Choi mjchoi@kangwon.ac.kr";
  description
  "Policies are used to bind an incoming flow to an appropriate
   SFP.";
  revision 2015-10-15 {
     reference
     "draft-shin-sfc-control-plane-yang-00 -
     Yang Data Model for Service Function Chaining Control Plane";
  }
  container classification-policy-table {
    description
    "One SFC is selected by the classification function according to
    the defined policy. The classification means service profile
    matching of traffic flows for identification of appropriate
    outbound forwarding actions.";
    list classification-policy-table {
      key flow-identifier;
      description
      "To classify the flow, flow identification is necessary.";
      leaf flow-identifier {
        type string;
        description
        "The flow identifier.";
      }
      leaf matching-condition {
        type string;
        description
        "The flow matching condition.";
      }
      leaf priority {
        type int32;
        description
        "Policy priority. The low value is high priority.";
      }
      leaf mapping-sfc-name {
        type string;
        description
        "The mapped service function name of the flow.";
      }
    }
  }
  container forwarding-policy-table {
    description
    "This policy is used to select SFIs defined in SFC and
     connect them. This policy is used in Service Function
     Forwarder (SFF). A SFF is responsible for delivering traffic
     received from the network to one or more connected service
     functions according to the policy table.";
    list Forwarding-Policy-Table {
      key index;
      description
      "The index of forwarding policy table.";
      leaf index {
        type int32;
        description
        "The index of forwarding policy table.";
      }
      leaf sff-name {
        type string;
             description "Name of Service Function Forwarder ";
      }
   }
}
}
