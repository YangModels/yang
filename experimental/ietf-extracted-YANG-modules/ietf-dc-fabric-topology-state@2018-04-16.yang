module ietf-dc-fabric-topology-state {

yang-version 1.1;
namespace
"urn:ietf:params:xml:ns:yang:ietf-dc-fabric-topology-state";
prefix sfabric;

import ietf-network-state {
    prefix nws;
    reference
    "RFC 8345:A Data Model for Network Topologies";
}
import ietf-dc-fabric-types {
    prefix fabrictypes;

    reference
    "draft-ietf-i2rs-yang-dc-fabric-network-topology-09
    NOTE TO RFC EDITOR:
    (1) Please replace above reference to draft-ietf-i2rs-yang
    -dc-fabric-network-topology-09 with RFC number when
    published (i.e. RFC xxxx).
    (2) Please replace the data in the revision statement
    with the data of publication when published.";
}

organization
"IETF I2RS (Interface to the Routing System) Working Group";

contact
"WG Web:    <http://tools.ietf.org/wg/i2rs/ >
 WG List:   <mailto:i2rs@ietf.org>

 Editor:    Yan Zhuang
            <mailto:zhuangyan.zhuang@huawei.com>

 Editor:    Danian Shi
            <mailto:shidanian@huawei.com>";

description
    "This module contains a collection of YANG definitions for
    Fabric state, representing topology that is either learned,
    or topology that results from applying toplogy that has been
    configured per the ietf-dc-fabric-topology model, mirroring
    the corresponding data nodes in this model.

    This model mirrors the configuration tree of ietf-dc-fabric
    -topology, but contains only read-only state data. The model
    is not needed when the implemtation infrastructure supports
    the Network Management Datastore Architecture(NMDA).

    Copyright (c) 2018 IETF Trust and the persons identified as
    authors of the code.  All rights reserved.

    Redistribution and use in source and binary forms, with or
    without modification, is permitted pursuant to, and subject
    to the license terms contained in, the Simplified BSD
    License set forth in Section 4.c of the IETF Trust's Legal
    Provisions Relating to IETF Documents
    (http:s//trustee.ietf.org/license-info).

    This version of this YANG module is part of
    draft-ietf-i2rs-yang-dc-fabric-network-topology;
    see the RFC itself for full legal notices.

    NOTE TO RFC EDITOR: Please replace above reference to
    draft-ietf-i2rs-yang-dc-fabric-network-topology-09 with RFC
    number when published (i.e. RFC xxxx).";

    revision "2018-04-16"{
        description
            "Initial revision.
             NOTE TO RFC EDITOR:
             Please replace the following reference to
             draft-ietf-i2rs-yang-dc-fabric-network-topology-09
             with RFC number when published (i.e. RFC xxxx).";
        reference
          "draft-ietf-i2rs-yang-dc-fabric-network-topology-09";
    }

//grouping statements
    grouping fabric-network-type {
      description "Identify the topology type to be fabric.";
      container fabric-network {
          presence "indicates fabric Network";
        description
          "The presence of the container node indicates
           fabric Topology";
      }
    }

    grouping fabric-options {
        description "Options for a fabric";

        leaf gateway-mode {
            type enumeration {
                enum centralized {
                    description "The Fabric uses centerilized
                    gateway, in which gateway is deployed on SPINE
                    node.";
                }
                enum distributed {
                    description "The Fabric uses distributed
                    gateway, in which gateway is deployed on LEAF
                    node.";
                }
            }
            default "distributed";
            description "Gateway mode of the fabric";
        }

        leaf traffic-behavior {
            type enumeration {
                enum normal {
                    description "Normal means no policy is needed
                    for all traffic";
                }
                enum policy-driven {
                    description "Policy driven means policy is
                    needed for the traffic otherwise the traffic
                    will be discard.";
                }
            }
            default "normal";
            description "Traffic behavior of the fabric";
        }

        leaf-list capability-supported {
            type fabrictypes:service-capabilities;
            description
                "It provides a list of supported services of the
                fabric. The service-capabilities is defined as
                identity-ref. Developers can define more services
                by defining new identies.";
        }
    }

    grouping device-attributes {
        description "device attributes";
        leaf device-ref {
            type fabrictypes:node-ref;
            description
                "The device that the fabric includes which refers
                 to a node in another topolopogy.";
        }
        leaf-list role {
            type fabrictypes:device-role;
            default fabrictypes:leaf;
            description
                "It is a list of devce-role to represent the roles
                that a device plays within a PoD, such as SPINE,
                LEAF, Border, or Border-Leaf.
                The device-role is defined as identity-ref. If more
                than 2 stage is used for a PoD, developers can
                define new identities for the device-role.";
        }
    }

    grouping link-attributes {
        description "Link attributes";
        leaf link-ref {
            type fabrictypes:link-ref;
            description
                "The link that the fabric includes which refers to
                a link in another topology.";
        }
    }

    grouping port-attributes {
        description "Port attributes";
        leaf port-ref {
            type fabrictypes:tp-ref;
            description
                "The port that the fabric includes which refers to
                a termination-point in another topology.";
        }
        leaf port-type {
            type fabrictypes:port-type;
            description
                "Port type is defined as identiy-ref. If current
                types includes ethernet or serial. If more types
                are needed, developers can define new identities.";
        }
        leaf bandwidth {
            type fabrictypes:bandwidth;
            description
                "Bandwidth of the port. It is defined as
                identity-ref. If more speeds are introduced,
                developers can define new identies for them.
                Current speeds include 1M, 10M, 100M, 1G, 10G,
                40G and 100G.";
        }
    }

    grouping fabric-attributes {
        description "Attributes of a fabric";

        leaf fabric-id {
                type fabrictypes:fabric-id;
                description
                    "Fabric id";
        }

        leaf name {
            type string;
            description
                "Name of the fabric";
        }

        leaf type {
            type fabrictypes:underlay-network-type;
            description
                "The type of physical network that implements this
                fabric.Examples are vlan, and trill.";
        }

        container vni-capacity {
            description "The range of the VNI(VXLAN Network
            Identifier defined in RFC 7348)s that the PoD uses.";

            leaf min {
                type int32;
                description
                    "The lower limit Vni.";
            }

            leaf max {
                type int32;
                description
                    "The upper limite Vni.";
            }
        }

        leaf description {
            type string;
            description
                "Description of the fabric";
        }

        container options {
            description "Options of the fabric";
            uses fabric-options;
        }

        list device-nodes {
            key device-ref;
            description "Device nodes that include in a fabric.";
            uses device-attributes;
        }

        list device-links {
            key link-ref;
            description "Links that include within a fabric.";
            uses link-attributes;
        }

        list device-ports {
            key port-ref;
            description "Ports that include in the fabric.";
            uses port-attributes;
        }
    }

    // augment statements

    augment "/nws:networks/nws:network/nws:network-types" {
      description
        "Introduce new network type for Fabric-based logical
        topology";
      uses fabric-network-type;
    }

    augment "/nws:networks/nws:network/nws:node" {
      when "/nws:networks/nws:network/nws:network-types"
      +"/sfabric:fabric-network"{
        description "Augmentation parameters apply only for
        networks with fabric topology.";
      }
      description "Augmentation for fabric nodes.";
      container fabric-attributes-state {
        description
          "Attributes for a fabric network";
        uses fabric-attributes;
      }
    }
}
