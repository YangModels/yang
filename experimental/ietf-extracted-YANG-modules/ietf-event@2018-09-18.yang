module ietf-event {
  yang-version 1.1;
  namespace "urn:ietf:params:xml:ns:yang:ietf-event";
  prefix evt;

  import ietf-yang-types {
    prefix yang;
  }

  organization
    "IETF xxx Working Group";
  contact
    "Zitao Wang: wangzitao@huawei.com
     Qin Wu: bill.wu@huawei.com";
  description
    "This module defines a model for the service topology.";

  revision 2018-09-18 {
    description
      "Initial revision.";
    reference "foo";
  }

  identity event-type {
    description
      "Base identity for event type";
  }

  identity frequency {
    description
      "Base identity for frequency";
  }

  identity periodic {
    base frequency;
    description
      "Identity for periodic trigger";
  }

  identity scheduling {
    base frequency;
    description
      "Identity for scheduling trigger";
  }

  identity immediate {
    base frequency;
    description
      "Identity for immediate trigger";
  }

  typedef match-value {
    type union {
      type yang:xpath1.0;
      type yang:object-identifier;
      type string;
    }
    description
      "This type is used to match resources of type 'target'.
       Since the type 'target' is a union of different types,
       the 'match-value' type is also a union of corresponding
       types.";
  }

  typedef target {
    type union {
      type instance-identifier;
      type yang:object-identifier;
      type yang:uuid;
      type string;
    }
    description
      "If the target is modelled in YANG, this type will
       be an instance-identifier.
       If the target is an SNMP object, the type will be an
       object-identifier.
       If the target is anything else, for example a distinguished
       name or a CIM path, this type will be a string.
       If the target is identified by a UUID use the uuid
       type.
       If the server supports several models, the presedence should
       be in the order as given in the union definition.";
  }

  grouping start-end-grouping {
    description
      "A grouping that provides start and end times for
       Event objects.";
    leaf start {
      type yang:date-and-time;
      description
        "The date and time when the Event object
         starts to create triggers.";
    }
    leaf end {
      type yang:date-and-time;
      description
        "The date and time when the Event object
         stops to create triggers.
         It is generally a good idea to always configure
         an end time and to refresh the end time as needed
         to ensure that agents that lose connectivity to
         their Controller do not continue executing Schedules
         forever.";
    }
  }

  container events {
    leaf evt-smp-min {
      type uint32;
      description
        "Sets the minimum value for data instance sampling";
    }
    leaf evt-smp-instance-max {
      type uint32;
      description
        "Sets the maximum value for data instance instance sampling.";
    }
    list event {
      key "event-name type";
      leaf event-name {
        type string;
        description
          "Event name";
      }
      leaf type {
        type identityref {
          base event-type;
        }
        description
          "Type of event";
      }
      leaf event-description {
        type string;
        description
          "Event description";
      }
      leaf-list target {
        type target;
        description
          "targeted objects";
      }
      leaf clear {
        type boolean;
        default "false";
        description
          "A flag indicate whether the event be closed";
      }
      list related-event {
        key "event-name type";
        leaf event-name {
          type string;
          description
            "Event name";
        }
        leaf type {
          type identityref {
            base event-type;
          }
          description
            "Type of event";
        }
        description
          "List for related events";
      }
      list trigger {
        key "name";
        leaf name {
          type string;
          description
            "Trigger name";
        }
        leaf type {
          type enumeration {
            enum "existence" {
              description
                "Indicates that the trigger type is 'existence'.
                 For 'existence', the specific test is as selected.
                 When an object appears, vanishes
                 or changes value, the trigger fires.";
            }
            enum "boolean" {
              description
                "Indicates that the trigger type is 'boolean'.
                 If the test result is true the trigger fires.  The
                 trigger will not fire again until the value has become false and
                 come back to true.";
            }
            enum "threshold" {
              description
                "Indicates that the trigger type is 'threshold'.
                 The event that may be triggered when a YANG instance
                 at data-instance list is found.  If the first sample after this
                 instance becomes active is greater than or equal to 'rising-value'
                 and the 'startup' is equal to 'rising' then one threshold rising
                 event is triggered for that instance.";
            }
          }
          description
            "Trigger type";
        }
        leaf trigger-description {
          type string;
          description
            "Trigger description";
        }
        container frequency {
          leaf type {
            type identityref {
              base frequency;
            }
            description
              "Type of trigger frequency";
          }
          container periodic {
            when "derived-from-or-self(../type, 'periodic')";
            description
              "A periodic timing object triggers periodically
               according to a regular interval.";
            leaf interval {
              type uint32 {
                range "1..max";
              }
              units "seconds";
              mandatory true;
              description
                "The number of seconds between two triggers
                 generated by this periodic timing object.";
            }
            uses start-end-grouping;
          }
          container scheduling {
            when "derived-from-or-self(../type, 'scheduling')";
            description
              "A scheduling timing object triggers.";
            leaf-list month {
              type string;
              description
                "A set of months at which this scheduling timing
                 will trigger.";
            }
            leaf-list day-of-month {
              type uint8 {
                range "0..59";
              }
              description
                "A set of days of the month at which this
                 scheduling timing will trigger.";
            }
            leaf-list day-of-week {
              type uint8 {
                range "0..59";
              }
              description
                "A set of weekdays at which this scheduling timing
                 will trigger.";
            }
            leaf-list hour {
              type uint8 {
                range "0..59";
              }
              description
                "A set of hours at which the scheduling timing will
                 trigger.";
            }
            leaf-list minute {
              type uint8 {
                range "0..59";
              }
              description
                "A set of minutes at which this scheduling timing
                 will trigger.";
            }
            leaf-list second {
              type uint8 {
                range "0..59";
              }
              description
                "A set of seconds at which this calendar timing
                 will trigger.";
            }
            uses start-end-grouping;
          }
          container immediate {
            when "derived-from-or-self(../type, 'immediate')";
            leaf immediate {
             type empty;
             mandatory true;
             description
              "This immediate Event object triggers immediately
               when it is configured.";
          }
          description
           "This immediate Event object triggers immediately
            when it is configured.";
         }
          description
            "Container for frequency";
        }
        choice test {
          description
            "Choice test";
          container existences {
            leaf-list target {
              type leafref {
                path "/events/event/target";
              }
              description
                "List for target objects";
            }
            leaf enable {
              type boolean;
              description
                "Startup";
            }
            description
              "Container for existence";
          }
          container boolean {
            leaf comparison {
              type enumeration {
                enum "unequal" {
                  description
                    "Indicates that the comparision type is 'unequal'.";
                }
                enum "equal" {
                  description
                    "Indicates that the comparision type is 'equal'.";
                }
                enum "leass" {
                  description
                    "Indicates that the comparision type is 'less'.";
                }
                enum "less-or-equal" {
                  description
                    "Indicates that the comparision type is 'less or equal'.";
                }
                enum "greater" {
                  description
                    "Indicates that the comparision type is 'greater'.";
                }
                enum "greater-or-equal" {
                  description
                    "Indicates that the comparision type is 'greater or equal'.";
                }
              }
              description
                "Comparison type";
            }
            leaf value {
              type match-value;
              description
                "Compartion value";
            }
            leaf-list target {
              type leafref {
                path "/events/event/target";
              }
              description
                "List for target objects";
            }
            leaf enable {
              type boolean;
              description
                "Startup";
            }
            description
              "Container for boolean test";
          }
          container threshold {
            leaf rising-value {
              type match-value;
              description
                "Sets the rising threshold to the specified value, ]
                 When the current sampled value is greater than or equal to
                 this threshold, and the value at the last sampling interval
                 was less than this threshold, the event is triggered. ";
            }
            leaf-list rising-target {
              type leafref {
                path "/events/event/target";
              }
              description
                "List for target objects";
            }
            leaf falling-value {
              type match-value;
              description
                "Sets the falling threshold to the specified value";
            }
            leaf-list falling-target {
              type leafref {
                path "/events/event/target";
              }
              description
                "List for target objects";
            }
            leaf delta-rising-value {
              type match-value;
              description
                "Sets the delta rising threshold to the specified value";
            }
            leaf-list delta-rising-target {
              type leafref {
                path "/events/event/target";
              }
              description
                "List for target objects";
            }
            leaf startup {
              type enumeration {
                enum "rising" {
                  description
                    "If the first sample after this
                     instance becomes active is greater than or equal to 'rising-value'
                     and the 'startup' is equal to 'rising' then one threshold rising
                     event is triggered for that instance.";
                }
                enum "falling" {
                  description
                    "If the first sample
                     after this instance becomes active is less than or equal to
                     'falling-value' and the 'startup' is equal to 'falling' then one
                     threshold falling event is triggered for that instance.";
                }
                enum "rising-or-falling" {
                  description
                    "That event is
                       also triggered if the first sample after this entry becomes
                       active is less than or equal or rising than to this threshold and
                       'startup' is equal to 'rising-or-falling'.";
                }
              }
              description
                "Startup";
            }
            description
              "Container for threshold";
          }
        }
        description
          "List for trigger";
      }
      list action {
        key "action-name";
        leaf action-name {
          type string;
          description
            "Action name";
        }
        notification event-notification {
          leaf event-name {
            type leafref {
              path "/events/event/event-name";
            }
            description
              "Report the event name";
          }
          leaf type {
            type leafref {
              path "/events/event/type";
            }
            description
              "Report the event type";
          }
          leaf-list target {
            type target;
            description
              "Report the target objects";
          }
          description
            "This notification is used to report that an operator
             acted upon an Event.";
        }
        action set {
          input {
            leaf-list target {
              type target;
              description
                "Report the target objects";
            }
            anydata value {
              description
                "Inline set content.";
            }
          }
        }
        leaf-list trigger-event {
          type leafref {
            path "../../event-name";
          }
          description
            "This action trigger another event";
        }
        description
          "List for Actions";
      }
      description
        "List for Events";
    }
    description
      "YANG data module for defining event triggers
       and actions for network management purposes";
  }
}
