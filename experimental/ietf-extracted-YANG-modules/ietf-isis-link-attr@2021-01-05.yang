module ietf-isis-link-attr {
  yang-version 1.1;
  namespace "urn:ietf:params:xml:ns:yang:ietf-isis-link-attr";

  prefix isis-link-attr;

  import ietf-inet-types {
    prefix inet;
    reference "RFC 6991 - Common YANG Data Types";
  }

  import ietf-routing {
    prefix "rt";
  }

  import ietf-isis {
    prefix "isis";
  }

  organization
    "IETF LSR - Link State Routing Working Group";

  contact
     "WG Web:   <http://tools.ietf.org/wg/lsr>
      WG List:  <mailto:lsr@ietf.org>

      Author:   Yingzhen Qu
                <mailto:yqu@futurewei.com>
      Author:   Acee Lindem
                <mailto:acee@cisco.com>
      Author:   Stephane Litkowski
                <mailto:slitkows.ietf@gmail.com>";

  description
    "This YANG module defines the configuration and operational
     state for IS-IS application specific link attributes feature as
     defined in RFC 8919.

     This YANG model conforms to the Network Management
     Datastore Architecture (NMDA) as described in RFC 8342.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  reference "RFC XXXX";

  revision 2021-01-05 {
    description
      "Initial version";
    reference
      "RFC XXXX: A YANG Data Model for IS-IS.";
  }

  identity sabm-bit {
    description
      "Base identity for sabm bits.";
    reference "RFC 8919: IS-IS Application-Specific Link Attributes";
  }

  identity rsvp-te-bit {
    base sabm-bit;
    description
      "R bit, RSVP-TE.";
  }

  identity sr-policy-bit {
    base sabm-bit;
    description
      "S bit, Segment Routing Policy.";
  }

  identity lfa-bit {
    base sabm-bit;
    description
      "F bit, Loop Free Alternate (LFA). Includes all LFA types.";
  }

  grouping application-identifier-bit-mask {
    description
      "Identification of the set of applications associated with link
       attribute advertisements";

    leaf l-flag {
      type boolean;
      description
        "Legacy Flag. When set, all of the applications
         specified in the bit mask MUST use the legacy
         advertisements.";
    }
    leaf sabm-length {
      type uint8;
      description
        "Standard Application Identifier Bit Mask Length in
         octets.";
    }
    leaf r-flag {
      type boolean;
      default false;
      description
        "Reserved.";
    }
    leaf udabm-length {
      type uint8;
      description
      "User Defined Application Identifier Bit Mask Length
      in octets.";
    }
    container sabm {
      leaf-list sabm-bits {
        type identityref {
          base sabm-bit;
        }
        description
          "SABM bits list. This list will contain
           identities for the bits which are set in the
           SABA bits.";
      }
      description
        "Standard Application Identifier Bit Mask.";
    }
    container udabm {
      description
        "User Defined Application Identifier Bit Mask.
         This container is to be augmented by user defined
         applications.";
    }
  }

  grouping application-specific-link-attributes-sub-tlv {
    description
      "Grouping for specification of the applications and
       application-specific attribute values.";

    container application-specific-link-attributes-sub-tlvs {
      list asla-sub-tlvs {
        uses application-identifier-bit-mask;
        uses isis:unknown-tlvs;
        description
          "List of application specific link attributes sub-tlvs.";
      }
      description
        "Application specific link attributes sub-tlv.";
    }
  }

  grouping application-specific-srlg-tlv {
    description
      "Grouping of a TLV to advertise application-specific
       SRLGs for a given link.";
    container application-specific-srlg-tlv {
      list as-srlg-tlvs {
        leaf neighbor-system-id {
          type isis:system-id;
          description
            "Neighbor System-ID.";
        }
        leaf pseudo-node-id {
          type uint8;
          description
            "Pseudo-node ID.";
        }
        uses application-identifier-bit-mask;
        leaf length-of-sub-tlvs {
          type uint8;
          description
            "Length of sub-tlvs.";
        }

        container link-id-sub-tlvs {
          description
            "Link Identifier sub-TLVs.";
          container link-local-remote-ids {
            description
              "Link local/remote identifier sub-tlv.";
            leaf link-local-id {
              type union {
                type inet:ipv4-address;
                type uint32;
              }
              description
                "Local identifier of the link.
                 It could be an IPv4 address or a local identifier.";
            }
            leaf link-remote-id {
              type union {
                type inet:ipv4-address;
                type uint32;
              }
              description
                "Remote identifier of the link.
                It could be an IPv4 address or a remotely learned
                identifier.";
            }
          }
          container ipv4-interface-addr {
            leaf ipv4-int-addr {
              type inet:ipv4-address;
              description
                "IPv4 address for the interface.";
            }
            description
              "IPv4 interface address sub-tlv.";
          }
          container ipv4-neighbor-addr {
            leaf ipv4-neighbor-addr {
              type inet:ipv4-address;
              description
                "IPv4 address for a neighboring router
                on this link.";
            }
            description
              "IPv4 neighbor address sub-tlv.";
          }
          container ipv6-interface-addr {
            leaf ipv6-int-addr {
              type inet:ipv6-address;
              description
                "IPv6 address for the interface.";
            }
            description
              "IPv6 interface address sub-tlv.";
          }
          container ipv6-neighbor-addr {
            leaf ipv6-neighbor-addr {
              type inet:ipv6-address;
              description
                "IPv6 address for a neighboring router
                on this link.";
            }
            description
              "IPv6 neighbor address sub-tlv.";
          }
        }

        container srlgs {
          description "List of SRLGs.";
          leaf-list srlg {
            type uint32;
            description
              "SRLG value of the link.";
          }
        }

        description
          "List of application specific SRLG tlvs.";
      }
      description
        "Application specific SRLG tlv.";
    }
  }

  augment "/rt:routing/" +
          "rt:control-plane-protocols/rt:control-plane-protocol"+
          "/isis:isis/isis:interfaces/isis:interface" {
    when "/rt:routing/rt:control-plane-protocols/"+
                     "rt:control-plane-protocol/rt:type = 'isis:isis'" {
      description
        "This augment ISIS routing protocol when used.";
    }
    description
      "This augments ISIS protocol configuration
       with TE attributes per application.";

    container isis-link-attr {
      choice link-attr-op-mode {
        mandatory "true";
        leaf legacy {
          type empty;
          description
            "Only send legacy advertisements.";
        }
        leaf transition {
          type empty;
          description
            "Send both application-specific and legacy advertisements.";
        }
        leaf app-specific{
          type empty;
          description
            "Only send application-specific advertisements.";
        }
        description
          "Link attributes mode";
      }
      description
        "Link attributes operation mode.";
    }
  }

  /* TLV 22 */
  augment "/rt:routing/" +
          "rt:control-plane-protocols/rt:control-plane-protocol"+
          "/isis:isis/isis:database/isis:levels/isis:lsp"+
          "/isis:extended-is-neighbor/isis:neighbor"+
          "/isis:instances/isis:instance" {
    when "/rt:routing/rt:control-plane-protocols/"+
         "rt:control-plane-protocol/rt:type = 'isis:isis'" {
      description
        "This augment ISIS routing protocol when used";
    }
    description
      "This augments ISIS protocol LSDB TLV22.";

       uses application-specific-link-attributes-sub-tlv;
  }

  /* TLV 223 */
  augment "/rt:routing/" +
          "rt:control-plane-protocols/rt:control-plane-protocol"+
          "/isis:isis/isis:database/isis:levels/isis:lsp"+
          "/isis:mt-is-neighbor/isis:neighbor"+
          "/isis:instances/isis:instance" {
    when "/rt:routing/rt:control-plane-protocols/"+
         "rt:control-plane-protocol/rt:type = 'isis:isis'" {
      description
        "This augment ISIS routing protocol when used";
    }
    description
      "This augments ISIS protocol LSDB TLV22.";

       uses application-specific-link-attributes-sub-tlv;
  }

  /* application-specific SRLG TLV 238 */
  augment "/rt:routing/" +
          "rt:control-plane-protocols/rt:control-plane-protocol"+
          "/isis:isis/isis:database/isis:levels/isis:lsp" {
    when "/rt:routing/rt:control-plane-protocols/"+
         "rt:control-plane-protocol/rt:type = 'isis:isis'" {
      description
        "This augment ISIS routing protocol when used";
    }
    description
      "This augments ISIS protocol LSDB router capability.";

    uses application-specific-srlg-tlv;
  }
}
