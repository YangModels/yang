module ietf-nat {
  yang-version 1.1;
  namespace "urn:ietf:params:xml:ns:yang:ietf-nat";

  //namespace to be assigned by IANA
  prefix "nat";

  import ietf-inet-types { prefix inet; }
  import ietf-yang-types { prefix yang; }
  import ietf-interfaces { prefix if; }

  organization "IETF OPSAWG (Operations and Management Area Working Group)";

  contact

    "WG Web:   <https://datatracker.ietf.org/wg/opsawg/>
     WG List:  <mailto:opsawg@ietf.org>

     WG Chair: Ignas Bagdonas
               <mailto:ibagdona@gmail.com>

     WG Chair: Joe Clarke
               <mailto:jclarke@cisco.com>

     WG Chair: Tianran Zhou
               <mailto:zhoutianran@huawei.com>

     Editor:  Mohamed Boucadair
              <mailto:mohamed.boucadair@orange.com>

     Editor:  Senthil Sivakumar
              <mailto:ssenthil@cisco.com>

     Editor:  Chritsian Jacquenet
              <mailto:christian.jacquenet@orange.com>

     Editor:  Suresh Vinapamula
              <mailto:sureshk@juniper.net>

     Editor:  Qin Wu
              <mailto:bill.wu@huawei.com>";
  description
    "This module is a YANG module for NAT implementations
     (including NAT44 and NAT64 flavors).

     Copyright (c) 2017 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2017-10-30 {
    description
      "Initial revision.";
    reference
      "RFC XXXX: A YANG Data Model for Network Address Translation
                 (NAT) and Network Prefix Translation (NPT)";
  }

  /*
   * Definitions
   */

  typedef percent {
    type uint8 {
      range "0 .. 100";
    }
    description
      "Percentage";
  }

  /*
   * Identities
   */

  identity nat-type {
    description
      "Base identity for nat type.";
  }

  identity nat44 {
    base nat:nat-type;
    description
      "Identity for traditional NAT support.";
    reference
      "RFC 3022: Traditional IP Network Address Translator
                 (Traditional NAT)";
  }

  identity basic-nat {
    base nat:nat44;
    description
      "Identity for Basic NAT support.";
    reference
      "RFC 3022: Traditional IP Network Address Translator
                 (Traditional NAT)";
  }

  identity napt {
    base nat:nat44;
    description
      "Identity for NAPT support.";
    reference
      "RFC 3022: Traditional IP Network Address Translator
                 (Traditional NAT)";
  }

  identity dst-nat {
    base nat:nat-type;
    description
      "Identity for Destination NAT support.";
  }

  identity nat64 {
    base nat:nat-type;
    description
      "Identity for NAT64 support.";
    reference
      "RFC 6146: Stateful NAT64: Network Address and Protocol
                 Translation from IPv6 Clients to IPv4 Servers";
  }

  identity clat {
    base nat:nat-type;
    description
      "Identity for CLAT support.";
    reference
      "RFC 6877: 464XLAT: Combination of Stateful and Stateless
                 Translation";
  }
  identity eam {
    base nat:nat-type;
    description
      "Identity for EAM support.";
    reference
     "RFC 7757: Explicit Address Mappings for Stateless IP/ICMP
                Translation";
  }

  identity nptv6 {
    base nat:nat-type;
    description
      "Identity for NPTv6 support.";
    reference
      "RFC 6296: IPv6-to-IPv6 Network Prefix Translation";
  }

  identity vrf-routing-instance {
    description
      "This identity represents a VRF routing instance.";
    reference
      "Section 8.9 of RFC 4026.";
  }

 /*
  * Grouping
  */

  grouping port-number {
    description
      "Individual port or a range of ports.
       When only start-port-number is present,
       it represents a single port.";

    leaf start-port-number {
      type inet:port-number;
      description
        "Begining of the port range.";
      reference
        "Section 3.2.9 of RFC 8045.";
    }

    leaf end-port-number {
      type inet:port-number;

      must ". >= ../start-port-number"
        {
          error-message
            "The end-port-number must be greater than or
             equal to start-port-number.";
        }
      description
        "End of the port range.";
      reference
        "Section 3.2.10 of RFC 8045.";
    }
  }

  grouping port-set {
    description
      "Indicates a set of ports.

       It may be a simple port range, or use the Port Set ID (PSID)
       algorithm to represent a range of transport layer
       ports which will be used by a NAPT.";

    choice port-type {
      default port-range;
      description
        "Port type: port-range or port-set-algo.";
      case port-range {
         uses port-number;
       }

      case port-set-algo {
        leaf psid-offset {
          type uint8 {
            range 0..15;
          }

          description
            "The number of offset bits (a.k.a., 'a' bits).

             Specifies the numeric value for the excluded port
             range/offset bits.

             Allowed values are between 0 and 15 ";

          reference
            "Section 5.1 of RFC 7597";
        }

        leaf psid-len {
          type uint8 {
             range 0..15;
          }
          mandatory true;

         description
           "The length of PSID, representing the sharing
            ratio for an IPv4 address.

            (also known as 'k').

            The address-sharing ratio would be 2^k.";

          reference
            "Section 5.1 of RFC 7597";
        }

        leaf psid {
          type uint16;
          mandatory true;
          description
            "Port Set Identifier (PSID) value, which
             identifies a set of ports algorithmically.";
          reference
            "Section 5.1 of RFC 7597";
        }
      }
      reference
        "Section 7597: Mapping of Address and Port with
                       Encapsulation (MAP-E)";
    }
  }

  grouping mapping-entry {
    description
      "NAT mapping entry.";

    leaf index {
      type uint32;
      description
        "A unique identifier of a mapping entry.";
    }

    leaf type {
      type enumeration {
        enum "static"  {
          description
            "The mapping entry is explicitly configrued
             (e.g., via command-line interface).";
        }

        enum "dynamic-implicit" {
          description
            "This mapping is created implicitely as a side effect
             of processing a packet that requires a new mapping.";

        }

        enum "dynamic-explicit" {
          description
            "This mapping is created as a result of an explicit
             request, e.g., a PCP message.";

        }
      }
        description
          "Indicates the type of a mapping entry. E.g.,
           a mapping can be: static, implicit dynamic
           or explicit dynamic.";
    }

    leaf transport-protocol {
      type uint8;
      description
        "Upper-layer protocol associated with this mapping.
         Values are taken from the IANA protocol registry.
         For example, this field contains 6 (TCP) for a TCP
         mapping or 17 (UDP) for a UDP mapping.

         If this leaf is not instantiated, then the mapping
          applies to any protocol.";
    }

    leaf internal-src-address {
      type inet:ip-prefix;
      description
        "Corresponds to the source IPv4/IPv6 address/prefix
         of the packet received on an internal
         interface.";
    }

    container internal-src-port {
      description
        "Corresponds to the source port of the
         packet received on an internal interface.

         It is used also to indicate the internal
         source ICMP identifier.

         As a reminder, all the ICMP Query messages contain
         an 'Identifier' field, which is referred to in this
         document as the 'ICMP Identifier'.";

       uses port-number;
    }

    leaf external-src-address {
      type inet:ip-prefix;
      description
        "Source IP address/prefix of the packet sent
         on an external interface of the NAT.";
    }

    container external-src-port {
      description
        "Source port of the packet sent
         on an external interafce of the NAT.

         It is used also to indicate the external
         source ICMP identifier.";

      uses port-number;
    }

    leaf internal-dst-address {
      type inet:ip-prefix;
      description
        "Corresponds to the destination IP address/prefix
         of the packet received on an internal interface
         of the NAT.

         For example, some NAT implementations support
         the translation of both source and destination
         addresses and ports, sometimes referred to
         as 'Twice NAT'.";
      }

    container internal-dst-port {
      description
        "Corresponds to the destination port of the
         IP packet received on the internal interface.

         It is used also to include the internal
         destination ICMP identifier.";

      uses port-number;
    }
    leaf external-dst-address {
      type inet:ip-prefix;
      description
        "Corresponds to the destination IP address/prefix
         of the packet sent on an external interface
         of the NAT.";
    }

    container external-dst-port {
      description
        "Corresponds to the destination port number of
         the packet sent on the external interface
         of the NAT.

         It is used also to include the external
         destination ICMP identifier.";

      uses port-number;
    }

    leaf lifetime {
      type uint32;
      units "seconds";
      description
        "When specified, it is used to track the connection that is
         fully-formed (e.g., once the three-way handshake
         TCP is completed) or the duration for maintaining
         an explicit mapping alive. The mapping entry will be
         removed by the NAT instance once this lifetime is expired.

         When reported in a get operation, the lifetime indicates
         the remaining validity lifetime.

         Static mappings may not be associated with a
         lifetime. If no lifetime is associated with a
         static mapping, an explicit action is requried to
         remove that mapping.";
    }
  }

 /*
  * NAT Module
  */

  container nat {
    description
      "NAT module";

    container instances {
      description
        "NAT instances";

    list instance {
      key "id";

      description
        "A NAT instance.";

      leaf id {
        type uint32;
        description
          "NAT instance identifier.";
        reference
          "RFC 7659.";
      }

      leaf name {
        type string;
        description
         "A name associated with the NAT instance.";
      }

      leaf enable {
        type boolean;
        description
         "Status of the the NAT instance.";
      }

      container capabilities {
        description
          "NAT capabilities";

        leaf-list nat-flavor {
          type identityref {
            base nat-type;
          }
          description
            "Type of NAT.";
        }

        leaf-list nat44-flavor {
          when "../nat-flavor = 'nat44'";
          type identityref {
            base nat44;
          }
          description
            "Type of NAT44: Basic NAT or NAPT.";
        }

        leaf restricted-port-support {
          type boolean;
          description
            "Indicates source port NAT restriction
             support.";
          reference
             "RFC 7596: Lightweight 4over6: An Extension to
                 the Dual-Stack Lite Architecture.";
        }

        leaf static-mapping-support {
          type boolean;
          description
            "Indicates whether static mappings are supported.";
        }

        leaf port-randomization-support {
          type boolean;
          description
            "Indicates whether port randomization is supported.";
          reference
            "Section 4.2.1. of RFC 4787.";
        }

        leaf port-range-allocation-support {
          type boolean;
          description
            "Indicates whether port range allocation is supported.";
          reference
            "Section 1.1 of RFC 7753.";
        }

        leaf port-preservation-suport {
          type boolean;
          description
            "Indicates whether port preservation is supported.";
          reference
            "Section 4.2.1. of RFC 4787.";
        }

        leaf port-parity-preservation-support {
          type boolean;
          description
            "Indicates whether port parity preservation is supported.";
          reference
            "Section 8 of RFC 7857.";
        }

        leaf address-roundrobin-support {
          type boolean;
          description
           "Indicates whether address allocation round robin is supported.";
        }

        leaf paired-address-pooling-support {
          type boolean;
          description
            "Indicates whether paired-address-pooling is supported";
           reference
             "REQ-2 of RFC 4787.";
        }

        leaf endpoint-independent-mapping-support {
          type boolean;
          description
            "Indicates whether endpoint-independent-
             mapping in Section 4 of RFC 4787 is
             supported.";
           reference
             "Section 4 of RFC 4787.";
        }

        leaf address-dependent-mapping-support {
          type boolean;
          description
            "Indicates whether address-dependent-mapping is supported.";
           reference
             "Section 4 of RFC 4787.";
        }

        leaf address-and-port-dependent-mapping-support {
          type boolean;
          description
            "Indicates whether address-and-port-dependent-mapping is supported.";
           reference
             "Section 4 of RFC 4787.";
        }

        leaf endpoint-independent-filtering-support {
          type boolean;
          description
            "Indicates whether endpoint-independent-filtering is supported.";
           reference
             "Section 5 of RFC 4787.";
        }

        leaf address-dependent-filtering {
          type boolean;
          description
            "Indicates whether address-dependent-filtering is supported.";
           reference
             "Section 5 of RFC 4787.";
        }

        leaf address-and-port-dependent-filtering {
          type boolean;
          description
            "Indicates whether address-and-port-dependent is supported.";
           reference
             "Section 5 of RFC 4787.";
        }
      }

      list nat-pass-through {
        key id;

        description
         "IP prefix NAT pass through.";

        leaf id {
          type uint32;
          description
            "An identifier of the IP prefix pass
             through.";
        }

        leaf prefix {
          type inet:ip-prefix;
          description
            "The IP addresses that match
             should not be translated. According to
             REQ#6 of RFC6888, it must be possible
             to administratively turn off translation
             for specific destination addresses
             and/or ports.";
          reference
            "REQ#6 of RFC6888.";
        }

        leaf port {
          type inet:port-number;
          description
            "According to REQ#6 of RFC6888, it must
             be possible to  administratively turn off
             translation for specific destination addresses
             and/or ports.

             If no prefix is defined, the NAT pass through
             bound to a given port applies for any destination
             address.";

          reference
            "REQ#6 of RFC6888.";
        }
      }

     list policy {
       key id;
       description
         "NAT parameters for a given instance";

       leaf id {
         type uint32;
         description
           "An identifier of the NAT policy.";
       }

       container clat-parameters {
         description
           "CLAT parameters.";

         list clat-ipv6-prefixes {
           when "../../../capabilities/nat-flavor = 'clat' ";
           key ipv6-prefix;
           description
             "464XLAT double translation treatment is
              stateless when a dedicated /64 is available
              for translation on the CLAT. Otherwise, the
              CLAT will have both stateful and stateless
              since it requires NAT44 from the LAN to
              a single IPv4 address and then stateless
              translation to a single IPv6 address.";
            reference
              "RFC 6877: 464XLAT: Combination of Stateful and Stateless
                         Translation";

            leaf ipv6-prefix {
              type inet:ipv6-prefix;
              description
                "An IPv6 prefix used for CLAT.";
            }
          }

          list ipv4-prefixes {
            when "../../../capabilities/nat-flavor = 'clat'";
            key ipv4-prefix;
            description
              "Pool of IPv4 addresses used for CLAT.
               192.0.0.0/29 is the IPv4 service continuity
               prefix.";
            reference
              "RFC 7335: IPv4 Service Continuity Prefix";

            leaf ipv4-prefix {
              type inet:ipv4-prefix;
              description
                "464XLAT double translation treatment is
                 stateless when a dedicated /64 is available
                 for translation on the CLAT.  Otherwise, the
                 CLAT will have both stateful and stateless
                 since it requires NAT44 from the LAN to
                 a single IPv4 address and then stateless
                 translation to a single IPv6 address.
                 The CLAT performs NAT44 for all IPv4 LAN
                 packets so that all the LAN-originated IPv4
                 packets appear from a single IPv4 address
                 and are then statelessly translated to one
                 interface IPv6 address that is claimed by
                 the CLAT.

                 An IPv4 address from this pool is also
                 provided to an application that makes
                 use of literals.";

             reference
               "RFC 6877: 464XLAT: Combination of Stateful and Stateless
                          Translation";
           }
         }
       }

       list nptv6-prefixes {
         when "../../capabilities/nat-flavor = 'nptv6' ";
         key translation-id;
         description
           "Provides one or a list of (internal IPv6 prefix,
            external IPv6 prefix) required for NPTv6.
            In its simplest form, NPTv6 interconnects two network
            links, one of which is an 'internal' network link
            attached to a leaf network within a single
            administrative domain and the other of which is an
            'external' network with connectivity to the global
            Internet.";
          reference
            "RFC 6296: IPv6-to-IPv6 Network Prefix Translation";

          leaf translation-id {
            type uint32;
            description
            "An identifier of the NPTv6 prefixes.";
          }

          leaf internal-ipv6-prefix {
            type inet:ipv6-prefix;
            description
              "An IPv6 prefix used by an internal interface
               of NPTv6.";
            reference
              "RFC 6296: IPv6-to-IPv6 Network Prefix Translation";
         }

         leaf external-ipv6-prefix {
           type inet:ipv6-prefix;
           description
             "An IPv6 prefix used by the external interface
              of NPTv6.";
           reference
             "RFC 6296: IPv6-to-IPv6 Network Prefix Translation";
         }
       }

       list eam {
         when "../../capabilities/nat-flavor = 'eam' ";
         key ipv4-prefix;
         description
           "The Explicit Address Mapping Table, a conceptual
            table in which each row represents an EAM.

            Each EAM describes a mapping between IPv4 and IPv6
            prefixes/addresses.";
         reference
           "Section 3.1 of RFC 7757.";

         leaf ipv4-prefix {
           type inet:ipv4-prefix;
           description
             "The IPv4 prefix of an EAM.";
           reference
             "Section 3.2 of RFC 7757.";
         }

         leaf ipv6-prefix {
           type inet:ipv6-prefix;
           description
             "The IPv6 prefix of an EAM.";
           reference
             "Section 3.2 of RFC 7757.";
         }
       }

       list nat64-prefixes {
         when "../../capabilities/nat-flavor = 'nat64' " +
              " or ../../capabilities/nat-flavor = 'clat'";
         key nat64-prefix;
         description
           "Provides one or a list of NAT64 prefixes
            with or without a list of destination IPv4 prefixes.

            Destination-based Pref64::/n is discussed in
            Section 5.1 of [RFC7050]). For example:
            192.0.2.0/24 is mapped to 2001:db8:122:300::/56.
            198.51.100.0/24 is mapped to 2001:db8:122::/48.";
         reference
           "Section 5.1 of RFC7050.";

         leaf nat64-prefix {
           type inet:ipv6-prefix;
           description
             "A NAT64 prefix. Can be NSP or a Well-Known
              Prefix (WKP).

              Organizations deploying stateless IPv4/IPv6
              translation should assign a Network-Specific
              Prefix to their IPv4/IPv6 translation service.

              For stateless NAT64, IPv4-translatable IPv6
              addresses must use the selected Network-Specific
              Prefix.  Both IPv4-translatable IPv6 addresses
              and IPv4-converted IPv6 addresses should use
              the same prefix.";
           reference
             "Sections 3.3 and 3.4 of RFC 6052.";
         }
         list destination-ipv4-prefix {
           key ipv4-prefix;
           description
             "An IPv4 prefix/address.";

           leaf ipv4-prefix {
             type inet:ipv4-prefix;
             description
               "An IPv4 address/prefix.";
            }
          }

          leaf stateless-enable {
            type boolean;
            description
              "Enable explicitly statless NAT64.";
         }
       }

       list external-ip-address-pool {
         key pool-id;

         description
           "Pool of external IP addresses used to
            service internal hosts.

            A pool is a set of IP prefixes.";

         leaf pool-id {
           type uint32;
           description
             "An identifier of the address pool.";
         }

         leaf external-ip-pool {
           type inet:ipv4-prefix;
           description
             "An IPv4 prefix used for NAT purposes.";
         }
       }

       container port-set-restrict {
         when "../../capabilities/restricted-port-support = 'true'";

         description
           "Configures contiguous and non-contiguous port ranges.";

         uses port-set;
       }

       leaf dst-nat-enable {
         type boolean;
         default false;
         description
           "Enable/Disable destination NAT.
            A NAT44 may be configured to enable
            Destination NAT, too.";
        }

        list dst-ip-address-pool {
          when "../../capabilities/nat-flavor = 'dst-nat' ";

          key pool-id;

          description
            "Pool of IP addresses used for destination NAT.";

          leaf pool-id {
            type uint32;
            description
              "An identifier of the address pool.";
          }

          leaf dst-in-ip-pool {
            type inet:ip-prefix;
            description
              "Internal IP prefix/address";
          }

          leaf dst-out-ip-pool {
            type inet:ip-prefix;
            description
              "IP address/prefix used for destination NAT.";
          }
        }

        list supported-transport-protocols {
          key transport-protocol-id;

          description
            "Supported transport protocols.
             TCP and UDP are supported by default.";

          leaf transport-protocol-id {
            type uint8;
            mandatory true;
            description
              "Upper-layer protocol associated with this mapping.
               Values are taken from the IANA protocol registry.
               For example, this field contains 6 (TCP) for a TCP
               mapping or 17 (UDP) for a UDP mapping.";
          }

          leaf transport-protocol-name {
                 type string;
                 description
                  "For example, TCP, UDP, DCCP, and SCTP.";
          }
        }

        leaf subscriber-mask-v6 {
          type uint8 {
            range "0 .. 128";
          }

          description
            "The subscriber-mask is an integer that indicates
             the length of significant bits to be applied on
             the source IPv6 address (internal side) to
             unambiguously identify a CPE.

             Subscriber-mask is a system-wide configuration
             parameter that is used to enforce generic
             per-subscriber policies (e.g., port-quota).

             The enforcement of these generic policies does not
             require the configuration of every subscriber's
             prefix.

             Example: suppose the 2001:db8:100:100::/56 prefix
             is assigned to a NAT64 serviced CPE. Suppose also
             that 2001:db8:100:100::1 is the IPv6 address used
             by the client that resides in that CPE. When the
             NAT64 receives a packet from this client,
             it applies the subscriber-mask (e.g., 56) on
             the source IPv6 address to compute the associated
             prefix for this client (2001:db8:100:100::/56).
             Then, the NAT64 enforces policies based on that
             prefix (2001:db8:100:100::/56), not on the exact
             source IPv6 address.";

        }

        list subscriber-match {
          key sub-match-id;

          description
            "IP prefix match.";

          leaf sub-match-id {
            type uint32;
            description
              "An identifier of the subscriber mask.";
          }

          leaf sub-mask {
            type inet:ip-prefix;
            mandatory true;
            description
              "The IP address subnets that match
               should be translated. E.g., all addresses
               that belong to the 192.0.2.0/24 prefix must
               be processed by the NAT.";
          }
        }

        leaf paired-address-pooling {
          type boolean;
          default true;
          description
            "Paired address pooling informs the NAT
             that all the flows from an internal IP
             address must be assigned the same external
             address.";

          reference
            "RFC 4787: Network Address Translation (NAT) Behavioral Requirements
                       for Unicast UDP";
        }

        leaf mapping-type {
          type enumeration {
            enum "eim"  {
              description
                "endpoint-independent-mapping.";
              reference
                "Section 4 of RFC 4787.";
            }

            enum "adm"  {
              description
                "address-dependent-mapping.";
              reference
                "Section 4 of RFC 4787.";
            }

            enum "edm"  {
              description
                "address-and-port-dependent-mapping.";
              reference
                "Section 4 of RFC 4787.";
            }
          }
          description
            "Indicates the type of a NAT mapping.";
        }

        leaf filtering-type {
          type enumeration {
            enum "eif"  {
              description
                "endpoint-independent-filtering.";
              reference
                "Section 5 of RFC 4787.";
            }

            enum "adf"  {
              description
                "address-dependent-filtering.";
              reference
                "Section 5 of RFC 4787.";
            }

            enum "edf"  {
              description
                "address-and-port-dependent-filtering";
              reference
                "Section 5 of RFC 4787.";
            }
          }
            description
              "Indicates the type of a NAT filtering.";
        }

        list port-quota {
          when "../../capabilities/nat44-flavor = "+
               "'napt' or "+
               "../../capabilities/nat-flavor = "+
               "'nat64'";

          key quota-type;
          description
            "Configures a port quota to be assigned per
             subscriber. It corresponds to the maximum
             number of ports to be used by a subscriber.";

          leaf port-limit {
            type uint16;
            description
              "Configures a port quota to be assigned per
               subscriber. It corresponds to the maximum
               number of ports to be used by a subscriber.";
            reference
              "REQ-4 of RFC 6888.";
          }

          leaf quota-type {
              type uint8;

              description
                "Indicates whether the port quota applies to
                 all protocols (0) or to a specific transport.";
          }
        }

          leaf port-allocation-type {
            type enumeration {
              enum "random"  {
                description
                  "Port randomization is enabled.";
              }

              enum "port-preservation"  {
                description
                  "Indicates whether the NAT should
                   preserve the internal port number.";
              }

              enum "port-parity-preservation"  {
                description
                  "Indicates whether the NAT should
                   preserve the port parity of the
                   internal port number.";
              }

              enum "port-range-allocation"  {
                description
                  "Indicates whether the NAT assigns a
                   range of ports for an internal host.";
              }
            }
              description
                "Indicates the type of a port allocation.";
          }

          leaf address-roundrobin-enable {
            type boolean;

            description
              "Enable/disable address allocation
               round robin.";
          }

          container port-set {
            when "../port-allocation-type='port-range-allocation'";

            description
              "Manages port-set assignments.";

            leaf port-set-size {
              type uint16;
              description
                "Indicates the size of assigned port
                 sets.";
            }

            leaf port-set-timeout {
              type uint32;
              units "seconds";
              description
                "Inactivty timeout for port sets.";
            }
          }

          container timers {
            description
              "Configure values of various timeouts.";

            leaf udp-timeout {
              type uint32;
              units "seconds";
              default 300;
              description
                "UDP inactivity timeout. That is the time a mapping
                 will stay active without packets traversing the NAT.";
              reference
                "RFC 4787: Network Address Translation (NAT) Behavioral
                           Requirements for Unicast UDP";
            }

            leaf tcp-idle-timeout {
              type uint32;
              units "seconds";
              default 7440;
              description
                "TCP Idle timeout should be
                 2 hours and 4 minutes.";
              reference
                "RFC 5382: NAT Behavioral Requirements for TCP";
            }

            leaf tcp-trans-open-timeout {
              type uint32;
              units "seconds";
              default 240;
              description
                "The value of the transitory open connection
                 idle-timeout.

                 Section 2.1 of [RFC7857] clarifies that a NAT
                 should provide different configurable

                 parameters for configuring the open and
                 closing idle timeouts.

                 To accommodate deployments that consider
                 a partially open timeout of 4 minutes as being
                 excessive from a security standpoint, a NAT may
                 allow the configured timeout to be less than
                 4 minutes.

                 However, a minimum default transitory connection
                 idle-timeout of 4 minutes is recommended.";
              reference
                "Section 2.1 of RFC 7857.";
            }

            leaf tcp-trans-close-timeout {
              type uint32;
              units "seconds";
              default 240;
              description
                "The value of the transitory close connection
                idle-timeout.
                Section 2.1 of [RFC7857] clarifies that a NAT
                should provide different configurable
                parameters for configuring the open and
                closing idle timeouts.";
              reference
                "Section 2.1 of RFC 7857.";
            }

            leaf tcp-in-syn-timeout {
              type uint32;
              units "seconds";
              default 6;
              description
                "A NAT must not respond to an unsolicited
                inbound SYN packet for at least 6 seconds
                after the packet is received.  If during
                this interval the NAT receives and translates
                an outbound SYN for the connection the NAT
                must silently drop the original unsolicited
                inbound SYN packet.";
             reference
                "RFC 5382 NAT Behavioral Requirements for TCP";
            }

            leaf fragment-min-timeout {
              type uint32;
              units "seconds";
              default 2;
              description
                "As long as the NAT has available resources,
                the NAT allows the fragments to arrive
                over fragment-min-timeout interval.
                The default value is inspired from RFC6146.";
            }

            leaf icmp-timeout {
              type uint32;
              units "seconds";
              default 60;
              description
                "An ICMP Query session timer must not expire
                 in less than 60 seconds. It is recommended
                 that the ICMP Query session timer be made
                 configurable";
              reference
                "RFC 5508: NAT Behavioral Requirements for ICMP";
            }

            list per-port-timeout {
              key port-number;
              description
                "Some NATs are configurable with short timeouts
                 for some ports, e.g., as 10 seconds on
                 port 53 (DNS) and NTP (123) and longer timeouts
                 on other ports.";

              leaf port-number {
                type inet:port-number;
                description
                  "A port number.";
              }

              leaf port-timeout {
                type uint32;
                units "seconds";
                mandatory true;
                description
                  "Timeout for this port";
              }
            }

            leaf hold-down-timeout {
              type uint32;
              units "seconds";
              default 120;
              description
                "Hold down timer.

                 Ports in the hold down pool are not reassigned
                 until hold-down-timeout expires.

                 The length of time and the maximum
                 number of ports in this state must be
                 configurable by the administrator.
                 This is necessary in order
                 to prevent collisions between old
                 and new mappings and sessions. It ensures
                 that all established sessions are broken
                 instead of redirected to a different peer.";
              reference
                "REQ#8 of RFC 6888.";
            }

            leaf hold-down-max {
              type uint32;
              description
                "Maximum ports in the Hold down timer pool.

                 Ports in the hold down pool are not reassigned
                 until hold-down-timeout expires.

                 The length of time and the maximum
                 number of ports in this state must be
                 configurable by the administrator.
                 This is necessary in order
                 to prevent collisions between old
                 and new mappings and sessions. It ensures
                 that all established sessions are broken
                 instead of redirected to a different peer.";
              reference
                "REQ#8 of RFC 6888.";
            }
          }

          list algs {
            key name;
            description
              "ALG-related features.";

            leaf name {
              type string;
              description
                "The name of the ALG";
            }

            leaf transport-protocol {
              type uint32;
              description
                "The transport protocol used by the ALG.";
            }

            leaf transport-port {
              type inet:port-number;
              description
                "The port number used by the ALG.";
            }

            leaf status {
              type boolean;
              description
                "Enable/disable the ALG.";
            }
          }

          leaf all-algs-enable {
            type boolean;
            description
             "Enable/disable all ALGs.

              When specified, this parameter overrides the one
              that may be indicated, eventually, by the 'status'
              of an individual ALG.";
          }

          container notify-pool-usage {
            description
              "Notification of pool usage when certain criteria
               are met.";

            leaf pool-id {
              type uint32;
              description
                "Pool-ID for which the notification
                 criteria is defined";
            }

            leaf high-threshold {
              type percent;
              mandatory true;
              description
                "Notification must be generated when the
                 defined high threshold is reached.

                 For example, if a notification is
                 required when the pool utilization reaches
                 90%, this configuration parameter must
                 be set to 90%.";
            }

            leaf low-threshold {
              type percent;
              description
                "Notification must be generated when the defined
                 low threshold is reached.

                 For example, if a notification is required when
                 the pool utilization reaches below 10%,
                 this configuration parameter must be set to
                 10%.";
            }
          }

          container external-realm {
            description
              "Identifies the external realm of the NAT.";

            choice realm-type {
              description
                "Interface or VRF.";

              case interface {
                description
                  "External interface.";

                leaf external-interface {
                  type if:interface-ref;
                  description
                    "Name of an external interface.";
                }
              }

              case vrf {
                description
                  "External VRF instance.";

                leaf external-vrf-instance {
                  type identityref {
                  base vrf-routing-instance;
                }
                  description
                    "A VRF instance.";
                }
              }
            }
          }
        }

        container mapping-limit {
          description
            "Information about the configuration parameters that
             limits the mappings based upon various criteria.";

          leaf limit-per-subscriber {
            type uint32;
            description
              "Maximum number of NAT mappings per subscriber.

               A subscriber is identifier by a given prefix.";
          }

          leaf limit-per-vrf {
            type uint32;
            description
              "Maximum number of NAT mappings per VLAN/VRF.";
          }

          leaf limit-per-instance {
            type uint32;
            mandatory true;
            description
              "Maximum number of NAT mappings per instance.";
          }

          leaf limit-per-udp {
            type uint32;
            mandatory true;
            description
              "Maximum number of UDP NAT mappings per subscriber.";
          }

          leaf limit-per-tcp {
            type uint32;
            mandatory true;
            description
              "Maximum number of TCP NAT mappings per subscriber.";
          }

          leaf limit-per-icmp {
            type uint32;
            mandatory true;
            description
              "Maximum number of ICMP NAT mappings per subscriber.";
          }
        }

        container connection-limit {
          description
            "Information about the configuration parameters that
             rate limit the translation based upon various
             criteria.";

          leaf limit-per-subscriber {
            type uint32;
            units "bits/second";
            description
              "Rate-limit the number of new mappings
               and sessions per subscriber.";
          }
          leaf limit-per-vrf {
            type uint32;
            units "bits/second";
            description
              "Rate-limit the number of new mappings
               and sessions per VLAN/VRF.";
          }

          leaf limit-per-instance {
            type uint32;
            units "bits/second";
            mandatory true;
            description
              "Rate-limit the number of new mappings
               and sessions per instance.";
          }

          leaf limit-per-udp {
            type uint32;
            units "bits/second";
            mandatory true;
            description
              "Rate-limit the number of new UDP mappings
               and sessions per subscriber.";
          }

          leaf limit-per-tcp {
            type uint32;
            units "bits/second";
            mandatory true;
            description
              "Rate-limit the number of new TCP mappings
               and sessions per subscriber.";
          }

          leaf limit-per-icmp {
            type uint32;
            units "bits/second";
            mandatory true;
            description
              "Rate-limit the number of new ICMP mappings
               and sessions per subscriber.";
          }
        }

        container logging-info {
          description
            "Information about logging NAT events";
          leaf logging-enable {
            type boolean;
            description
              "Enable logging features.";
            reference
              "Section 2.3 of RFC 6908.";
          }

          leaf destination-address {
            type inet:ip-prefix;
            mandatory true;
            description
              "Address of the collector that receives
               the logs";
          }

          leaf destination-port {
            type inet:port-number;
            mandatory true;
            description
              "Destination port of the collector.";
          }

          choice protocol {

            description
              "Enable the protocol to be used for
               the retrieval of logging entries.";

            case syslog {
              leaf syslog {
                type boolean;
                description
                  "If SYSLOG is in use.";
              }
            }

            case ipfix {
              leaf ipfix {
                type boolean;
                description
                  "If IPFIX is in use.";
              }
            }

            case ftp {
              leaf ftp {
                type boolean;
                description
                  "If FTP is in use.";
              }
            }
          }
        }

        container mapping-table {
          when "../capabilities/nat-flavor = "+
               "'nat44' or "+
               "../capabilities/nat-flavor = "+
               "'nat64'or "+
               "../capabilities/nat-flavor = "+
               "'clat'or "+
               "../capabilities/nat-flavor = 'dst-nat'";

          description
            "NAT mapping table. Applicable for functions
             which maintains static and/or dynamic mappings,
             such as NAT44, Destination NAT, NAT64, or CLAT.";

          list mapping-entry {
            key "index";
            description
              "NAT mapping entry.";
            uses mapping-entry;
          }
        }

        container statistics {
          config false;

          description
            "Statistics related to the NAT instance.";

          container traffic-statistics {
            description
              "Generic traffic statistics.";

            leaf sent-packets {
              type yang:zero-based-counter64;
              description
                "Number of packets sent.";
            }

            leaf sent-bytes {
              type yang:zero-based-counter64;
              description
                "Counter for sent traffic in bytes.";
            }

            leaf rcvd-packets {
              type yang:zero-based-counter64;
              description
                "Number of received packets.";
            }

            leaf rcvd-bytes {
              type yang:zero-based-counter64;
              description
                "Counter for received traffic
                 in bytes.";
            }

            leaf dropped-packets {
              type yang:zero-based-counter64;
              description
                "Number of dropped packets.";
            }

            leaf dropped-bytes {
              type yang:zero-based-counter64;
              description
                "Counter for dropped traffic in
                bytes.";
            }
          }

          container mapping-statistics {
            when "../../capabilities/nat-flavor = "+
                 "'nat44' or "+
                 "../../capabilities/nat-flavor = "+
                 "'nat64'or "+
                 "../../capabilities/nat-flavor = 'dst-nat'";

           description
             "Mapping statistics.";

            leaf total-mappings {
              type yang:gauge32;
              description
                "Total number of NAT mappings present
                 at a given time. This variable includes
                 all the static and dynamic mappings.";
            }

            leaf total-tcp-mappings {
              type yang:gauge32;
              description
                "Total number of TCP mappings present
                at a given time.";
            }

            leaf total-udp-mappings {
              type yang:gauge32;
              description
                "Total number of UDP mappings present
                 at a given time.";
            }

           leaf total-icmp-mappings {
             type yang:gauge32;
              description
                "Total number of ICMP mappings present
                at a given time.";
            }
          }

          container pool-stats {

            when "../../capabilities/nat-flavor = "+
                 "'nat44' or "+
                 "../../capabilities/nat-flavor = "+
                 "'nat64'";

            description
              "Statistics related to address/prefix
               pool usage";

            leaf pool-id {
              type uint32;
              description
                "Unique Identifier that represents
                 a pool of addresses/prefixes.";
            }

            leaf addresses-allocated {
              type yang:gauge32;
              description
                "Number of allocated addresses in
                 the pool";
            }

            leaf addresses-free {
              type yang:gauge32;
              description
                "Number of unallocated addresses in
                 the pool at a given time.The sum of
                 unallocated and allocated
                 addresses is the total number of
                 addresses of the pool.";
            }

            container port-stats {

              description
                "Statistics related to port
                 usage.";

              leaf ports-allocated {
                type yang:gauge32;
                description
                  "Number of allocated ports
                   in the pool.";
              }

              leaf ports-free {
                type yang:gauge32;
                description
                  "Number of unallocated addresses
                   in the pool.";
              }
            }
          }
        }
      }
    }
  }

  /*
   * Notifications
   */

  notification nat-event {
    description
      "Notifications must be generated when the defined
       high/low threshold is reached. Related
       configuration parameters must be provided to
       trigger the notifications.";

    leaf id {
      type leafref {
        path
             "/nat/instances/"
              + "instance/id";
                }
      description
        "NAT instance ID.";
    }

    leaf policy-id {
      type leafref {
        path
             "/nat/instances/"
             + "instance/policy/id";
      }

      description
        "Policy ID.";
    }

    leaf pool-id {
      type leafref {
        path
             "/nat/instances/"
             + "instance/policy/"
             + "external-ip-address-pool/pool-id";
      }
      description
        "Pool ID.";
    }

    leaf notify-pool-threshold {
      type percent;
      mandatory true;
      description
        "A treshhold has been fired.";
    }
  }
}
