module ietf-ose-path-svc {
  namespace "urn:ietf:params:xml:ns:yang:ietf-ose-path-svc";
  prefix path-svc;

  import ietf-inet-types {
    prefix inet;
  }

  feature qos-custom {
    description
      "Enables support of the custom QoS profile.";
  }

  identity qos-profile-direction {
    description
      "Base identity for QoS profile direction.";
  }

  identity site-to-wan {
    base qos-profile-direction;
    description
      "Identity for Site-to-WAN direction.";
  }

  identity wan-to-site {
    base qos-profile-direction;
    description
      "Identity for WAN-to-Site direction.";
  }

  identity both {
    base qos-profile-direction;
    description
      "Identity for both WAN-to-Site direction
       and Site-to-WAN direction.";
  }

  identity protocol-type {
    description
      "Base identity for protocol field type.";
  }

  identity tcp {
    base protocol-type;
    description
      "TCP protocol type.";
  }

  identity udp {
    base protocol-type;
    description
      "UDP protocol type.";
  }

  identity icmp {
    base protocol-type;
    description
      "ICMP protocol type.";
  }

  identity icmp6 {
    base protocol-type;
    description
      "ICMPv6 protocol type.";
  }

  identity gre {
    base protocol-type;
    description
      "GRE protocol type.";
  }

  identity ipip {
    base protocol-type;
    description
      "IP-in-IP protocol type.";
  }

  identity hop-by-hop {
    base protocol-type;
    description
      "Hop-by-Hop IPv6 header type.";
  }

  identity routing {
    base protocol-type;
    description
      "Routing IPv6 header type.";
  }

  identity esp {
    base protocol-type;
    description
      "ESP header type.";
  }

  identity ah {
    base protocol-type;
    description
      "AH header type.";
  }

  container path-svc {
    list service {
      key "name";
      leaf name {
        type string;
      }
      leaf class-id {
        type string;
      }
      list traffic-class {
        key "name";
        leaf name {
          type string;
        }
        leaf dscp {
          type inet:dscp;
          description
            "DSCP value.";
        }
        leaf dot1p {
          type uint8 {
            range "0..7";
          }
          description
            "802.1p matching.";
        }
        leaf ipv4-src-prefix {
          type inet:ipv4-prefix;
          description
            "Match on IPv4 src address.";
        }
        leaf ipv6-src-prefix {
          type inet:ipv6-prefix;
          description
            "Match on IPv6 src address.";
        }
        leaf ipv4-dst-prefix {
          type inet:ipv4-prefix;
          description
            "Match on IPv4 dst address.";
        }
        leaf ipv6-dst-prefix {
          type inet:ipv6-prefix;
          description
            "Match on IPv6 dst address.";
        }
        leaf l4-src-port {
          type inet:port-number;
          must 'current() < ../l4-src-port-range/lower-port or current() > ../l4-src-port-range/upper-port' {
            description
              "If l4-src-port and l4-src-port-range/lower-port and
               upper-port are set at the same time, l4-src-port
               should not overlap with l4-src-port-range.";
          }
          description
            "Match on Layer 4 src port.";
        }
        container l4-src-port-range {
          leaf lower-port {
            type inet:port-number;
            description
              "Lower boundary for port.";
          }
          leaf upper-port {
            type inet:port-number;
            must '. >= ../lower-port' {
              description
                "Upper boundary for port.  If it
                 exists, the upper boundary must be
                 higher than the lower boundary.";
            }
            description
              "Upper boundary for port.";
          }
          description
            "Match on Layer 4 src port range.  When
             only the lower-port is present, it represents
             a single port.  When both the lower-port and
             upper-port are specified, it implies
             a range inclusive of both values.";
        }
        leaf l4-dst-port {
          type inet:port-number;
          must 'current() < ../l4-dst-port-range/lower-port or current() > ../l4-dst-port-range/upper-port' {
            description
              "If l4-dst-port and l4-dst-port-range/lower-port
               and upper-port are set at the same time,
               l4-dst-port should not overlap with
               l4-src-port-range.";
          }
          description
            "Match on Layer 4 dst port.";
        }
        container l4-dst-port-range {
          leaf lower-port {
            type inet:port-number;
            description
              "Lower boundary for port.";
          }
          leaf upper-port {
            type inet:port-number;
            must '. >= ../lower-port' {
              description
                "Upper boundary must be
                 higher than lower boundary.";
            }
            description
              "Upper boundary for port.  If it exists,
               upper boundary must be higher than lower
               boundary.";
          }
          description
            "Match on Layer 4 dst port range.  When only
             lower-port is present, it represents a single
             port.  When both lower-port and upper-port are
             specified, it implies a range inclusive of both
             values.";
        }
        leaf protocol-field {
          type union {
            type uint8;
            type identityref {
              base protocol-type;
            }
          }
          description
            "Match on IPv4 protocol or IPv6 Next Header field.";
        }
      }
      list application {
        key "name";
        leaf name {
          type string;
        }
        leaf category-id {
          type uint32;
        }
        leaf application-id {
          type uint32;
        }
      }
      container user {
        leaf list-name {
          type string;
        }
        leaf-list user-id {
          type string;
        }
        leaf-list group {
          type string;
        }
      }
      leaf-list site-id {
        type uint32;
      }
      leaf business-priority {
        type enumeration {
          enum high;
          enum normal;
          enum low;
          enum Voice;
          enum Critical_Data;
          enum Transactional;
          enum user-defined;
        }
      }
      container link-selection-mode {
        leaf mode {
          type enumeration {
            enum automatic;
            enum preferred;
            enum lowest-cost;
          }
        }
        leaf physical-port {
          type uint32;
        }
        leaf service-type {
          type enumeration {
            enum commodity;
            enum wireless;
            enum private;
          }
        }
        leaf service-provider {
          type string;
        }
      }
      leaf path-selection-mode {
        type enumeration {
          enum drop;
          enum underlay;
          enum overlay;
        }
      }
    }
  }
  container traffic-profile {
    choice qos-profile {
      description
        "Choice for traffic QoS profile.
         Can be standard profile or customized profile.";
      case standard {
        description
          "Standard QoS profile.";
        leaf profile {
          type string;
          description
            "QoS profile to be used.";
        }
      }
      case custom {
        description
          "Customized QoS profile.";
        container classes {
          if-feature "qos-custom";
          list class {
            key "class-id";
            leaf class-id {
              type string;
              description
                "Identification of the class of service.
                 This identifier is internal to the
                 administration.";
            }
            leaf direction {
              type identityref {
                base qos-profile-direction;
              }
              default "both";
              description
                "The direction to which the QoS profile
                 is applied.";
            }
            leaf rate-limit {
              type decimal64 {
                fraction-digits 5;
                range "0..100";
              }
              units "percent";
              description
                "To be used if the class must be rate-limited.
                 Expressed as percentage of the service
                 bandwidth.";
            }
            container latency {
              choice flavor {
                case lowest {
                  leaf use-lowest-latency {
                    type empty;
                    description
                      "The traffic class should use the path with the
                       lowest latency.";
                  }
                }
                case boundary {
                  leaf latency-boundary {
                    type uint16;
                    units "msec";
                    default "400";
                    description
                      "The traffic class should use a path with a
                       defined maximum latency.";
                  }
                }
                description
                  "Latency constraint on the traffic class.";
              }
              description
                "Latency constraint on the traffic class.";
            }
            container jitter {
              choice flavor {
                case lowest {
                  leaf use-lowest-jitter {
                    type empty;
                    description
                      "The traffic class should use the path with the
                       lowest jitter.";
                  }
                }
                case boundary {
                  leaf latency-boundary {
                    type uint32;
                    units "usec";
                    default "40000";
                    description
                      "The traffic class should use a path with a
                       defined maximum jitter.";
                  }
                }
                description
                  "Jitter constraint on the traffic class.";
              }
              description
                "Jitter constraint on the traffic class.";
            }
            container bandwidth {
              leaf guaranteed-bw-percent {
                type decimal64 {
                  fraction-digits 5;
                  range "0..100";
                }
                units "percent";
                mandatory true;
                description
                  "To be used to define the guaranteed bandwidth
                   as a percentage of the available service bandwidth.";
              }
              leaf end-to-end {
                type empty;
                description
                  "Used if the bandwidth reservation
                   must be done on the MPLS network too.";
              }
              description
                "Bandwidth constraint on the traffic class.";
            }
          }
        }
      }
    }
  }
}
