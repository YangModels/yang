module ietf-immutable {
  yang-version 1.1;
  namespace "urn:ietf:params:xml:ns:yang:ietf-immutable";
  prefix im;

  import ietf-yang-metadata {
    prefix md;
  }

  organization
    "IETF Network Modeling (NETMOD) Working Group";

  contact
    "WG Web: <https://datatracker.ietf.org/wg/netmod/>

     WG List: <mailto:netmod@ietf.org>

     Author: Qiufang Ma
             <mailto:maqiufang1@huawei.com>

     Author: Qin Wu
             <mailto:bill.wu@huawei.com>

     Author: Balazs Lengyel
             <mailto:balazs.lengyel@ericsson.com>

     Author: Hongwei Li
             <mailto:flycoolman@gmail.com>";

  description
    "This module defines a metadata annotation named 'immutable'
     to indicate the immutability of a particular instantiated
     data node. Any instantiated data node marked with
     immutable='true' by the server is read-only to the clients
     of YANG-driven management protocols, such as NETCONF,
     RESTCONF as well as SNMP and CLI requests.

     The module defines the immutable extension that indicates
     that data nodes based on the parent data-definition
     statement cannot be created, removed, or updated
     except according to the 'exceptions' argument.

     Copyright (c) 2022 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC HHHH
     (https://www.rfc-editor.org/info/rfcHHHH); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2022-12-14 {
    description
      "Initial revision.";
    // RFC Ed.: replace XXXX and remove this comment
    reference
      "RFC XXXX: YANG Extension and Metadata Annotation for
       Immutable Flag";
  }

  extension immutable {
    argument exceptions;
    description
      "The 'immutable' extension as a substatement to a data
       definition statement indicates that data nodes based on
       the parent statement MUST NOT be added, removed or
       updated by management protocols, such as NETCONF,
       RESTCONF or other management operations (e.g., SNMP
       and CLI requests) except when indicated by the
       exceptions argument.

       Immutable data MAY be marked as config true to allow
       'leafref', 'when' or 'must' constraints to be based
       on it.

       The statement MUST only be a substatement of the leaf,
       leaf-list, container, list, anydata, anyxml statements.
       Zero or one immutable statement per parent statement
       is allowed.
       No substatements are allowed.

       The argument is a list of space-separated operations that
       are permitted to be used for the specified node, while
       other operations are forbidden by the immutable extension.
       - create: allows users to create instances of the data node
       - update: allows users to modify instances of the data node
       - delete: allows users to delete instances of the data node

       To disallow all user write access, omit the argument;

       To allow only create and delete user access, provide
       the string 'create delete' for the 'exceptions' parameter.

       Equivalent YANG definition for this extension:

       leaf immutable {
         type bits {
           bit create;
           bit update;
           bit delete;
         }
         default '';
       }

       Immutability specified by the use of the 'immutable' extension
       statement (including any exception argument) is inherited by all
       child and descendant nodes of a container or a list. It is possible
       to override the inherited immutability property by placing another
       immutable extension statement on a specific child/descendant node.

       Adding immutable or removing values from the
       exceptions argument of an existing immutable statement
       are non-backwards compatible changes.
       Other changes to immutable are backwards compatible.";
  }

  md:annotation immutable {
    type boolean;
    description
      "The 'immutable' annotation indicates the immutability of an
       instantiated data node. Any data node instance marked as
       'immutable=true' is read-only to clients and cannot be
       updated through NETCONF, RESTCONF or CLI. It applies to the
       list and leaf-list entries. If a list entry is annotated
       with immutable='true', the whole instance is read-only and
       including any contained descendant data nodes.
       The default is 'immutable=false' if not specified for an instance.";
  }
}
