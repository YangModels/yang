module ietf-sfc-oam {
     namespace "urn:huawei:params:xml:ns:yang:sfc-oam";
     prefix sfcoam;
     import ietf-gen-oam {
       prefix goam;
     }
     import service-function  {
       prefix sfc-sf;
     }
     import service-function-path  {
       prefix sfc-sfp;
     }
     import service-function-forwarder  {
       prefix sfc-sff;
     }

     revision 2014-09-04 {
       description
       "Initial revision.";
     }

     identity sfc {
       base goam:technology-types;
       description
       "sfc type";
     }

     typedef SFC-layer {
       type enumeration {
       enum "Service function layer" {
         value 0;
       }
       enum "SFC forwarding layer" {
         value 1;
       }
       }
     }
    augment
    "/goam:domains/goam:domain/goam:MAs/goam:MA"
    +"/goam:connectivity-context" {

       case connectivity-context-sfc {
       leaf connectivity-context-sfp {
         type sfc-sfp:service-function-path-ref;
       }
       }

    }
    augment
    "/goam:domains/goam:domain/goam:MAs"
   +"/goam:MA/goam:MEP/goam:mp-address" {

       case sf-mep-address {
       description

       "Service function (or service function forwarder) address plus
    service function path id to identify one SFC MEP. A SFC MP can be a
    service function or service function forwarder!";

       leaf sf-mep-ref {
         when "/goam:domains/goam:domain/goam:technology='sfc'";
         type sfc-sf:service-function-ref;
       }

       leaf sfp-mep-ref {
         when "/goam:domains/goam:domain/goam:technology='sfc'";
         type sfc-sfp:service-function-path-ref;
       }
       }

       case sff-mep-address {
       description

       "Service function address plus service function path id to
       identify one SFC MEP. A SFC MP can be a service function or service
       function forwarder!";

       leaf sff-mep-ref {
         type sfc-sff:service-function-forwarder-ref;
       }

       leaf sfp-mep-ref {
         type sfc-sfp:service-function-path-ref;
       }
       }
     }

     augment
    "/goam:domains/goam:domain/goam:MAs/goam:MA/goam:MEP/goam:session"
    +"/goam:destination-mep-address/goam:mp-address" {

       case sf-mep-address {
       leaf sf-mep-ref {
         type sfc-sf:service-function-ref;
       }

       leaf sfp-mep-ref {
         type sfc-sfp:service-function-path-ref;
       }
       }

       case sff-mep-address {
       leaf sff-mep-ref {
         type sfc-sff:service-function-forwarder-ref;
       }

       leaf sfp-mep-ref {
         type sfc-sfp:service-function-path-ref;
       }
       }
     }

     augment
    "/goam:domains/goam:domain/goam:MAs/goam:MA/goam:MEP"
   +"/goam:session/goam:connectivity-context" {

       case connectivity-context-sfc {
      leaf connectivity-context-sfp {
         type sfc-sfp:service-function-path-ref;
       }
       }
     }

     //SFC extension of contiuity-check part

     /*
  augment "/goam:continuity-check/goam:input"
 +"/goam:source-mep/goam:mp-address" {

       case sf-mep-address {
       leaf sf-mep-ref {
         type sfc-sf:service-function-ref;
       }

       leaf sfp-mep-ref {
         type sfc-sfp:service-function-path-ref;
       }
       }

       case sff-mep-address {
       leaf sff-mep-ref {
         type sfc-sff:service-function-forwarder-ref;
       }

       leaf sfp-mep-ref {
         type sfc-sfp:service-function-path-ref;
       }
       }
     }*/

     augment "/goam:continuity-check/goam:input"
    +"/goam:destination-mp/goam:mp-address" {

       case sf-mep-address {
       leaf sf-mep-ref {
         type sfc-sf:service-function-ref;
       }

       leaf sfp-mep-ref {
         type sfc-sfp:service-function-path-ref;
       }
       }
       case sff-mep-address {

       leaf sff-mep-ref {
         type sfc-sff:service-function-forwarder-ref;
       }
       leaf sfp-mep-ref {
         type sfc-sfp:service-function-path-ref;
       }
       }
     }

     //SFC extension of connectity-verification part
/*
    augment "/goam:connectivity-verification"
    +"/goam:input/goam:source-mep/goam:mp-address" {

       case sf-mep-address {
       leaf sf-mep-ref {
         type sfc-sf:service-function-ref;
       }

       leaf sfp-mep-ref {
         type sfc-sfp:service-function-path-ref;
       }
       }

       case sff-mep-address {
       leaf sff-mep-ref {
         type sfc-sff:service-function-forwarder-ref;
       }

       leaf sfp-mep-ref {
         type sfc-sfp:service-function-path-ref;
       }
       }

     }*/

     augment "/goam:connectivity-verification"
    +"/goam:input/goam:destination-mp/goam:mp-address" {

       case sf-mep-address {
       leaf sf-mep-ref {
        type sfc-sf:service-function-ref;
       }

       leaf sfp-mep-ref {
         type sfc-sfp:service-function-path-ref;
       }
       }

       case sff-mep-address {
       leaf sff-mep-ref {
         type sfc-sff:service-function-forwarder-ref;
       }

       leaf sfp-mep-ref {
         type sfc-sfp:service-function-path-ref;
       }
       }
     }

     //SFC extension of path-discovery part

    augment "/goam:path-discovery/goam:input" {

       description
       "adds SFC specific items on the input";
       leaf path-discovery-layer {
       type SFC-layer;

       description
         "Identifying which SFC layer to run path discovery";
       }

     }

     /*augment "/goam:path-discovery/goam:input"
     +"/goam:source-mep/goam:mp-address" {

       case sf-mep-address {
       leaf sf-mep-ref {
         type sfc-sf:service-function-ref;
       }

       leaf sfp-mep-ref {
         type sfc-sfp:service-function-path-ref;
       }
       }

       case sff-mep-address {
       leaf sff-mep-ref {
         type sfc-sff:service-function-forwarder-ref;
       }

       leaf sfp-mep-ref {
         type sfc-sfp:service-function-path-ref;
       }
       }
     }*/

     augment "/goam:path-discovery/goam:input"
     +"/goam:destination-mp/goam:mp-address" {

       case sf-mep-address {
       leaf sf-mep-ref {
         type sfc-sf:service-function-ref;
       }

       leaf sfp-mep-ref {
         type sfc-sfp:service-function-path-ref;
       }
       }
       case sff-mep-address {
       leaf sff-mep-ref {
         type sfc-sff:service-function-forwarder-ref;
       }

       leaf sfp-mep-ref {
         type sfc-sfp:service-function-path-ref;
       }
       }
     }

    augment "/goam:path-discovery/goam:output"
    +"/goam:response/goam:destination-mp/goam:mp-address" {

       case sf-mep-address {
       leaf sf-mep-ref {
         type sfc-sf:service-function-ref;
       }

       leaf sfp-mep-ref {
         type sfc-sfp:service-function-path-ref;
       }
       }
       case sff-mep-address {
       leaf sff-mep-ref {
         type sfc-sff:service-function-forwarder-ref;
       }

       leaf sfp-mep-ref {
         type sfc-sfp:service-function-path-ref;
       }
       }
     }

     //SFC extension of performance-measurement part
    /*
    augment "/goam-rpc:initiated-performance-measurement/goam-
    rpc:input/goam-rpc:source-mep/goam-rpc:mp-address" {

       case sf-mep-address {
       leaf sf-mep-ref {
         type sfc-sf:service-function-ref;
       }

       leaf sfp-mep-ref {
         type sfc-sfp:service-function-path-ref;
       }
       }

       case sff-mep-address {
       leaf sff-mep-ref {
         type sfc-sff:service-function-forwarder-ref;
       }
       leaf sfp-mep-ref {
         type sfc-sfp:service-function-path-ref;
       }
       }
     }*/
     }
