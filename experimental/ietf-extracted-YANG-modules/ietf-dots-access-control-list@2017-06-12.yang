module ietf-dots-access-control-list {
      namespace "urn:ietf:params:xml:ns:yang:ietf-dots-access-control-list";
      prefix "dots-acl";
      import ietf-access-control-list {
       prefix "ietf-acl";
      }
      organization "McAfee, Inc.";
      contact "Konda, Tirumaleswar Reddy <TirumaleswarReddy_Konda@McAfee.com>";

      description
       "This module contains YANG definition for
        configuring filtering rules using DOTS data channel";

      revision 2017-06-12 {
       reference
       "https://tools.ietf.org/html/draft-ietf-dots-data-channel";
      }

    augment "/ietf-acl:access-lists/ietf-acl:acl/ietf-acl:access-list-entries/ietf-acl:ace/ietf-acl:actions/ietf-acl:packet-handling" {

      description "rate-limit action";

      case rate-limit {
        leaf rate-limit {
          type decimal64 {
           fraction-digits 2;
          }
          description "rate-limit action.";
        }
      }
    }

    augment "/ietf-acl:access-lists/ietf-acl:acl/ietf-acl:access-list-entries/ietf-acl:ace" {

      description "handle non-intial and initial fragments";

      leaf fragments {
          type empty;
          description "handle fragments.";
      }
    }
}
