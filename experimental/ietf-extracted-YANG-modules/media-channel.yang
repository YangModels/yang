module media-channel {

       namespace "http://www.tid.es/idealist ";

       prefix m-c;

       import optical-TED {

               prefix o-ted;

       }

       revision 2014-06-05;

       container media-channel {

               description "Media association that represents both
the topology

                               (i.e., path through the media) and
the resource (frequency slot) that

                               it occupies.  As a topological
construct, it represents a (effective)

                               frequency slot supported by a
concatenation of media elements

                               (fibers, amplifiers, filters,
switching matrices...).  This term is
                               used to identify the end-to-end
physical layer entity with its

                               corresponding (one or more) frequency
slots local at each link

                               filters.";

               reference "draft-ietf-ccamp-flexi-grid-fwk-01";

               container source {

                       leaf source-node {

                               type o-ted:optical-node-ref;

                       }

                       leaf source-port {

                               type o-ted:optical-node-port-ref;

                       }

               }

               container destination {

                       leaf destination-node {

                               type o-ted:optical-node-ref;

                       }

                       leaf destination-port {

                               type o-ted:optical-node-port-ref;

                       }
               }

               uses media-channel-attributes;

       }

       container network-media-channel {

               description "It is a media channel that transports an
Optical Tributary Signal ";

               reference "draft-ietf-ccamp-flexi-grid-fwk-01";

               container source {

                       leaf source-node {

                               type o-ted:optical-node-ref;

                       }

                       leaf source-transponder {

                               type o-ted:optical-transponder-ref;

                       }

               }

               container destination {

                       leaf destination-node {

                               type o-ted:optical-node-ref;

                       }
                       leaf destination-transponder {

                               type o-ted:optical-transponder-ref;

                       }

               }

               uses media-channel-attributes;

       }

       grouping media-channel-attributes {

               container effective-freq-slot {

                       description "The effective frequency

                       slot is an attribute of a media channel and,
being a frequency slot,

                       it is described by its nominal central
frequency and slot width";

                       reference "draft-ietf-ccamp-flexi-grid-fwk-
01";

                       leaf N {

                               type int32;

                               description

                                       "Is used to determine the
Nominal Central Frequency. The set of nominal

                                        central frequencies can be
built using the following expression f =
                                        193.1 THz + n x 0.00625 THz,
where 193.1 THz is ITU-T ''anchor

                                        frequency'' for transmission
over the C band, n is a positive or

                                        negative integer including
0.";

                               reference "draft-ietf-ccamp-flexi-
grid-fwk-01";

               }

                       leaf M {

                               type int32;

                               description

                                       "Is used to determine the
slot width. A slot width is constrained

                                       to be M x SWG (that is, M x
12.5 GHz), where M is an integer greater

                                       than or equal to 1.";

                               reference "draft-ietf-ccamp-flexi-
grid-fwk-01";

                       }

               }

               list link-channel {

                       key "link-id";
                       leaf link-id {

                               type int32;

                       }

                       uses link-channel;

               }

       }

       grouping link-channel {

               description "A link channel is one of the
concatenated elements of the media channel.";

               leaf N {

                       type int32;

                       description

                               "Is used to determine the Nominal
Central Frequency. The set of nominal

                                central frequencies can be built
using the following expression f =

                                193.1 THz + n x 0.00625 THz, where
193.1 THz is ITU-T ''anchor

                                frequency'' for transmission over
the C band, n is a positive or

                                negative integer including 0.";

                       reference "draft-ietf-ccamp-flexi-grid-fwk-
01";

               }
               leaf M {

                       type int32;

                       description

                               "Is used to determine the slot width.
A slot width is constrained

                               to be M x SWG (that is, M x 12.5
GHz), where M is an integer greater

                               than or equal to 1.";

                       reference "draft-ietf-ccamp-flexi-grid-fwk-
01";

               }

               leaf source-node {

                       type o-ted:optical-node-ref;

               }

               leaf source-port {

                       type o-ted:optical-node-port-ref;

               }

               leaf destination-node {

                       type o-ted:optical-node-ref;

               }

               leaf destination-port {

                       type o-ted:optical-node-port-ref;
               }

               leaf link {

                       type o-ted:optical-link-ref;

               }

               leaf bidireccional {

                       type boolean;

                       description "Determines whether the link is
bidireccional or not";

               }

       }

}
