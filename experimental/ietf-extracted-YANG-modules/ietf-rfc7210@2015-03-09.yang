module ietf-rfc7210 {
  /* replace with IANA namespace when assigned */
  namespace "urn:ietf:params:xml:ns:yang:ietf-rfc7210";
  prefix "ietf-rfc7210";

  import ietf-routing {
    prefix "rt";
  }

  import ietf-key-chain {
    prefix "kc";
  }

  organization
    "Ericsson";

  contact
    "I. Chen - ing-wher.chen@ericsson.com";

  description
    "This YANG module augments the ietf-key-chain module by " +
    "adding attributes defined in RFC 7210";
  revision 2015-03-09 {
    description
      "Initial revision.";
    reference
      "RFC XXXX: A YANG Data Model to augment ietf-key-chain " +
      "to support RFC 7210";
  }

  identity all-routing-protocols {
    base "rt:routing-protocol";
    description
      "All routing protocols";
  }

  feature rfc7210-admin-key-name {
    description
      "Support for RFC 7210 AdminKeyName field";
  }

  feature rfc7210-local-key-name {
    description
      "Support for RFC 7210 LocalKeyName field";
  }

  feature rfc7210-peer-key-name {
    description
      "Support for RFC 7210 PeerKeyName field";
  }

  feature rfc-7210-peers {
    description
      "Support for RFC 7210 Peers field";
  }

  feature rfc-7210-protocol-specific-info {
    description
      "Support for RFC 7210 ProtocolSpecificInfo field";
  }

  feature rfc-7210-interfaces {
    description
      "Support for RFC 7210 Interfaces field";
  }

  feature rfc-7210-protocol {
    description
      "Support for RFC 7210 Protocol field";
  }

  feature rfc-7210-KDF {
    description
      "Support for RFC 7210 KDF field";
  }

  feature rfc-7210-direction {
    description
      "Support for RFC 7210 Direction field";
  }

  augment "/kc:key-chains/kc:key" {
    description
      "Additional attributes of a key required by RFC 7210";

    leaf admin-key-name {
      if-feature rfc7210-admin-key-name;
      type string;
      description
        "RFC 7210 AdminKeyName field.";
    }
    leaf local-key-name {
      if-feature rfc7210-local-key-name;
      type string;
      description
        "RFC 7210 LocalKeyName field.";
    }
    leaf peer-key-name {
      if-feature rfc7210-peer-key-name;
      type string;
      description
        "RFC 7210 PeerKeyName field.";
    }
    leaf-list peers {
      if-feature rfc-7210-peers;
      type string;
      description
        "RFC 7210 Peers field.";
    }
    leaf-list interfaces {
      if-feature rfc-7210-interfaces;
      type string;
      description
        "RFC 7210 Interfaces field.";
    }
    leaf protocol {
      if-feature rfc-7210-protocol;
      type identityref {
        base "rt:routing-protocol";
      }
      default "all-routing-protocols";
      description
        "RFC 7210 Protocol field.";
    }
    leaf protocol-specific-info {
      if-feature rfc-7210-protocol-specific-info;
      type string;
      description
        "RFC 7210 ProtocolSpecificInfo field";
    }
    choice kdf {
      if-feature rfc-7210-KDF;
      default no-kdf;
      description
        "Key derivation functions.";
      case no-kdf {
        leaf no-kdf {
          type empty;
          description
            "No KDF used with the key.";
        }
      }
      case aes-128-cmac-kdf {
        leaf aes-128-cmac-kdf {
          type empty;
          description
            "AES-CMAC using 128-bit keys.";
        }
      }
      case hmac-sha-1-kdf {
       leaf hmac-sha-1-kdf {
          type empty;
          description
            "HMAC using SHA-1-hash.";
        }
      }
    }
    leaf direction {
      if-feature rfc-7210-direction;
      type enumeration {
        enum in {
          description
            "This key is for authenticating incoming messages.";
        }
        enum out {
          description
            "This key is for authenticating outgoing messages.";
        }
        enum both {
          description
            "This key is for authenticating both incoming and " +
            "outgoing messages.";
        }
      }
      default "both";
      description
        "Indicate whether the key is to authenticate incoming " +
        "or outgoing messages.";
    }
  }

}
