module hardware-entities {

   namespace "urn:com:nsn:hardware-entities";
   prefix "hwe";

   import yang-types {prefix "yt";}
   import complex-types {prefix "ct";}
   import udmcore {prefix "uc";}

   grouping PhysicalEntityProperties {
      // ...
      leaf mfgDate {type yt:date-and-time; }
      leaf-list uris {type string; }
   }

   // Physical entities representing equipment

   ct:complex-type HWModule {
      ct:extends uc:Equipment;
      description "Complex type representing module entries
                   (entPhysicalClass = module(9)) in entPhysicalTable";
      uses PhysicalEntityProperties;
   }

   // ...

   // Physical entities representing equipment holders

   ct:complex-type Chassis {
      ct:extends uc:EquipmentHolder;
      description "Complex type representing chassis entries
                   (entPhysicalClass = chassis(3)) in entPhysicalTable";
      uses PhysicalEntityProperties;
   }

   // ...
}
