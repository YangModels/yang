module ietf-tlm-philatelist-dashboard {
  yang-version 1.1;
  namespace 
    "urn:ietf:params:xml:ns:yang:ietf-tlm-philatelist-dashboard";
  prefix ietf-tlm-philatelist-dashboard;

  import ietf-tlm-philatelist-types {
    prefix ietf-tlm-philatelist-types;
  }

  organization
    "IETF GREEN (Getting Ready for Energy-Efficient Networking)
     Working Group";
  contact
    "WG Web:   <https://datatracker.ietf.org/group/green/about/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    "This YANG module defines the Telemetry Philatelist Dashboard.

    These definitions are used both by Philatelist Network 
    Controllers, and Philatelist Network Elements. Network Elements
    that are unaware of the Philatelist framework may also be 
    covered when a 'proxy mechanism' for the Philatelist information
    is added.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.

    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";

  revision 2024-04-15 {
    description
      "Restructured as part of the Telemetry Philatelist framework";
    reference
      "RFC XXXX: ...";
  }

  identity cm-gnmi {
    base ietf-tlm-philatelist-types:connection-method;
    description 
      "Connection method identity for gNMI-based mechanisms.
      ";
  }
  identity cm-restconf {
    base ietf-tlm-philatelist-types:connection-method;
    description
      "Connection method identity for RESTCONF-based mechanisms.
      ";
  }
  identity cm-netconf {
    base ietf-tlm-philatelist-types:connection-method;
    description
      "Connection method identity for NETCONF-based mechanisms.
      ";
  }
  identity cm-redfish {
    base ietf-tlm-philatelist-types:connection-method;
    description
      "Connection method identity for Redfish-based mechanisms.
      ";
  }
  identity gnmi-polling {
    base cm-gnmi;
    base ietf-tlm-philatelist-types:cm-polled;
    description 
      "Connection method identity for gNMI-based polling mechanisms.
      ";
  }
  identity restconf-get-polling {
    base cm-restconf;
    base ietf-tlm-philatelist-types:cm-polled;
    description 
      "Connection method identity for RESTCONF-based polling 
      mechanisms.
      ";
  }
  identity netconf-get-polling {  
    base cm-netconf;
    base ietf-tlm-philatelist-types:cm-polled;
    description 
      "Connection method identity for NETCONF-based polling 
      mechanisms.
      ";
  }
  identity restconf-yang-push-subscription {
    base cm-restconf;
    description 
      "Connection method identity for RESTCONF-based 
      subscription mechanisms.
      ";
  }
  identity netconf-yang-push-subscription {
    base cm-netconf;
    description 
      "Connection method identity for NETCONF-based 
      subscription mechanisms.
      ";
  }
  identity redfish-polling {
    base cm-redfish;
    description 
      "Connection method identity for Redfish-based polling
      mechanisms.
      ";
  }
  grouping access-g {
    description 
      "Grouping describing the basic set of access methods offered by
      Philatelist servers, i.e. Network Elements. The set of access      
      mechanisms may be extended by servers offering additional 
      mechanisms.  This grouping is also used by Network Controllers,
      when they need to find a way to interact with the 
      Network Elements.
      ";

    leaf method {
      type identityref {
        base ietf-tlm-philatelist-types:connection-method;
      }
      default ietf-tlm-philatelist-types:get-local-file-once;
      description 
        "Discriminator pointing out which access mechanism is
        offered. This value controls which detailed configuration
        nodes will be available.
        ";
    }
    container get-local-file-once {
      when "derived-from-or-self(../method, 
            'ietf-tlm-philatelist-types:get-local-file-once')";
      description 
        "The server itself does not offer any access mechanism for
        this dashboard item. Instead, philatelist controllers will
        need to read static values from a local on the controller. 
        How the file appears in a relevant location on the 
        controller is outside the scope of this specification.
        The file format used MUST adhere to RFC9195
        (https://datatracker.ietf.org/doc/rfc9195/)
        ";
      leaf filename { 
        type string; 
        description 
          "The name of the file containing the static data for the
          dashboard item. If the filename is not specified, the 
          controller should look for a file with the same name as the
          connection name.
          ";
      }
    }
    container get-static-url-once {
      when "derived-from-or-self(../method, 
            'ietf-tlm-philatelist-types:get-static-url-once')";
      description 
        "The server points to a URL the controller can use to
        download a file with static values for this dashboard item.
        The URL may or may not be pointing to the server itself, and
        could potentially even point to a URL on the controller 
        itself. How the static file contents pointed to by the URL
        appears on the webserver is outside the scope of this
        specification.
        ";
      leaf url { 
        type ietf-tlm-philatelist-types:something; 
        description 
          "The URL that the controller should read in order to 
          get the static data about the dashboard item.
          The file format used MUST adhere to RFC9195
          (https://datatracker.ietf.org/doc/rfc9195/)
          "; 
      }
    }
    container gnmi-polling {
      when "derived-from-or-self(../method, 'gnmi-polling')";
      description 
        "The server points to a gNMI interface the controller can
        poll at regular intervals to read the current sensor value
        for this dashboard item.
        ";
      leaf encoding { 
        type ietf-tlm-philatelist-types:something; 
        description 
          "The encoding of the data provided by this mechanism, 
          such as self-describing-gpb
          "; 
      } 
      leaf protocol { 
        type ietf-tlm-philatelist-types:something; 
        description 
          "The exact protocol parameters for this gNMI endpoint, 
          such as grpc no-tls
          "; 
      } 
    }
    container restconf-get-polling {
      when "derived-from-or-self(../method, 'restconf-get-polling')";
      description "FIXME";
      leaf xxx { type string; description "FIXME"; }
    }
    container netconf-get-polling {
      when "derived-from-or-self(../method, 'netconf-get-polling')";
      leaf xxx { type string; description "FIXME"; }
      description "FIXME";
    }
    container restconf-yang-push-subscription {
      when "derived-from-or-self(../method, 
            'restconf-yang-push-subscription')";
      leaf xxx { type string; description "FIXME"; }
      description "FIXME";
    }
    container netconf-yang-push-subscription {
      when "derived-from-or-self(../method, 
            'netconf-yang-push-subscription')";
      leaf xxx { type string; description "FIXME"; }
      description "FIXME";
    }
    container redfish-polling {
      when "derived-from-or-self(../method, 'redfish-polling')";
      leaf xxx { type string; description "FIXME"; }
      description "FIXME";
    }
    leaf frequency { 
      when "derived-from(../method, 
            'ietf-tlm-philatelist-types:cm-polled')";
      type ietf-tlm-philatelist-types:sample-frequency; 
      description 
        "The frequency with which the sensor data value collection
        should happen. E.g. once per 30 minutes, once per 5 minutes,
        once per 30 seconds or on-change.
        ";
    }
  }

  grouping provider-g {
    description 
      "Top-level provider grouping.  Devices will implement
      this as a config false container, or as a piece of instance
      data that a controller can read. Controllers implement this
      data structure as config true, configurable and readable by
      the operators.
      ";
    container dashboards {
      description 
        "Each device may support one or more dashboards. 
        Controllers can then choose the most advanced dashboard they 
        are aware of and interested in. A dashboard contains
        a list of sensors and/or controls that a controller may find
        useful for some particular use case.
        ";
      list dashboard {
        key id;
        description 
          "List of dashboards supported by a given device or 
          controller.
          ";
        leaf id {
          type identityref {
            base ietf-tlm-philatelist-types:dash-type;
          }
          description 
            "Formal dashboard id. The dashboard-items in this
            dashboard are found in ../items, and what items are
            available there depends on this dashboard id .
            ";
        }
        list items {
          key tsdb-path;
          description 
            "List of dashboard items. Some of the items are sensors
            which provide data to be read, some may be controls that
            the controller may use.
            ";
          leaf tsdb-path {
            type leafref {
              path ../../../../dash-items/dash-item/tsdb-path;
            }
            description 
              "Path to the sensor or control item on the dashboard.
              The format of the path is TSDB style, i.e. used MUST
              conform to the I-D.draft-kll-yang-label-tsdb, e.g.
              interfaces_interface_statistics_in_unicast_pkts
              Each dashboard item may point to multiple sensors, 
              as in the example above, where each interface would
              have a counter of incoming unicase packets.
              Each dashboard item may occur in more than one 
              dashboard, and is therefore further desribed in 
              ../../../../dash-items/dash-item
              ";
          }
        }
      }
    }
    container dash-items {
      description 
        "Container for all dashboard items. Each item may be part of
        (referenced by) multiple dashboards.
        ";
      list dash-item {
        key tsdb-path;
        description 
          "Dashboard item, a sensor or control item that is part 
          of a dashboard, i.e. a collection of sensors and controls
          relevant for a particular use case.
          Each dashboard item may occur in more than one dashboard.
          ";
        leaf tsdb-path {
          type string;
          description 
            "Path to the sensor or control item on the dashboard.
            The format of the path is TSDB style, i.e. used MUST
            conform to the I-D.draft-kll-yang-label-tsdb, e.g.
            interfaces_interface_statistics_in_unicast_pkts
            Each dashboard item may point to multiple sensors, as in
            the example above, where each interface would have
            a counter of incoming unicase packets.
            ";
        }
        leaf item-type { 
          type identityref { 
            base ietf-tlm-philatelist-types:dash-item-type; 
          }
          mandatory true;
          description 
            "The item type describes the type of dashboard item this
            is, including if it is a sensor or contol, sitting on
            the inside or outside of the parent component, the
            measurement quantity (e.g. temperature) and unit 
            (e.g. Celsius).

            See the ietf-tlm-philatelist-types:dash-item-type for a
            more detailed explanation, or if you intend to define a
            new type of dashboard item.
            ";
        }
        container accuracy {
          when "derived-from(../item-type, 
                'ietf-tlm-philatelist-types:sensor-type')";
          description 
            "The accuracy of the dasboard item (sensor). The
            accuracy described using two parameters. One is the max
            deviation relative to the sensor reading, the other one
            is a constant deviation offset.

            Example 1: if a sensor might produce values between 
            0 and 1000, and the sensor currently reports 555, but 
            the actual value is 531, that could be reported as a
            5% relative error with offset 0.

            Example 2: if a sensor might produce values between 
            0 and 1000, and the sensor currently reports 0, but 
            the actual value is 2, that could be reported as a
            0% relative error with offset 2 (or some slightly
            highger value, e.g. 5).

            The accuracy MUST be described such that there is a 96%
            confidence that the actual value V is within the reported
            value R so that:

              (measured-error) =  | R - V |
              (error-margin)   =  | R * (max-error-relative) | 
                                   + (max-error-offset)
              p( (measured-error) < (error-margin) ) >= 0.96
            ";
          leaf max-error-relative {
            type ietf-tlm-philatelist-types:something;
            description 
              "The part of the accuracy claim that depends on (varies
              in proportion to) the reported value.
              ";
          }
          leaf max-error-offset {
            type ietf-tlm-philatelist-types:something;
            description
              "The part of the accuracy claim that does not depend on
              (does not vary with) the reported value.
              ";
          }
        }
        list label {
          key name;
          description 
            "List of TSDB path labels. A single TSDB path often refer
            to a whole collection of readable sensors. Each such 
            sensor is distinguished by the values associated with
            labels in the path. Those labels are listed here.

            Example: interfaces_interface_statistics_in_unicast_pkts
            might have one label interfaces_interface_name. Concrete
            readouts going into the TSDB might have values like

            Metric: interfaces_interface_statistics_in_unicast_pkts
            Value: 5432100
            Labels:
              host = router-01
              interfaces_interface_name = eth0

            As can be seen in the example, a controller might inject
            labels that are not part of the tsdb-path (host), but
            helps the controller keep track of the incoming data
            streams.
            ";
          reference
            I-D.draft-kll-yang-label-tsdb;
          leaf name {
            type string;
            description 
              "The name of the label, in TSDB path notation.
              E.g. interfaces_interface_name
              ";
          }
          choice value-source {
            description 
              "The source of the values associated with the labels.
              Label values may be provided in several ways:
              + the server may provide values in runtime, in which
                case the runtime-values points to the dashboard item
                to read to get the actual values.
              + the controller or operator may pick one or more
                 values by configuration, in which case they are
                 listed under static-values .
              + the controller may pick one or more values using some
                internal mechanism of its own, in which case they
                will not be visible here.
              ";
            leaf-list static-values {
              type string;
              description 
                "One or more values configured by the controller or
                operator designating which instances of this TSDB
                path to collect data about. 

                Example: if the label name for this label entry is
                interfaces_interface_name, this could be a configured
                list of interface names to collect data about.
                ";
            }
            leaf-list runtime-values {
              type leafref {
                path ../../../dash-item/tsdb-path;
              }
              description 
                "One or more dashboard items to read label values
                from.

                Example: if the label name for this label entry is
                interfaces_interface_name, this could point to a
                dashboard item that collects the names of all 
                interfaces, or all interfaces relevant for a
                particular purpose or customer.
                ";
            }
          }
        }
        choice access-path {
          description 
          "This is the path used by the client (Network Controller)
          when asking the server (Network Element) for data.
          The format of the access-path depends on the specific
          access mechanism. If the access mechanism is YANG-based,
          this access path would be an XPath string. If the access
          mechanism is SNMP, it would be an OID. A redfish access
          mechanism would use a endpoint-local URL.
          The actual path may be constructed in one of several ways.
          ";
          leaf plain-string {
            type string;
            description 
              "The given string is used as is, without substitution
              of any labels or special characters.
              ";
          }
          leaf string-with-labels {
            type string;
            description 
              "The given string contains references of the form

              $(label_name)

              i.e. a dollar-sign, a left-parenthesis, 
              the name of the label - case sensitive and without 
              whitespace - and finally a right-parenthesis.

              This expression refers to the labels-value pairs from

              ../label/name  and  ../label/value-source

              The reference expression is substituted with the
              label value before use.

              Example: The access path for an SNMP GET-based node
              interfaces_interface_statistics_in_unicast_pkts
              might have access path

              1.3.6.1.2.1.2.2.1.11.$(interfaces_interface_num)

              which gives the final OID string

              1.3.6.1.2.1.2.2.1.11.4711

              if the ../label[name='interfaces_interface_num'] value
              is 4711.
              ";
          }
          leaf url-with-labels {
            type string;
            description 
              "The given string contains references of the forms

              {label_name}
              {label_name:3}
              {?label_name}

              etc. as defined in RFC6570.

              This expression refers to the labels-value pairs from

              ../label/name  and  ../label/value-source

              The reference expression is substituted with the
              label value before use according to the RFC6570 rules.

              Example 1: The access path for a NETCONF get-based node
              interfaces_interface_statistics_in_unicast_pkts
              might have access path

              /if:interfaces/interface[name='{interfaces_interface_na
              me}']/statistics/in-unicast-pkts

              Any prefixes used (as if: above) are mapped to the
              corresponding namespace (NETCONF) or module name
              (RESTCONF) using the ../../../prefix-mappings list.

              Example 2: The access path for a Redfish-based node

              Systems_EthernetInterfaces_EthernetInterfaceMetrics_Dro
              ppedPackets

              might have access path

              /redfish/v1/Systems/VM1/EthernetInterfaces/{interfaces_
              interface_num}/EthernetInterfaceMetrics/DroppedPackets
              ";
          }
        }
        leaf access-params {
          type leafref {
            path ../../../accesses/access/id;
          }
          description 
            "Points to the specific access method to be used with
            this dashboard item. 
            ";
        }
      }
    }
    container accesses {
      description 
        "Holds a list of all the access methods that have been
        defined for dashboard items on the Network Element.
        ";
      list access {
        key id;
        description
          "One specific access method to be used with some dashboard
          items.
          ";
        leaf id {
          type string;
          description 
            "Name for this access method.
            ";
        }
        uses access-g;
      }
    }
    container prefix-mappings {
      description 
        "Contains the mappings for prefixes used in the access-path
        to the XML namespace (NETCONF) or module name (RESTCONF).
        ";
      list prefix-mapping {
        key prefix;
        description 
          "List of access-path prefixes and their mapping to
          namespace and module name.
          ";
        leaf prefix {
          type string;
          description 
            "Prefix, as used in the dash-item/access-path.
            The prefix is case sensitive, and should not contain
            the ending colon (:).
            ";
        }
        leaf namespace {
          type string;
          description 
            "XML namespace corresponding to the prefix name.
            Used by NETCONF-based access mechanisms.
            ";
        }
        leaf module-name {
          type string;
          description 
            "YANG module name corresponding to the prefix name.
            Used by RESTCONF-based access mechanisms.
            ";
        }
      }
    }
  }
}
