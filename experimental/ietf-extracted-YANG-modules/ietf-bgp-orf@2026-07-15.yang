module ietf-bgp-orf {
  yang-version 1.1;
  namespace "urn:ietf:params:xml:ns:yang:ietf-bgp-orf";
  prefix orf;

  import ietf-routing-types {
    prefix rt-types;
    reference
      "RFC 8294: Common YANG Data Types for the Routing Area";    
  }
  import ietf-routing {
    prefix rt;
    reference
      "RFC 8349: A YANG Data Model for Routing Management
                 (NMDA Version)";
  }
  import ietf-inet-types {
    prefix inet;
    reference
      "RFC 9911: Common YANG Data Types";
  }
  import ietf-yang-types {
    prefix yang;
    reference
      "RFC 9911: Common YANG Data Types";
  }  
  import ietf-bgp {
    prefix bgp;
    reference
      "RFC XXXX: YANG Model for Border Gateway Protocol (BGP-4)";
  }

  organization
    "IETF Inter-Domain Routing (IDR) Working Group";
  contact
    "WG Web:   https://datatracker.ietf.org/wg/idr
     WG List:  IDR <mailto:idr@ietf.org>

     Editor:   Fan Zhang
               <mailto:zhangf52@chinatelecom.cn>
     Editor:   Aijun Wang
               <mailto:wangaj3@chinatelecom.cn>
     Editor:   Changwang Lin
               <mailto:linchangwang.04414@h3c.com>";
  description
    "This YANG module defines a generic configurtion and management
     for the BGP Outbound Route Filtering (ORF). Type-specific ORF
     modules may augment this module.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-07-15 {
    description
      "Initial revision.";
    reference
      "RFC 5291: Outbound Route Filtering Capability for BGP-4
       RFC 5292: Address-Prefix-Based Outbound Route Filter for
                 BGP-4
       RFC 7543: Covering Prefixes Outbound Route Filter for BGP-4";
  }

  /*
   * Features
   */

  feature address-prefix-orf {
    description
      "Support for Address Prefix ORF for BGP-4.";
    reference
      "RFC 5292: Address-Prefix-Based Outbound Route Filter for
                 BGP-4";
  }

  feature cp-orf {
    description
      "Support for Covering Prefixes ORF for BGP-4.";
    reference
      "RFC 7543: Covering Prefixes Outbound Route Filter for BGP-4";
  }  

  /*
   * Identities
   */  

  identity orf-type {
    description
      "Base ORF type.";
    reference
      "RFC 5291: Outbound Route Filtering Capability for BGP-4";
  }

  identity address-prefix-orf {
    base orf-type;
    description
      "Address Prefix ORF.";
    reference
      "RFC 5292: Address-Prefix-Based Outbound Route Filter for
                 BGP-4";
  }

  identity cp-orf {
    base orf-type;
    description
      "Covering Prefixes ORF.";
    reference
      "RFC 7543: Covering Prefixes Outbound Route Filter for BGP-4";
  }

  /*
   * Typedefs
   */  

  typedef orf-send-receive {
    type enumeration {
      enum receive {
        value 1;
        description
          "The local speaker is willing to receive ORF entries from
           its peer.";
      }
      enum send {
        value 2;
        description
          "The local speaker would like to send ORF entries to its
           peer.";
      }
      enum both {
        value 3;
        description
          "The local speaker supports both sending and receiving ORF
           entries.";
      }
    }
    description
      "ORF Send/Receive field.";
    reference
      "RFC 5291: Outbound Route Filtering Capability for BGP-4,
                 Section 5";
  }

  typedef evpn-route-type {
    type enumeration {
      enum ethernet-auto-discovery {
        value 1;
        description
          "Ethernet Auto-Discovery Route.";
      }
      enum mac-ip-advertisement {
        value 2;
        description
          "MAC/IP Advertisement Route.";
      }
      enum inclusive-multicast {
        value 3;
        description
          "Inclusive Multicast Route.";
      }
      enum ethernet-segment {
        value 4;
        description
          "Ethernet Segment.";
      }
    }
    description
      "Route Type value when AFI is L2VPN.";
    reference
      "RFC 7543: Covering Prefixes Outbound Route Filter for BGP-4,
                 Section 2";    
  }

  /*
   * Groupings
   */

  grouping orf-capability {
    description
      "Grouping for ORF Capabilities for a bgp speaker.";
    list capability {
      key "orf-type";
      description
        "List of ORF capabilities for each ORF types.";
      leaf orf-type {
        type identityref {
          base orf-type;
        }
        description
          "The ORF type supoorted by the BGP speaker.";
      }
      leaf send-receive {
        type orf-send-receive;
        default "both";
        description
          "Indicating whether the sender supports receiving ORF
           entries, or sending ORF entries, or both.";
      }
    }
    reference
      "RFC 5291: Outbound Route Filtering Capability for BGP-4,
                 Section 5";
  }

  grouping address-prefix-orf-entries {
    description
      "Grouping for Address Prefix ORF entries for BGP";
    list address-prefix-orf-entry {
      key "sequence";
      description
        "List of Address Prefix ORF entries of an address family.";
      leaf sequence {
        type uint32;
        description
          "Sequence number of the Address Prefix ORF entries.";
      }
      leaf match {
        type enumeration {
          enum permit {
            description
              "Permit the peer to pass updates for the set of routes
               that match the ORF entry.";
          }
          enum deny {
            description
              "Deny the peer to pass the updates for the set of  
               routes that match the ORF entry.";
          }
        }
        description
          "Specifiying whether this entry is PERMIT or DENY.";
      }
      leaf prefix {
        type inet:ip-prefix;
        description
          "IP prefix to be matched by the Address Prefix ORF entry.";
      }
      leaf minlen {
        type uint8;
        description
          "Minimum prefix length (in bits) for matching.
           A value of 0 indicates that the field is unspecified.";
      }
      leaf maxlen {
        type uint8;
        description
          "Maximum prefix length (in bits) for matching.
           A value of 0 indicates that the field is unspecified.";
      }
      reference
        "RFC 5292: Address-Prefix-Based Outbound Route Filter for
                   BGP-4, Section 2";
    }
  }

  grouping cp-orf-common-parameters {
    description
      "Grouping for common parameters of a CP-ORF entry for BGP";

    leaf sequence {
      type uint32;
      description
        "Sequence number of the Covering Prefixes ORF entries.";
    }
    leaf match {
      type enumeration {
        enum permit {
          description
            "Permit the peer to pass updates for the set of routes
              that match the ORF entry.";
        }
        enum deny {
          description
            "Deny the peer to pass the updates for the set of  
              routes that match the ORF entry.";
        }
      }
      description
        "Specifiying whether this entry is PERMIT or DENY.";
    }
    leaf minlen {
      type uint8;
      description
        "Minimum length of the selected route (measured in bits).";
    }
    leaf maxlen {
      type uint8;
      description
        "Maximum length of the selected route (measured in bits).";
    }
    leaf vpn-route-target {
      type rt-types:route-target;
      description
        "The VPN Route Target carried by the selected route.";
    }
    leaf import-route-target {
      type rt-types:route-target;
      config false;
      description
        "The Import Route Target carried in the CP-ORF entry.";
    }
    reference
      "RFC 7543: Covering Prefixes Outbound Route Filter for BGP-4,
                 Section 2";    
  }

  grouping cp-orf-ipv4-entries {
    description
      "Grouping for CP-ORF entries for IPv4 MPLS-labeled VPN.";
    list cp-orf-ipv4-entry {
      key "sequence";
      description
        "List of IPv4 CP-ORF entries.";
      uses cp-orf-common-parameters {
        refine "minlen" {
          must '. <= 32';
        }
        refine "maxlen" {
          must '. <= 32';
        }
      }
      leaf route-type {
        type uint8;
        default 0;
        description
          "The type of the selected route.";
      }      
      leaf host-address {
        type inet:ipv4-address;
        description
          "The address covered by the selected route.";
      }
    }
    reference
      "RFC 7543: Covering Prefixes Outbound Route Filter for BGP-4,
                 Section 2"; 
  } 

  grouping cp-orf-ipv6-entries {
    description
      "Grouping for CP-ORF entries for IPv6 MPLS-labeled VPN.";
    list cp-orf-ipv6-entry {
      key "sequence";
      description
        "List of IPv6 CP-ORF entries.";
      uses cp-orf-common-parameters {
        refine "minlen" {
          must '. <= 128';
        }
        refine "maxlen" {
          must '. <= 128';
        }
      }
      leaf route-type {
        type uint8;
        default 0;
        description
          "The type of the selected route.";
      }          
      leaf host-address {
        type inet:ipv6-address;
        description
          "The address covered by the selected route.";        
      }
    }
    reference
      "RFC 7543: Covering Prefixes Outbound Route Filter for BGP-4,
                 Section 2"; 
  } 

  grouping cp-orf-evpn-entries {
    description
      "Grouping for CP-ORF entries for EVPN.";
    list cp-orf-evpn-entry {
      key "sequence";
      description
        "List of EVPN CP-ORF entries.";
      uses cp-orf-common-parameters {
        refine "minlen" {
          must '. <= 48';
          description
            "Minimum length of the selected route (measured in bits).
             For Ethernet Auto-Discovery, Inclusive Multicast,
             and Ethernet Segment routes, Minlen MUST be 0.
             For MAC/IP Advertisement routes, Minlen MUST be 
             less than or equal to 48.";
        }
        refine "maxlen" {
          must '. <= 48';
          description
            "Maximum length of the selected route (measured in bits).
             For Ethernet Auto-Discovery, Inclusive Multicast,
             and Ethernet Segment routes, Maxlen MUST be 0.
             For MAC/IP Advertisement routes, Maxlen MUST be 
             less than or equal to 48.";          
        }
      }
      leaf route-type {
        type evpn-route-type;
        description
          "The type of the selected route.";
      }           
      leaf host-address {
        type yang:mac-address;
        description
          "The address covered by the selected route.
           For Ethernet Auto-Discovery, Inclusive Multicast,
           and Ethernet Segment routes, Host Address MUST be absent.
           For MAC/IP Advertisement routes, Host Address MUST 
           contain exactly 48 bits.";
      }
    }
    reference
      "RFC 7543: Covering Prefixes Outbound Route Filter for BGP-4,
                 Section 2"; 
  }   

  /*
   * Data nodes
   */

  augment
    "/rt:routing/rt:control-plane-protocols"
  + "/rt:control-plane-protocol/bgp:bgp/bgp:neighbors/bgp:neighbor"
  + "/bgp:afi-safis/bgp:afi-safi/bgp:ipv4-unicast" {
    if-feature "address-prefix-orf";
    description
      "Address Prefix ORF augmentation for the IPv4 unicast address
       family of a BGP neighbor.";
    uses orf-capability;
    container address-prefix-orf-entries-sent {
      description
        "Address Prefix ORF entries sent";
      uses address-prefix-orf-entries {
        refine "address-prefix-orf-entry/minlen" {
          must '. <= 32';
        }
        refine "address-prefix-orf-entry/maxlen" {
          must '. <= 32';
        }
      }
    }
    container address-prefix-orf-entries-received {
      config false;
      description
        "Address Prefix ORF entries received";
      uses address-prefix-orf-entries {
        refine "address-prefix-orf-entry/minlen" {
          must '. <= 32';
        }
        refine "address-prefix-orf-entry/maxlen" {
          must '. <= 32';
        }
      }
    }
  }

  augment
    "/rt:routing/rt:control-plane-protocols"
  + "/rt:control-plane-protocol/bgp:bgp/bgp:neighbors/bgp:neighbor"
  + "/bgp:afi-safis/bgp:afi-safi/bgp:ipv6-unicast" {
    if-feature "address-prefix-orf";
    description
      "Address Prefix ORF augmentation for the IPv6 unicast address
       family of a BGP neighbor.";
    uses orf-capability;
    container address-prefix-orf-entries-sent {
      description
        "Address Prefix ORF entries sent";
      uses address-prefix-orf-entries {
        refine "address-prefix-orf-entry/minlen" {
          must '. <= 128';
        }
        refine "address-prefix-orf-entry/maxlen" {
          must '. <= 128';
        }
      }
    }
    container address-prefix-orf-entries-received {
      config false;
      description
        "Address Prefix ORF entries received";
      uses address-prefix-orf-entries {
        refine "address-prefix-orf-entry/minlen" {
          must '. <= 128';
        }
        refine "address-prefix-orf-entry/maxlen" {
          must '. <= 128';
        }
      }
    }
  }

  augment
    "/rt:routing/rt:control-plane-protocols"
  + "/rt:control-plane-protocol/bgp:bgp/bgp:peer-groups"
  + "/bgp:peer-group/bgp:afi-safis/bgp:afi-safi/bgp:ipv4-unicast" {
    if-feature "address-prefix-orf";
    description
      "Address Prefix ORF augmentation for the IPv4 unicast address
       family of a BGP peer group.";
    uses orf-capability;
    uses address-prefix-orf-entries {
      refine "address-prefix-orf-entry/minlen" {
        must '. <= 32';
      }
      refine "address-prefix-orf-entry/maxlen" {
        must '. <= 32';
      }
    }
    container address-prefix-orf-entries-sent {
      description
        "Address Prefix ORF entries sent";
      uses address-prefix-orf-entries {
        refine "address-prefix-orf-entry/minlen" {
          must '. <= 32';
        }
        refine "address-prefix-orf-entry/maxlen" {
          must '. <= 32';
        }
      }
    }
  }

  augment
    "/rt:routing/rt:control-plane-protocols"
  + "/rt:control-plane-protocol/bgp:bgp/bgp:peer-groups"
  + "/bgp:peer-group/bgp:afi-safis/bgp:afi-safi/bgp:ipv6-unicast" {
    if-feature "address-prefix-orf";
    description
      "Address Prefix ORF augmentation for the IPv6 unicast address
       family of a BGP peer group.";
    uses orf-capability;
    container address-prefix-orf-entries-sent {
      description
        "Address Prefix ORF entries sent";
      uses address-prefix-orf-entries {
        refine "address-prefix-orf-entry/minlen" {
          must '. <= 128';
        }
        refine "address-prefix-orf-entry/maxlen" {
          must '. <= 128';
        }
      }
    }
  }

  augment
    "/rt:routing/rt:control-plane-protocols"
  + "/rt:control-plane-protocol/bgp:bgp/bgp:neighbors/bgp:neighbor"
  + "/bgp:afi-safis/bgp:afi-safi/bgp:l3vpn-ipv4-unicast" {
    if-feature "cp-orf";
    description
      "CP-ORF augmentation for the Unicast IPv4 MPLS L3VPN address
       family of a BGP neighbor.";
    uses orf-capability;
    container cp-orf-ipv4-entries-sent {
      description
        "IPv4 CP-ORF entries sent";
      uses cp-orf-ipv4-entries;
    }
    container cp-orf-entries-received {
      config false;
      description
        "IPv4 CP-ORF entries received";
      uses cp-orf-ipv4-entries;
    }
  }

  augment
    "/rt:routing/rt:control-plane-protocols"
  + "/rt:control-plane-protocol/bgp:bgp/bgp:neighbors/bgp:neighbor"
  + "/bgp:afi-safis/bgp:afi-safi/bgp:l3vpn-ipv6-unicast" {
    if-feature "cp-orf";
    description
      "CP-ORF augmentation for the Unicast IPv6 MPLS L3VPN address
       family of a BGP neighbor.";
    uses orf-capability;
    container cp-orf-entries-sent {
      description
        "IPv6 CP-ORF entries sent";
      uses cp-orf-ipv6-entries;
    }
    container cp-orf-entries-received {
      config false;
      description
        "IPv6 CP-ORF entries received";
      uses cp-orf-ipv6-entries;
    }
  }

  augment
    "/rt:routing/rt:control-plane-protocols"
  + "/rt:control-plane-protocol/bgp:bgp/bgp:neighbors/bgp:neighbor"
  + "/bgp:afi-safis/bgp:afi-safi/bgp:l2vpn-evpn" {
    if-feature "cp-orf";
    description
      "CP-ORF augmentation for the EVPN address
       family of a BGP neighbor.";
    uses orf-capability;
    container cp-orf-entries-sent {
      description
        "EVPN CP-ORF entries sent";
      uses cp-orf-evpn-entries;
    }
    container cp-orf-entries-received {
      config false;
      description
        "EVPN CP-ORF entries received";
      uses cp-orf-evpn-entries;
    }
  }  

  augment
    "/rt:routing/rt:control-plane-protocols"
  + "/rt:control-plane-protocol/bgp:bgp/bgp:peer-groups"
  + "/bgp:peer-group/bgp:afi-safis/bgp:afi-safi"
  + "/bgp:l3vpn-ipv4-unicast" {
    if-feature "cp-orf";
    description
      "CP-ORF augmentation for the Unicast IPv4 MPLS L3VPN address
       family of a BGP peer group.";
    uses orf-capability;
    container cp-orf-ipv4-entries-sent {
      description
        "IPv4 CP-ORF entries sent";
      uses cp-orf-ipv4-entries;
    }
  }

  augment
    "/rt:routing/rt:control-plane-protocols"
  + "/rt:control-plane-protocol/bgp:bgp/bgp:peer-groups"
  + "/bgp:peer-group/bgp:afi-safis/bgp:afi-safi"
  + "/bgp:l3vpn-ipv6-unicast" {
    if-feature "cp-orf";
    description
      "CP-ORF augmentation for the Unicast IPv6 MPLS L3VPN address
       family of a BGP peer group.";
    uses orf-capability;
    container cp-orf-entries-sent {
      description
        "IPv6 CP-ORF entries sent";
      uses cp-orf-ipv6-entries;
    }
  }

  augment
    "/rt:routing/rt:control-plane-protocols"
  + "/rt:control-plane-protocol/bgp:bgp/bgp:peer-groups"
  + "/bgp:peer-group/bgp:afi-safis/bgp:afi-safi"
  + "/bgp:l2vpn-evpn" {
    if-feature "cp-orf";
    description
      "CP-ORF augmentation for the EVPN address
       family of a BGP peer group.";
    uses orf-capability;
    container cp-orf-entries-sent {
      description
        "EVPN CP-ORF entries sent";
      uses cp-orf-evpn-entries;
    }
  }
}
