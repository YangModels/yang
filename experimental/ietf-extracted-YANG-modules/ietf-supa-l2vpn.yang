module ietf-supa-l2vpn {
  namespace "urn:ietf:params:xml:ns:yang:ietf-supa-l2vpn";
  // replace with IANA namespace when assigned
  prefix l2vpn;

  import ietf-interfaces {
    prefix if;
  }

  organization "IETF";
  contact
    "Editor: Ying Cheng
    chengying10@chinaunicom.cn

    Vikram Choudhary
    vikschw@gmail.com
    ";

  description
    "This YANG module defines a generic service
    configuration model for L2VPN (Layer 2 Virtual
    Private Network), based on which programmers can
    develop applications to configure L2VPN instances.";
  revision 2015-04-09 {
    description
      "Initial revision";
    reference "RFC4664";
  }

  container l2vpn-instances {
    description "an abstracted L3VPN information
     model for DDC service to use L3VPN.";

    list l2vpn-instance {
      key "name";
      description
        "Indicates the name of the L2VPN instance";

      leaf name {
        type string;
        description "L2VPN instance name";
      }

      leaf service-type {
        type enumeration {
          enum e-line {
            value "0";
            description "the service type is e-line";
          }
          enum e-tree {
            value "1";
            description "the service type is e-tree";
          }
          enum e-lan {
            value "2";
            description "the service type is e-lan";
          }
        }
        mandatory true;
        description
          "The service type of this instance,
          user may choose from e-line, e-tree, e-lan";
       }

      leaf instance-oper-state {
        type enumeration {
          enum Planned {
            value 1;
            description "VPN Service is Planned";
          }
          enum Active {
            value 2;
            description "VPN Service is Active";
          }
          enum Active-Error {
            value 3;
            description "VPN Service is Active but with Errors";
          }
          enum Active-Suspended {
            value 4;
            description "VPN Service is Active but partly
      Suspended";
          }
          enum Disconnected {
            value 5;
            description "VPN Service is Disconnected";
          }
          enum Suspended {
            value 6;
            description "VPN Service is Suspended";
          }
        }
    description
      "This part indicates the operational state
      of VPN, e.g., planed, active, with Errors...
      User may use this value to inquire the status
      of this instance";
      }

      leaf instance-admin-state {
        type enumeration {
          enum Enabled {
            value 1;
            description "VPN Service Administratively Enabled";
          }
          enum Disabled {
            value 2;
            description "VPN Service Administratively Disabled";
          }
          enum Planed {
            value 3;
            description "VPN Service is Planned";
          }
        }
    description
      " This part indicates the administrative state
      of VPN, e.g., enabled, disabled, planned.
      User may use this value to manage the instance";
      }

    leaf life-cycle-state {
      type enumeration {
      enum planned {
        value 1;
        description
        "VPN Service Planned";
      }
      enum installed {
        value 2;
        description
        "VPN Service Installed";
      }
      enum removed {
        value 3;
        description
        "VPN Service Removed";
      }
      }
    description
      " This part indicates the life cycle state
      of VPN, e.g., installed, removed, planned.";
    }

    leaf instance-availability-status {
      type enumeration {
      enum degraded {
        value 1;
        description
        "VPN Service Degraded";
      }
      enum failed {
        value 2;
        description
        "VPN Service Failed";
      }
      }
    description
      " This part indicates the availability status
      of VPN, e.g., degraded, failed.";
    }

    leaf instance-cfg-revision {
      type string;
      description
      "Indicates current service configuration revision";
    }

    leaf instance-sla-policy {
      type string;
      description
      "Indicates SLA decision policy name";
    }

    leaf service-quality {
        type enumeration {
          enum gold {
            value 0;
            description
          "Best quality of service is guaranteed.";
          }
          enum silver {
            value 1;
            description
        "Better quality of service than bronze class is
        guaranteed.";
          }
          enum bronze {
            value 2;
            description
         "Average quality of service is guaranteed.";
          }
    }
         default "bronze";
        description "Quality of service.";
      }

      list "access-interface" {
        key "interface-id";
        description "Access interface ID";

        leaf interface-id {
          type if:interface-ref;
          description "Access interface ID";
        }

        leaf role {
          when "../../instance-service-type = 'e-tree'" {
        description
        "root or leaf, only available in e-tree mode";
      }
          type enumeration {
            enum root {
              value "0";
              description "root interface";
              }
            enum leaf {
              value "1";
              description "leaf interface";
            }
          }
          mandatory true;
          description
          "the role of interface";
        }

        leaf node-id {
          type string;
          mandatory true;
          description "physical node ID of access PE";
        }

        leaf interface-name {
          type if:interface-ref;
          mandatory true;
          description
            "physical access interface name of access PE";
        }

        leaf access-type {
          type enumeration {
            enum port{
              value "0";
              description "The access type is port.";
            }
            enum vlan{
              value "1";
              description "The access type is vlan.";
            }
      }
          default "port";
          description
            "This value describes the access type,
            options are port and vlan; port is chose
            when the access is the entire port, while vlan
            means the access is the vlan of the port.";
        }
        leaf user-circuit-bitmap {
          when "../../ access-type = 'vlan'"{
        description "Only available when access-type is vlan.";
      }
          type string;
          mandatory true;
          description
            "This value describes the scope of vlan:
      use ',' or '-' to indicate the scope, e.g. 1,3,5-7.";
        }
      }
    }
  }
}
