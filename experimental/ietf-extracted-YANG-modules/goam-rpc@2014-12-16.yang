module goam-rpc {
     namespace "urn:ietf:params:xml:ns:yang:goam-rpc";
     prefix goam-rpc;
   import ietf-interfaces {
   prefix if;
   }
   import ietf-inet-types {
   prefix inet;
    }
   import ietf-yang-types {
   prefix yang;
   }
  organization "IETF LIME (Layer Independent OAM Management in Multi-Layer Environment) Working Group";
   description
   "This YANG module defines the abstract notification and rpc command for multi-layer OAM management to be used
   within IETF in a protocol independent manner.";
   revision 2014-12-16 {
   description
   "Initial revision.";
   reference " RFC XXXX: A YANG Data Model for Layer independent OAM management";
   }
   /*
   * identity definitions,
   */
   identity technology-types {
   description
    "this is the base identity of technology types which are
   ethernet, bfd, mpls, sfc, ipv4, ipv6";
   }
   identity mpls {
    base technology-types;
   description
   "mpls technology type";
   }
   identity sfc {
   base technology-types;
   description
   "sfc type";
   }
   identity ipv4 {
    base technology-types;
    description
    "technology of ipv4";
    }
   identity ipv6 {
   base technology-types;
   description
   "technology of ipv6";
   }
   /*
    * typedef definitions
   */
   typedef vni {
   type uint32;
   }
   grouping mp-address {
       choice mp-address {
         case mac-address {
           leaf mac-address {
             type yang:mac-address;
           }
         }
         case ipv4-address {
           leaf ipv4-address {
             type inet:ipv4-address;
           }
         }
         case ipv6-address {
           leaf ipv6-address {
             type inet:ipv6-address;
           }
         }
       }
     }
   typedef MP-id {
   type union{
type uint32 {
   range "1..8191";
}
type yang:mac-address;
    type inet:ipv4-address;
    type inet:ipv6-address;
}
   description
   "Defines type for MPID";
    }
   typedef Context-Identifier {
   type union {
   type vni;
   type uint32;
   }
   description
   "defines context identifier types VNI, etc..";
   }
   typedef oam-counter32 {
   type yang:zero-based-counter32;
    description
    "defines 32 bit counter for OAM";
   }
   /*
   * grouping definitions
   */
grouping maintenance-stats {
       description
         "grouping for maintenance statistics, this will be augmented
          by others who use this component";
       choice maintenance-stats {
         default "maintenance-null";
         case maintenance-null {
           description
             "this is a place holder when no maintenance statis is needed";
           leaf maintenance-null {
             type empty;
             description
               "there is no maintenance statistics to be defined";
           }
         }
       }
     }
grouping default-parameter{
    description
         "grouping for default parameters, this will be augmented
          by others who use this component";
          choice other-function-parameters {
         default "parameters-null";
         case parameters-null {
           description
             "this is a place holder when no specific parameter is needed";
           leaf parameters-null {
             type empty;
             description
               "there is no specific parameter to be defined";
           }
         }
       }
}
grouping MD-status {
       description
         "collection of maintenance domain related status";
       leaf error-message {
         type string {
           length "0..255";
         }
         description
           "Error message to indicate more details.";
       }
leaf oper-status {
           type enumeration{
enum up;
enum down;
}
           description
" This leaf specifies the operational status of the
               Maintenance Domain (MD)";
         }
leaf sub-oper-status {
           type enumeration{
enum mdDown;
enum maDown;
enum oamAppDown;
enum pathDown;}
           description
" This leaf specifies the reason why the MD operational
               status as mentioned by the leaf Oper-Status
               is down.
               The mdDown indicates the MD is down.
               The maDown indicates the MA table is
               down.
               The oamAppDown indicates that the
               OAM application has notified that the entity
               monitored by this MEG is down.
               The pathDown indicates that the underlying
               path is down";
         }
 }
grouping measurement-time-group{
   container measurement-timing {
      description
        "Data definitions related to measurement timing";
      choice measurement-timing {
        mandatory true;
        description
          "This will be augmented by specific technologies who use this component";
        case measurement-timing-null {
          leaf time-null {
            type empty;
            description
              "there is no measurement time define";
          }
    }
}
}
}
   /*
    * below is definitions of rpc commands
   */
rpc continuity-check {
       description
         "Generates continuity-check and return response";
       input {
         leaf technology {
 status current;
         type identityref
 {
           base technology-types;
         }
 mandatory true;
         description
         "Defines the technology";
         }
         leaf md-name-string{
status current;
description
"Defines the MA-Domain name.";
type string;
}
         leaf md-level{
         mandatory true;
         status current;
         description
         "Defines the MD-Level";
         type int32;
}
         leaf ma-name-string{
         mandatory true;
         description
        "Define the MA-Name";
         type string;
}
         container source-mep {
           uses mp-address;
           leaf mep-id {
           type MP-id;
           }
         }
         container destination-mep {
           uses mp-address;
           leaf MP-id {
           type MP-id;
           }
         }
         list outgoing-interfaces {
           key "interface";
           leaf interface {
           type if:interface-ref;
           }
         }
       }
       output {
uses maintenance-stats {
          description
         "maintenance Stats of CC";
           }
         }
}
rpc connectivity-verification {
 description
"connectivity-verification and return response";
       input {
         leaf technology {
 status current;
         type identityref
 {
           base technology-types;
         }
 mandatory true;
         description
         "Defines the technology";
         }

         leaf md-name-string{
status current;
description
"Defines the MA-Domain name.";
type string;
}
         leaf md-level{
         mandatory true;
         status current;
         description
         "Defines the MD-Level";
         type int32;
}
         leaf ma-name-string{
         mandatory true;
         description
         "Define the MA-Name";
         type string;
}
        container source-mep {
           uses mp-address;
           leaf mep-id {
           type MP-id;
           }
         }
         container destination-mep {
           uses mp-address;
           leaf mep-id {
           type MP-id;
           }
         }
         list outgoing-interfaces {
           key "interface";
           leaf interface {
           type if:interface-ref;
           }
         }
       }
       output {
uses maintenance-stats {
          description
         "maintenance Stats of CV";
           }
         }
}
rpc path-discovery {
       description
          "path discovery and return response";
       input {
         leaf technology {
 status current;
         type identityref
 {
           base technology-types;
         }
 mandatory true;
         description
         "Defines the technology";
         }
         leaf md-name-string{
status current;
description
"Defines the MA-Domain name.";
type string;
}
         leaf md-level{
         mandatory true;
         status current;
         description
         "Defines the MD-Level";
         type int32;
}
         leaf ma-name-string{
         mandatory true;
         description
         "Define the MA-Name";
         type string;
}
         container source-mep {
           uses mp-address;
           leaf mep-id {
           type MP-id;
           }
         }

         container destination-mep {
           uses mp-address;
           leaf mep-id {
           type MP-id;
           }
         }
         list outgoing-interfaces {
           key "interface";
           leaf interface {
           type if:interface-ref;
           }
         }
       }
       output {
         list response{
         key "response-index";
         leaf response-index{
type uint8;
}
         container destination-mp {
           uses mp-address;
           leaf mp-id {
             type MP-id;
           }
         }
uses maintenance-stats {
          description
         "maintenance Stats of path discovery ";
           }
         }
}
}
rpc initiated-performance-measurement {
       description
       "Generates performance-measurement";
       input {
         leaf technology {
 status current;
         type identityref
 {
           base technology-types;
         }
 mandatory true;
         description
         "Defines the technology";
         }
         leaf md-name-string{
         status current;
         description
         "Defines the MA-Domain name";
         type string;
}
         leaf md-level{
         mandatory true;
         status current;
         description
         "Defines the MD-Level";
         type int32;
}
         leaf ma-name-string{
         mandatory true;
         description
         "Define the MA-Name";
         type string;
}
         container source-mep {
           uses mp-address;
           leaf mep-id {
           type MP-id;
           }
         }
         container destination-mep {
           uses mp-address;
           leaf mep-id {
           type MP-id;
           }
         }

         list outgoing-interfaces {
           key "interface";
           leaf interface {
           type if:interface-ref;
           }
         }
         leaf interval {
           default "0";
           description
           "Defines perform measurement Interval";
           type uint32;
           }
         leaf pm-type{
           description
           "Indicate the type of perform measurement";
           type uint32;
         }
uses measurement-time-group;
       }
output {
uses maintenance-stats {
          description
         "maintenance Stats of performance-measurement ";
           }
         }
}
rpc revoke-performance-measurement {
       description
       "Revoke performance measurement";
       input {
         leaf technology {
 status current;
         type identityref
 {
           base technology-types;
         }
 mandatory true;
         description
         "Defines the technology";
         }
         leaf md-name-string{
         status current;
         description
         "Defines the MA-Domain name.";
         type string;
}
         leaf md-level{
         mandatory true;
         status current;
         description
         "Defines the MD-Level";
         type int32;
}
         leaf ma-name-string{
         mandatory true;
         description
         "Define the MA-Name";
         type string;
}

         container source-mep {
           uses mp-address;
           leaf mep-id {
           type MP-id;
           }
         }
         container destination-mep {
           uses mp-address;
           leaf mep-id {
           type MP-id;
           }
         }
         list outgoing-interfaces {
           key "interface";
           leaf interface {
           type if:interface-ref;
           }
         }
         leaf interval {
           default "0";
           description
           "Defines perform measurement Interval";
           type uint32;
           }
         leaf pm-type{
           description
           "Indicate the type of perform measurement";
           type uint32;
         }
       }
}
rpc initiated-other-function{
       description
       "Generates other-function";
       input {
         leaf technology {
 status current;
         type identityref
 {
           base technology-types;
         }
 mandatory true;
         description
         "Defines the technology";
         }
         leaf function-name{
type string;
description
"Indicate the function name ";
}
         leaf md-name-string{
         status current;
         description
         "Defines the MA-Domain name.";
         type string;
}

         leaf md-level{
         mandatory true;
         status current;
         description
         "Defines the MD-Level";
         type int32;
}

         leaf ma-name-string{

         mandatory true;
         description
         "Define the MA-Name string.";
         type string;
}
         container source-mep {
           uses mp-address;
           leaf mep-id {
           type MP-id;
           }
         }
         container destination-mep {
           uses mp-address;
           leaf mep-id {
           type MP-id;
           }
         }
         list outgoing-interfaces {
           key "interface";
           leaf interface {
           type if:interface-ref;
           }
         }
        uses default-parameter;
       }
       output {
uses maintenance-stats {
          description
         "maintenance Stats of performance-measurement ";
           }
         }
}
rpc revoke-other-function{
       description
       "Revoke other-function";
       input {
         leaf technology {
 status current;
         type identityref
 {
           base technology-types;
         }
 mandatory true;
         description
         "Defines the technology";
         }
         leaf function-name{
type string;
description
"Indicate the function name ";
}
         leaf md-name-string{
         status current;
         description
         "Defines the MA-Domain name.";
         type string;
}
         leaf md-level{
         mandatory true;
         status current;
         description
         "Defines the MD-Level";
         type int32;
}
         leaf ma-name-string{

         mandatory true;
         description
         "Define the MA-Name";
         type string;
}
         container source-mep {
           uses mp-address;
           leaf mep-id {
           type MP-id;
           }
         }
         container destination-mep {
           uses mp-address;
           leaf mep-id {
           type MP-id;
           }
         }
         list outgoing-interfaces {
           key "interface";
           leaf interface {
           type if:interface-ref;
           }
         }
        uses default-parameter;
       }
   }
   /*
    * below is definitions of notifications
   */

notification defect-codition-notification {
         leaf technology {
 status current;
         type identityref
 {
           base technology-types;
         }
 mandatory true;
         description
         "Defines the technology";
         }
         leaf md-name-string{
status current;
description
"Defines the MA-Domain name.";
type string;
}
leaf md-level{
         mandatory true;
         status current;
         description
         "Defines the MD-Level";
         type int32;
}
         leaf ma-name-string{
         mandatory true;
         description
         "Define the MA-Name";
         type string;
}
leaf mep-id {
mandatory true;
status current;
description
"Assign MEPID in the range of 1..8191";
         type MP-id;
}
         container remote-mepid {
          choice MEP-ID{
  default "MEP-ID-int";
   case MEP-ID-int{
    leaf MEP-ID-int{
 type int32;
}
   }
  }
         }
uses MD-status;
     }
   }
