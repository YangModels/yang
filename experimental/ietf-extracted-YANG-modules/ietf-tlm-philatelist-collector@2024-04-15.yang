module ietf-tlm-philatelist-collector {
  yang-version 1.1;
  namespace 
    "urn:ietf:params:xml:ns:yang:ietf-tlm-philatelist-collector";
  prefix ietf-tlm-philatelist-collector;

  import ietf-tlm-philatelist-types {
    prefix ietf-tlm-philatelist-types;
  }
  import ietf-tlm-philatelist-dashboard {
    prefix ietf-tlm-philatelist-dashboard;
  }
  import ietf-tlm-philatelist-index {
    prefix ietf-tlm-philatelist-index;
  }

  organization
    "IETF GREEN (Getting Ready for Energy-Efficient Networking)
     Working Group";
  contact
    "WG Web:   <https://datatracker.ietf.org/group/green/about/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    'This YANG module defines the Telemetry Philatelist Collector.
    These definitions are for Philatelist Network Controllers.

    A Network Controller with the Collector role programs one or more
    SOURCES (typically Network Elements) to generate a STREAM of 
    telemetry data. A SOURCE may be a Provider, or a proxy mechanism
    standing in for the Provider.
    The STREAM is then sent to a specific DESTINATION PARTITION
    in a Time Series Database (TSDB). Partitions are also known as
    buckets, intervals, segments, etc. in various implementations.

    Each STREAM consists of timestamped sensor values from each
    sensor in a sensor group.

               +-------------+
               |  COLLECTOR  |
               +-------------+                     ___________
                      |                           /DESTINATION\
            +------------------+                 (  PARTITION  )
            v                  v                 |\___________/|
      +------------+    +------------+  STREAM 1 |             |
      |   SOURCE   |    |   SOURCE   |  =======> |             |
      | - sensor 1 |    | - sensor 1 |           |             |
      | - sensor 2 |    | - sensor 4 |  STREAM 2 |             |
      | - sensor 3 |    | - sensor 7 |  =======> |             |
      +------------+    +------------+           |             |
                \\                      STREAM 3 |             |
                  =============================>  \___________/

    '+"
    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.

    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";

  revision 2024-04-15 {
    description
      "Restructured as part of the Telemetry Philatelist framework";
    reference
      "RFC XXXX: ...";
  }

  container tlm-collector {
    description 
      "Root container for the Philatelist Collector function.
      ";
    container organizations {
      description 
        "List of organizations that the collected data pertains to.
        Data belonging to one organization will not mix with that of
        another.
        ";
      list organization {
        key name;
        description 
          "Organization that this collection process pertains to.
          ";

        leaf name {
          type string;
          description 
            "Collector's name of the organization.
            ";
        }
        container device-groups {
          description 
            "List of device-groups.
            ";
          list device-group {
            key name;
            description 
              "A device-group contains a group of similar devices
              that will have collection performed in the same way.
              ";
            leaf name {
              type string;
              description 
                "Name of the device-group.
                ";
            }
            leaf-list devices {
              type string;
              description 
                "Points to the devices members of this device-group.
                The exact meaning of these names is implementation
                specific.
                ";
            }
            uses ietf-tlm-philatelist-dashboard:provider-g;
          }
        }

        container tlm-streams {
          description 
            "List of telemetry streams pertainin to this
            organization.
            ";
          list tlm-stream {
            key id;
            description 
              "A stream of telemetry data that is collected from a
              device-group that share a particular dashboard.
              ";
            leaf id { 
              type ietf-tlm-philatelist-types:something; 
              description 
                "Identifier of the telemetry stream.
                "; 
            }
            list sources { 
              key "device-group dash-name";
              description 
                "List of sources to collect from. Each source points
                to a device-group and a dashboard name to collect
                from each device in the device-group.
                ";
              leaf device-group { 
                type leafref { 
                  path ../../../../device-groups/device-group/name;
                }
                description 
                  "The device-group to collect from.
                  "; 
              }
              leaf dash-name { 
                type leafref { 
                  path "../../../../device-groups/device-group/"+
                    "dashboards/dashboard/id";
                }
                description 
                  "The name of the dashboard 
                  "; 
              }
            }
            leaf destination { 
              type ietf-tlm-philatelist-index:partition-ref-t; 
              description 
                "The TSDB Partition (bucket, interval, segment, etc.)
                that the collected telemetry data is sent to.
                "; 
            }
          }
        }
      }
    }
  }

  augment "/tlm-collector/organizations/organization/device-groups/"+
    "device-group/dash-items/dash-item/label/value-source" {
    description 
      "Some additional value-sources that the collector enables
      (that are not available to providers).
      ";
    case controller-managed-value {
      leaf controller-managed-value {
        type empty;
        description
          "The Collector will determine the label value by its
          own discretion.
          ";
      }
    }
    case controller-provided-value {
      leaf controller-provided-value {
        type string;
        description
          "The Collector will determine the label value by its
          own discretion, and that value is configured here.
          ";
      }
    }
  }
}
