module tunnel-policy {
  namespace "urn:huawei:params:xml:ns:yang:tunnel-policy";
  // replace with IANA namespace when assigned
  prefix tnlp;

  import bgp {
 prefix bgp;
 //draft-ietf-idr-bgp-model
  }

  import ietf-inet-types {
 prefix inet;
 //rfc6991-Common YANG Data Types
  }

  organization
 "Huawei Technologies Co., Ltd.";
  contact
 "Huawei Industrial Base Bantian, Longgang Shenzhen 518129
     People's Republic of China
     Website: http://www.huawei.com Email: support@huawei.com";
  description
 "This YANG module defines the tunnel policy configuration
  data for tunnel policy service.

  VPN data needs to be carried by tunnels. By default, the
  system selects LSPs to carry VPN services without performing
  load balancing. If this cannot meet the requirements of VPN
  services, a tunnel policy needs to be used. The tunnel policy
  may be a tunnel type prioritizing policy or a tunnel binding
  policy. Determine which type of tunnel policy to use based
  on your actual requirements:
  * A tunnel type prioritizing policy can change the tunnel
    type selected for VPN services and allow load balancing
    among tunnels.
  * A tunnel binding policy can bind a VPN service to
    specified MPLS TE tunnels to provide QoS guarantee for
    the VPN service.

  Terms and Acronyms

  ... ";

  revision 2018-09-15 {
 description
   "Initial revision.";
  }

  typedef tnlmbaseTnlPolicyType {
 type enumeration {
   enum "invalid" {
     description
       "Tunnel policy with null configurations.";
   }
   enum "tnlSelectSeq" {
     description
       "Tunnel select-seq policy. This policy allows you
        to specify the sequence in which different types
        of tunnels are selected and the number of tunnels
        for load balancing.";
   }
   enum "tnlBinding" {
     description
       "Tunnel binding policy. This policy allows you to
        specify the next hop to be bound to a TE tunnel.
        After a TE tunnel is bound to a destination
        address, VPN traffic destined for that destination
        address  will be transmitted over the TE tunnel.";
   }
 }
 description
   "tunnel policy type";
  }
  typedef tnlmbaseSelTnlType {
 type enumeration {
   enum "invaild" {
     description
       "Search for invalid tunnels.";
   }
   enum "lsp" {
     description
       "Search for LDP LSPs.";
   }
   enum "cr-lsp" {
     description
       "Search for CR-LSPs.";
   }
   enum "gre" {
     description
       "Search for GREs.";
   }
   enum "ldp" {
     description
       "Search for LDP LSPs.";
   }
   enum "bgp" {
     description
       "Search for BGP LSPs.";
   }
   enum "srbe-lsp" {
     description
       "Search for SR-LSPs.";
   }
   enum "sr-te" {
     description
       "Search for SR-TE.";
   }
   enum "te" {
     description
       "Search for TE.";
   }
 }
 description
   "tunnel select type";
  }

  typedef tnlPolicyExist {
 type enumeration {
   enum "true" {
     description
       "The tunnel policy has been configured.";
   }
   enum "false" {
     description
       "The tunnel policy has not been configured.";
   }
 }
 description
   "tunnel policy state";
  }

  typedef rtpMatchMode {
 type enumeration {
   enum "permit" {
     description
       "Matching mode of filters.";
   }
   enum "deny" {
     description
       "Matching mode of filters.";
   }
 }
 description
   "match mode";
  }
  typedef rtpTnlSelMchType {
 type enumeration {
   enum "matchNHopPF" {
     description
       "Match IPv4 next hops by an IPv4 prefix.";
   }
   enum "matchNHopAcl" {
     description
       "Match IPv4 next hops by an ACL.";
   }
 }
 description
   "tunnel selector type";
  }

  /*
A tunnel policy determines which type of tunnels can be
selected by an application module.

Tunnel policies can be classified into two modes:
Select-seq: The system selects a tunnel for an application
program based on the tunnel type priorities defined in the
tunnel policy.
Tunnel binding: The system selects only a specified tunnel
for an application program.

The two modes are mutually exclusive.

Configuration example:
#
tunnel-policy policy1
 description policy1
 tunnel binding destination 1.1.1.1 te Tunnel0/0/0 down-switch
#
tunnel-policy policy2
 tunnel select-seq cr-lsp gre lsp load-balance-number 2
#
tunnel-policy policy3
 tunnel binding destination 1.1.1.1 te Tunnel0/0/0 down-switch
 tunnel binding destination 3.3.3.3 te Tunnel0/0/0
                                        ignore-destination-check
 tunnel binding destination 5.5.5.5 te Tunnel0/0/0
#
  */

  container tnlmGlobal {
 description
   "Global parameters for tunnel policy.";
 leaf nonexistentCheckFlag {
   type boolean;
   default "true";
   description
     "Nonexistent config check flag of tunnel policy.
      By default, if you specify a nonexistent tunnel policy
      in a command, the command does not take effect. To enable
      the system to allow a nonexistent tunnel policy to be
      specified in a command, run the tunnel-policy
      nonexistent-config-check disable command.";
 }
  }

  container tunnelPolicys {
 description
   "List of global tunnel policy configurations. A tunnel
    policy can  be used to specify a rule for selecting
    tunnels.";

 list tunnelPolicy {
   key "tnlPolicyName";

   description
     "A policy for selecting tunnels to carry services. The
      tunnel management module searches for and returns the
      required tunnels based on the tunnel policy. By default,
      no tunnel policy is configured, the system selects an
      available tunnel in the order of conventional LSPs,
      CR-LSPs, and Local_IFNET LSPs, and load balancing is
      not performed.";

   leaf tnlPolicyName {
     type string {
       length "1..39";
     }
     description
       "Name of a tunnel policy. The value is a string of 1 to
        39 case-sensitive characters, spaces not supported.";
   }
   leaf tnlPolicyExist {
     type tnlPolicyExist;
     config false;
     description
       "Whether a tunnel policy has been configured.";
   }
   leaf tpSubCount {
     type uint32;
     config false;
     description
       "Number of times a tunnel policy is referenced.";
   }
   leaf description {
     type string {
       length "1..80";
     }
     description
       "Description of a tunnel policy.";
   }

   leaf tnlPolicyType {
     type tnlmbaseTnlPolicyType;
     default "invalid";
     description
       "Tunnel policy type. The available options are sel-seq,
        binding, and invalid. A tunnel policy can be configured
        with only one policy type.";
   }
   container tpNexthops {
     must "not(../tnlPolicyType='tnlBinding') or "
          + "(../tnlPolicyType='tnlBinding' "
          + "and count(tpNexthop)>=1)";
     description
       "List of tunnel binding configurations.";
     list tpNexthop {
       when "not(../../tnlPolicyType='tnlSelectSeq') or "
            + "../../tnlPolicyType='tnlBinding'";
       key "nexthopIPaddr";
       max-elements  "65535";
       description
         "Rule for binding a TE tunnel to a destination address,
          so that the VPN traffic destined for that destination
          address can be transmitted over the TE tunnel.";
       leaf nexthopIPaddr {
         type inet:ipv4-address-no-zone;
         description
           "Destination IP address to be bound to a tunnel.";
       }
       leaf downSwitch {
         type boolean;
         default "false";
         description
           "Enable tunnel switching. After this option is
            selected, if the bound TE tunnel is unavailable,
            the system will select an available tunnel in
            the order of conventional LSPs, CR-LSPs, and
            Local_IFNET tunnels.";
       }
       leaf ignoreDestCheck {
         type boolean;
         default "false";
         description
           "Do not check whether the destination address of the
            TE tunnel matches the destination address specified
            in the tunnel policy.";
       }
       leaf isIncludeLdp {
         type boolean;
         must "(../isIncludeLdp='true' and not "
              + "(../downSwitch='true')) or "
              + "../isIncludeLdp='false'";
         default "false";
         description
           "Is loadbalance with LDP";
       }
       container tpTunnels {
         description
           "List of tunnels available for an application.";
         list tpTunnel {
           key "tunnelName";
           min-elements  "1";
           max-elements  "16";
           description
             "Tunnel.";
           leaf tunnelName {
             type string {
               length "1..47";
             }
             description
               "Name of the specified tunnel.";
           }
         }
       }
     }
   }
   container tnlSelSeqs {
     when "not(../tnlPolicyType='invalid' or "
          + "../tnlPolicyType='tnlBinding')";
     must "not(../tnlPolicyType='tnlSelectSeq') or "
          + "(../tnlPolicyType='tnlSelectSeq' and "
          + "count(tnlSelSeq)>=1)";
     description
       "Sequence in which different types of tunnels are
        selected.
        If the value is INVALID, no tunnel type has been
        configured.";
     container tnlSelSeq {
       when "not(../../tnlPolicyType='invalid' or "
            + "../../tnlPolicyType='tnlBinding') or "
            + "../../tnlPolicyType='tnlSelectSeq'";
       presence "create tnlSelSeq";
       description
         "Sequence in which different types of tunnels are
          selected. If the value is INVALID, no tunnel type
          has been configured.";
       leaf loadBalanceNum {
         type uint32 {
           range "1..64";
         }
         default "1";
         description
           "Sequence in which different types of tunnels are
            selected. The available tunnel types are CR-LSP,
            and LSP. LSP tunnels refer to LDP LSP tunnels
            here.";
       }
       leaf selTnlType1 {
         type tnlmbaseSelTnlType;
         default "invaild";
         description
           "Sequence in which different types of tunnels are
            selected. If the value is INVALID, no tunnel type
            has been configured.";
       }
       leaf selTnlType2 {
         when "not(../selTnlType1='invaild' and "
              + "../../../tnlPolicyType='tnlSelectSeq' or "
              + "../selTnlType1='invaild')";
         type tnlmbaseSelTnlType;
         default "invaild";
         description
           "Sequence in which different types of tunnels are
            selected. If the value is INVALID, no tunnel type
            has been configured.";
       }
       leaf selTnlType3 {
         when "not(../selTnlType1='invaild' or "
              + "../selTnlType2='invaild')";
         type tnlmbaseSelTnlType;
         default "invaild";
         description
           "Sequence in which different types of tunnels are
            selected. If the value is INVALID, no tunnel type
            has been configured.";
       }
       leaf selTnlType4 {
         when "not(../selTnlType1='invaild' or "
              + "../selTnlType2='invaild' or "
              + "../selTnlType3='invaild')";
         type tnlmbaseSelTnlType;
         default "invaild";
         description
           "Sequence in which different types of tunnels are
            selected. If the value is INVALID, no tunnel type
            has been configured.";
       }
       leaf selTnlType5 {
         when "not(../selTnlType1='invaild' or "
              + "../selTnlType2='invaild' or "
              + "../selTnlType3='invaild' or "
              + "../selTnlType4='invaild')";
         type tnlmbaseSelTnlType;
         default "invaild";
         description
           "Sequence in which different types of tunnels are
            selected. If the value is INVALID, no tunnel type
            has been configured.";
       }
       leaf selTnlType6 {
         when "not(../selTnlType1='invaild' or "
              + "../selTnlType2='invaild' or "
              + "../selTnlType3='invaild' or "
              + "../selTnlType4='invaild' or "
              + "../selTnlType5='invaild')";
         type tnlmbaseSelTnlType;
         default "invaild";
         description
           "Sequence in which different types of tunnels are
            selected. If the value is INVALID, no tunnel type
            has been configured.";
       }
       leaf unmix {
         type boolean;
         default "false";
         description
           "unmix flag.";
       }
     }
   }
 }

  }//End of container tunnelPolicys

  /*
  The tunnel selector is specific to BGP/MPLS IP VPN services
  (a type of VPN service), selecting a tunnel policy for
  VPNv4/VPNv6 routes on the backbone network.

  A tunnel selector selects tunnel policies for routes after
  filtering routes based on some route attributes such as the
  route distinguisher (RD) and next hop. This makes tunnel
  selection more flexible.
  A tunnel selector is often used on the autonomous system
  boundary router (ASBR) in inter-AS VPN Option B or the
  superstratum provider edge (SPE) in hierarchy of VPN (HoVPN).
  */
  container tunnelSelectors {
 description
   "List of tunnel selectors.";
 list tunnelSelector {
   key "name";
   max-elements  "65535";
   description
     "Tunnel selector. Usually used in BGP VPN Option B or
      BGP VPN Option C, tunnel selector selects a proper
      tunnel policy for routes.";

   leaf name {
     type string {
       length "1..40";
     }
     description
       "Name of a tunnel selector. The name is a string of
        1 to 40 case-sensitive characters without spaces.";
   }

   container tunnelSelectorNodes {
     description
       "List of tunnel selector nodes.";
     list tunnelSelectorNode {
       key "nodeSequence";
       min-elements  "1";
       max-elements  "65535";

       leaf nodeSequence {
         type uint32 {
           range "0..65535";
         }
         description
            "Sequence number of a node.
             Specifies the index of a node of the tunnel
             selector.
             When a route-policy is used to filter a route,
             the route first matches the node with the
             smallest node value.";
       }
       leaf matchMode {
         type rtpMatchMode;
         mandatory true;
         description
           "Matching mode of nodes.";
       }
       container matchCondition {
         description
           "Match Type List";

         container matchDestPrefixFilters {
           description
             "Match IPv4 destination addresses by the prefix
              filter. The configurations of matching IPv4
              destination addresses by the prefix filter are
              mutually exclusive with the configurations of
              matching IPv4 destination addresses based on
              ACL rules.";

           container matchDestPrefixFilter {
             presence "create matchDestPrefixFilter";
             description
               "Match an IPv4 destination address by the prefix
                filter.";
             leaf prefixName {
               type "string";
               description
                 "Name of the specified prefix filter when IPv4
                  destination addresses are matched.";
             }
           }
         } // End of matchDestPrefixFilters

         container matchIPv4NextHops {
           description
             "Match IPv4 next hops by the prefix filter or ACL
              filter. The configurations of matching IPv4 next
              hops by the prefix filter are mutually exclusive
              with the configurations of matching IPv4 next
              hops by the ACL filter.";

           container matchIPv4NextHop {
             presence "create matchIPv4NextHop";
             description
               "Match an IPv4 next hop by the prefix or ACL.";
             leaf matchType {
               type rtpTnlSelMchType;
               description
                 "Match type. IPv4 next hops are matched with
                  either the prefix or ACL.";
             }
             leaf prefixName {
               when "not(../matchType='matchNHopAcl' or "
                    + "not(../matchType)) or "
                    + "../matchType='matchNHopPF'";
               type "string";
               description
                 "Name of the specified prefix when IPv4 next hops
                  are matched.";
             }
             leaf aclNameOrNum {
               when "not(../matchType='matchNHopPF' or "
                    + "not(../matchType)) or "
                    + "../matchType='matchNHopAcl'";
               type string {
                 length "1..32";
               }
               description
                 "Name of the specified ACL when next hops are
                  matched, which can be a value ranging from
                  2000 to 2999 or a string beginning with a-z
                  or A-Z.";
             }
           }
         } //End of container matchIPv4NextHops

         container matchIPv6NextHops {
           description
             "Match IPv6 next hops by the IPv6 prefix filter.";
           container matchIPv6NextHop {
             presence "create matchIPv6NextHop";
             description
               "Match an IPv6 next hop by the IPv6 prefix
                filter.";

             leaf ipv6PrefixName {
               type "string";
               description
                 "Name of the specified prefix filter when IPv6
                  next hops are matched.";
             }
           }
         } //End of container matchIPv6NextHops

         container matchCommunityFilters {
           description
             "Match community attribute filters.";
           list matchCommunityFilter {
             key "cmntyNameOrNum";
             max-elements  "32";
             description
               "Match a community attribute filter.";
             leaf cmntyNameOrNum {
               type string {
                 length "1..51";
                 pattern '((0*[1-9][0-9]?)|(0*1[0-9][0-9])|'
                       + '([^?-9][^?0,50})|'
                       + '([][^?^?-9][^?)';
               }
               description
                 "Name or index of a community attribute filter.
                  It can be a numeral or a string. The ID of a
                  basic community attribute filter is an integer
                  ranging from 1 to 99; the ID of an advanced
                  community attribute filter is an integer
                  ranging from 100 to 199. The name of a community
                  attribute filter is a string of 1 to 51
                  characters. The string cannot contain only
                  digits.";
             }
             leaf wholeMatch {
               type boolean;
               default "false";
               description
                 "All the communities are matched. It is valid to
                  only basic community attribute filters.";
             }
             leaf sortMatch {
               type boolean;
               default "false";
               description
                 "Match all community attributes in sequence.It
                  is valid to only Advanced community attribute
                  filters.";
             }
           }
         } //End of container matchCommunityFilters

         container matchRdFilters {
           description
             "Match RD filters.";
           container matchRdFilter {
             presence "create matchRdFilter";
             description
               "Match an RD filter.";
             leaf rdIndex {
               type uint32 {
                 range "1..1024";
               }
               description
                 "Index of an RD filter.";
             }
           }
         } //End of container matchRdFilters

       }//End of container matchCondition
       container applyAction {
         description
           "Set Type List";
         container applyTnlPolicys {
           description
             "Set tunnel policies.";
           container applyTnlPolicy {
             presence "create applyTnlPolicy";
             description
               "Set a tunnel policy.";
             leaf tnlPolicyName {
               type string {
                 length "1..39";
               }
               description
                 "Name of a tunnel policy. The name is a
                  string of 1 to 39 case-sensitive characters,
                  spaces not supported.";
             }
           }
         }
       } //End of container applyAction

     }

   } //End of container tunnelSelectorNodes

 } //End of list tunnelSelector

  } //End of container tunnelSelectors
