module ietf-bgp {
  yang-version "1.1";
  namespace "urn:ietf:params:xml:ns:yang:ietf-bgp";
  prefix "bgp";

  import ietf-routing-policy {
    prefix rpol;
    reference
      "RFC ZZZZ: A YANG Data Model for Routing Policy Management";
  }

  include ietf-bgp-common;
  include ietf-bgp-common-multiprotocol;
  include ietf-bgp-common-structure;
  include ietf-bgp-neighbor;
  include ietf-bgp-global;
  include ietf-bgp-peer-group;

  organization
    "IETF IDR Working Group";

  contact
    "WG Web:   <http://tools.ietf.org/wg/idr>
     WG List:  <idr@ietf.org>

     Authors: Keyur Patel (keyur at arrcus.com),
              Mahesh Jethanandani (mjethanandani at gmail.com),
              Susan Hares (shares at ndzh.com";

  description
    "This module describes a YANG model for BGP protocol
     configuration. It is a limited subset of all of the configuration
     parameters available in the variety of vendor implementations,
     hence it is expected that it would be augmented with vendor-
     specific configuration data as needed. Additional modules or
     submodules to handle other aspects of BGP configuration,
     including policy, VRFs, VPNs, and additional address families
     are also expected.

     This model supports the following BGP configuration level
     hierarchy:
      BGP
        |
        +-> [ global BGP configuration ]
          +-> AFI / SAFI global
        +-> peer group
          +-> [ peer group config ]
          +-> AFI / SAFI [ per-AFI overrides ]
        +-> neighbor
          +-> [ neighbor config ]
          +-> [ optional pointer to peer-group ]
          +-> AFI / SAFI [ per-AFI overrides ]";

  revision "2018-05-09" {
    description
      "Initial Version";
    reference
      "RFC XXXX, BGP Model for Service Provider Network ";
  }

  /*
   * Groupings
   */
  container bgp {
    description
      "Top-level configuration for the BGP router";

    container global {
      presence "Enables global configuration of BGP";
      description
        "Global configuration for the BGP router";
      uses bgp-global-base;
      uses rpol:apply-policy-group;
    }

    container neighbors {
      description
        "Configuration for BGP neighbors";
      uses bgp-neighbor-list;
    }

    container peer-groups {
      description
        "Configuration for BGP peer-groups";
      uses bgp-peer-group-list;
    }
  }
}
