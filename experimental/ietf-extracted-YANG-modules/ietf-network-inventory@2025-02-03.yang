module ietf-network-inventory {
  yang-version 1.1;
  namespace "urn:ietf:params:xml:ns:yang:ietf-network-inventory";
  prefix nwi;

  import iana-hardware {
    prefix ianahw;
    reference
      "https://www.iana.org/assignments/yang-parameters";
  }
  import ietf-yang-types {
    prefix yang;
    reference
      "RFC 6991: Common YANG Data Types";
  }
  import ietf-inet-types {
    prefix inet;
    reference
      "RFC 6991: Common YANG Data Types";
  }

  organization
    "IETF IVY Working Group";
  contact
    "WG Web:   <https://datatracker.ietf.org/wg/ivy/>
     WG List:  <mailto:inventory-yang@ietf.org>

     Editor:   Chaode Yu
               <yuchaode@huawei.com>

     Editor:   Sergio Belotti
               <sergio.belotti@nokia.com>

     Editor:   Jean-Francois Bouquier
               <jeff.bouquier@vodafone.com>

     Editor:   Fabio Peruzzini
               <fabio.peruzzini@telecomitalia.it>

     Editor:   Phil Bedard
               <phbedard@cisco.com>";
  description
    "This module defines a base model for retrieving network
     inventory.

     The model fully conforms to the Network Management
     Datastore Architecture (NMDA).

     Copyright (c) 2025 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.

  revision 2025-02-03 {
    description
      "Initial version";
    reference
      "RFC XXXX: A YANG Data Model for Network Inventory.";
  }

  /*
   * Identities
   */

  identity non-hardware-component-class {
    description
      "Base identity for non hardware components (e.g., software
       components) in a managed device.";
  }

  identity ne-type {
    description
      "Base identity for Network Element (NE) types.";
  }

  identity ne-physical {
    base nwi:ne-type;
    description
      "A physical network element (NE). ";
  }

  /*
   * Editors' Note: This identity may need to be moved to
   *                iana-hardware update
   */

  identity transceiver-module {
    base ianahw:hardware-class;
    description
      "This identity is applicable if the hardware class is some sort
       of self-contained sub-system which contains one or more
       transceivers (e.g., optical or electrical transceivers).

       A transceiver-module component can only be contained by a
       port component.";
  }

  /*
   * Types
   */

  typedef ne-ref {
    type leafref {
      path  "/nwi:network-inventory/nwi:network-elements"
          + "/nwi:network-element/nwi:ne-id";
    }
    description
      "This type is intended to be used by data models that need to
      reference Network Element.";
  }

  /*
   * Groupings
   */

  grouping port-ref {
    description
      "This grouping is intended to be used by data models that need
      to reference a port component within a Network Element.";
    leaf ne-ref {
      type nwi:ne-ref;
      description
        "The reference to the Network Element which contains the
        port to be referenced.";
    }
    leaf port-ref {
      type leafref {
        path
          "/nwi:network-inventory/nwi:network-elements/"
        + "nwi:network-element[nwi:ne-id=current()/../ne-ref]"
        + "/nwi:components/nwi:component/nwi:component-id";
      }
      must "derived-from-or-self (/nwi:network-inventory/
            nwi:network-elements/nwi:network-element
            [nwi:ne-id=../ne-ref]/nwi:components/nwi:component
            [nwi:component-id=current()]/nwi:class, 'ianahw:port')";
      description
        "The reference to the port component.";
    }
  }

  grouping channel-ref {
    description
      "This grouping is intended to be used by data models that need
       to reference one or more breakout channels within a
       transceivers module component.";
    leaf ne-ref {
      type nwi:ne-ref;
      description
        "The reference to the Network Element which contains the
         transceiver module to be referenced.";
    }
    leaf transceiver-module-ref {
      type leafref {
        path
          "/nwi:network-inventory/nwi:network-elements/"
        + "nwi:network-element[nwi:ne-id=current()/../ne-ref]"
        + "/nwi:components/nwi:component/nwi:component-id";
      }
      must "derived-from-or-self (/nwi:network-inventory/
            nwi:network-elements/nwi:network-element
            [nwi:ne-id=../ne-ref]/nwi:components/nwi:component
            [nwi:component-id=current()]/nwi:class,
            'nwi:transceiver-module')";
      description
        "The reference to the transceivers module component.";
    }
    leaf-list channel-ref {
      type leafref {
        path  "/nwi:network-inventory/nwi:network-elements"
            + "/nwi:network-element[nwi:ne-id=current()/../ne-ref]/"
            + "nwi:components/"
            + "nwi:component[nwi:component-id="
            + "current()/../transceiver-module-ref]/"
            + "nwi:transceiver-module-specific-info/"
            + "nwi:breakout-channels/nwi:breakout-channel/"
            + "nwi:channel-id";
      }
      description
        "The references to the breakout channels.";
    }
  }

  grouping common-entity-attributes {
    description
      "The set of attributes which are common to all the entities
       (e.g., component, network elements) defined in this module.";
    leaf uuid {
      type yang:uuid;
      config false;
      description
        "The Universally Unique Identifier of the entity
         (e.g., component).";
    }
    leaf name {
      type string;
      description
        "The name of the  entity (e.g., component), as specified by
         a network manager, that provides a non-volatile 'handle'
         for the entity and that can be modified anytime during the
         entity lifetime.

         If no configured value exists, the server MAY set the value
         of this node to a locally unique value in the operational
         state.";
    }
    leaf description {
      type string;
      description
        "The textual description of the entity (e.g., component).";
    }
    leaf alias {
      type string;
      description
        "The alias name of the entity (e.g., component). This alias
         name can be specified by network manager.";
    }
    leaf hardware-rev {
      type string;
      config false;
      description
        "The vendor-specific hardware revision string for the entity
         (e.g., component).";
    }
    leaf software-rev {
      type string;
      config false;
      description
        "The vendor-specific software revision string for the entity
         (e.g., component).";
    }
    leaf-list software-patch-rev {
      type string;
      config false;
      description
        "The vendor-specific patch software revision string for the
         entity (e.g., component).";
    }
    leaf mfg-name {
      type string;
      config false;
      description
        "The name of the manufacturer of this entity
         (e.g., component).";
    }
    leaf mfg-date {
      type yang:date-and-time;
      config false;
      description
        "The date of manufacturing of the entity (e.g., component).";
    }
    leaf serial-number {
      type string;
      config false;
      description
        "The vendor-specific serial number of the the entity
         (e.g., component) instance. It is expected that vendors
         assign unique serial numbers to different network element
         instances within the scope of the product name.";
    }
    leaf product-name {
      type string;
      config false;
      description
        "The vendor-specific and human-interpretable string
         describing the entity (e.g., component) type. It is expected
         that vendors assign unique product names to different entity
         (e.g., component) types within the scope of the vendor.";
    }
  }

  /* 
   * Data Nodes
   */

  container network-inventory {
    description
      "Top-level container for network inventory.";
    container network-elements {
      description
        "The top-level container for the list of network elements
         within the network.";
      list network-element {
        key "ne-id";
        description
          "The list of network elements within the network.";
        leaf ne-id {
          type string;
          description
            "An identifier that uniquely identifies the NE in
             a network.";
        }
        leaf ne-type {
          type identityref {
            base nwi:ne-type;
          }
          default "nwi:ne-physical";
          config false;
          description
            "The NE type.";
        }
        uses common-entity-attributes;
        container components {
          description
            "The top-level container for the list of components
             within a network element.";
          list component {
            key "component-id";
            description
              "The list of components within a network element.";
            leaf component-id {
              type string;
              description
                "An identifier that uniquely identifies the component
                 in a node.";
            }
            leaf class {
              type union {
                type identityref {
                  base ianahw:hardware-class;
                }
                type identityref {
                  base non-hardware-component-class;
                }
              }
              config false;
              mandatory true;
              description
                "The type of the component.";
            }
            uses common-entity-attributes {
              refine "hardware-rev" {
                description
                  "The vendor-specific hardware revision string for
                   the component. The preferred value is the hardware
                   revision identifier actually printed on the
                   component itself (if present).";
                reference
                  "RFC 6933: Entity MIB (Version 4) -
                             entPhysicalHardwareRev";
              }
              refine "software-rev" {
                reference
                  "RFC 6933: Entity MIB (Version 4) -
                             entPhysicalSoftwareRev";
              }
              refine "mfg-name" {
                description
                  "The name of the manufacturer of this physical
                   component.
                   The preferred value is the manufacturer name
                   string actually printed on the component itself
                   (if present).

                   Note that comparisons between instances of the
                   'model-name', 'firmware-rev', 'software-rev', and
                   'serial-number' nodes are only meaningful amongst
                   components with the same value of 'mfg-name'.

                   If the manufacturer name string associated with
                   the physical component is unknown to the server,
                   then this node is not instantiated.";
                reference
                  "RFC 6933: Entity MIB (Version 4) -
                             entPhysicalMfgName";
              }
              refine "mfg-date" {
                description
                  "The date of manufacturing of the managed
                   component.";
                reference
                  "RFC 6933: Entity MIB (Version 4) -
                             entPhysicalMfgDate";
              }
            }
            leaf firmware-rev {
              type string;
              config false;
              description
                "The vendor-specific firmware revision string for the
                 component.";
              reference
                "RFC 6933: Entity MIB (Version 4) -
                           entPhysicalFirmwareRev";
            }
            leaf part-number {
              type string;
              config false;
              description
                "The vendor-specific part number of the component
                 type. It is expected that vendors assign unique part
                 numbers to different component types within the
                 scope of the vendor.";
            }
            leaf asset-id {
              type string;
              config false;
              description
                "This node is a user-assigned asset tracking
                 identifier for the component.

                 A server implementation MAY map this leaf to the
                 entPhysicalAssetID MIB object.  Such an
                 implementation needs to use some mechanism to handle
                 the differences in size and characters allowed
                 between this leaf and entPhysicalAssetID.

                 The definition of such a mechanism is outside the
                 scope of this document.";
              reference
                "RFC 6933: Entity MIB (Version 4) -
                           entPhysicalAssetID";
            }
            container child-component-ref {
              config false;
              description
                "A placeholder for adding the reference to child
                 component(s): to further discuss whether to define
                 a child leaf-list as RFC 8348 or a list of
                 sub-components as openconfig-platform.";
            }
            leaf parent-rel-pos {
              type int32 {
                range "0 .. 2147483647";
              }
              config false;
              description
                "The relative position with respect to the parent
                 component among all the sibling components.";
              reference
                "RFC 6933: Entity MIB (Version 4) -
                           entPhysicalParentRelPos";
            }
            leaf parent {
              type leafref {
                path "../../component/component-id";
                require-instance false;
              }
              config false;
              description
                "The identifier of the component that physically
                contains this component.

                If this leaf is not instantiated, it indicates that 
                this component is not contained in any other 
                component.

                In the event that a physical component is contained
                by more than one physical component
                (e.g., double-wide modules), this node contains the
                identifier of one of these components.
                An implementation MUST use the same name every time
                this node is instantiated.";
              reference
                "RFC 6933: Entity MIB (Version 4) - 
                           entPhysicalContainedIn";

            }
            leaf is-fru {
              type boolean;
              config false;
              description
                "This node indicates whether or not this component is
                 considered a 'field-replaceable unit' by the vendor.
                 If this node contains the value 'true', then this
                 component identifies a field-replaceable unit.
                 For all components that are permanently contained
                 within a field-replaceable unit, the value 'false'
                 should be returned for this node.";
              reference
                "RFC 6933: Entity MIB (Version 4) -
                           entPhysicalIsFRU";
            }
            leaf-list uri {
              type inet:uri;
              config false;
              description
                "This node contains identification information about
                 the component.";
              reference
                "RFC 6933: Entity MIB (Version 4) - entPhysicalUris";
            }
            container chassis-specific-info {
              when
                "derived-from-or-self(../nwi:class,
                'ianahw:chassis')";
              config false;
              description
                "This container contains some attributes belong to
                 chassis only.";
            }
            container slot-specific-info {
              when
                "derived-from-or-self(../nwi:class,
                'ianahw:container')";
              config false;
              description
                "This container contains some attributes belong to
                 slot only.";
            }
            container board-specific-info {
              when
                "derived-from-or-self(../nwi:class,
                'ianahw:module')";
              config false;
              description
                "This container contains some attributes belong to
                 board only.";
            }
            container port-specific-info {
              when
                "derived-from-or-self(../nwi:class, 'ianahw:port')";
              config false;
              description
                "This container contains some attributes belong to
                 port only.";
            }
            container transceiver-module-specific-info {
              when
                "derived-from-or-self(../nwi:class,
                'nwi:transceiver-module')";
              config false;
              description
                "This container contains some attributes belong to
                 transceivers modules only.";
              container breakout-channels {
                presence
                  "When present, it indicates that port breakout is
                   supported.";
                description
                  "Top level container for the list of breakout
                   channels supported by the transceivers module.";
                list breakout-channel {
                  key "channel-id";
                  leaf channel-id {
                    type uint8;
                    description
                      "An identifier that uniquely identifies the
                       breakout channel within the transceiver
                       module.";
                  }
                  description
                    "The list of breakout channels supported by the
                     transceivers module.";
                }
              }
            }
          }
        }
      }
    }
  }
}
