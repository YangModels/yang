module lisp {
  namespace "urn:ietf:params:xml:ns:yang:lisp";
  prefix lisp;

  import ietf-inet-types {
    prefix inet;
  }
  import lisp-address-types {
    prefix lcaf;
  }

  organization "IETF LISP (Locator/ID Separation Protocol) Working Group";
  contact
    "lisp@ietf.org";
  description
    "This YANG module defines the generic configuration
     data for LISP. The module can be extended by vendors
     to define vendor-specific LISP configuration
     parameters and policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.

    ";

  revision 2015-03-23 {
    description
      "Initial revision.";
  }

  typedef interface-name {
    description
      "Name of a device interface";
    type string;
  }

  typedef map-reply-action {
    description
      "Defines the lisp map-cache ACT type";
    type enumeration {
      enum "no-action" {
        value 0;
      }
      enum "natively-forward" {
        value 1;
      }
      enum "send-map-request" {
        value 2;
      }
      enum "drop" {
        value 3;
      }
    }
  }

  typedef eid-id {
    type string;
  }

  typedef instance-id-type {
    type uint32 {
      range "0..16777214";
    }
  }

  typedef auth-key-type {
    type enumeration {
      enum "none" {
        value 0;
      }
      enum "hmac-sha-1-96" {
        value 1;
      }
      enum "hmac-sha-256-128" {
        value 2;
      }
    }
  }

  feature itr {
    description
      "ITR operation supported";
  }

  feature etr {
    description
      "ETR operation supported";
  }

  feature proxy-itr {
    description
      "PITR operation supported";
  }

  feature proxy-etr {
    description
      "PETR operation supported";
  }

  feature map-server {
    description
      "MS operation supported";
  }

  feature map-resolver {
    description
      "MR operation supported";
  }

  grouping locators {
    list rloc {
      key "name";
      leaf name {
        type string;
      }
      choice address-type {
        case interface-address {
          leaf interface {
            type interface-name;
          }
        }
        case lisp-address {
          container locator-address {
            uses lcaf:lisp-address;
          }
        }
      }
      leaf priority {
        type uint8;
      }
      leaf weight {
        type uint8;
      }
      leaf multicast-priority {
        type uint8;
      }
      leaf multicast-weight {
        type uint8;
      }
    }
  }

  grouping mappings {
    list mapping {
      key "id";
      leaf id {
        type eid-id;
      }
      container eid {
        uses lcaf:lisp-address;
      }
      leaf ttl {
        type uint32;
      }
      choice locator-list {
        case negative-mapping {
          leaf map-reply-action {
            type map-reply-action;
          }
        }
        case positive-mapping {
          container rlocs {
            uses locators;
          }
        }
        default "positive-mapping";
      }
    }
  }

  container itr-cfg {
    if-feature itr;
    presence "LISP ITR operation enabled";
    config true;
    container rloc-probing {
      presence "RLOC probing active";
      leaf interval {
        type uint16;
        units "seconds";
        description
          "Interval in seconds";
      }
      leaf retries {
        type uint8;
        description
          "Number of retries";
      }
      leaf retries-interval {
        type uint16;
        units "seconds";
        description
          "Interval in seconds between retries";
      }
    }
    container itr-rlocs {
      description
        "List of RLOCs of the ITR included in Map-Requests";
      list itr-rloc {
        key "id";
        leaf id {
          type string;
        }
        container address {
          uses lcaf:lisp-address;
        }
      }
    }
    container local-eids {
      list local-eid {
        min-elements 1;
        key "id";
        leaf id {
          type eid-id;
        }
        container eid-address {
          uses lcaf:lisp-address;
        }
      }
    }
    container map-resolvers {
      list map-resolver {
        min-elements 1;
        key "id";
        leaf id {
          type eid-id;
        }
        container eid-address {
          uses lcaf:lisp-address;
        }
        leaf-list map-resolver-address {
          type inet:ip-address;
        }
      }
    }
    container proxy-etrs {
      list proxy-etr {
        key "id";
        leaf id {
          type eid-id;
        }
        container eid-address {
          uses lcaf:lisp-address;
        }
        leaf-list proxy-etr-address {
          type inet:ip-address;
        }
      }
    }
    container map-cache {
      uses mappings {
        augment "mapping" {
          leaf static {
            description
              "A configured mapping is a static mapping. If the mapping
               is learned, it is operational data and static is false.";
            type boolean;
            default "true";
          }
        }
      }
    }
  }
  container etr-cfg {
    if-feature etr;
    presence "LISP ETR operation enabled";
    config true;
    container local-eids {
      list local-eid {
        min-elements 1;
        key "id";
        leaf id {
          type eid-id;
        }
        container eid-address {
          uses lcaf:lisp-address;
        }
        container map-servers {
          list map-server {
            key "address";
            leaf address {
              type inet:ip-address;
            }
            leaf auth-key {
              type string;
            }
            leaf auth-key-type {
              type auth-key-type;
            }
          }
        }
        container rlocs {
          uses locators;
        }
        leaf record-ttl {
          type uint32;
        }
        leaf want-map-notify {
          type boolean;
        }
        leaf proxy-reply {
          type boolean;
        }
        leaf registration-interval {
          units "seconds";
          type uint16;
          default "60";
        }
      }
    }
  }
  container map-server-cfg {
    if-feature map-server;
    presence "LISP Map Server operation enabled";
    config true;
    container sites {
      list site {
        key "site-id";
        leaf site-id {
          type uint64;
        }
        container devices {
          list device {
            key "device-id";
            leaf device-id {
              type uint64;
            }
            container auth-key {
              leaf auth-key-value {
                description
                  "clear text authentication key";
                type string;
              }
              leaf auth-key-type {
                type auth-key-type;
              }
            }
            container eids {
              list eid {
                key "id";
                leaf id {
                  type eid-id;
                }
                container eid-address {
                  uses lcaf:lisp-address;
                }
                leaf more-specifics-accepted {
                  type boolean;
                }
                leaf mapping-expiration-timeout {
                  type int16;
                  units "seconds";
                  default "180";
                }
              }
            }
          }
        }
      }
    }
    container registered-mappings {
      uses mappings;
    }
    choice mapping-system {
      mandatory true;
      container ddt-mapping-system {
        presence "DDT Mapping System in use";
        leaf-list ddt-root {
          type inet:ip-address;
        }
        container authoritative-eids {
          list authoritative-eid {
            key "id";
            leaf id {
              type eid-id;
            }
            container eid-address {
              uses lcaf:lisp-address;
            }
          }
        }
      }
      container alt-mapping-system {
        presence "ALT Mapping System in use";
      }
    }
  }
  container map-resolver-cfg {
    if-feature map-resolver;
    presence "LISP Map-Resolver operation enabled";
    config true;
    choice mapping-system {
      mandatory true;
      container ddt-mapping-system {
        presence "DDT Mapping System in use";
        leaf-list ddt-root {
          type inet:ip-address;
        }
      }
      container alt-mapping-system {
        presence "ALT Mapping System in use";
      }
    }
  }
  container proxy-itr-cfg {
    if-feature proxy-itr;
    presence "LISP PITR operation enabled";
    config true;
    container servicing-eids {
      list eid {
        key "id";
        leaf id {
          type eid-id;
        }
        container eid-address {
          uses lcaf:lisp-address;
        }
      }
    }
    container map-resolvers {
      list map-resolver {
        key "id";
        leaf id {
          type eid-id;
        }
        container eid-address {
          uses lcaf:lisp-address;
        }
        leaf-list map-resolver {
          min-elements 1;
          type inet:ip-address;
        }
      }
    }
    container map-cache {
      uses mappings;
    }
  }
  container proxy-etr-cfg {
    if-feature proxy-etr;
    presence "LISP PETR operation enabled";
    config true;
    container servicing-eids {
      list eid {
        key "id";
        leaf id {
          type eid-id;
        }
        container eid-address {
          uses lcaf:lisp-address;
        }
      }
    }
  }
}
