module ietf-ucpe-interfaces-ports {
 namespace "urn:ietf:params:xml:ns:yang:ietf-ucpe-interfaces-ports";
 prefix ucpe-interface;

 import ietf-ucpe {
   prefix ietf-nfv;
 }
 import ietf-ucpe-interfaces {
   prefix ietf-if;
 }

 organization "SFR";
 contact
   "Dmytro Shytyi
    EMail:ietf.dmytro@shytyi.net";
 description
    "This is a Network Function Virtualization (NFV) YANG
    model for interfaces.

    Copyright (c) 2019 IETF Trust and the persons identified as
    authors of the code.  All rights reserved.

    Redistribution and use in source and binary forms, with or
    without modification, is permitted pursuant to, and subject to
    the license terms contained in, the Simplified BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.";

 revision 2019-10-19 {
   description
     "Yang model is cleaned";
   reference "draft-shytyi-opsawg-vysm-04";
 }
 revision 2019-10-03 {
   description
     "Initial revision.";
   reference "draft-shytyi-opsawg-vysm-01";
 }
 augment "/ietf-nfv:ucpe/ietf-if:interfaces/ietf-if:interface" {
   list ports {
     key "port";
     leaf port {
       type string;
       description
         "Name of the connector";
     }
     leaf link {
       type leafref {
         path "../../../../ietf-nfv:links/ietf-nfv:link";
       }
       description
         "Link that is connected to the port
          via connector";
     }
     description
       "Set of the connectors the physical
        interface has";
   }
   description
     "ucpe ports of the interface";
 }
}
