module tunnel64 {
    namespace "urn:ietf:params:xml:ns:yang:ietf-tunnel64";
    prefix tunnel64;

    import ietf-inet-types {
         prefix inet;
        }

    import ietf-interfaces{
         prefix if;
       }
    organization "Internet Area Working Group (intarea)";
    contact
    "WG List:  <mailto:intarea@ietf.org>

     Author:   Guangying Zheng
               <mailto:zhengguangying@huawei.com>";

  description
    "This module contains a collection of YANG definitions
     of tunneling for IPv6 configuration.";

  revision 2015-05-21 {
    description
      "Initial Revision";
    reference
      "This model references RFC2893,RFC3056,RFC4214.";
  }

  feature tunneling-for-IPv6 {
    description
      "This feature represents the feeture of tunneling for IPv6.";
  }

    container tunneling-for-IPv6 {

    list Tunnel{

            key tunnel-name;
            min-elements 0;
             max-elements unbounded;

             leaf tunnel-name {
                config true;
                type string;
            }
            leaf tunnel-interface-name {
                config false;
                type if:interface-ref;

            }
            leaf tunnel-type {
                config true;
                type enumeration {
                    enum manual {
                        value 0;
                        description "a manual IPv6 tunnel";
                    }
                    enum 6to4 {
                        value 1;
                        description "a 6to4 tunnel";
                    }
                    enum auto-tunnel {
                        value 2;
                        description "an IPv4-compatible IPv6 tunnel";
                    }
                }
            }
            leaf source-ip-address {
                config true;
                type inet:ipv4-address;

            }
            leaf source-interface {
                config true;
                type if:interface-ref;

            }
            leaf destination-ip-address {
                config true;
                type inet:ipv4-address;

            }
        }

    }
}
