module ietf-bgp-srv6-services {
  yang-version 1.1;
  namespace "urn:ietf:params:xml:ns:yang:ietf-bgp-srv6-services";
  // replace with IANA namespace when assigned
  prefix bgp-srv6-svc ;

  import ietf-inet-types {
    prefix "inet";
    reference "RFC 6991: Common YANG Data Types";
  }

  import ietf-routing-types {
    prefix "rt-types";
    reference
      "RFC 8294: Common YANG Data Types for the Routing Area";
  }

  import ietf-routing {
    prefix "rt";
    reference
      "RFC 8349: A YANG Data Model for Routing Management (NMDA
       version)";
  }

  import ietf-srv6-types {
    prefix srv6-types;
    reference "RFC XXXX: YANG Data Model for SRv6";
    // RFC Editor: replace XXXX with actual RFC number and remove
    // this note
  }

  import ietf-srv6-base {
    prefix srv6;
  }

  import ietf-bgp {
    prefix bgp;
  }

  organization
     "IETF BESS Working Group";

  contact
     "BESS working group - bess@ietf.org";

  description
    "This YANG module defines a data model to configure and
     manage SRv6 extensions in BGP.

     Terms and Acronyms

     AF : Address Family

     BGP (bgp) : Border Gateway Protocol

     EVPN: Ethernet VPN

     SR : Segment Routing

     SID : Segment Identifier

     SRv6 : Segment Routing with IPv6 Data plane

     VPN : Virtual Private Network

     VRF : Virtual Routing and Forwarding

    ";

  revision 2019-07-08 {
    description
      "Initial revision" ;
    reference "";
  }

  // Sid type union
  typedef sid-type {
    type union {
      type rt-types:mpls-label;
      type srv6-types:srv6-sid;
    }
    description "Type definition for Segment Identifier. This is
                 a union type which can be either a SR MPLS SID in the
                 form of a label,  or a SRv6 SID in the form of
                 an IPv6 address.";
    reference "TBD";
  }

  grouping route-key-leafs {
    description "Grouping for key leafs identifying a route";
    leaf prefix {
      type union {
         type inet:ip-prefix;
         type string;
      }
      description "BGP Prefix. This is a temp definition to
                  cover ip-prefix and other NLRI formats.
                  Import the type once defined in base
                  BGP RIB model";
    }
    leaf neighbor {
      type inet:ip-address;
      description "BGP Neighbor";
    }
    leaf add-path-id {
      type uint32;
      description "Add-path ID";
    }
  }

  grouping common-bgp-route-grouping {
    description "BGP route list" ;
    container routes {
      config false;
      description "BGP Route in local RIB";
      list route {
        key "prefix neighbor add-path-id";
        description "BGP route list";
        uses route-key-leafs;
      }
    }
  }

  grouping common-bgp-vpn-route-grouping {
    description "BGP route list" ;
    container routes {
      config false;
      description "BGP VPN Route in local RIB";
      list route {
        key "rd prefix neighbor add-path-id";
        description "Route List";

        leaf rd {
          type rt-types:route-distinguisher;
          description "Route Distinguisher";
        }
        uses route-key-leafs;
      }
    }
  }

  //
  //  SRv6 extensions related Groupings
  //

  grouping srv6-grouping {
    description "SRv6 container";

    container segment-routing {
      description "Segment-routing parameters";

      container srv6 {
        description "Segment-routing with IPv6 dataplane (SRv6) parameters";
      }
    }
  }

  grouping srv6-locator-grouping {
    description "SRv6 locator ref";
    leaf locator {
      type leafref {
        path "/rt:routing/srv6:srv6/srv6:locators/srv6:locator/srv6:name";
      }
      description "Reference to an SRv6 Locator";
    }
  }

  grouping segment-routing-srv6-locator-grouping {
    description
      "An absolute reference to an SRv6 locator";

    container segment-routing {
      description "Segment-routing parameters";

      container srv6 {
        description "Segment-routing with IPv6 dataplane (SRv6) parameters";
        uses srv6-locator-grouping;
      }
    }
  }

  // SRv6 VPN Sid allocation mode
  grouping srv6-sid-mode {
    description "SRv6 VPN SID allocation mode";
    leaf sid-alloc-mode {
      type enumeration {
        enum per-ce {
          description "Allocate SRv6 SID per CE";
        }
        enum per-route {
          description "Allocate SRv6 SID per prefix";
        }
        enum per-vpn {
          description "Allocate SRv6 SID per VPN";
        }
      }
      description "BGP SRv6 SID allocation model";
    }
  }

  grouping srv6-attr-sid-info {
    description "SRv6 SID info per route";
    container srv6 {
      description "Per Route SRv6 parameters";
      list received-sids {
        key "received-sid";
        description "List of received SRv6 SIDs";
        leaf received-sid {
          type srv6-types:srv6-sid;
          description "Received SID";
        }
      }
      list local-sids {
        key "local-sid";
        description "List of local SRv6 SIDs";
        leaf local-sid {
          type srv6-types:srv6-sid;
          description "Local SID";
        }

        uses srv6-locator-grouping;
      }
    }
  }
  //
  // BGP Specific Paramters
  //

  // SRv6 Loc designation
  augment "/rt:routing/rt:control-plane-protocols/rt:control-plane-protocol/" +
          "bgp:bgp/bgp:global" {
    description
      "Augment BGP global";
    uses segment-routing-srv6-locator-grouping;
  }

  // Augment AF with route list
  augment "/rt:routing/rt:control-plane-protocols/rt:control-plane-protocol/" +
          "bgp:bgp/bgp:global/bgp:afi-safis/bgp:afi-safi/bgp:ipv4-unicast" {
    description
      "Augment BGP SAFI route";
    uses common-bgp-route-grouping;
  }
  augment "/rt:routing/rt:control-plane-protocols/rt:control-plane-protocol/" +
          "bgp:bgp/bgp:global/bgp:afi-safis/bgp:afi-safi/bgp:ipv6-unicast" {
    description
      "Augment BGP SAFI route";
    uses common-bgp-route-grouping;
  }
  augment "/rt:routing/rt:control-plane-protocols/rt:control-plane-protocol/" +
          "bgp:bgp/bgp:global/bgp:afi-safis/bgp:afi-safi/bgp:l3vpn-ipv4-unicast" {
    description
      "Augment BGP SAFI route";
    uses common-bgp-vpn-route-grouping;
  }
  augment "/rt:routing/rt:control-plane-protocols/rt:control-plane-protocol/" +
          "bgp:bgp/bgp:global/bgp:afi-safis/bgp:afi-safi/bgp:l3vpn-ipv6-unicast" {
    description
      "Augment BGP SAFI route";
    uses common-bgp-vpn-route-grouping;
  }
  /* TODO
  augment "/rt:routing/rt:control-plane-protocols/rt:control-plane-protocol/" +
          "bgp:bgp/bgp:global/bgp:afi-safis/bgp:afi-safi/bgp:l2vpn-evpn" {
    description
      "Augment BGP SAFI route";
    uses common-bgp-vpn-route-grouping;
  }
  */

  // SRv6 VPN SID allocation mode configuration.
  augment "/rt:routing/rt:control-plane-protocols/rt:control-plane-protocol/" +
          "bgp:bgp/bgp:global/bgp:afi-safis/bgp:afi-safi/bgp:ipv4-unicast" {
    description
      "Augment BGP global IPv4 unicast AF mode
       to add SR specific parameters";
    container segment-routing {
      description "Segment Routing specific parameters";
      container srv6 {
        description "SRv6 specific parameters";
        uses srv6-locator-grouping;
        uses srv6-sid-mode;
      }
    }
  }

  augment "/rt:routing/rt:control-plane-protocols/rt:control-plane-protocol/" +
          "bgp:bgp/bgp:global/bgp:afi-safis/bgp:afi-safi/bgp:ipv6-unicast" {
    description
      "Augment BGP global IPv6 unicast AF mode
       to add SR specific parameters";
    container segment-routing {
      description "Segment Routing specific parameters";
      container srv6 {
        description "SRv6 specific parameters";
        uses srv6-locator-grouping;
        uses srv6-sid-mode;
      }
    }
  }

  augment "/rt:routing/rt:control-plane-protocols/rt:control-plane-protocol/" +
          "bgp:bgp/bgp:global/bgp:afi-safis/bgp:afi-safi/bgp:l3vpn-ipv4-unicast" {
    description
      "Augment BGP L3VPN IPv4 unicast AF mode
       to add SR specific parameters";
    container segment-routing {
      description "Segment Routing specific parameters";
      container srv6 {
        description "SRv6 specific parameters";
        uses srv6-locator-grouping;
        uses srv6-sid-mode;
      }
    }
  }

  augment "/rt:routing/rt:control-plane-protocols/rt:control-plane-protocol/" +
          "bgp:bgp/bgp:global/bgp:afi-safis/bgp:afi-safi/bgp:l3vpn-ipv6-unicast" {
    description
      "Augment BGP L3VPN IPv6 unicast AF mode
       to add SR specific parameters";
    container segment-routing {
      description "Segment Routing specific parameters";
      container srv6 {
        description "SRv6 specific parameters";
        uses srv6-locator-grouping;
        uses srv6-sid-mode;
      }
    }
  }

  // SRv6 local and remote sids per route.
  augment "/rt:routing/rt:control-plane-protocols/rt:control-plane-protocol/" +
          "bgp:bgp/bgp:global/bgp:afi-safis/bgp:afi-safi/bgp:ipv4-unicast/" +
          "bgp-srv6-svc:routes/bgp-srv6-svc:route" {
    description
      "Augment AF route with SRv6 SID info";
    uses srv6-attr-sid-info;
  }
  augment "/rt:routing/rt:control-plane-protocols/rt:control-plane-protocol/" +
          "bgp:bgp/bgp:global/bgp:afi-safis/bgp:afi-safi/bgp:ipv6-unicast/" +
          "bgp-srv6-svc:routes/bgp-srv6-svc:route" {
    description
      "Augment AF route with SRv6 SID info";
    uses srv6-attr-sid-info;
  }

  augment "/rt:routing/rt:control-plane-protocols/rt:control-plane-protocol/" +
          "bgp:bgp/bgp:global/bgp:afi-safis/bgp:afi-safi/bgp:l3vpn-ipv4-unicast/" +
          "bgp-srv6-svc:routes/bgp-srv6-svc:route" {
    description
      "Augment AF route with SRv6 SID info";
    uses srv6-attr-sid-info;
  }

  augment "/rt:routing/rt:control-plane-protocols/rt:control-plane-protocol/" +
          "bgp:bgp/bgp:global/bgp:afi-safis/bgp:afi-safi/bgp:l3vpn-ipv6-unicast/" +
          "bgp-srv6-svc:routes/bgp-srv6-svc:route" {
    description
      "Augment AF route with SRv6 SID info";
    uses srv6-attr-sid-info;
  }

/* TODO
  augment "/rt:routing/rt:control-plane-protocols/rt:control-plane-protocol/" +
          "bgp:bgp/bgp:global/bgp:afi-safis/bgp:afi-safi/bgp:l2vpn-evpn/" +
          "bgp-srv6-svc:routes/bgp-srv6-svc:route" {
    description
      "Augment AF route with SRv6 SID info";
    uses srv6-attr-sid-info;
  }
  */

}
