module ietf-i2nsf-reg-interface {
 yang-version 1.1;

 namespace "urn:ietf:params:xml:ns:yang:ietf-i2nsf-reg-interface";

 prefix nsfreg;

 import ietf-inet-types {
  prefix inet;
  reference "RFC 6991";
 }
 import ietf-i2nsf-capability {
  prefix capa;
  reference "draft-ietf-i2nsf-capability-data-model-05";
 }

 organization
  "IETF I2NSF (Interface to Network Security Functions)
   Working Group";

 contact
  "WG Web: <http://tools.ietf.org/wg/i2nsf>
   WG List: <mailto:i2nsf@ietf.org>

   Editor: Sangwon Hyun
   <mailto:shyun@mju.ac.kr>
   Editor: Jaehoon Paul Jeong
   <mailto:pauljeong@skku.edu>
   Editor: Taekyun Roh
   <mailto:tkroh0198@skku.edu>
   Editor: Sarang Wi
   <mailto:dnl9795@skku.edu>
   Editor: Jung-Soo Park
   <mailto:pjs@etri.re.kr>";

 description
  "This module defines a YANG data model for I2NSF
   registration interface.

   Copyright (c) 2020 IETF Trust and the persons
   identified as authors of the code. All rights reserved.

   Redistribution and use in source and binary forms, with or
   without modification, is permitted pursuant to, and subject
   to the license terms contained in, the Simplified BSD License
   set forth in Section 4.c of the IETF Trust's Legal Provisions
   Relating to IETF Documents
   (http://trustee.ietf.org/license-info).

   This version of this YANG module is part of RFC XXXX; see
   the RFC itself for full legal notices.";

 revision "2020-01-21" {
  description "Initial revision";
  reference
   "RFC XXXX: I2NSF Registration Interface YANG Data Model";
 }

 container nsf-registrations {
  description
   "Information of an NSF that DMS registers
    to Security Controller";
  list nsf-information {
   key "capability-name";
   description
    "Required information for registration";
   leaf capability-name {
    type string;
    mandatory true;
    description
     "Unique name of this registered NSF";
   }
   container nsf-capability-info {
    description
     "Capability description of this NSF";
      uses nsf-capability-info;
   }
   container nsf-access-info {
    description
     "Network access information of this NSF";
     uses nsf-access-info;
   }
  }
 }

 grouping nsf-performance-capability {
  description
   "Description of the performance capabilities
    of an NSF";

  container processing {
   description
    "Processing power of an NSF in the unit of GHz (gigahertz)";

   leaf processing-average {
    type uint16;
    description
     "Average processing power";
   }
   leaf processing-peak {
    type uint16;
    description
     "Peak processing power";
   }
  }
  container bandwidth {
   description
    "Network bandwidth available on an NSF
     in the unit of Mbps (megabits per second)";

   container outbound {
    description
     "Outbound network bandwidth";
    leaf outbound-average {
     type uint32;
     units "Mbps";
     description
      "Average outbound bandwidth";
    }
    leaf outbound-peak {
     type uint32;
     units "Mbps";
     description
      "Peak outbound bandwidth";
    }
   }
   container inbound {
    description
     "Inbound network bandwidth";
    leaf inbound-average {
     type uint32;
     units "Mbps";
     description
      "Average inbound bandwidth";
    }
    leaf inbound-peak {
     type uint32;
     units "Mbps";
     description
      "Peak inbound bandwidth";
    }
   }
  }
 }

 grouping nsf-capability-info {
  description
   "Capability description of an NSF";
  container security-capability {
   description
    "Description of the security capabilities of an NSF";
     uses "capa:nsf-capabilities";
   reference "draft-ietf-i2nsf-capability-data-model-05";
  }
  container performance-capability {
   description
    "Description of the performance capabilities of an NSF";
   uses nsf-performance-capability;
  }
 }

 grouping nsf-access-info {
  description
   "Information required to access an NSF";
  leaf capability-name {
   type string;
   description
     "Unique name of this NSF's capability";
  }
  leaf ip {
   type inet:ip-address;
   description
    "IPv4/IPv6 address of this NSF";
  }
  leaf port {
   type inet:port-number;
   description
    "Port available on this NSF";
  }
 }

 rpc nsf-capability-query {
  description
   "Description of the capabilities that the
    Security Controller requests to the DMS";
  input {
   container query-nsf-capability {
    description
     "Description of the capabilities to request";
    uses "capa:nsf-capabilities";
    reference
     "draft-ietf-i2nsf-capability-data-model-05";
    }
  }
  output {
   container nsf-access-info {
    description
     "Network access information of an NSF
      with the requested capabilities";
    uses nsf-access-info;
   }
  }
 }
}
