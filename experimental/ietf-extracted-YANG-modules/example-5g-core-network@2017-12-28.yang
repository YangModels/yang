module example-5g-core-network {

   yang-version "1.1";

  /*** NAMESPACE / PREFIX DEFINITION ***/
   namespace "urn:example:5g-core-network";
   prefix "core-net";

  /*** LINKAGE (IMPORTS / INCLUDES) ***/
   import ietf-yang-schema-mount {
     prefix yangmnt;
     reference "draft-ietf-netmod-schema-mount: YANG Schema Mount";
   }

  /*** META INFORMATION ***/
   organization
        "Ericsson (China) Communications Company Ltd.
         Ericsson Tower, No. 5 Lize East Street,
         Chaoyang District Beijing 100102, P.R. China";

   contact
        "Editor:   Chin Chen
                   <mailto:chin.chen@ericsson.com>";

   description
        "This YANG module provide the example on 5G core network
structure.";

   revision 2017-12-28 {
     description
       "Initial revision.";
     reference
          "RFC XXXX: A YANG Data Model for 5G Core Network
Structure.";
   }

   /*** TYPE DEFINITIONS ***/

   identity network-function-type {
       description
           "Base identity for derivation of network functions";
   }

   identity nssf  {
      base network-function-type;
      description
         "Network Slice Selection Function";
      reference
         "";
   }

   identity nef  {
      base network-function-type;
      description
         "Network Exposure Function";
      reference
         "";
   }

   identity nrf  {
      base network-function-type;
      description
         "NF Repository Function";
      reference
         "";
   }

   identity pcf  {
      base network-function-type;
      description
         "Policy Control function";
      reference
         "";
   }

   identity udm  {
      base network-function-type;
      description
         "Unified Data Management";
      reference
         "";
   }

   identity ausf  {
      base network-function-type;
      description
         "Authentication Server Function";
      reference
         "";
   }

   identity amf  {
      base network-function-type;
      description
         "Core Access and Mobility Management Function";
      reference
         "";
   }

   identity smf  {
      base network-function-type;
      description
         "Session Management Function";
      reference
         "";
   }

   identity upf  {
      base network-function-type;
      description
         "User Plane Function";
      reference
         "";
   }

  /*** SCHEMA DEFINITIONS ***/
   container ietf-yang-library {
     description
       "YANG Module Library as defined in
        draft-ietf-netconf-yang-library";
   }

   container interfaces {
     description
      "Interface list as defined by RFC7223/RFC7224";
   }

   container hardware {
     description
       "Hardware / vendor-specific data relevant to the platform.
       This container is an anchor point for platform-specific
       configuration and operational state data.  It may be further
       organized into chassis, line cards, ports, etc.  It is
       expected that vendor or platform-specific augmentations
       would be used to populate this part of the device model";
   }

   container system-management {
       description
         "System management for physical or virtual device.";
   }

   container virtual-network-functions {
      description
         "Container for list of configured virtual network
           functions.";
      list virtual-network-function {
         key "name";
         description
            "Lisf for instance of virtual network function";

         leaf name {
            type string;
            description
               "The virtual network function name.";
         }

         leaf enable {
            type boolean;
            description
               "Enable the virtual network fucntion.";
         }

         leaf description {
            type string;
            description
               "Describe the virtual network fucntion.";
         }

         container network-functions {
            description
               "Container for list of configured network
                 functions.";
            list network-function {
               key "name";
               description
                   "Lisf for instance of network function";

               leaf name {
                   type string;
                   description
                       "The network function name.";
               }

               leaf type {
                   type identityref {
                       base network-function-type;
                   }
                   mandatory true;
                   description
                       "The network function type  e.g., UPF, SMF,
AMF etc.";
               }

               leaf enable {
                   type boolean;
                   description
                       "Enable the network fucntion.";
               }

               leaf description {
                   type string;
                   description
                       "Describe the network fucntion.";
               }
               choice root {
                  description
                    "Well known mount points.";
                  case upf-root {
                     description
                       "Container for mount point.";
                     yangmnt:mount-point "upf-root" {
                       description
                         "Root models that support network function
UPF.";
                     }
                  }
                  case amf-root {
                     description
                       "Container for mount point.";
                     yangmnt:mount-point "amf-root" {
                       description
                         "Root models that support network function
AMF.";
                     }
                  }
                  case smf-root {
                     description
                       "Container for mount point.";
                     yangmnt:mount-point "smf-root" {
                        description
                         "Root models that support network function
SMF.";
                     }
                  }
               }
            }
         }
      }
   }
}
