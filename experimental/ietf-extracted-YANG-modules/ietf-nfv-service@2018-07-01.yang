module ietf-nfv-service {

  namespace "urn:ietf:params:xml:ns:yang:nfv-service";
  prefix nfv-service;
        organization
                "Ecole Polytechnique/Telecom ParisTech/SFR";
        contact
                "Dmytro Shytyi
                EMail:ietf.dmytro@shytyi.net";
        description
                "This is a Network Function Virtualization (NFV) YANG
                service model.";
        revision 2018-07-01 {
                description
                "Initial revision.";
                reference
        "draft-shytyi-netmod-vysm-00";
        }

  list virtualization {
    key name;
    leaf name {
                type string;
                description "Name of the instance of the service";
    }

    // may replace this with other ways of refering to the devices.
    leaf-list device {
                type string;
                description "List of the devices in available in the
                orchestrator";
    }

  list links{
                key link;
                leaf link{
                        type string;
                description "Name of the virtual link from the pool
                of the links";
                }
          description "Pool of the virtual links that connect VMs and
          Interfaces";
        }
        list interfaces{
                key interface;
                leaf interface{
                        type string;
                         description "Name of physical interface";
                }
                list ports{
                        key port;
                        leaf port{
                                type string;
                        description "Name of the connector";
                        }
                        leaf link{
                                type leafref{
                                        path "../../../links/link";
                                }
                          description "Link that is connected to
                          the port via connector";
                        }
                        description "Set of the connectors the
                        physical interface has";
                }
                description "Set of physical interfaces";
        }
        list switches{
          key switch;
                leaf switch{
                        type string;
                        description "Name of the forwarding domain";
                }
                list ports{
                        key port;
                        leaf port{
                                type string;
                                description "Name of the connector";
                        }
                        leaf name{
                          type string;
                                description "Name of the subconnector";
                        }
                        leaf link{
                                type leafref{
                                        path "../../../links/link";
                                }
                        description "Link that is connected to the
                        switch via port";
                        }
                  description "Set of the connectors the
                  forwarding domain has";
                }
                description "Set of the forwarding domains";

        }

        list vms{
                key vm;
                leaf vm{
                        type string;
                description "Name of the Virtual Machine";
                }
                list ports{
                        key port;
                        leaf port{
                                type string;
                                description "Name of the connector";
                        }
                        leaf name{
                                type string;
                                description "Name of the subconnector";
                        }
                        leaf link{
                                type leafref{
                                        path "../../../links/link";
                                }
                                description "Link that connects the
                                VM with a switch or     Interface
                                via connector";
                        }
                  description "Set of Virtual Machine connectors";
                }

                leaf ram{
                        type string;
                        description "Amount of memory to allocate for
                        the Guest OS";
                }
                leaf cpu{
                        type string;
                        description "Amount of cpus to allocate for the
                        Guest OS";
                }
                list storages{
                        key id;
                        leaf id{
                                type string;
                                description "Name of the Storage";
                        }
                        leaf location{
                                type string;
                                description "External location where
                                the image is saved.";
                        }
                        description "Virtual storge of the image
                        for the Virtual Machine";
                }
                description "Set of the Virtual Machines configured
                on the universal Customer-Premises Equipment";
        }
        description "This is an RFS skeleton service";
  }
  }
