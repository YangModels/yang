submodule sfc-topology {
  belongs-to sfc-control-planes {
    prefix sfc-st;
  }
  organization "ETRI.";
  contact
  "M-K. Shin mkshin@etri.re.kr
   M-J Choi mjchoi@kangwon.ac.kr";
  description
  "This module shows the connectivity map of currently working
   SFCs, SFPs and SFIs.";
  revision 2015-10-15 {
     reference
     "draft-shin-sfc-control-plane-yang-00 -
     Yang Data Model for Service Function Chaining Control Plane";
  }
  container sfc-topology {
    description
    "This container shows the connectivity map of
     currently working SFCs, SFPs and SFIs. ";
    leaf name {
      type string;
      description
      "The name of service function chain or service function
       path or service function instances.";
    }
    list lists-of-sf-node {
      key name;
      description
      "A list of service functions that compose the service
       chain.";
      leaf name {
        type string;
        description
        "A list of service functions that compose the service
         chain.";

      }
      leaf order {
        type uint8;
        description
        "The order of the service functions.";

      }
    }
  }
  rpc show-sfc-topology {
    description
    "Display the topology of service function chain.";
    input {
      leaf sfc-name {
        type string;
        description
        "The name of service function chain.";
      }
    }
    output {
      list lists-of-sf-node {
        key name;
        description
        "A list of service functions that compose the service
         chain.";
        leaf name {
          type string;
          description
          "A list of service functions that compose the service
           chain.";
        }
        leaf order {
          type uint8;
          description
          "The order of the service functions.";
         }
      }
   }
}
}
