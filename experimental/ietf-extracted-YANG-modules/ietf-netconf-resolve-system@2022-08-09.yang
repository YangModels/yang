module ietf-netconf-resolve-system {
   yang-version 1.1;
   namespace "urn:ietf:params:xml:ns:yang:ietf-netconf-resolve-system";
   prefix ncrs;

   import ietf-netconf {
     prefix nc;
     reference
       "RFC 6241: Network Configuration Protocol (NETCONF)";
   }

   import ietf-netconf-nmda {
     prefix ncds;
     reference
       "RFC 8526: NETCONF Extensions to Support the Network
        Management Datastore Architecture";
   }
   organization
     "IETF NETMOD (Network Modeling) Working Group";

   contact
     "WG Web:   <http://tools.ietf.org/wg/netmod/>
      WG List:  <mailto:netmod@ietf.org>
      Author: Qiufang Ma
              <mailto:maqiufang1@huawei.com>
      Author: Qin Wu
              <mailto:bill.wu@huawei.com>
      Author: Chong Feng
              <mailto:frank.fengchong@huawei.com>";

   description
     "This module defines an extension to the NETCONF protocol
      that allows the NETCONF client to control whether the server
      is allowed to copy referenced system configuration
      automatically without the client doing so explicitly.

       Copyright (c) 2022 IETF Trust and the persons identified
       as authors of the code. All rights reserved.

       Redistribution and use in source and binary forms, with
       or without modification, is permitted pursuant to, and
       subject to the license terms contained in, the Revised
       BSD License set forth in Section 4.c of the IETF Trust's
       Legal Provisions Relating to IETF Documents
       (https://trustee.ietf.org/license-info).

       This version of this YANG module is part of RFC HHHH
       (https://www.rfc-editor.org/info/rfcHHHH); see the RFC
       itself for full legal notices.

       The key words 'MUST', 'MUST NOT', 'REQUIRED', 'SHALL',
       'SHALL NOT', 'SHOULD', 'SHOULD NOT', 'RECOMMENDED',
       'NOT RECOMMENDED', 'MAY', and 'OPTIONAL' in this document
       are to be interpreted as described in BCP 14 (RFC 2119)
       (RFC 8174) when, and only when, they appear in all
       capitals, as shown here.";

   revision 2022-08-09 {
     description
       "Initial version.";
     reference
       "RFC XXXX: System-defined Configuration";
   }

 augment /nc:edit-config/nc:input {
   description
     "Allows the server to automatically configure
      referenced system configuration to make configuration
      valid.";
    leaf resolve-system {
      type empty ;
      description
        "When present, the server is allowed to automatically
         configure referenced system configuration into the
         target configuration datastore.";
     }
  }

 augment /nc:copy-config/nc:input {
   description
     "Allows the server to automatically configure
      referenced system configuration to make configuration
      valid.";
    leaf resolve-system {
      type empty ;
      description
        "When present, the server is allowed to automatically
         configure referenced system configuration into the
         target configuration datastore.";
     }
  }

 augment /ncds:edit-data/ncds:input {
   description
     "Allows the server to automatically configure
      referenced system configuration to make configuration
      valid.";
    leaf resolve-system {
      type empty ;
      description
        "When present, the server is allowed to automatically
         configure referenced system configuration into the
         target configuration datastore.";
    }
  }
}
