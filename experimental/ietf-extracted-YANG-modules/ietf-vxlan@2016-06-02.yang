module ietf-vxlan {
    namespace "urn:ietf:params:xml:ns:yang:ietf-vxlan";
    prefix "vxlan";

    import ietf-interfaces {
      prefix "if";
     }

    import ietf-inet-types {
       prefix "inet";
     }

    import ietf-yang-types {
       prefix yang;
     }

    organization
      "IETF NVO3(Network Virtualization Overlays) Working Group";

      contact
       "
         WG List:  <mailto:nvo3@ietf.org>

         WG Chair: Matthew Bocci
                  <mailto:matthew.bocci@alcatel-lucent.com>

         WG Chair: Benson Schliesser
                  <mailto:bensons@queuefull.net>

         Editor:   Fangwei Hu
                   <mailto:hu.fangwei@zte.com.cn>

         Editor:   Ran Chen
                   <mailto:chen.ran@zte.com.cn>

         Editor:   Mallik Mahalingam
                   <mailto:mallik_mahalingam@yahoo.com>

         Editor:   Zu Qiang
                   <mailto:Zu.Qiang@Ericsson.com>
        ";

    description
       "The YANG module defines a generic configuration
         model for VxLAN protocol";

    revision 2016-06-02 {
       description
         "03 revision. Update the YANG data model based on thec comments of IETF 96th meeting.";
       reference
         "draft-chen-nvo3-vxlan-yang-02";
     }

    revision 2015-12-01 {
       description
         "02 revision.";
       reference
         "draft-chen-nvo3-vxlan-yang-02";
     }

    revision 2015-10-12 {
       description
         "01 revision.";
       reference
         "draft-chen-nvo3-vxlan-yang-01";
     }

    revision 2015-05-05 {
      description "Initial revision";
      reference
         "draft-chen-nvo3-vxlan-yang-00";
    }

    /* Typedefs  */

    typedef bgp-rt-type {
      type enumeration {
        enum import {
        description "For import";
       }
       enum export {
         description "For export";
       }
       enum both {
         description "For both import and export";
       }
     }
     description "BGP route-target type. Import from BGP YANG";
    }

    typedef vlan {
      type uint16 {
        range 1..4094;
      }
      description
      "Typedef for VLAN";
    }

    typedef vxlan-id {
      type uint32;
      description
        "Typedef for VxLAN ID.";
    }

    typedef inner-vlan-handling-mode {
       type enumeration {
         enum discard-inner-vlan {
              description
                "Discard inner-VLAN.";
         }
         enum no-discard-inner-vlan {
              description
                "No discard inner-VLAN.";
         }
       }
       default discard-inner-vlan ;
       description
        "Typedef for inner-vlan-handling-mode";
    }

    typedef address-family-type {
       type enumeration {
         enum ipv4 {
           description
             "IPv4";
         }
         enum ipv6 {
           description
             "IPv6";
         }
       }
       description
         "Typedef for address family type.";
     }

    /* Configuration Data */

      container vxlan{

        leaf global-enable {
          type empty ;
          mandatory true ;
          description 'VXLAN global enble.';
        }

        list vxlan-instance {
           key vxlan-id ;
           leaf vxlan-id {
             type vxlan-id;
             description "VxLAN ID.";
           }

           leaf description {
            type string {
              length 0..64 {
                description 'VXLAN instance description information.';
              }
            }
            description 'The description information of VXLAN instance.';
           }

           leaf unknow-unicast-drop {
            type enumeration {
              enum enable {
                value 1 ;
                description 'Unknown unicast drop enable.';
              }
              enum disable {
                value 2 ;
                description 'Unknown unicast drop disable.';
              }
            }
            default enable ;
            description 'Unknow unicast drop configuration of VXLAN instance.';
          }

           leaf filter-vrrp {
             type enumeration {
              enum enable {
                value 1 ;
                description 'VRRP packets filter.';
              }
              enum disable {
                value 2 ;
                description 'VRRP packets not filter.';
              }
            }
            default enable ;
            description 'VRRP packets filter configuration of VXLAN instance.';
           }

           container vxlan-evpn {
              leaf route-distinguisher {
                type string;
                description "VxLAN EVPN BGP RD";
              }

              list vpn-targets {
                key rt-value;
                description "VxLAN EVPN Route Targets";
                leaf rt-value {
                  type string;
                  description "Route-Target value";
                }

                leaf rt-type {
                  type bgp-rt-type;
                  mandatory true;
                  description "Type of RT";
                }
              }
              description
                 "EVPN VxLAN parameters.";
            }
          description
             "VxLAN instance.";
        }

        list vtep-instances {
            key vtep-id ;
            leaf vtep-id {
               type uint32;
               description
               "VTEP ID.";
            }

            leaf vtep-name{
               type string;
               description
                "VTEP instance name.";
            }

            leaf source-interface {
               type if:interface-ref;
               description
                     "Source interface name.";
            }

            leaf multicast-ip {
                type inet:ip-address;
                mandatory true ;
                description
                  "VxLAN multicast IP address.";
            }

            leaf inner-vlan-handling-mode {
                type inner-vlan-handling-mode;
                description
                   "The inner vlan tag handling mode.";
            }

            list bind-vxlan-id {
                key vxlan-id;
                leaf vxlan-id {
                  type vxlan-id;
                  description
                       "VxLAN ID.";
                }
                description
                  "VxLAN ID list for the VTEP.";
            }
            description
                "VTEP instance.";
        }

        list static-vxlan-tunnel{
            key vxlan-tunnel-id;
            leaf vxlan-tunnel-id {
               type uint32;
               description
                     "Static VxLAN tunnel ID.";
            }

            leaf vxlan-tunnel-name {
               type string;
               description
               "Name of the static VxLAN tunnel.";
            }

            list address-family {
               key "af";
               leaf af {
                 type address-family-type;
                 description
                 "Address family type value.";
               }

               leaf tunnel-source-ip {
                 type address-family-type;
                 description
                 "Source IP address for the static VxLAN tunnel";
               }

               leaf tunnel-destination-ip {
                  type address-family-type;
                  description
                   "Destination IP address for the static VxLAN tunnel";
               }

               list bind-vxlan-id {
                  key vxlan-id;
                  leaf vxlan-id {
                    type vxlan-id;
                    description
                       "VxLAN ID.";
                  }
                  description
                     "VxLAN ID list for the VTEP.";
               }

                description
                   "Per-af params.";
             }
            description
              "Configure the static VxLAN tunnel";
        }

        container redundancy-group-binds {
           list redundancy-group-bind {
              key 'vxlan-id redundancy-group';
              leaf vxlan-id {
                type uint32 {
                  range 1..16777215 {
                    description 'The value of VXLAN,it must between 1 to 16777215.';
                  }
                }
                description 'VXLAN ID binding by redundancy group.';
              }

              leaf redundancy-group {
                type uint32 {
                   range 1..4294967293 {
                      description 'The value of redundancy group,it must between 1 to'
                          + ' 4294967293.';
                    }
                }
                description 'Redundancy group ID.';
              }
              description 'Redundancy group bind table.';
           }
           description 'Redundancy group bind table.';
        }

     description
       "VxLAN configure model.";
    }

      /* Operational  data */
    container vxlan-state{
      config false ;
      container vxlan {
        container vxlan-tunnels {
          list vxlan-tunnel {
             key 'local-ip remote-ip';
             leaf local-ip {
               type address-family-type ;
               description 'Local IP of tunnel.';
             }

             leaf remote-ip {
               type address-family-type ;
               description 'Remote IP of tunnel.';
             }

             leaf static-tunnel-id {
               type uint32 ;
               description 'Static tunnel ID.';
             }

             leaf evpn-tunnel-id {
               type uint32 ;
               description 'EVPN tunnel ID.';
             }

            container statistics {
               container tunnel-statistics {
                 leaf in-bytes {
                    type string {
                      length 0..24 ;
                    }
                    description 'Total bytes received.';
                 }

                 leaf out-bytes {
                   type string {
                     length 0..24 ;
                   }
                   description 'Total bytes sent.';
                 }

                 leaf in-packets {
                   type string {
                      length 0..24;
                   }
                   description 'Total packets received.';
                 }

                 leaf out-packets {
                   type string {
                     length 0..24 ;
                   }
                   description 'Total packets sent.';
                 }
                 description 'Total tunnel statistics.';
              }

              container tunnel-vni-statistics {
               list tunnel-vni-statistic {
                key vxlan-id ;
                leaf vxlan-id {
                  type uint32 ;
                  description 'The VXLAN in tunnel.';
                }

                leaf in-bytes {
                  type string {
                    length 1..24 ;
                  }
                  description 'Total bytes received.';
                }

                leaf out-bytes {
                  type string {
                    length 1..24 ;
                  }
                  description 'Total bytes sent.';
                }

                leaf in-packets {
                  type string {
                    length 1..24 ;
                  }
                  description 'Total packets received.';
                }

                leaf out-packets {

                  type string {
                    length 1..24 ;
                  }
                  description 'Total packets sent.';
                }
                description 'Statistics in VXLAN tunnel.';
              }
              description 'Statistics in VXLAN tunnel.';
            }
             description 'Tunnel statistics.' ;
          }
            description 'VXLAN tunnel info.';
        }
          description 'VXLAN tunnel Info.';
      }
      description 'Information of VXLAN state.';
    }
    description 'Information of VXLAN state.';
   }

  }
