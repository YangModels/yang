module ietf-netconf-fragmentation {
    yang-version 1.1;
    namespace "urn:ietf:params:xml:ns:yang:ietf-netconf-fragmentation";
    prefix fgm;

        import ietf-netconf-datastores{
         prefix ncds;
        }

    import ietf-yang-types {
      prefix yang;
    }

    import ietf-netconf {
      prefix nc;
    }

    organization
      "IETF NETCONF Working Group";
    contact
      "WG Web:  <https://datatracker.ietf.org/wg/netconf/>

       WG List:  <mailto:netconf@ietf.org>

       Author:   Guangying Zheng
                         <zhengguangying@huawei.com>

       Author:   Zitao Wang
                         <wangzitao@huawei.com>";
    description
      "This document introduces an extension to NETCONF (Network Configuration) protocol.
          The extension allows NETCONF to handle large size data as fragmented RPC messages.
          Specifically, this document defines a new get-block capability and relevant
          operations to handle the fragmentations.";

    revision 2017-10-23 {
      description
        "Initial revision.";
      reference "draft-zheng-netconf-fragmentation-00";
    }

        rpc get-block {
      description
        "Retrieve data from an NMDA datastore.";
      input {
        leaf source {
          type ncds:datastore;
          mandatory true;
          description
            "Datastore from which to retrieve data.";
        }

        choice filter-spec {
          description
            "The content filter specification for this request.";

          anydata subtree-filter {
            description
              "This parameter identifies the portions of the
               target datastore to retrieve.";
            reference "RFC 6241, Section 6.";
          }
          leaf xpath-filter {
            if-feature nc:xpath;
            type yang:xpath1.0;
            description
              "This parameter contains an XPath expression
               identifying the portions of the target
               datastore to retrieve.";
          }
        }
    }
       }
       rpc discard-fragmentation {
           description
       "Discard the netconf fragmentation, if the discard parameter is conveyed,
               it means the operation is terminated.
               Then it doesn't need to reply the remaining fragmentations.";
   }

}
