module ietf-isis-pics {
  yang-version 1.1;
  namespace "urn:ietf:params:xml:ns:yang:ietf-isis-pics";
  prefix isis-pics;

  import iana-isis-pics {
    prefix "iana-isis-pics";
  }

  organization
    "IETF LSR - Link State Routing Working Group";
  contact
    "WG Web:   <http://datatracker.ietf.org/wg/lsr>
     WG List:  <mailto:lsr@ietf.org>

     Author:   Yingzhen Qu
               <mailto:yingzhen.ietf@gmail.com>
     Author:   Les Ginsberg
               <mailto:ginsberg@cisco.com>
     Author:   Tony Przygienda
               <mailto:prz@juniper.net>
     Author:   Bruno Decraene
               <mailto:bruno.decraene@orange.com>
     Author:   Yongqing Zhu
               <mailto:zhuyq8@chinatelecom.cn>";

  description
    "The YANG module is used to query an IS-IS implementation
     for Protocol Implementation Conformance Statement (PICS).

     This YANG model conforms to the Network Management
     Datastore Architecture (NMDA) as described in RFC 8342.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  reference
    "RFC XXXX: YANG Data Model for IS-IS PICS";

  revision 2025-05-05 {
    description
      "Initial Version";
    reference
      "RFC XXXX: YANG Data Model for IS-IS PICS.";
  }

  typedef support {
    type boolean;
    default "false";
    description
      "When set to True, it means a feature or definition is
       supported/implemented.";
  }

  container isis-pics {
    config false;
    description
      "IS-IS Protocol Implementation Conformance Statement (PICS).";
    leaf-list supported-isis-pics {
      type identityref {
        base iana-isis-pics:isis-pics;
      }
      description
        "List of supported isis pics.";
    }

    container isis-pics-mptlv {

      description
        "IS-IS Protocol Implementation Conformance Statement (PICS)
         for RFC xxxx: Multi-part TLVs in IS-IS. This container is
         meant to be augmented by RFC PICS module where a TLV is
         defined.";
    }
  }
}
