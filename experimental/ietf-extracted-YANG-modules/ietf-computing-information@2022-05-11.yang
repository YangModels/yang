module ietf-computing-information {
  yang-version "1.1";
  namespace "urn:ietf:params:xml:ns:yang: ietf-computing-information";

  prefix computing-information;

  import ietf-inet-types {
    prefix inet ;
    revision-date 2013-07-15 ;
    reference "RFC 6991: Common YANG Data Types";
  }

  organization
    "IETF cats(Computing-Aware Traffic Steering)Working Group";

  contact
    "WG Web:   <http://datatracker.ietf.org/group/cats/>
     WG List:  <mailto:cats@ietf.org>

     Author:   Xuewei Wang
               <mailto:wangxuewei1@ruijie.com.cn>
     Author:   Huijuan Yao
               <mailto:yaohuijuan@chinamobile.com>
     Author:   Zhiqiang Li
               <mailto:lizhiqiangyjy@chinamobile.com> ";

  description
    "This document defines a YANG data model used for computing information awareness.

     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2022-05-11 {
    description 'First draft.'
                ;
    reference 'RFC XXXX: A YANG Data Model for Computing '
            + 'Information Awareness.'
                ;
  }

  container awareness {
    description 'transferring of computing information of the service.'
                ;
    container computing-information {
      description 'computing information transferring.'
                  ;
      container service-instance {
        description 'computing information of a service instance.'
                    ;
           leaf service-ID {
             type inet:ip-prefix;
             description ' The ID of the service provided by the service instance '
                         ;
           }
           leaf service-domain-name {
             type string;
             description ' The domain name of the service provided by the service instance '
                         ;
           }
           leaf computing-energy-consumption {
             type uint32
             description ' the value of computing energy consumption '
                         ;
           }
           leaf computing-cost {
             type uint32
             description ' the comprehensive computing cost '
                         ;
           }
           leaf peak-value-of-available-computing {
             type uint32
             description ' the peak value of available computing '
                         ;
           }
           leaf number-of-available-service-connections {
             type uint32
             description ' the number of available service connections '
                         ;
           }
           leaf CPU-performance {
             type uint16;
             description ' the CPU utilization'
                         ;
           }
           leaf GPU-performance {
             type uint16;
             description ' the GPU utilization'
                         ;
           }
           leaf NPU-performance {
             type uint16;
             description ' the NPU utilization'
                         ;
           }
           leaf storage-capacity {
             type uint32;
             description ' The capacity of the storage '
                         ;
           }
           leaf service-delay {
             type uint32;
             description ' Service processing latency '
                         ;
        }
      }
    }
  }
}
