module vxlan-gpe {

  namespace "urn:cisco:params:xml:ns:yang:vxlan-gpe";

  prefix vxlan-gpe;

  import ietf-inet-types { prefix inet; }
  import ietf-yang-types { prefix yang; }

  organization "Cisco Systems, Inc.";
  contact "Reinaldo Penno <repenno@cisco.com>";

  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2013-11-26 {
    description
    "Initial revision.";
  }

//    0                   1                   2                   3
//    0 1 2 3 4 5 6 7 8 9 0 1 2 3 4 5 6 7 8 9 0 1 2 3 4 5 6 7 8 9 0 1
//   +-+-+-+-+-+-+-+-+-+-+-+-+-+-+-+-+-+-+-+-+-+-+-+-+-+-+-+-+-+-+-+-+
//   |       Source Port = xxxx      |       Dest Port = 4789        |
//   +-+-+-+-+-+-+-+-+-+-+-+-+-+-+-+-+-+-+-+-+-+-+-+-+-+-+-+-+-+-+-+-+
//   |           UDP Length          |        UDP Checksum           |
//   +-+-+-+-+-+-+-+-+-+-+-+-+-+-+-+-+-+-+-+-+-+-+-+-+-+-+-+-+-+-+-+-+
//   |R|R|R|R|I|P|R|R|   Reserved    |   Protocol Type               |
//   +-+-+-+-+-+-+-+-+-+-+-+-+-+-+-+-+-+-+-+-+-+-+-+-+-+-+-+-+-+-+-+-+
//   |                VXLAN Network Identifier (VNI) |   Reserved    |
//   +-+-+-+-+-+-+-+-+-+-+-+-+-+-+-+-+-+-+-+-+-+-+-+-+-+-+-+-+-+-+-+-+

  typedef vxlan-gpw-header-flag-type {
    type bits {
      bit r1 {
        position 0;
        description "reserved";
      }
      bit r2 {
        position 1;
        description "reserved";
      }
      bit r3 {
        position 2;
        description "reserved";
      }
      bit r4 {
        position 3;
        description "reserved";
      }
      bit i {
        position 5;
        description "Some description";
      }
      bit p {
        position 6;
        description "Some description";
      }
      bit r7 {
        position 7;
        description "reserved";
      }
      bit r8 {
        position 8;
        description "reserved";
      }
    }
    description "vxlan-gpe Header Flags";
    reference "http://tools.ietf.org/html/draft-quinn-vxlan-gpe-01";
  }

  container vxlan-gpe-header {
    description "Network Service Base header";

    leaf gpe-header-flag-value {
        type vxlan-gpw-header-flag-type;
    }

    leaf reserved {
      default 0;
      type uint8;
    }

    leaf protocol-type {
      type uint16;
      // Reinaldo: Another option is to import Opendaylight L2 Types so have ethertype
    }

    leaf-list vni {
      type uint8;
      min-elements 3;
      max-elements 3;
    }

    leaf reserved2 {
      default 0;
      type uint8 {
        range "0 .. 255";
      }
      description "Reserved field";
    }
  }
}
