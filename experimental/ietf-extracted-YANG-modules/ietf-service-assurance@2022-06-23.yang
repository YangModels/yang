module ietf-service-assurance {
  yang-version 1.1;
  namespace "urn:ietf:params:xml:ns:yang:ietf-service-assurance";
  prefix sain;

  import ietf-yang-types {
    prefix yang;
    reference
      "RFC 6991: Common YANG Data Types";
  }

  organization
    "IETF OPSAWG Working Group";
  contact
    "WG Web:   <https://datatracker.ietf.org/wg/opsawg/>
     WG List:  <mailto:opsawg@ietf.org>
     Author:   Benoit Claise  <mailto:benoit.claise@huawei.com>
     Author:   Jean Quilbeuf   <mailto:jean.quilbeu@huawei.com>";
  description
    "This module defines objects for assuring services based on their
     decomposition into so-called subservices, according to the SAIN
     (Service Assurance for Intent-based Networking) architecture.

     The subservices hierarchically organised by dependencies constitute
     an assurance graph. This module should be supported by an assurance
     agent, able to interact with the devices in order to produce a
     health status and symptoms for each subservice in the assurance
     graph.

     This module is intended for the following use cases:
     * Assurance graph configuration:
       - subservices: configure a set of subservices to assure, by
         specifying their types and parameters.
       - dependencies: configure the dependencies between the
         subservices, along with their type.
     * Assurance telemetry: export the health status of the subservices,
       along with the observed symptoms.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";

  revision 2022-06-23 {
    description
      "Initial version.";
    reference
      "RFC xxxx: YANG Modules for Service Assurance";
  }

  identity subservice-idty {
    description
      "Base identity for subservice types.";
  }

  identity service-instance-idty {
    base subservice-idty;
    description
      "Identity representing a service instance.";
  }

  identity dependency-type {
    description
      "Base identity for representing dependency types.";
  }

  identity informational {
    base dependency-type;
    description
      "Indicates that symptoms of the dependency might be of interest
       for the dependent, but the status of the dependency should not
       have any impact on the dependent.";
  }

  identity impacting {
    base dependency-type;
    description
      "Indicates that the status of the dependency directly impacts the
       status of the dependent.";
  }

  grouping symptom {
    description
      "A grouping for the symptoms for a specific subservice.";
    leaf id {
      type string;
      description
        "A globally unique identifier for the symptom, to be generated
         by the SAIN agent that detected the symptom.";
    }
    leaf health-score-weight {
      type uint8 {
        range "0 .. 100";
      }
      description
        "The weight to the health score incurred by this symptom. The
         higher the value, the more of an impact this symptom has. If a
         subservice health score is not 100, there must be at least one
         symptom with a health score weight larger than 0.";
    }
    leaf description {
      type string;
      description
        "Description of the symptom, i.e., text describing what the
         symptom is, to be computer-consumable and be displayed on a
         human interface. It is not intended for random end users but
         for network/system/software engineers that use their local
         context to provide and interpret such information. Therefore,
         no mechanism for language tagging is needed.";
    }
    leaf start-date-time {
      type yang:date-and-time;
      description
        "Date and time at which the symptom was detected.";
    }
    leaf stop-date-time {
      type yang:date-and-time;
      description
        "Date and time at which the symptom stopped being detected.
         must after the start-date-time.";
    }
  }

  grouping subservice-dependency {
    description
      "Represents a dependency to another subservice.";
    leaf type {
      type leafref {
        path "/subservices/subservice/type";
      }
      description
        "The type of the subservice to refer to (e.g., device).";
    }
    leaf id {
      type leafref {
        path "/subservices/subservice[type=current()/../type]/id";
      }
      description
        "The identifier of the subservice to refer to.";
    }
    leaf dependency-type {
      type identityref {
        base dependency-type;
      }
      description
        "Represents the type of dependency (e.g., informational,
         impacting).";
    }
  }

  leaf assurance-graph-version {
    type yang:counter64;
    config false;
    mandatory true;
    description
      "The assurance graph version, which increases by 1 for each new
       version, that cause structural changes to the graph. Structural
       changes include addition or deletion of subservices and
       modification of a subservice parameters, dependencies or
       maintenance windows. Structural changes correspond to changes in
       the nodes that are config true.

       The counter wraps around when the maximum value is reached.";
  }
  leaf assurance-graph-last-change {
    type yang:date-and-time;
    config false;
    mandatory true;
    description
      "Date and time at which the assurance graph last changed after the
       changes (dependencies and/or maintenance windows parameters) are
       applied to the subservice(s). These date and time must be more
       recent or equal compared to the more recent value of any changed
       subservices last-change";
  }
  container subservices {
    description
      "Root container for the subservices.";
    list subservice {
      key "type id";
      description
        "List of configured subservices.";
      leaf type {
        type identityref {
          base subservice-idty;
        }
        description
          "Type of the subservice, for instance, device or interface.";
      }
      leaf id {
        type string;
        description
          "Identifier of the subservice instance. Must be unique among
           subservices of the same type.";
      }
      leaf last-change {
        type yang:date-and-time;
        config false;
        description
          "Date and time at which the structure for this
           subservice instance last changed, i.e., dependencies and/or
           maintenance windows parameters.";
      }
      leaf label {
        type string;
        config false;
        description
          "Label of the subservice, i.e., text describing what the
           subservice is to be displayed on a human interface.

           It is not intended for random end users but for
           network/system/software engineers that use their local
           context to provide and interpret such information.
           Therefore, no mechanism for language tagging is needed.";
      }
      leaf under-maintenance {
        type boolean;
        default "false";
        description
          "A flag indicating whether this particular subservice is
           under maintenance. Under this circumstance, the subservice
           symptoms and the symptoms of its dependencies in the
           assurance graph are not taken into account. Instead,
           the subservice should report a single symptom 'Under
           Maintenance'.

           The operator changing the under-maintenance value must set
           the maintenance-contact variable.

           When the subservice is not under maintenance any longer, the
           under-maintenance flag must return to its default value and
           the under-maintenance-owner variable deleted.";
      }
      leaf maintenance-contact {
        when "../under-maintenance = 'true'";
        type string;
        mandatory true;
        description
          "A string used to model an administratively assigned name of
           the resource that changed the under-maintenance value to
           'true'.

           It is suggested that this name contain one or more of the
           following: IP address, management station name,
           network manager's name, location, or phone number. In some
           cases the agent itself will be the owner of an entry. In
           these cases, this string shall be set to a string starting
           with 'monitor'.";
      }
      choice parameter {
        mandatory true;
        description
          "Specify the required parameters per subservice type. Each
           module augmenting this module with a new subservice type,
           that is a new identity based on subservice-idty should
           augment this choice as well, by adding a container
           available only if the current subservice type is
           the newly added identity.";
        container service-instance-parameter {
          when "derived-from-or-self(../type,
                'sain:service-instance-idty')";
          description
            "Specify the parameters of a service instance.";
          leaf service {
            type string;
            mandatory true;
            description
              "Name of the service.";
          }
          leaf instance-name {
            type string;
            mandatory true;
            description
              "Name of the instance for that service.";
          }
        }
        // Other modules can augment their own cases into here
      }
      leaf health-score {
        type union {
          type uint8 {
            range "0 .. 100";
          }
          type enumeration {
            enum missing {
              value -1;
              description
                "Explictly represent the fact that the health score is
                 missing. This could be used when metrics crucial to
                 establish the health score are not collected anymore.";
            }
          }
        }
        config false;
        description
          "Score value of the subservice health. A value of 100 means
           that subservice is healthy. A value of 0 means that the
           subservice is broken. A value between 0 and 100 means that
           the subservice is degraded.";
      }
      leaf symptoms-history-start {
        type yang:date-and-time;
        config false;
        description
          "Date and time at which the symptoms history starts for this
           subservice instance, either because the subservice instance
           started at that date and time or because the symptoms before
           that were removed due to a garbage collection process.";
      }
      container symptoms {
        config false;
        description
          "Symptoms for the subservice.";
        list symptom {
          key "start-date-time id";
          description
            "List of symptoms the subservice. While the start-date-time
             key is not necessary per se, this would get the entries
             sorted by start-date-time for easy consumption.";
          uses symptom;
        }
      }
      container dependencies {
        description
          "Indicates the set of dependencies of the current subservice,
           along with their types.";
        list dependency {
          key "type id";
          description
            "List of dependencies of the subservice.";
          uses subservice-dependency;
        }
      }
    }
  }
}
