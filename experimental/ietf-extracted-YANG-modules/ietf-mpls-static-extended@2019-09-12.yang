module ietf-mpls-static-extended {
  yang-version 1.1;
  namespace "urn:ietf:params:xml:ns:yang:ietf-mpls-static-extended";
  prefix "mpls-static-ext";

  import ietf-mpls {
    prefix "mpls";
    reference "draft-ietf-mpls-base-yang: MPLS Base YANG Data Model";
  }

  import ietf-routing {
    prefix "rt";
    reference "RFC8349: A YANG Data Model for Routing Management";
  }

  import ietf-routing-types {
    prefix "rt-types";
    reference "RFC8294: Common YANG Data Types for the Routing Area";
  }

  import ietf-mpls-static {
    prefix "mpls-static";
    reference "RFC XXXX: A YANG Data Model for MPLS Static LSPs";
  }

  organization "IETF MPLS Working Group";

  contact
    "WG Web:   <http://tools.ietf.org/wg/mpls/>

     WG List:  <mailto:mpls@ietf.org>

     Editor:   Tarek Saad
               <mailto:tsaad@juniper.net>

     Editor:   Rakesh Gandhi
               <mailto:rgandhi@cisco.com>

     Editor:   Xufeng Liu
               <mailto: xufeng.liu.ietf@gmail.com>

     Editor:   Vishnu Pavan Beeram
               <mailto:vbeeram@juniper.net>

     Editor:   Igor Bryskin
               <mailto: Igor.Bryskin@huawei.com>";

  description
    "This YANG module contains the Extended MPLS Static LSP YANG
     data model. The model fully conforms to the Network Management
     Datastore Architecture (NMDA).

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  // RFC Ed.: replace XXXX with actual RFC number and remove this
  // note.

  // RFC Ed.: update the date below with the date of RFC publication
  // and remove this note.

  revision "2019-09-12" {
    description
      "Latest revision of MPLS Static LSP Extended YANG module";
    reference "RFC XXXX: A YANG Data Model for MPLS Static LSPs";
  }

  grouping bidir-static-lsp {
    description
      "grouping for top level list of static bidirectional LSPs";
    leaf forward-lsp {
      type mpls-static:static-lsp-ref;
      description
        "Reference to a configured static forward LSP";
    }
    leaf reverse-lsp {
      type mpls-static:static-lsp-ref;
      description
        "Reference to a configured static reverse LSP";
    }
  }

  augment "/rt:routing/mpls:mpls/mpls-static:static-lsps" {
    description
      "Augmentation for static MPLS LSPs";

    leaf bandwidth {
      type rt-types:bandwidth-ieee-float32;
      units "Bytes per second";
      description
        "Bandwidth using offline calculation";
    }
    leaf lsp-priority-setup {
      type uint8 {
        range "0..7";
      }
      description "LSP setup priority";
    }
    leaf lsp-priority-hold {
      type uint8 {
        range "0..7";
      }
      description "LSP hold priority";
    }
  }

  augment "/rt:routing/mpls:mpls" {
    description "Augmentations for MPLS Static LSPs";
    container bidir-static-lsps {
      description
        "Statically configured bidirectional LSPs";
      list bidir-static-lsp {
        key name;
        description "List of static bidirectional LSPs";

        leaf name {
          type string;
          description "Name that identifies the bidirectional LSP";
        }
        uses bidir-static-lsp;
      }
    }
  }
}
