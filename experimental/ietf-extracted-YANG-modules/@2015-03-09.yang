module "file-transfer" {

        namespace "urn:ietf:params:xml:ns:yang:file-trans";
        prefix "ft";

        import "ietf-system" {
                prefix "sys";
        }
        import "ietf-inet-types" {
                prefix "inet";
        }
        description "File transfer YANG model";
        organization "NETMOD Working Group";
        contact
        "qui.sun@external.telekom.de
         ian.farrer@telekom.de
        ";
    revision "2015-03-09" {
        description
            "Initial version for file transfer YANG model.
             This model can be used for file transfering and uploading.
            ";
    }

        feature "transfer-scp" {
                description "Indicate the transfer is through scp";
        }
        feature "transfer-ftp" {
                description "Indicate the transfer is through ftp";
        }
        feature "transfer-http" {
                description "Indicate the transfer is through http";
        }
        feature "transfer-https" {
                description "Indicate the transfer is through https";
        }

    /* typedefs */
        typedef "percent" {
                type "uint8" {
                        range "0 .. 100";
                }
        }
    typedef "lifetime" {
        type uint32;
        units seconds;
    }

    /* augments */
        augment "/sys:system-state" {
                container "file-transfer-state" {
            config false;
                        list "file-transfered" {
                                leaf "index" {
                                        type "uint32";
                    mandatory true;
                                }
                                leaf "file-name" {
                                        type "string";
                    mandatory true;
                                }
                                leaf "remote-file-path" {
                                        type "inet:uri";
                    mandatory true;
                    description
                      "A URI for the remote file path. This can be a URI of
                       type HTTP/HTTPS/FTP/SCP, depending on the protocol
                       which is being used for the transfer.  The transfer protocol
                       is indicated through the URI. ";
                                }
                                leaf "local-file-path" {
                                        type "inet:uri";
                    mandatory true;
                    description
                      "A URI for the local file path. This is a URI of type file. ";
                                }
                                leaf "credential-method" {
                    type enumeration {
                        enum password;
                        enum certificate;
                        enum ssh-key;
                    }
                                }
                container "transfer-status" {
                    config false;
                    leaf status {
                        type enumeration {
                            enum planned;
                            enum in-progress;
                            enum transfer-failed;
                            enum md5check-failed;
                            enum verification-failed;
                            enum done;
                        }
                    mandatory true;
                    }
                    leaf status-msg {
                        type string;
                        description "Additional system messages.";
                    }
                    leaf progress {
                        when "../status = 'in-progress'";
                        type percent;
                        mandatory true;
                    }
                }
                leaf retried-times {
                    type uint8;
                }
                        }
                }
        }
    rpc transfer {
        input {
            leaf action {
                mandatory true;
                type enumeration {
                    enum upload {
                        description
                            "Specify the upload action. The server sends
                             the file identified by the local-file-path
                             to the URI identified by the remote-file-path.";
                    }
                    enum download {
                        description
                            "Specify the download action. The server retrives
                            the file identified by the remote-file-path
                            to the URI identified by the local-file-path.";
                    }
                }
            }
            leaf file-name {
                type string;
            }
            leaf local-file-path {
                type inet:uri;
                mandatory true;
                description
                    "A URI for the local file path. This MUST be a URI
                    of type file.
                    ";
            }
            leaf remote-file-path {
                type inet:uri;
                mandatory true;
                description
                  "A URI for the remote file path. This can be a URI of
                   type HTTP/HTTPS/FTP/SCP, depending on the protocol
                   which is being used for the transfer. The transfer
                   protocol is specified in the choice of 'trans-method'.";
            }
                        choice "trans-method" {
                mandatory true;
                case "scp" {
                                    container "scp" {
                                        presence "true";
                        if-feature "transfer-scp";
                                    }
                }
                case "ftp" {
                                    container "ftp" {
                                            presence "true";
                        if-feature "transfer-ftp";
                                    }
                }
                                case "http" {
                    container "http" {
                                            presence "true";
                        if-feature "transfer-http";
                    }
                }
                case "https" {
                                    container "https" {
                                            presence "true";
                        if-feature "transfer-https";
                                    }
                }
            }
                        choice "credentials" {
                                case "password" {
                    container "password" {
                        presence true;
                        leaf password {
                            type string;
                            mandatory true;
                        }
                    }
                }
                case "certificate" {
                    container "certificate" {
                        presence "true";
                        leaf local-path {
                            type inet:uri;
                            mandatory true;
                        }
                    }
                }
                case "ssh-key" {
                    container "ssh-key" {
                        presence "true";
                        leaf local-path {
                            type inet:uri;
                            mandatory true;
                        }
                    }
                }
                        }
            leaf credential-valid-time {
                type lifetime;
                description
                    "The valid duration for the credential method
                     above.";
            }
            leaf md5-checksum {
                type string;
                description
                    "MD5 checking is optional.";
            }
            leaf timeframe {
                type uint32;
            }
            leaf retry-times {
                type uint8;
            }
            leaf retry-interval {
                type uint32;
            }
            leaf retry-interval-increment {
                type percent;
            }
        }
        output {
            leaf index {
                type uint32;
                mandatory true;
            }
            description
                " When the server receives the RPC request of
                  'transfer', if the transfering process starts
                  successfully, the server MUST assign an index
                  to that process and reply it to the client as
                  an output parameter.
                ";
        }
    }
}
