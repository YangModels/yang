module ietf-savi {
namespace "urn:ietf:params:xml:ns:yang:ietf-savi";
prefix "savi";

import ietf-interfaces {
  prefix "if";
}

import ietf-inet-types {
   prefix "inet";
}

import ietf-yang-types {
   prefix yang;
}

organization
    "IETF SAVI Working Group";
contact
  "
     Editor:   Wei Meng
               <mailto:meng.wei2@zte.com.cn>
     Editor:   Cui Wang
               <mailto:wang.cui1@zte.com.cn>
  ";
description "The YANG module defines a generic configuration model for SAVI";

revision 2015-12-24 {
   description "01 revision.";
   reference "draft-meng-savi-yang-01";
}

revision 2015-07-06 {
   description "Initial revision";
   reference "draft-meng-savi-yang-00";
}

/* Configuration Data */

 container savi {
  description 'Configure SAVI parameters.' ;

  container global{
    leaf ip-version {
      type uint8 ;
      mandatory true ;
      description 'IP Version.' ;
    }
    leaf enable {
      type boolean ;
      mandatory true ;
      description 'Enable.' ;
    }
    leaf arrange-mode {
      type uint8 ;
      description 'Arrange mode.' ;
    }
    leaf max-dad-delay {
        type uint16 {
        range 1..4094 {
        description 'The value of delay time,it must between 1 to 409'
        + '4.'
        ;
        }
      }
      description 'Max DAD delay time.' ;
    }
    leaf max-dad-prepare-delay {
      type uint16 {
        range 1..4094 {
        description 'The value of delay time,it must between 1 to 409'
        + '4.'
        ;
        }
      }
      description 'Max DAD prepare delay time.' ;
    }
    leaf max-ns-delay {
      type uint16 {
        range 1..4094 {
        description 'The value of delay time,it must between 1 to 409'
        + '4.'
        ;
        }
      }
      description 'Max NS delay time.' ;
    }
    leaf dhcp-only {
      type boolean ;
      mandatory true ;
      description 'DHCP ONLY.' ;
    }
    description 'Global configuration.' ;
  }

  container interface {
    list interface {
      key index ;
      leaf index {
        type uint32 {
          range 1..16777215 {
            description 'The value of index,it must between 1 to 16777215.' ;
          }
        }
        description 'Interface index.' ;
      }
      leaf interface-name {
        type string;
        mandatory true;
        description 'Interface name.' ;
      }
      leaf enable {
        type boolean;
        mandatory true;
        description 'Enable.' ;
      }
      leaf validation-status {
        type uint8;
        mandatory true;
        description 'Validation status.' ;
      }
      leaf filting-number {
        type uint8;
        mandatory true;
        description 'Filting number.' ;
      }
      description 'Interface.' ;
    }
    description 'Interface.' ;
  }

  container binding {
    list binding-info {
      key ip-addr ;
      leaf ip-addr {
        type inet:ipv6-address;
        description 'IP address.' ;
        }
      leaf interface-index {
        type uint32;
        mandatory true;
        description 'Interface index.' ;
      }
      leaf ip-addr-type {
        type uint8;
        mandatory true;
        description 'IP Address type.' ;
      }
      leaf type {
       type uint8;
       mandatory true;
       description 'Binding type.' ;
      }
      leaf mac-addr {
        type yang:mac-address;
        mandatory true;
        description 'Mac Address.' ;
      }
      leaf status {
        type uint8;
        mandatory true;
        description 'The status of binding information.' ;
      }
      leaf lifetime {
        type uint32;
        mandatory true;
        description 'The lifetime of binding information.' ;
      }
      leaf row-status {
        type uint8;
        mandatory true;
        description 'The row status of binding information.' ;
      }
      description 'Binding information.' ;
    }
    description 'Binding information.' ;
  }

  container filtering {
    list filtering-info {
      key interface-index;
      leaf ip-addr {
        type inet:ipv6-address;
        description 'IP address.' ;
      }
      leaf interface-index {
        type uint32;
        mandatory true;
        description 'Interface index.' ;
      }
      leaf ip-addr-type {
        type uint8;
        mandatory true;
        description 'IP Address type.' ;
      }
      leaf mac-addr {
        type yang:mac-address;
        mandatory true;
        description 'Mac address.' ;
      }
      description 'Filtering information.' ;
    }
  description 'Filtering information.' ;
  }
 }
}
