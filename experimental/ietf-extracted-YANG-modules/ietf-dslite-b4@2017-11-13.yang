module ietf-dslite-b4 {
  yang-version 1.1;
  namespace "urn:ietf:params:xml:ns:yang:ietf-dslite-b4";
  prefix dslite-b4;

  import ietf-inet-types { prefix inet; }
  import ietf-interfaces { prefix if; }
  import iana-if-type { prefix ianaift; }

  organization "IETF Softwire Working Group";

  contact

    "WG Web:   <https://datatracker.ietf.org/wg/softwire/>
     WG List:  <mailto:softwires@ietf.org>

     WG Chair: Ian Farrer
               <mailto:ianfarrer@gmx.com>

     WG Chair: Yong Cui
               <mailto:cuiyong@tsinghua.edu.cn>

     Editor:  Mohamed Boucadair
              <mailto:mohamed.boucadair@orange.com>

     Editor:  Christian Jacquenet
              <mailto:christian.jacquenet@orange.com>

     Editor:  Senthil Sivakumar
              <mailto:ssenthil@cisco.com>";

  description
    "This module is a YANG module for DS-Lite B4 implementations.

     Copyright (c) 2017 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2017-11-13 {
    description
      "Initial revision.";
    reference
      "RFC XXXX: YANG Data Modules for Dual-Stack Lite (DS-Lite)";
  }

augment "/if:interfaces/if:interface" {
  when "if:type = 'ianaift:tunnel'";
  description
    "Augments Interface module with B4 parameters.
     IANA interface types are maintained at this registry:
     https://www.iana.org/assignments/ianaiftype-mib/ianaiftype-mib.

       tunnel (131),       -- Encapsulation interface";

  leaf b4-ipv6-address {
    type inet:ipv6-address;
    description
      "The IPv6 address used by the B4 element.";
    reference
      "RFC 6333: Dual-Stack Lite Broadband Deployments Following
                 IPv4 Exhaustion";
  }

  leaf aftr-ipv6-addr {
    type inet:ipv6-address;
    description
      "The AFTR's IPv6 address.";
    reference
      "RFC 6333: Dual-Stack Lite Broadband Deployments Following
                 IPv4 Exhaustion";
  }

  leaf b4-ipv4-address {
    type inet:ipv4-address;
    default "192.0.0.2";
    description
      "IPv4 address of the DS-Lite B4.

       192.0.0.0/29 is reserved for the B4 element.

       This address can be used to report ICMP problems and will
       appear in traceroute outputs.";
     reference
       "RFC 6333: Dual-Stack Lite Broadband Deployments Following
                  IPv4 Exhaustion";
  }

  leaf tunnel-mtu {
    type uint16;
    description
      "Configures a tunnel MTU.

       [RFC6908] specifies that since fragmentation and reassembly is
       not optimal, the operator should do everything possible to
       eliminate the need for it.  If the operator uses simple
       IPv4-in-IPv6 softwire, it is recommended that the MTU size of
       the IPv6 network between the B4 and the AFTR accounts for
       the additional overhead (40 bytes).";
     reference
       "RFC 6908: Deployment Considerations for Dual-Stack Lite";
  }

  leaf v6-v4-dscp-preservation {
    type boolean;
    description
      "Copies the DSCP value from the IPv6 header and vice versa.

       Operators should use this model by provisioning the network such
       that the AFTR copies the DSCP value in the IPv4 header to
       the Traffic Class field in the IPv6 header, after the
       encapsulation for the downstream traffic.";
    reference
      "Section 2.10 of RFC 6908.";
  }
 }
}
