module common-types {
    namespace "urn:cisco:params:xml:ns:yang:common-types";
    // replace with IANA namespace when assigned
    prefix c-types;

    organization
       "IETF NETMOD (NETCONF Data Modeling Language) Working Group";

    contact
        "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com

        Editor: Alexander Clemm
        alex@cisco.com

        Editor: Andy Bierman
        andy@yumaworks.com";

     description
        "This module contains a collection of generally useful
        YANG types could be referred from multiple speciality
        components.

        Terms and Acronyms
         CoS (cos): Class of Service

         ICMP (icmp): Internet Control Message Protocol

         IGMP (igmp): Internet Group Management Protocol

         IP (ip): Internet Protocol

         IPv4 (ipv4):Internet Protocol Version 4

         IPv6 (ipv6): Internet Protocol Version 6

         TCP (tcp): Transmission Control Protocol

         ToS (tos): Type of Service

         TTL (ttl): Time to Live

         UDP (udp): User Datagram Protocol

         VLAN (vlan): Virtual Local Area Network
         ";
    revision 2012-10-12 {
        description "Initial revision. ";
    }

    /* Typedefs */

    typedef  cos {
        type uint8 {
            range "0..7";
        }
        description
            "Class of Service.
            An integer that is in the range of the layer 2 CoS values.
            This corresponds to the 802.1p and ISL CoS values.";
        reference "IEEE 802.1p";
    }

    typedef tos {
        type uint8 {
            range "0..15";
        }
        description
            "tos stands for Type of service .
            The tos field are five bits in the IPv4 header.
            It could specify a datagrams priority and
            request a route for low-delay, high-throughput,
            or highly-reliable service.

            Based on these TOS values, a packet would be placed in
            an prioritized outgoing queue, or take a route with
            appropriate latency, throughput, or reliability.
            The following are TOS field values (expressed as
            binary numbers):

                            1000   --   minimize delay
                            0100   --   maximize throughput
                            0010   --   maximize reliability
                            0001   --   minimize monetary cost
                            0000   --   normal service

           .";

        reference
             "RFC 791 Internet Protocol
                Protocol Specification
             RFC 1122 Requirements for Internet Hosts --
                Communication Layers
             RFC 1349 Type of Service in the Internet Protocol
                Suite
             RFC 2474 Definition of the Differentiated Services
                Field (DS Field)
                      in the IPv4 and IPv6 Headers
             RFC 3168 The Addition of Explicit Congestion
                Notification (ECN) to IP
             ";
    }

    typedef  precedence {
        type uint8 {
            range "0..7";
        }
        description
            "Indicates the IP precedence.
            Precedence is three bits in IP header.

            Value       Description
            -------------------
            000 (0)     Routine or Best Effort
            001 (1)     Priority
            010 (2)     Immediate
            011 (3)     Flash - mainly used for Voice Signaling
                        or for Video.
            100 (4)     Flash Override
            101 (5)     Critical -mainly used for Voice RTP.
            110 (6)     Internet
            111 (7)     Network";

        reference
            "RFC 791 Internet Protocol Chapter 3.1
            Protocol Specification";
    }

    typedef tcp-flag-type {
        type bits {
            bit fin {
                position 0;
                description "No more data from sender";
            }
            bit syn {
                position 1;
                description "Synchronize sequence numbers";
            }
            bit rst {
                position 2;
                description "Reset the connection";
            }
            bit psh {
                position 3;
                description "Push Function";
            }
            bit ack {
                position 4;
                description "Acknowledgment field significant";
            }
            bit urg {
                position 5;
                description "Urgent Pointer field significant";
            }
        }
        description "TCP flag type";
        reference "RFC 793 TRANSMISSION CONTROL PROTOCOL";
    }

    typedef ether-type {
        type string {
            pattern '0x[0-9a-fA-F]{4}';
        }
        description
                "ether-type is 0x0-0xffff. The protocol number
                is a four-byte hexadecimal number prefixed with 0x.
                Valid protocol numbers are from 0x0 to 0xffff.

                This list shows the EtherType values and their
                corresponding protocol keywords:

                0x0600 xns-idp Xerox XNS IDP

                0x0BAD vines-ip Banyan VINES IP

                0x0baf vines-echo Banyan VINES Echo

                0x6000 etype-6000 DEC unassigned, experimental

                0x6001 mop-dump DEC Maintenance Operation Protocol
                    (MOP) Dump/Load Assistance

                0x6002 mop-console DEC MOP Remote Console

                0x6003 decnet-iv DEC DECnet Phase IV Route

                0x6004 lat DEC Local Area Transport (LAT)

                0x6005 diagnostic DEC DECnet Diagnostics

                0x6007 lavc-sca DEC Local-Area VAX Cluster (LAVC), SCA

                0x6008 amber DEC AMBER

                0x6009 mumps DEC MUMPS

                0x0800 ip Malformed, invalid, or deliberately corrupt
                    IP frames

                0x8038 dec-spanning DEC LANBridge Management

                0x8039 dsm DEC DSM/DDP

                0x8040 netbios DEC PATHWORKS DECnet NETBIOS Emulation

                0x8041 msdos DEC Local Area System Transport

                0x8042 etype-8042 DEC unassigned

                0x809B appletalk Kinetics EtherTalk (AppleTalk over
                    Ethernet)

                0x80F3 aarp Kinetics AppleTalk Address Resolution
                    Protocol (AARP)

                bpdu-sap      BPDU SAP encapsulated packets
                bpdu-snap     BPDU SNAP encapsulated packets
                ipx-arpa      IPX Advanced Research Projects Agency
                            (ARPA)
                ipx-non-arpa  IPX non arpa
                lacp          Link Aggregation Control Protocol(LACP)
                            encapsulated packets
                pagp          Port Aggregation Protocol(PAGP)
                            encapsulated packets
                vtp           VTP packets
                ";
    }

    typedef ip-protocol {
        type uint8{
           range "0..255";
        }
        description
            "The Internet Protocol (IP) is the principal communications
            protocol used for relaying datagrams (also known as network
            packets) across an internetwork using the Internet Protocol
            Suite.

            IP protocol number value is 0 to 255. It is an 8 bit field
            in the packet header";
        reference
            "IANA Protocol Numbers
            RFC5237 IANA Allocation Guidelines for the Protocol Field";
    }

    typedef igmp-code {
        //TODO: need more work. In NxOs, range is 0..15.
        // Could not match the IGMP with 0..15
        type uint8 ;/* {
            range "0..15";
        }*/
        //IGMP v1 4 bits 0-15
        //IGMP v2 8bits. 0-
        //NXOS only support v1, but XR support v2.
        //

        description
            "Many of these IGMP types have a 'code' field.  Here is
            the list of the types again with their assigned
            code fields.

            Type       Name                                  Reference
            ---------  ------------------------------------  ---------
            0x11       IGMP Membership Query                 [RFC1112]
            0x12       IGMPv1 Membership Report              [RFC1112]
            0x13       DVMRP                                 [RFCDVMRP]
            0x14       PIM version 1                         [PIMv1]
            0x15       Cisco Trace Messages
            0x16       IGMPv2 Membership Report              [RFC2236]
            0x17       IGMPv2 Leave Group                    [RFC2236]
            0x1e       Multicast Traceroute Response         [Fenner]
            0x1f       Multicast Traceroute                  [Fenner]
            0x22       IGMPv3 Membership Report              [RFC3376]
            ";
        reference
            "IANA Internet Group Management Protocol (IGMP) Type
            Numbers";
    }

    typedef icmp-type {
        type uint32 {
            range "0..255";
        }
        description
            "icmp-type is the Internet Control Message Protocol (ICMP)
            'type' field.
            The ICMP header starts after the IPv4 header. All ICMP
            packets will have an 8-byte header and variable-sized
            data section.
            The first 4 bytes of the header will be consistent.
            The first byte is for the ICMP type. The second byte is
            for the ICMP code.
            ICMP type is specified below

            Type    Name                                    Reference
            ----    -------------------------               ---------
              0     Echo Reply                               [RFC792]
              1     Unassigned                                  [JBP]
              2     Unassigned                                  [JBP]
              3     Destination Unreachable                  [RFC792]
              4     Source Quench                            [RFC792]
              5     Redirect                                 [RFC792]
              6     Alternate Host Address                      [JBP]
              7     Unassigned                                  [JBP]
              8     Echo                                     [RFC792]
              9     Router Advertisement                    [RFC1256]
             10     Router Selection                        [RFC1256]
             11     Time Exceeded                            [RFC792]
             12     Parameter Problem                        [RFC792]
             13     Timestamp                                [RFC792]
             14     Timestamp Reply                          [RFC792]
             15     Information Request                      [RFC792]
             16     Information Reply                        [RFC792]
             17     Address Mask Request                     [RFC950]
             18     Address Mask Reply                       [RFC950]
             19     Reserved (for Security)                    [Solo]
             20-29  Reserved (for Robustness Experiment)        [ZSu]
             30     Traceroute                              [RFC1393]
             31     Datagram Conversion Error               [RFC1475]
             32     Mobile Host Redirect              [David Johnson]
             33     IPv6 Where-Are-You                 [Bill Simpson]
             34     IPv6 I-Am-Here                     [Bill Simpson]
             35     Mobile Registration Request        [Bill Simpson]
             36     Mobile Registration Reply          [Bill Simpson]
             37-255 Reserved                                    [JBP]";
        reference
            "RFC1700 ASSIGNED NUMBERS
            RFC792 Internet Control Message Protocol
            RFC4443 Internet Control Message Protocol (ICMPv6)
                for the Internet Protocol Version 6 (IPv6)
                Specification
            RFC2780 IANA Allocation Guidelines For Values In
                the Internet Protocol and Related Headers";
    }

    typedef icmp-code {
        type uint32 {
            range "0..255";
        }
        description
            "ICMP subtype to the given type.
            The ICMP header starts after the IPv4 header. All ICMP
            packets will have an 8-byte header and variable-sized
            data section.
            The first 4 bytes of the header will be consistent.
            The first byte is for the ICMP type. The second byte
            is for the ICMP code. ";
        reference "RFC2 INTERNET CONTROL MESSAGE PROTOCOL";
    }

    typedef vlan-identifier {
        type uint16 {
            range "1 .. 4095";
        }
        description
                "This type denotes a VLAN tag.  ";
        reference
            "RFC3069 VLAN Aggregation for Efficient IP Address
                Allocation
            IEEE 802.1Q";
    }

    typedef time-to-live {
        type uint8 {
            range "0..255";
        }
        description "The TTL is an 8-bit field in IP header.
            The maximum TTL value is 255.";
    }
}
