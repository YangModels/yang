module ietf-srv6-mirror-sid {
  yang-version 1.1;
  namespace "urn:ietf:params:xml:ns:yang:ietf-srv6-mirror-sid";
  prefix srv6ms;

  import ietf-inet-types {
    prefix inet;
    reference "RFC 6991: Common YANG Data Types";
  }
  import ietf-routing {
    prefix rt;
    reference "RFC 8349: A YANG Data Model for Routing Management (NMDA Version)";
  }
  import ietf-segment-routing {
    prefix sr;
    reference "RFC 9020: YANG Data Model for Segment Routing";
  }
  import ietf-srv6-base {
    prefix srv6;
    reference "I-D.ietf-spring-srv6-yang-base: YANG Data Model for SRv6 Base";
  }

  organization
    "IETF Link State Routing (LSR) Working Group";
  contact
    "WG Web:   <https://datatracker.ietf.org/wg/lsr/>
     WG List:  <mailto:lsr@ietf.org>

     Editor:   Tao He
               <mailto:het21@chinaunicom.cn>";
  description
    "This YANG module defines a data model for the configuration
     and operational state of the SRv6 Mirror SID (End.M) protection
     entries used by SRv6 path egress protection.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all capitals,
     as shown here.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://www.rfc-editor.org/info/rfcXXXX); see the RFC
     itself for full legal notices.";

  revision 2026-09-15 {
    description
      "Initial revision.";
    reference
      "draft-ietf-lsr-srv6-mirror-sid-igp-encoding";
  }

  feature mirror-sid {
    description
      "This feature indicates that the device supports the SRv6
       Mirror SID (End.M) behavior and can be configured to protect
       a primary egress node.";
  }

  grouping mirror-sid-entry {
    description
      "Configuration and state of a single SRv6 Mirror SID
       protection entry.";
    leaf mirror-sid {
      type inet:ipv6-address;
      mandatory true;
      description
        "The SRv6 Mirror SID (End.M) instantiated on this node.
         The SID MUST be allocated from a locator of this node.";
    }
    leaf-list protected-locator {
      type inet:ipv6-prefix;
      description
        "An SRv6 locator of the primary egress node that is
         protected by this Mirror SID.";
    }
    leaf forwarding-context {
      type string;
      description
        "Name of the local forwarding context (for example, the
         FIB table) that is associated with this Mirror SID and
         that reproduces the forwarding behavior of the protected
         egress node.";
    }
    leaf enabled {
      type boolean;
      default "true";
      description
        "Controls whether this Mirror SID protection entry is
         advertised in the IGP and used for protection.";
    }
  }

  augment "/rt:routing/sr:segment-routing/srv6:srv6/srv6:locators/srv6:locator" {
    description
      "Augments an SRv6 locator with the Mirror SID protection entries
       that are allocated from it.";
    list mirror-sid {
      if-feature "mirror-sid";
      key "mirror-sid";
      description
        "Mirror SID protection entries configured under this locator.";
      uses mirror-sid-entry;
    }
  }
}
