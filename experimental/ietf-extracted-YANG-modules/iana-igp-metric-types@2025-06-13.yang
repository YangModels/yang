module iana-igp-metric-types {
  yang-version 1.1;
  namespace "urn:ietf:params:xml:ns:yang:iana-igp-metric-types";
  prefix iana-metric-types;

  organization
    "Internet Assigned Numbers Authority (IANA)";

  contact
    "Internet Assigned Numbers Authority

     ICANN
     12025 Waterfront Drive, Suite 300
     Los Angeles, CA 90094-2536
     United States of America

     Tel:    +1 310 301 5800
      <mailto:iana@iana.org>";

  description
    "The YANG module defines the identities for Interior Gateway
     Protocol (IGP) Metric-Types.

     This YANG module is maintained by IANA and reflects the 'IGP
     Metric-Type' registry.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This initial version of this YANG module is part of RFC XXXX
     (https://www.rfc-editor.org/info/rfcXXXX); see the RFC itself
     for full legal notices.

     //RFC Ed.: replace XXXX with actual RFC number and remove
       this note

     //RFC Ed.: replace IANA_FOO_URL and remove this note.

     The latest version of this YANG module is available at
     <IANA_FOO_URL>.";

  revision 2025-06-13 {
    description
      "Initial Version";
    reference
      "RFC XXXX: YANG Data Model for OSPF Flexible Algorithm";
  }

  identity metric-type {
    description
      "Base identity for IGP Metric-Type. The metric types
       are defined in IANA IGP Metric-Type registry.";
  }

  identity igp-metric {
    base metric-type;
    description
      "IGP Metric.";  
  }
  identity min-unidirectional-link-delay {
    base metric-type;
    description
      "Min Unidirectional Link Delay as defined in RFC8570 Section 4.2
       and RFC7471 Section 4.2.";
  }

  identity te-default-metric {
    base metric-type;
    description
      "STraffic Engineering Default Metric as defined in RFC5305
       Section 3.7 and Traffic Engineering Metric as defined in 
       RFC3630, Section 2.5.5.";
  }

  identity bandwidth-metric {
    base metric-type;
    description
      "Bandwidth metric.";
  }
}
