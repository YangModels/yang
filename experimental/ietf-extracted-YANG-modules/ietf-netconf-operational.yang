module ietf-netconf-operational {

  namespace "urn:ietf:params:xml:ns:yang:ietf-netconf-operational";
  prefix "oper";

  import ietf-yang-types {
    prefix yang;
  }
  import ietf-inet-types {
    prefix inet;
  }
  import ietf-netconf {
    prefix nc;
  }

  rpc get-operational {
    input {
      choice filter-spec {
        anyxml subtree-filter {
          description
            "This parameter identifies the portions of the
             operational state datastore to retrieve.";
          reference "RFC 6241, Section 6.";
        }
        leaf xpath-filter {
          if-feature nc:xpath;
          type yang:xpath1.0;
          description
            "This parameter contains an XPath expression
             identifying the portions of the operational state
             datastore to retrieve.";
        }
      }
    }

    output {
      anyxml data {
        description
          "Copy of the operational state data that matched the filter
           criteria (if any).  An empty data container indicates that
           the request did not produce any results.";
        }
    }
  }

  rpc edit-operational {
    input {
      leaf default-operation {
        type enumeration {
          enum merge {
            description
              "The default operation is merge.";
          }
          enum replace {
            description
              "The default operation is replace.";
          }
          enum none {
            description
              "There is no default operation.";
          }
        }
        default "merge";
        description
          "The default operation to use.";
      }

      choice edit-content {
        mandatory true;
        description
          "The content for the edit operation.";

        anyxml data {
          description
            "Inline data content.";
        }
        leaf url {
          if-feature nc:url;
          type inet:uri;
          description
            "URL-based config content.";
        }
      }
    }
  }
}
