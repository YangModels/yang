module ietf-tvr-schedule {
  yang-version 1.1;
  namespace "urn:ietf:params:xml:ns:yang:ietf-tvr-schedule";
  prefix tvr-schd;

  import ietf-schedule {
    prefix "schedule";
    reference
      "RFC 9922: A Common YANG Data Model for Scheduling";
  }

  organization
    "IETF TVR - Time Variant Routing Working Group";
  contact
    "WG Web:   <http://datatracker.ietf.org/wg/tvr>
     WG List:  <mailto:tvr@ietf.org>

     Author:   Yingzhen Qu
               <mailto:yingzhen.ietf@gmail.com>
     Author:   Acee Lindem
               <mailto:acee.ietf@gmail.com>
     Author:   Marc Blanchet
               <mailto:marc.blanchet@viagenie.ca>
     Author:   Eric Kinzie
               <mailto:ekinzie@labn.net>
     Author:   Don Fedyk
               <mailto:dfedyk@labn.net>";

  description
    "The YANG module contains common YANG definitions for
     time-variant schedule.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-05-19 {
    description
      "Initial Version";
    reference
      "RFC XXXX: A YANG Data Model for Scheduled Attributes.";
  }

  grouping tvr-schedule {
    list schedule {
      key schedule-id;
      leaf schedule-id {
        type uint32;
        description
          "Identifies the schedule.";
      }
      choice schedule-type {
        description
          "Choice of schedule type.";
        case period {
          description
            "A schedule with a single instance.";
          uses schedule:period-of-time;
        }
        case recurrence {
          description
            "A schedule with recurrence. The time is defined in UTC
             format.";
          uses schedule:recurrence-utc;
        }
      }

      description
        "list of schedules.";
    }
    description
      "A common grouping definition of schedules.";
  }

}
