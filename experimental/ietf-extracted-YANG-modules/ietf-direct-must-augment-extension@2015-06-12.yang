module ietf-direct-must-augment-extension {

  namespace
    "urn:ietf:params:xml:ns:yang:ietf-direct-must-augment-extension";
  prefix "direct-must-augment-ex";

  organization
    "IETF NETMOD (NETCONF Data Modeling Language) Working Group";

  contact
    "WG Web:   <http://tools.ietf.org/wg/netmod/>
     WG List:  <mailto:netmod@ietf.org>

     Editor:   Vladimir Vassilev
               <mailto:vladimir@transpacket.com>";

  description
    "This module contains extension of the standard augment statement.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: update the date below with the date of RFC publication
  // and remove this note.
  revision 2015-06-12 {
    description
      "Initial revision.";
    reference
      "RFC XXXX: Direct Must Augment Extension";
  }

  /*
   * Extension
   */

  extension augment {
    argument target;
    description
      "This extension introduces a direct must augment statement
       capable of augmenting existing data nodes with new must
       sub-statements.";
  }
}
