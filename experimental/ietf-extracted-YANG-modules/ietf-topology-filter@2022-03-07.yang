module ietf-topology-filter {
  yang-version 1.1;
  namespace "urn:ietf:params:xml:ns:yang:ietf-topology-filter";
  prefix topo-filt;

  import ietf-inet-types {
    prefix inet;
    reference
      "RFC 6991: Common YANG Data Types";
  }
  import ietf-network {
    prefix nw;
    reference
      "RFC 8345: A YANG Data Model for Network Topologies";
  }
  import ietf-te-types {
    prefix te-types;
    reference
      "RFC 8776: Common YANG Data Types for Traffic Engineering";
  }
  import ietf-te-topology {
    prefix tet;
    reference
      "RFC 8795: YANG Data Model for Traffic Engineering Topologies";
  }

  organization
    "IETF Traffic Engineering Architecture and Signaling (TEAS)
     Working Group.";
  contact
    "WG Web:   <http://tools.ietf.org/wg/teas/>
     WG List:  <mailto:teas@ietf.org>
     Editor:   Vishnu Pavan Beeram
               <mailto:vbeeram@juniper.net>

     Editor:   Tarek Saad
               <mailto:tsaad@juniper.net>

     Editor:   Rakesh Gandhi
               <mailto:rgandhi@cisco.com>

     Editor:   Xufeng Liu
               <mailto:xufeng.liu.ietf@gmail.com>";

  description
    "This YANG module defines data definitions for managing
     topology filters.

     Copyright (c) 2022 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX; see the
     RFC itself for full legal notices.";

  revision 2022-03-07 {
    description
      "Initial revision.";
    reference
      "RFC XXXX: YANG Data Model for Topology Filters.";
  }

  /*
   * T Y P E D E F S
   */

  typedef igp-protocol {
    type enumeration {
      enum ospfv2 {
        description
          "OSPFv2.";
      }
      enum ospfv3 {
        description
          "OSPFv3.";
      }
      enum isis {
        description
          "IS-IS.";
      }
    }
    description
      "IGP Protocol Type.";
  }

  /*
   * G R O U P I N G S
   */
  /*
   * Grouping - Topology Information Source.
   */

  grouping igp-topology-info-source {
    description
      "Grouping for igp topology information source.";
    leaf protocol-id {
      type igp-protocol;
      description
        "IGP Protocol Type.";
    }
    leaf instance-id {
      type uint32;
      description
        "Information Source Instance.";
    }
    leaf division-id {
      type uint32;
      description
        "Information Source Division.";
    }
  }

  /*
   * Grouping - IGP Domain Identifier.
   */

  grouping igp-domain-identifier {
    description
      "Grouping for igp domain identifier.";
    container igp-domain-identifier {
      description
        "Container for igp domain identifier.";
      uses igp-topology-info-source;
      leaf algo-id {
        type uint8;
        description
          "Algorithm ID.";
      }
      leaf mt-id {
        type uint16;
        description
          "Multi Topology ID.";
      }
    }
  }

  /*
   * Grouping - Topology Reference
   */

  grouping topology-reference {
    description
      "Grouping for topology reference.";
    container topology-ref {
      description
        "Container for topology reference.";
      uses igp-domain-identifier;
      uses te-types:te-topology-identifier;
    }
  }

  /*
   * Grouping - Topology Information Sources
   */

  grouping topology-info-sources {
    description
      "Grouping for topology information sources.";
    list info-source {
      key "source-id instance-id division-id";
      description
        "List of information-sources.";
      leaf source-id {
        type tet:te-info-source;
        description
          "Information Source.";
      }
      leaf instance-id {
        type uint32;
        description
          "Information Source Instance.";
      }
      leaf division-id {
        type uint32;
        description
          "Information Source Division.";
      }
    }
  }

  /*
   * Grouping - Custom Topology Filters
   */

  grouping custom-topology-filters {
    description
      "Grouping for custom topology filters.";
    leaf-list link-affinity {
      type string;
      description
        "List of link affinities.";
    }
    leaf-list link-name {
      type string;
      description
        "List of link names.";
    }
    leaf-list node-prefix {
      type inet:ip-prefix;
      description
        "List of node IDs.";
    }
    leaf-list as {
      type inet:as-number;
      description
        "List of AS numbers.";
    }
    uses topology-info-sources;
  }

  /*
   * Grouping - Topology Filters
   */

  grouping topology-filters {
    description
      "Grouping for topology filters.";
    container topology-filters {
      presence "Enable Topology Filters.";
      description
        "Container for topology filters.";
      list topology-filter {
        key "name";
        description
          "List of topology filters.";
        leaf name {
          type string;
          description
            "A string that uniquely identifies the topology filter.";
        }
        uses topology-reference;
        container include-any {
          description
            "Include-any filters.";
          uses custom-topology-filters;
        }
        container include-all {
          description
            "Include-all filters.";
          uses custom-topology-filters;
        }
        container exclude {
          description
            "Exclude filters.";
          uses custom-topology-filters;
        }
      }
    }
  }

  /*
   * Grouping - Topology Filter Sets
   */

  grouping topology-filter-sets {
    description
      "Grouping for topology filter sets.";
    container topology-filter-sets {
      presence "Enable Topology Filter-Sets.";
      description
        "Container for topology filter sets.";
      list topology-filter-set {
        key "name";
        description
          "List of topology filter sets.";
        leaf name {
          type string;
          description
            "A string that uniquely identifies the topology
             filter-set.";
        }
        leaf-list topology-filter {
          type leafref {
            path "../../../topo-filt:topology-filters/"
               + "topo-filt:topology-filter/topo-filt:name";
          }
          description
            "Reference to a specific topology filter from the list
             of topology filters.";
        }
      }
    }
  }

  /*
   *  Augment - Topology Filters / Topology Filter-Sets
   */

  augment "/nw:networks" {
    description
      "Augment networks with topology-filters and
       topology-filter-sets.";
    uses topology-filters;
    uses topology-filter-sets;
  }
}
