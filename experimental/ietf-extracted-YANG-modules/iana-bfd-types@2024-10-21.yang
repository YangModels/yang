module iana-bfd-types {
  yang-version 1.1;
  namespace "urn:ietf:params:xml:ns:yang:iana-bfd-types";
  prefix iana-bfd-types;

  organization
    "IANA";
  contact
    "Internet Assigned Numbers Authority

     Postal: ICANN
             12025 Waterfront Drive, Suite 300
             Los Angeles, CA 90094-2536
             United States of America
     Tel:    +1 310 301 5800
     <mailto:iana@iana.org>";
  description
    "This module defines YANG data types for IANA-registered
     BFD parameters.

     This YANG module is maintained by IANA and reflects the
     'BFD Diagnostic Codes' and 'BFD Authentication Types'
     registries.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     The initial version of this YANG module is part of RFC 9127;
     see the RFC itself for full legal notices.";
  reference
    "RFC 9127: YANG Data Model for Bidirectional Forwarding
     Detection (BFD)";

  revision 2024-10-21 {
    description
      "Add NULL and Meticulous ISAAC authentication type.";
    reference
      "RFC XXXX: Optimizing BFD Authentication,
       I-D.ietf-bfd-stability: BFD Stability.";
  }

  revision 2021-10-21 {
    description
      "Initial revision.";
    reference
      "RFC 9127: YANG Data Model for Bidirectional Forwarding
       Detection (BFD)";
  }

  /*
   * Type definitions
   */

  typedef diagnostic {
    type enumeration {
      enum none {
        value 0;
        description
          "No Diagnostic.";
      }
      enum control-expiry {
        value 1;
        description
          "Control Detection Time Expired.";
      }
      enum echo-failed {
        value 2;
        description
          "Echo Function Failed.";
      }
      enum neighbor-down {
        value 3;
        description
          "Neighbor Signaled Session Down.";
      }
      enum forwarding-reset {
        value 4;
        description
          "Forwarding Plane Reset.";
      }
      enum path-down {
        value 5;
        description
          "Path Down.";
      }
      enum concatenated-path-down {
        value 6;
        description
          "Concatenated Path Down.";
      }
      enum admin-down {
        value 7;
        description
          "Administratively Down.";
      }
      enum reverse-concatenated-path-down {
        value 8;
        description
          "Reverse Concatenated Path Down.";
      }
      enum mis-connectivity-defect {
        value 9;
        description
          "Mis-connectivity defect.";
        reference
          "RFC 5880: Bidirectional Forwarding Detection (BFD)
           RFC 6428: Proactive Connectivity Verification, Continuity
           Check, and Remote Defect Indication for the MPLS
           Transport Profile";
      }
    }
    description
      "BFD diagnostic codes as defined in RFC 5880.  Values are
       maintained in the 'BFD Diagnostic Codes' IANA registry.
       Range is 0 to 31.";
    reference
      "RFC 5880: Bidirectional Forwarding Detection (BFD)";
  }

  typedef auth-type {
    type enumeration {
      enum reserved {
        value 0;
        description
          "Reserved.";
      }
      enum simple-password {
        value 1;
        description
          "Simple Password.";
      }
      enum keyed-md5 {
        value 2;
        description
          "Keyed MD5.";
      }
      enum meticulous-keyed-md5 {
        value 3;
        description
          "Meticulous Keyed MD5.";
      }
      enum keyed-sha1 {
        value 4;
        description
          "Keyed SHA1.";
      }
      enum meticulous-keyed-sha1 {
        value 5;
        description
          "Meticulous Keyed SHA1.";
      }
      enum null {
        value 6;
        description
          "NULL Auth. Used for stability measurement.";
      }
      enum optimized-md5-meticulous-keyed-isaac {
        value 7;
        description
          "BFD Optimized Authentication using Meticulous Keyed
           MD5 as the strong authentication and Meticulous Keyed
           ISAAC as the 'optimized' authentication.";
      }
      enum optimized-sha1-meticulous-keyed-isaac {
        value 8;
        description
          "BFD Optimized Authentication using Meticulous Keyed
           SHA-1 as the strong authentication and Meticulous Keyed
           ISAAC as the 'optimized' authentication.";
      }
    }
    description
      "BFD authentication type as defined in RFC 5880.  Values are
       maintained in the 'BFD Authentication Types' IANA registry.
       Range is 0 to 255.";
    reference
      "RFC 5880: Bidirectional Forwarding Detection (BFD),
       I-D.ietf-bfd-optimizing-authentication:
           Optimizing BFD Authentication,
       I-D.ietf-bfd-stability: BFD Stability.";
  }
}
