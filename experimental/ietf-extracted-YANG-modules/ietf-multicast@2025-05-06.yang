module ietf-multicast {
  yang-version 1.1;
  namespace "urn:ietf:params:xml:ns:yang:ietf-multicast";
  prefix ietf-multicast;

  import ietf-yang-types {
    prefix yang;
    reference
      "RFC 6991: Common YANG Data Types";
  }
  import ietf-inet-types {
    prefix inet;
    reference
      "RFC 6991: Common YANG Data Types";
  }
  import ietf-routing-types {
    prefix rt-types;
    reference
      "RFC 8294: Common YANG Data Types for the Routing Area";
  }
  import ietf-routing {
    prefix rt;
    reference
      "RFC 8349: A YANG Data Model for Routing Management
                 (NMDA Version)";
  }
  import ietf-te-types {
    prefix te-types;
    reference
      "RFC 8776: Common YANG Data Types for Traffic Engineering";
  }
  import ietf-bier {
    prefix bier;
    reference
      "I-D.ietf-bier-bier-yang: YANG Data Model for BIER Protocol";
  }
  import ietf-sr-policy {
    prefix sr-policy;
    reference
      "I-D.ietf-spring-sr-policy-yang: YANG Data Model for Segment
       Routing Policy";
  }

  organization
    " IETF MBONED (MBONE Deployment) Working Group";
  contact
    "WG List:  <mailto:mboned@ietf.org>

     Editor:   Zheng Zhang
               <mailto:zhang.zheng@zte.com.cn>
     Editor:   Cui Wang
               <mailto:lindawangjoy@gmail.com>
     Editor:   Ying Cheng
               <mailto:chengying10@chinaunicom.cn>
     Editor:   Xufeng Liu
               <mailto:xufeng.liu.ietf@gmail.com>
     Editor:   Mahesh Sivakumar
               <mailto:sivakumar.mahesh@gmail.com>
    ";

  // RFC Ed.: replace XXXX with actual RFC number and remove
  // this note

  description
    "The module defines the YANG definitions for multicast service
     management. This model indicates the overlay, transport protocol
     used by a multicast flow. And the underlay protocol used for
     the transport layer building.

     Copyright (c) 2025 IETF Trust and the persons identified as
     authors of the code.  All rights reserved.

     Redistribution and use in source and binary forms, with or
     without modification, is permitted pursuant to, and subject
         to the license terms contained in, the Revised BSD License
     set forth in Section 4.c of the IETF Trust's Legal Provisions
     Relating to IETF Documents
     (https://trustee.ietf.org/license-info).

     This version of this YANG module is part of RFC XXXX; see the
     RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2025-05-06 {
    description
      "Initial revision.";
    reference
      "RFC XXXX: A YANG Data Model for multicast service management
           YANG.";
  }

  /*
   *feature
   */

  feature bier {
    description
      "Cooperation with BIER technology.";
    reference
      "RFC 8279:
         Multicast Using Bit Index Explicit Replication (BIER)";
  }

  feature sr {
    description
      "Cooperation with Segment Routing technology.";
    reference
      "RFC 8402: Segment Routing Architecture";
  }

  feature mldp {
    description
      "Cooperation with MLDP technology.";
    reference
      "RFC 6388:
         Label Distribution Protocol Extensions
         for Point-to-Multipoint and Multipoint-to-Multipoint
         Label Switched Paths";
  }

  feature p2mp-te {
    description
      "Cooperation with RSVP TE P2MP technology.";
    reference
      "RFC 4875: Extensions to Resource Reservation Protocol -
        Traffic Engineering (RSVP-TE) for Point-to-Multipoint TE
        Label Switched Paths (LSPs)";
  }

  feature pim {
    description
      "Cooperation with PIM technology.";
    reference
      "RFC 7761: Protocol Independent Multicast - Sparse Mode
       (PIM-SM): Protocol Specification (Revised)";
  }

  /*
   *typedef
   */

  typedef ip-multicast-source-address {
    type union {
      type enumeration {
        enum * {
          description
            "Any source address.";
        }
      }
      type inet:ipv4-address;
      type inet:ipv6-address;
    }
    description
      "Multicast source IP address type.";
  }

  typedef tree-sid {
    type union {
      type rt-types:mpls-label;
      type inet:ip-prefix;
    }
    description
      "The type of the Segment Identifier of a Replication segment
       is a SR-MPLS label or a SRv6 SID.";
  }
  /*
   * Identities
   */

  identity multicast-service {
    base rt:control-plane-protocol;
    description
      "Identity for the multicast model.";
  }

  identity overlay-type {
    description
      "Base identity for the type of multicast overlay technology.";
  }

  identity transport-type {
    description
      "Identity for the multicast transport technology.";
  }

  identity underlay-type {
    description
      "Identity for the multicast underlay technology.";
  }

  identity tunnel-encap-type {
    description
      "Base identity for the type of multicast flow tunnel
       encapsulation.";
  }

  identity tunnel-encap-vxlan {
    base tunnel-encap-type;
    description
      "The VXLAN encapsulation is used for flow encapsulation.";
    reference
      "RFC 7348: Virtual eXtensible Local Area Network (VXLAN):
       A Framework for Overlaying Virtualized Layer 2 Networks
       over Layer 3 Networks";
  }

  identity tunnel-encap-nvgre {
    base tunnel-encap-type;
    description
      "The NVGRE encapsulation is used for flow encapsulation.";
    reference
      "RFC 7637: NVGRE: Network Virtualization Using Generic
       Routing Encapsulation";
  }

  identity tunnel-encap-geneve {
    base tunnel-encap-type;
    description
      "The GENEVE encapsulation is used for flow encapsulation.";
    reference
      "RFC 8926: Geneve: Generic Network Virtualization
       Encapsulation";
  }

  identity overlay-pim {
    base overlay-type;
    description
      "Using PIM as multicast overlay technology.";
    reference
      "I-D.ietf-bier-pim-signaling:
         PIM Signaling Through BIER Core";
  }

  identity mld {
    base overlay-type;
    description
      "Using MLD as multicast overlay technology.";
    reference
      "I-D.ietf-bier-mld:
         BIER Ingress Multicast Flow Overlay
         using Multicast Listener Discovery Protocols";
  }

  identity mld-snooping {
    base overlay-type;
    description
      "Using MLD-snooping as multicast overlay technology.";
    reference
      "RFC 4541:
         Considerations for Internet Group Management
         Protocol (IGMP) and Multicast Listener
         Discovery (MLD) Snooping Switches";
  }

  identity evpn {
    base overlay-type;
    description
      "Using EVPN as multicast overlay technology.";
    reference
      "RFC 7432: BGP MPLS-Based Ethernet VPN
       RFC 9572: Updates on EVPN BUM Procedures
       RFC 9624: EVPN Broadcast, Unknown Unicast, or Multicast
         (BUM) Using Bit Index Explicit Replication (BIER)";
  }

  identity mvpn {
    base overlay-type;
    description
      "Using MVPN as multicast overlay technology.";
    reference
      "RFC 6513: Multicast in MPLS/BGP IP VPNs
       RFC 7716:
         Global Table Multicast with BGP Multicast VPN
         (BGP-MVPN) Procedures
       RFC 8556: Multicast VPN Using Bit Index Explicit Replication
         (BIER)";
  }

  identity bier {
    base transport-type;
    description
      "Using BIER as multicast transport technology.";
    reference
      "RFC 8279:
         Multicast Using Bit Index Explicit Replication (BIER)";
  }

  identity bier-te {
    base transport-type;
    description
      "Using BIER-TE as multicast transport technology.";
    reference
      "RFC 9262:
         Traffic Engineering for Bit Index Explicit Replication
         (BIER-TE)";
  }

  identity mldp {
    base transport-type;
    description
      "Using mLDP as multicast transport technology.";
    reference
      "RFC 6388:
         Label Distribution Protocol Extensions
         for Point-to-Multipoint and Multipoint-to-Multipoint
         Label Switched Paths";
  }

  identity rsvp-te-p2mp {
    base transport-type;
    description
      "Using P2MP TE as multicast transport technology.";
    reference
      "RFC 4875:
         Extensions to Resource Reservation Protocol
         - Traffic Engineering (RSVP-TE) for Point-to-Multipoint
         TE Label Switched Paths (LSPs).";
  }

  identity sr-p2mp {
    base transport-type;
    description
      "Using Segment Routing  as multicast transport technology.";
    reference
      "I-D.ietf-pim-sr-p2mp-policy:
         Segment Routing Point-to-Multipoint Policy.";
  }

  identity pim {
    base transport-type;
    description
      "Using PIM as multicast transport technology.";
    reference
      "RFC 7761:
         Protocol Independent Multicast - Sparse Mode
         (PIM-SM): Protocol Specification (Revised).";
  }

  identity bgp {
    base underlay-type;
    description
      "Using BGP as underlay technology to build the multicast
       transport layer. For example, using BGP as BIER underlay.";
    reference
      "I-D.ietf-bier-idr-extensions: BGP Extensions for BIER.";
  }

  identity ospf {
    base underlay-type;
    description
      "Using OSPF as multicast underlay technology.
       For example, using OSPF as BIER underlay.";
    reference
      "RFC 8444:
         OSPFv2 Extensions for Bit Index Explicit Replication (BIER),
       I-D.ietf-bier-ospfv3-extensions:
         OSPFv3 Extensions for BIER.";
  }

  identity isis {
    base underlay-type;
    description
      "Using IS-IS as multicast underlay technology.
       For example, using IS-IS as BIER underlay.";
    reference
      "RFC 8401:
         Bit Index Explicit Replication (BIER) Support via IS-IS";
  }

  identity babel {
    base underlay-type;
    description
      "Using BABEL as multicast underlay technology.
       For example, using BABEL as BIER underlay.";
    reference
      "RFC 8966: The Babel Routing Protocol
       I-D.zhang-bier-babel-extensions: BIER in BABEL";
  }

  identity rift {
    base underlay-type;
    description
      "Using RIFT as multicast underlay technology.
       For example, using RIFT as BIER underlay.";
    reference
      "RFC 9692: RIFT: Routing in Fat Trees.
       I-D.zzhang-bier-rift: Supporting BIER with RIFT";
  }

  identity event-type {
    description
      "The events of the multicast service.";
  }

  identity event-up {
    base event-type;
    description
      "The multicast service works.";
  }

  identity event-down {
    base event-type;
    description
      "There is something wrong with ingress or egress node,
       and node can't work properlay.";
  }

  identity protocol-enabled {
    base event-type;
    description
      "The protocol that is used for multicast
       flows have been enabled.";
  }

  identity protocol-disabled {
    base event-type;
    description
      "The protocol that is used by multicast
       flows have been disabled.";
  }

  grouping general-multicast-key {
    description
      "The general multicast keys. They are used to differentiate
       multicast service.";
    leaf source-address {
      type ip-multicast-source-address;
      description
        "The IP source address of the multicast flow. The
         value set to * means that the receiver interests
         in all source that relevant to one given group.";
    }
    leaf group-address {
      type rt-types:ip-multicast-group-address;
      mandatory true;
      description
        "The IP group address of multicast flow. This
         type represents a version-neutral IP multicast group
         address. The format of the textual representation
         implies the IP version.";
      reference
        "RFC 8294: Common YANG Data Types for the Routing Area.";
    }
  }

  grouping optional-multicast-key {
    description
      "The optional multicast keys. They are used to differentiate
       multicast service.";
    leaf vpn-rd {
      type rt-types:route-distinguisher;
      description
        "A Route Distinguisher is used to differentiate
         routes from different MVPNs.";
      reference
        "RFC 8294: Common YANG Data Types for the Routing Area.
         RFC 6513: Multicast in MPLS/BGP IP VPNs.";
    }
    leaf mac-address {
      type yang:mac-address;
      description
        "The mac address of flow. In the EVPN situation, the L2
         flow that is called
         BUM (Broadcast, Unknown Unicast, Multicast)
         can be sent to the other PEs that
         are in a same broadcast domain.";
      reference
        "RFC 6991: Common YANG Data Types.
         RFC 7432: BGP MPLS-Based Ethernet VPN.";
    }
    leaf vni-value {
      type uint32;
      description
        "The value of VXLAN network identifier, virtual subnet ID
         or virtual net identifier. This value and vni-type is used
         to indicate a specific virtual multicast service.";
    }
  }

  // multicast-key

  grouping encap-type {
    description
      "The encapsulation type used for flow forwarding.
       This encapsulation acts as the inner encapsulation,
       as compare to the outer multicast-transport encapsulation.";
    choice encap-type {
      case mpls {
        description
          "The BIER forwarding depends on mpls.";
        reference
          "RFC 8296: Encapsulation for Bit Index Explicit
           Replication (BIER) in MPLS and Non-MPLS Networks.";
      }
      case eth {
        description
          "The BIER forwarding depends on ethernet.";
        reference
          "RFC 8296: Encapsulation for Bit Index Explicit
           Replication (BIER) in MPLS and Non-MPLS Networks.";
      }
      case ipv6 {
        description
          "The BIER forwarding depends on IPv6.";
        reference
          "I-D.ietf-bier-bierin6: BIER in IPv6 (BIERin6)";
      }
      description
        "The encapsulation type in BIER.";
    }
  }

  // encap-type
  grouping bier-key {
    description
      "The key parameters set for BIER/BIER TE forwarding.";
    reference
      "RFC 8279: Multicast Using Bit Index Explicit Replication
       (BIER).";
    leaf sub-domain {
      type uint16;
      description
        "The subdomain ID that the multicast flow belongs to.";
    }
    leaf bitstringlength {
      type uint16;
      description
        "The bitstringlength used by BIER forwarding.";
    }
    leaf set-identifier {
      type uint16;
      description
        "The set identifier used by the multicast flow.";
    }
    leaf bier-encap-type {
      type identityref {
        base bier:bier-encapsulation;
      }
      description
        "The BIER encapsulation that can be used in either MPLS
         networks or non-MPLS networks.";
    }
  }

  grouping transport-tech {
    description
      "The transport technology selected for the multicast service.
       For one specific multicast flow.";
    leaf type {
      type identityref {
        base transport-type;
      }
      description
        "The type of transport technology";
    }
    choice transport-tech-type {
      description
        "The type of transport technology";
      case bier {
        if-feature "bier";
        description
          "Using BIER as the transport technology.
           The BIER technology is introduced in RFC8279.
           The parameters are consistent with the definition in
           BIER YANG data model.";
        reference
          "RFC 8296: Encapsulation for Bit Index Explicit
             Replication (BIER) in MPLS and Non-MPLS Networks
           I-D.ietf-bier-bier-yang:
             YANG Data Model for BIER Protocol.";
        uses bier-key;
      }
      case bier-te {
        if-feature "bier";
        description
          "Using BIER-TE as the transport technology.
           The BIER-TE technology is introduced in RFC9262.
           The parameters are consistent with the definition in
           BIER and BIER TE YANG data model.";
        reference
          "RFC 9262: Tree Engineering for Bit Index Explicit
             Replication (BIER-TE)
           I-D.ietf-bier-bier-yang: YANG Data Model for BIER Protocol
           I-D.ietf-bier-te-yang: A YANG data model for Traffic
             Engineering for Bit Index Explicit Replication
             (BIER-TE)";
        //uses bier-key;
        list bitstring {
          key "name";
          leaf name {
            type string;
            description
              "The name of the bitstring";
          }
          list bier-te-adj {
            key "adj-id";
            leaf adj-id {
              type uint16;
              description
                "The link adjacency ID used for BIER TE forwarding.";
            }
            description
              "The adjacencies ID used for BIER TE bitstring
               encapsulation.";
          }
          description
            "The bitstring name and detail used for BIER TE
             forwarding encapsulation. One or more bitstring can be
             used for backup path.";
        }
      }
      case mldp {
        if-feature "mldp";
        description
          "Using MLDP as the transport technology.";
        reference
          "RFC 6388:
             Label Distribution Protocol Extensions
             for Point-to-Multipoint and Multipoint-to-Multipoint
             Label Switched Paths";
      }
      case rsvp-te-p2mp {
        if-feature "p2mp-te";
        description
          "Using RSVP TE P2MP as the transport technology.";
        reference
          "RFC 4875: Extensions to Resource Reservation Protocol -
            Traffic Engineering (RSVP-TE) for Point-to-Multipoint TE
            Label Switched Paths (LSPs)
           RFC 8776: Common YANG Data Types for Traffic Engineering";
        leaf template-name {
          type te-types:te-template-name;
          description
            "A type for the name of a TE node template or TE link
             template.";
        }
      }
      case pim {
        if-feature "pim";
        description
          "Using PIM as the transport technology.";
        reference
          "RFC 7761: Protocol Independent Multicast - Sparse Mode
           (PIM-SM): Protocol Specification (Revised)";
        uses pim;
      }
      case sr-p2mp {
        if-feature "sr";
        description
          "Using SR P2MP as the transport technology.
           The ingress replication and the treesid
           function will not be used at the same time.";
        reference
          "RFC 8402: Segment Routing Architecture
           RFC 9524: Segment Routing Replication for Multipoint
             Service Delivery
           I-D.ietf-pim-sr-p2mp-policy: Segment Routing
             Point-to-Multipoint Policy
           I-D.ietf-spring-sr-policy-yang: YANG Data Model for
             Segment Routing Policy";
        leaf-list ir-sr-policies {
          type leafref {
            path "/rt:routing/"
               + "sr-policy:segment-routing/"
               + "sr-policy:traffic-engineering/"
               + "sr-policy:attributes/"
               + "sr-policy:segment-lists/"
               + "sr-policy:segment-list/"
               + "sr-policy:name";
          }
          description
            "The segment list used for ingress replication.";
        }
      }
      // sr-p2mp
    }
  }

  // underlay-tech

  grouping underlay-tech {
    description
      "The underlay technology selected for the transport layer.
       The underlay technology has no straight relationship with
       the multicast overlay, it is used for transport path
       building, for example BIER forwarding path building.";
    leaf type {
      type identityref {
        base underlay-type;
      }
      description
        "The type of underlay technology";
    }
    choice underlay-tech-type {
      description
        "The type of underlay technology";
      case ospf {
        description
          "Using OSPF as the underlay technology.
           If OSPF protocol supports multiple topology feature,
           the associated topology name may be assigned.
           In case the topology name is assigned, the specific
           OSPF topology is used for underly to building the
           transport layer.";
        reference
          "RFC 4915: Multi-Topology Routing
           RFC 9129: YANG Data Model for the OSPF Protocol";
        leaf topology-id {
          type uint8;
          description
            "The MT-ID for the topology enabled in OSPF protocol";
        }
      }
      case isis {
        description
          "Using IS-IS as the underlay technology.
           If IS-IS protocol supports multiple topology feature,
           the associated topology name may be assigned.
           In case the topology name is assigned, the specific
           IS-IS topology is used for underly to building the
           transport layer.";
        reference
          "RFC 5120: M-IS-IS: Multi Topology Routing in IS-IS
           RFC 9130: YANG Data Model for the IS-IS Protocol";
      }
      case pim {
        description
          "Using PIM as the underlay technology.";
        reference
          "RFC 7761: Protocol Independent Multicast - Sparse Mode
           (PIM-SM): Protocol Specification (Revised)";
        uses pim;
      }
    }
  }

  // underlay-tech

  /*overlay*/
  grouping overlay-tech {
    container dynamic-overlay {
      leaf type {
        type identityref {
          base overlay-type;
        }
        description
          "The type of overlay technology";
      }
      choice overlay-tech-type {
        description
          "The type of overlay technology";
        case evpn {
          description
            "EVPN technology is used for multicast overlay.";
          reference
            "RFC 7432: BGP MPLS-Based Ethernet VPN
             RFC 9624: EVPN Broadcast, Unknown Unicast, or
             Multicast (BUM) Using Bit Index Explicit Replication
             (BIER)";
        }
        case mld {
          description
            "MLD/IGMP can be used as multicast overlay
             when BIER is used as transport technology.";
          reference
            "I-D:ietf-bier-mld: BIER Ingress Multicast Flow Overlay
             using Multicast Listener Discovery Protocols";
          leaf mld-instance-group {
            type rt-types:ip-multicast-group-address;
            description
              "The multicast address used for multiple MLD instance
               support.";
          }
        }
        case mld-snooping {
          description
            "MLD/IGMP snooping can be used as multicast overlay
             when BIER is used as transport technology.";
          reference
            "RFC 9166:A YANG Data Model for Internet Group
             Management Protocol (IGMP) and Multicast Listener
                         Discovery (MLD) Snooping";
          leaf mld-snooping-group {
            type rt-types:ip-multicast-group-address;
            description
              "The multicast address used for MLD-snooping.";
          }
        }
        case mvpn {
          description
            "MVPN technology is used for multicast overlay.
             The global table multicast can also be achieved.";
          reference
            "RFC 6513: Multicast in MPLS/BGP IP VPNs
             RFC 7716: Global Table Multicast with BGP Multicast VPN
             (BGP-MVPN) Procedures
             RFC 8556: Multicast VPN Using Bit Index Explicit
             Replication (BIER)";
        }
        case pim {
          description
            "PIM can be used as multicast overlay
             when BIER is used as transport technology.";
          reference
            "RFC 7761: Protocol Independent Multicast - Sparse Mode
             (PIM-SM): Protocol Specification (Revised)
             I-D.ietf-bier-pim-signaling: PIM Signaling Through BIER
             Core";
        }
      }
      description
        "The dynamic overlay technologies and associated parameter
         that may be set.";
    }
    description
      "The overlay technology used for multicast service.";
  }

  // overlay-tech
  /*transport*/

  grouping pim {
    description
      "The required information of pim transportion.";
    leaf source-address {
      type ip-multicast-source-address;
      description
        "The IP source address of the multicast flow. The
         value set to * means that the receiver interests
         in all source that relevant to one given group.";
    }
    leaf group-address {
      type rt-types:ip-multicast-group-address;
      mandatory true;
      description
        "The IP group address of multicast flow. This
         type represents a version-neutral IP multicast group
         address. The format of the textual representation
         implies the IP version.";
    }
    reference
      "RFC 7761: Protocol Independent Multicast - Sparse Mode
                 (PIM-SM): Protocol Specification (Revised).";
  }

  container multicast-service {
    description
      "The model of multicast YANG data. Include keys, overlay,
       transport and underlay.";
    list multicast-keys {
      key "source-address group-address";
      uses general-multicast-key;
      uses optional-multicast-key;
      container multicast-overlay {
        description
          "The overlay information of multicast service.
           Overlay technology is used to exchange multicast
           flows information. Overlay technology may not be
           used in SDN controlled situation. Different overlay
           technologies can be chosen according to different
           deploy consideration.";
        leaf vni-type {
          type identityref {
            base tunnel-encap-type;
          }
          description
            "The encapsulated type for the multicast flow,
             it is used to carry the virtual network identifier
             for the multicast service.
             When this type is set, the associated vni-value
             MUST be set.";
        }
        container ingress-egress {
          description
            "The ingress and egress nodes address collection.
             The ingress node may use the egress nodes set
             directly to encapsulate the multicast flow by
             transport technology.";
          leaf-list ingress-nodes {
            type inet:ip-address;
            description
              "The ip address of ingress node for one or more
               multicast flow. Or the ingress node of MVPN,
               EVPN and BIER.
               In MVPN, this is the address of ingress
               PE; in BIER, this is the BFR-prefix of BFIR.
               Two or more ingress nodes may exist for the
               redundant ingress node protection.";
          }
          leaf-list egress-nodes {
            type inet:ip-address;
            description
              "The ip address of egress nodes for the multicast flow.
               Or the egress node of MVPN, EVPN and BIER.
               In MVPN, this is the address of egress PE;
               in BIER, this is the BFR-prefix of BFER.";
          }
        }
        container bier-ids {
          if-feature "bier";
          description
            "The BFR-ids of ingress and egress BIER nodes for
             one or more multicast flows. This overlay is used
             with BIER transport technology. The egress nodes
             set can be used to encapsulate the multicast flow
             directly in the ingress node.";
          reference
            "RFC 8279: Multicast Using Bit Index Explicit
             Replication (BIER)";
          leaf sub-domain {
            type uint16;
            description
              "The sub-domain that this multicast flow belongs to.";
          }
          leaf-list ingress-nodes {
            type uint16;
            description
              "The BFR-ID of the ingress node.";
          }
          leaf-list egress-nodes {
            type uint16;
            description
              "The BFR-ID of the egress node.";
          }
        }
        uses overlay-tech;
      }
      container multicast-transport {
        description
          "The transportion of multicast service. Transport
           protocol is responsible for delivering multicast
           flows from ingress nodes to egress nodes with or
           without specific encapsulation. Different transport
           technology can be chosen according to different
           deploy consideration. Once a transport technology
           is chosen, associated protocol should be triggered
           to run.";
        uses transport-tech;
      }
      container multicast-underlay {
        description
          "The underlay of multicast service. Underlay protocol
           is used to build transport layer. Underlay protocol
           need not be assigned in ordinary network since
           existed underlay protocol fits well, but it can be
           assigned in particular networks for better
           controll. Once an underlay technology is chosen,
           associated protocol should be triggered to run.";
        uses underlay-tech;
      }
      description
        "The model of multicast YANG data. Include keys,
         overlay, transport and underlay.";
    }
  }

  /*Notifications*/

  notification ingress-egress-event {
    leaf event-type {
      type identityref {
        base event-type;
      }
      description
        "The event type.";
    }
    container multicast-key {
      uses general-multicast-key;
      uses optional-multicast-key;
      description
        "The associated multicast keys that are influenced by
         ingress or egress node failure.";
    }
    uses overlay-tech;
    container transport-tech {
      description
        "The modules can be used to forward multicast flows.";
      uses transport-tech;
    }
    container underlay-tech {
      description
        "There is something wrong with the module which is
         used to build multicast transport layer.";
      uses underlay-tech;
    }
    description
      "Notification events for the ingress or egress nodes. Like
       node failure, overlay/ transport/ underlay module
       loading/ unloading. And the potential failure about some
       multicast flows and associated
       overlay/ transport/ underlay technologies.";
  }
}
