module ietf-yang-push-revision {
  yang-version 1.1;
  namespace
    "urn:ietf:params:xml:ns:yang:ietf-yang-push-revision";
  prefix ypm;
  import ietf-subscribed-notifications {
    prefix sn;
    reference
      "RFC 8639: Subscription to YANG Notifications";
  }
  import ietf-yang-revisions {
    prefix rev;
    reference
      "RFC XXXX: draft-ietf-netmod-yang-module-versioning-06, Updated YANG
      Module Revision Handling";
  }
  import ietf-yang-semver {
    prefix ysver;
    reference
      "RFC XXXX: draft-ietf-netmod-yang-semver-08, YANG Semantic Versioning";
  }

  organization "IETF NETCONF (Network Configuration) Working Group";
  contact
    "WG Web:   <http:/tools.ietf.org/wg/netconf/>
     WG List:  <mailto:netconf@ietf.org>
     Authors:  Thomas Graf
               <mailto:thomas.graf@swisscom.com>
               Benoit Claise
               <mailto:benoit.claise@huawei.com>
               Alex Huang Feng
               <mailto:alex.huang-feng@insa-lyon.fr>";

  description
    "Defines YANG push event notification header with the revision and
    the revision-label. Adds the support of the revision and
    revision-label selection in the YANG push subscription RPCs.

    Copyright (c) 2023 IETF Trust and the persons identified as
    authors of the code.  All rights reserved.

    Redistribution and use in source and binary forms, with or without
    modification, is permitted pursuant to, and subject to the license
    terms contained in, the Revised BSD License set forth in Section
    4.c of the IETF Trust's Legal Provisions Relating to IETF Documents
    (https://trustee.ietf.org/license-info).

    This version of this YANG module is part of RFC XXXX; see the RFC
    itself for full legal notices.";

  revision 2023-01-12 {
    description
      "First revision";
    reference
      "RFC XXXX: Support of Versioning in YANG Notifications Subscription";
  }

  feature yang-push-revision-supported {
    description
      "This feature indicates the YANG Subscription Notifications supports
      the revision and revision-label defined in this YANG module.";
  }

  grouping yang-push-module-version-config {
    description
      "This grouping combines the revision and revision-label leaves, with
       the revison being configurable.";
    leaf revision {
      type rev:revision-date-or-label;
      description
        "This references the YANG module revision to be sent in the subscription.";
    }
    leaf revision-label {
      type ysver:version;
      description
        "This references the YANG module semversion to be sent in the subscription.";
    }
  }

  grouping yang-push-module-version {
    description
      "This grouping combines the revision and revision-label leaves, with
       the revison being non configurable.";
    leaf revision {
      type rev:revision-date-or-label;
      config false;
      mandatory true;
      description
        "This references the YANG module revision of the sent notification message.";
    }
    leaf revision-label {
      type ysver:version;
      description
        "This references the YANG module semversion of the sent notification message.";
    }
  }

  // Subscription parameters
  augment "/sn:establish-subscription/sn:input/sn:target" {
    description
      "Augment the establish-subscription RPC from the ietf-subscribed-notifications
      YANG module with the yang-push-module-version-config grouping.";
    uses ypm:yang-push-module-version-config;
  }
  augment "/sn:modify-subscription/sn:input/sn:target" {
  description
      "Augment the modify-subscription RPC from the ietf-subscribed-notifications
      YANG module with the yang-push-module-version-config grouping.";
          uses ypm:yang-push-module-version-config;
  }

  // Subscription notifications
  augment "/sn:subscription-started/sn:target" {
  description
      "Augment the subscription-started RPC from the ietf-subscribed-notifications
      YANG module with the yang-push-module-version grouping.";
    uses ypm:yang-push-module-version;
  }
  augment "/sn:subscription-modified/sn:target" {
  description
      "Augment the subscription-modified RPC from the ietf-subscribed-notifications
      YANG module with the yang-push-module-version grouping.";
    uses ypm:yang-push-module-version;
  }

  // Subscription container
  augment "/sn:subscriptions/sn:subscription/sn:target" {
  description
      "Augment the subscriptions RPC from the ietf-subscribed-notifications
      YANG module with the yang-push-module-version grouping.";
    uses ypm:yang-push-module-version;
  }
}
