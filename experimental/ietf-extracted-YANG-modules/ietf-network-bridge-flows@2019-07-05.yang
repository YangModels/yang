module ietf-network-bridge-flows {
  namespace "urn:ietf:params:xml:ns:yang:ietf-network-bridge-flows";
  prefix flow;

  import ietf-network-bridge {
    prefix netbr;
  }
  import ietf-inet-types {
    prefix inet;
    revision-date 2013-07-15;
  }
  import ietf-yang-types {
    prefix yang;
    revision-date 2013-07-15;
  }

  organization
    "IETF NETMOD (NETCONF Data Modeling Language) Working Group";
  contact
    "WG Web:   <http://tools.ietf.org/wg/netmod/>
     WG List:  <mailto:netmod@ietf.org>

     Editor:   Vladimir Vassilev
               <mailto:vladimir@transpacket.com>";
  description
    "This module contains a collection of YANG definitions for
     description and management of network bridge based on
     flows.

     Copyright (c) 2019 IETF Trust and the persons identified as
     authors of the code. All rights reserved.

     Redistribution and use in source and binary forms, with or
     without modification, is permitted pursuant to, and subject
     to the license terms contained in, the Simplified BSD
     License set forth in Section 4.c of the IETF Trust's
     Legal Provisions Relating to IETF Documents
     (http://trustee.ietf.org/license-info).

     This version of this YANG module is part of RFC XXXX; see
     the RFC itself for full legal notices.";

  revision 2019-07-05 {
    description
      "Unreleased revision.";
    reference
      "RFC XXXX: Network Bridge";
  }

  typedef vlan-pcp {
    type uint8 {
      range "0..7";
    }
    description
      "IEEE 802.1p priority. It indicates the frame priority level.
       Values are from 0 (best effort) to 7 (highest);
       1 represents the lowest priority.";
  }

  typedef vlan-id {
    type uint16 {
      range "0..4095";
    }
  }

  typedef ether-type {
    type uint32;
  }

  typedef vlan-cfi {
    type int32;
  }

  grouping address {
    choice address {
      case ipv4 {
        leaf ipv4-address {
          type inet:ipv4-prefix;
        }
      }
      case ipv6 {
        leaf ipv6-address {
          type inet:ipv6-prefix;
        }
      }
    }
  }

  grouping ordered {
    leaf order {
      type int32;
    }
  }

  grouping action-list {
    list action {
      key "order";
      uses ordered;
      uses action;
    }
  }

  grouping action {
    choice action {
      case output-action-case {
        container output-action {
          leaf out-port {
            type netbr:port-ref;
          }
          leaf max-length {
            type uint16;
          }
        }
      }
      case controller-action-case {
        container controller-action {
          leaf max-length {
            type uint16;
          }
        }
      }
      case drop-action-case {
        container drop-action {
          presence "no content action";
        }
      }
      case pop-vlan-action-case {
        container pop-vlan-action {
          presence "no content action";
        }
      }
      case push-vlan-action-case {
        container push-vlan-action {
          leaf ethernet-type {
            type uint16;
          }
          leaf tag {
            type int32;
          }
          leaf pcp {
            type int32;
          }
          leaf cfi {
            type vlan-cfi;
          }
          leaf vlan-id {
            type vlan-id;
          }
        }
      }
      case set-vlan-cfi-action-case {
        container set-vlan-cfi-action {
          leaf vlan-cfi {
            type vlan-cfi;
          }
        }
      }
      case set-vlan-id-action-case {
        container set-vlan-id-action {
          leaf vlan-id {
            type vlan-id;
          }
        }
      }
      case set-vlan-pcp-action-case {
        container set-vlan-pcp-action {
          leaf vlan-pcp {
            type vlan-pcp;
          }
        }
      }
      case strip-vlan-action-case {
        container strip-vlan-action {
          presence "no content action";
        }
      }
    }
  }

  grouping mac-address-filter {
    leaf address {
      type yang:mac-address;
      mandatory true;
    }
    leaf mask {
      type yang:mac-address;
    }
  }

  grouping ethernet-match-fields {
    container ethernet-source {
      presence "Match field is active and set";
      description
        "Ethernet source address.";
      uses mac-address-filter;
    }
    container ethernet-destination {
      presence "Match field is active and set";
      description
        "Ethernet destination address.";
      uses mac-address-filter;
    }
    container ethernet-type {
      presence "Match field is active and set";
      description
        "Ethernet frame type.";
      leaf type {
        type ether-type;
        mandatory true;
      }
    }
  }

  grouping vlan-match-fields {
    container vlan-id {
      presence "Match field is active and set";
      description
        "VLAN id.";
      leaf vlan-id-present {
        type boolean;
      }
      leaf vlan-id {
        type vlan-id;
      }
    }
    leaf vlan-pcp {
      type vlan-pcp;
      description
        "VLAN priority.";
    }
  }

  grouping match {
    leaf in-port {
      type netbr:port-ref;
    }
    container ethernet-match {
      uses ethernet-match-fields;
    }
    container vlan-match {
      uses vlan-match-fields;
    }
  }

  grouping raw-packet {
    description
      "Basic packet structure.";
    leaf ingress {
      type netbr:port-ref;
    }
    leaf payload {
      type binary;
    }
  }

  grouping packet-in {
    leaf packet-in-reason {
      type identityref {
        base packet-in-reason;
      }
    }
    uses raw-packet;
  }

  grouping ethernet-packet {
    description
      "Ethernet packet headers structure.";
    leaf source {
      type yang:mac-address;
    }
    leaf destination {
      type yang:mac-address;
    }
  }

  identity packet-in-reason {
    description
      "Base identity for all the available packet in reasons.";
  }

  identity no-match {
    base packet-in-reason;
    description
      "No matching flow in the classifier";
  }

  identity send-to-controller {
    base packet-in-reason;
    description
      "Explicit instruction to send packet to controller";
  }

  identity invalid-ttl {
    base packet-in-reason;
    description
      "Packet with invalid TTL";
  }

  notification packet-received {
    description
      "Delivery of incoming packet.";
    uses packet-in;
    container match {
      uses match;
    }
  }

  rpc transmit-packet {
    description
      "Sending packet out.";
    input {
      leaf egress {
        type netbr:port-ref;
      }
      uses raw-packet;
      uses action-list;
    }
  }

  container packet-in-message {
    uses packet-in;
    container match {
      uses match;
    }
  }

  grouping flow {
    container match {
      uses match;
    }
    container actions {
      uses action-list;
    }
    leaf priority {
      type uint16;
    }
    leaf container-name {
      type string;
    }
    leaf flow-name {
      type string;
    }
  }

  typedef flow-id {
    type inet:uri;
  }

  container flows {
    list flow {
      key "id";
      leaf id {
        type flow-id;
      }
      uses flow;
      container flow-statistics {
        config false;
        leaf packet-count {
          type yang:counter64;
        }
        leaf byte-count {
          type yang:counter64;
        }
      }
    }
  }
}
