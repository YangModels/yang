module ietf-mpted {
  yang-version 1.1;
  namespace "urn:ietf:params:xml:ns:yang:ietf-mpted";
  prefix mpted;

  import ietf-te {
    prefix te;
    reference
      "draft-ietf-teas-yang-te: A YANG Data Model for Traffic
       Engineering Tunnels, Label Switched Paths, and Interfaces";
  }
  import ietf-routing-types {
    prefix rt-types;
    reference
      "RFC8294: Common YANG Data Types for the Routing Area";
  }
  import ietf-inet-types {
    prefix inet;
    reference
      "RFC6991: Common YANG Data Types";
  }

  organization
    "IETF Traffic Engineering Architecture and Signaling (TEAS)
     Working Group.";
  contact
    "WG Web:   <https://datatracker.ietf.org/wg/teas/>
     WG List:  <mailto:teas@ietf.org>

     Editor:   Vishnu Pavan Beeram
               <mailto:vishnupavan.ietf@gmail.com>

     Editor:   Kireeti Kompella
               <mailto:kireeti.ietf@gmail.com>";
  description
    "This module defines a YANG data model for Multipath Traffic
     Engineering Directed Acyclic Graph (MPTED) tunnels.  It is
     intended to be used as part of the IETF TEAS framework to
     enable the configuration and management of MPTED tunnels on
     an MPTED tunnel originator.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://www.rfc-editor.org/info/rfcXXXX); see the RFC
     itself for full legal notices.";

  revision 2026-11-02 {
    description
      "Initial revision.
       This revision introduces the YANG data model for
       Multipath Traffic Engineering Directed Acyclic Graph
       (MPTED) tunnels.";
    reference
      "RFC XXXX: A YANG Data Model for Multipath Traffic
       Engineering Directed Acyclic Graph (MPTED) Tunnels and
       Junctions";
  }

  identity mpted-tunnel-type {
    description
      "Base identity of MPTED tunnel type.";
  }

  identity mpted-tunnel-type-mpls-siglab {
    base mpted-tunnel-type;
    description
      "MPLS MPTED tunnel with signaled label switching.";
  }

  identity mpted-signaling-type {
    description
      "Base identity for MPTED signaling type.";
  }

  identity mpted-signaling-rsvp {
    base mpted-signaling-type;
    description
      "MPTED RSVP signaling.";
    reference
      "draft-kbr-teas-mptersvp: RSVP-TE Extensions for Multipath
       Traffic Engineered Directed Acyclic Graph Tunnels";
  }

  identity mpted-signaling-pcep {
    base mpted-signaling-type;
    description
      "MPTED PCEP signaling.";
  }
  identity mpted-signaling-bgp {
    base mpted-signaling-type;
    description
      "MPTED BGP signaling.";
  }

  identity mpted-signaling-grpc {
    base mpted-signaling-type;
    description
      "MPTED gRPC signaling.";
  }

  identity mpted-tunnel-status {
    description
      "Base identity for MPTED tunnel status.";
  }

  identity mpted-tunnel-up {
    base mpted-tunnel-status;
    description
      "MPTED tunnel is up.";
  }

  identity mpted-tunnel-down {
    base mpted-tunnel-status;
    description
      "MPTED tunnel is down.";
  }

  identity mpted-tunnel-degraded {
    base mpted-tunnel-status;
    description
      "MPTED tunnel is degraded.";
  }

  identity mpted-junction-status {
    description
      "Base identity for MPTED JUNCTION status.";
  }

  identity mpted-junction-up {
    base mpted-junction-status;
    description
      "MPTED JUNCTION Up.";
  }

  identity mpted-junction-down {
    base mpted-junction-status;

    description
      "MPTED JUNCTION Down.";
  }

  identity mpted-junction-degraded {
    base mpted-junction-status;
    description
      "MPTED JUNCTION Degraded.";
  }

  identity mpted-jct-phop-status {
    description
      "Base identity for MPTED JCT-PHOP status.";
  }

  identity mpted-jct-phop-up {
    base mpted-jct-phop-status;
    description
      "MPTED JCT-PHOP Up.";
  }

  identity mpted-jct-phop-down {
    base mpted-jct-phop-status;
    description
      "MPTED JCT-PHOP Down.";
  }

  identity mpted-jct-nhop-status {
    description
      "Base identity for MPTED JCT-NHOP status.";
  }

  identity mpted-jct-nhop-up {
    base mpted-jct-nhop-status;
    description
      "MPTED JCT-NHOP Up.";
  }

  identity mpted-jct-nhop-down {
    base mpted-jct-nhop-status;
    description
      "MPTED JCT-NHOP Down.";
  }

  identity mpted-jct-nhop-degraded {
    base mpted-jct-nhop-status;
    description
      "MPTED JCT-NHOP Degraded.";

  }

  identity mpted-opt-metric-type {
    description
      "Base identity of MPTED optimization metric type.";
  }

  identity mpted-opt-metric-te {
    base mpted-opt-metric-type;
    description
      "TE Metric.";
  }

  identity mpted-opt-metric-igp {
    base mpted-opt-metric-type;
    description
      "IGP Metric.";
  }

  identity mpted-opt-metric-delay {
    base mpted-opt-metric-type;
    description
      "Delay Metric.";
  }

  identity mpted-bw-spec-type {
    description
      "Base identity for MPTED bandwidth specification type.";
  }

  identity mpted-bw-spec-explicit {
    base mpted-bw-spec-type;
    description
      "Explicit MPTED bandwidth specification type.";
  }

  identity mpted-bw-spec-auto {
    base mpted-bw-spec-type;
    description
      "Automatic MPTED bandwidth specification type.";
  }

  grouping mpted-ingress {
    description
      "Grouping for MPTED ingress information.";
    leaf ingress-id {
      type inet:ip-address;
      description

        "IP-address of the ingress node.";
    }
    leaf set-bandwidth {
      when "derived-from-or-self(../../../bandwidth-spec-type, "
         + "'mpted:mpted-bw-spec-explicit')" {
        description
          "Applicable only when bandwidth specification
           type is explicit.";
      }
      type uint64;
      units "bytes per second";
      description
        "Explicitly specified bandwidth at the ingress of
         the MPTED tunnel.";
    }
    container auto-bandwidth {
      when "derived-from-or-self(../../../bandwidth-spec-type, "
         + "'mpted:mpted-bw-spec-auto')" {
        description
          "Applicable only when bandwidth specification
           type is automatic.";
      }
      description
        "Container for auto-bandwidth parameters.";
      uses mpted-ingress-autobw-config;
      container overflow {
        description
          "Auto-bandwidth overflow parameters.";
        uses mpted-autobw-overflow-config;
      }
      container underflow {
        description
          "Auto-bandwidth underflow parameters.";
        uses mpted-autobw-underflow-config;
      }
    }
  }

  grouping mpted-ingress-autobw-config {
    description
      "MPTED tunnel ingress auto-bandwidth parameters.";
    leaf min-bw {
      type uint64;
      units "bytes per second";
      description
        "Minimum bandwidth at the ingress of the
         auto-bandwidth enabled MPTED tunnel.";
    }
    leaf max-bw {
      type uint64;
      units "bytes per second";
      description
        "Maximum bandwidth at the ingress of the
         auto-bandwidth enabled MPTED tunnel.";
    }
    leaf adjust-threshold {
      type rt-types:percentage;
      description
        "Bandwidth demand at the ingress for the current
         bandwidth adjustment interval is compared to the
         current bandwidth allocation for the ingress of
         the MPTED tunnel.  If the percentage difference
         in bandwidth is greater than or equal to the percentage
         specified by this leaf, the bandwidth allocation
         for the ingress is adjusted to the current bandwidth
         demand.";
    }
  }

  grouping mpted-autobw-overflow-config {
    description
      "MPTED tunnel ingress auto-bandwidth overflow parameters.";
    leaf enabled {
      type boolean;
      default "false";
      description
        "Enables auto-bandwidth overflow adjustment on the
         MPTED tunnel ingress.";
    }
    leaf overflow-threshold {
      type rt-types:percentage;
      description
        "Bandwidth percentage change to trigger
         an overflow event";
    }
    leaf trigger-event-count {
      type uint16;
      description
        "Number of consecutive overflow sample
         events needed to trigger an overflow adjustment";
    }
  }

  grouping mpted-autobw-underflow-config {
    description
      "MPTED tunnel ingress auto-bandwidth underflow parameters.";
    leaf enabled {
      type boolean;
      default "false";
      description
        "Enables auto-bandwidth underflow adjustment on the
         MPTED tunnel ingress.";
    }
    leaf underflow-threshold {
      type rt-types:percentage;
      description
        "Bandwidth percentage change to trigger
         an underflow event";
    }
    leaf trigger-event-count {
      type uint16;
      description
        "Number of consecutive underflow sample
         events needed to trigger an underflow adjustment";
    }
  }

  grouping tunnel-status-info {
    description
      "Grouping for tunnel status information.";
    leaf current-version {
      type uint32;
      config false;
      description
        "Current version of the MPTED tunnel.";
    }
    leaf status {
      type identityref {
        base mpted-tunnel-status;
      }
      config false;
      description
        "Status of the MPTED tunnel";
    }
    leaf max-flow-throughput {
      type uint64;
      units "bytes per second";
      config false;
      description
        "Max-flow throughput of the MPTED DAG of the instance of
         the tunnel that is currently in use, i.e., the maximum
         bandwidth that the DAG can carry from the ingress nodes
         to the egress nodes.";
    }
    leaf min-metric {
      type uint64;
      config false;
      description
        "Metric of the best ingress-to-egress path in the MPTED
         DAG of the instance of the tunnel that is currently in
         use.  The units are those of the optimization-metric.";
    }
    leaf max-metric {
      type uint64;
      config false;
      description
        "Metric of the worst ingress-to-egress path in the MPTED
         DAG of the instance of the tunnel that is currently in
         use.  The units are those of the optimization-metric.";
    }
  }

  grouping tunnel-instance-status-info {
    description
      "Grouping for tunnel instance status information.";
    leaf instance-id {
      type uint32;
      config false;
      description
        "Identifier of the MPTED tunnel instance.";
    }
    leaf status {
      type identityref {

        base mpted-tunnel-status;
      }
      config false;
      description
        "Status of the MPTED tunnel instance";
    }
  }

  grouping junction-info {
    description
      "Grouping for junction information.";
    leaf node-id {
      type inet:ip-address;
      description
        "IP-address of the junction node.";
    }
    leaf current-jct-instance {
      type uint32;
      description
        "Current instance identifier of the MPTED tunnel
         junction.";
    }
    leaf bandwidth-requested {
      type uint64;
      units "bytes per second";
      description
        "Bandwidth to be reserved for the junction.  A value of
         zero means that no bandwidth is reserved.";
    }
  }

  grouping junction-status-info {
    description
      "Grouping for junction status information.";
    uses junction-info;
    leaf mtu {
      type uint16;
      description
        "MTU at the junction node.  This is the smallest MTU value
         among the MTUs received from all JCT-NHOPs.";
    }
    leaf status {
      type identityref {
        base mpted-junction-status;
      }
      description
        "Status of the JUNCTION.";
    }
  }
  grouping mpted-jct-hop-info {
    description
      "Grouping for junction hop information.";
    leaf hop-address {
      type inet:ip-address;
      description
        "IP-address of the peer.";
    }
    leaf hop-index {
      type uint32;
      description
        "Index of the peer interface.";
    }
    leaf hop-version {
      type uint32;
      description
        "Version of the Hop.";
    }
  }

  grouping mpted-jct-phop-status-info {
    description
      "Grouping for junction phop status information.";
    uses mpted-jct-hop-info;
    leaf in-label {
      type rt-types:mpls-label;
      description
        "Label used by incoming packets on the JCT-PHOP.";
    }
    leaf status {
      type identityref {
        base mpted-jct-phop-status;
      }
      description
        "Status of the JCT-PHOP.";
    }
  }

  grouping mpted-jct-nhop-info {
    description
      "Grouping for junction nhop information.";
    uses mpted-jct-hop-info;
    leaf backup {
      type boolean;
      description
        "Indicates that the JCT-NHOP is a backup next-hop.";
    }
    leaf load-share {
      type uint16;
      config false;
      description
        "Effective relative load share of the JCT-NHOP.  It is
         derived from the bandwidth-requested values of the
         JCT-NHOPs of the junction.  It is zero for a JCT-NHOP that
         is not active, and it is the same for all active
         JCT-NHOPs if their bandwidth-requested values are all
         zero.";
    }
    leaf bandwidth-requested {

      type uint64;
      units "bytes per second";
      description
        "Bandwidth value of the JCT-NHOP, which determines its
         load share.  Only the ratio of these values across the
         JCT-NHOPs of a junction is used.  It does not by itself
         cause a bandwidth reservation.";
    }
  }

  grouping mpted-jct-nhop-status-info {
    description
      "Grouping for junction nhop status information.";
    uses mpted-jct-nhop-info;
    leaf bandwidth-reserved {
      type uint64;
      units "bytes per second";
      description
        "Amount of bandwidth reserved on the TE link associated
         with the JCT-NHOP.  It is zero if the bandwidth of the
         junction is zero.  It is also zero for a backup JCT-NHOP,
         because the RSVP-TE signaling for MPTED tunnels
         (draft-kbr-teas-mptersvp) does not reserve bandwidth
         toward backup next-hops.";
    }
    leaf out-label {
      type rt-types:mpls-label;
      description
        "Label used by outgoing packets on the JCT-NHOP.";
    }
    leaf status {
      type identityref {
        base mpted-jct-nhop-status;
      }
      description
        "Status of the JCT-NHOP.";
    }
  }

  grouping dag-span-constraints {
    description
      "Grouping for parameters that control the span of
       the MPTED DAG.";
    leaf max-jcts {
      type uint16;
      description
        "Maximum number of junctions in the DAG.";
    }
    leaf min-nhops {
      type uint16;
      description
        "Minimum number of next-hops per junction.";
    }
    leaf max-nhops {
      type uint16;
      description
        "Maximum number of next-hops per junction.";
    }
  }

  grouping hop-constraints {
    description
      "Grouping for parameters that constrain hops
       of the MPTED DAG.";
    leaf minimum-bandwidth {
      type uint64;
      units "bytes per second";
      description
        "Minimum bandwidth per hop of the MPTED DAG.";
    }
  }

  augment "/te:te" {
    description
      "Augmentation for MPTED tunnels.";
    container mpted-tunnels {
      description
        "Container for MPTED tunnels.";
      list tunnel {
        key "originator identifier";
        unique "name";
        description
          "MPTED tunnel entry.";
        leaf originator {
          type inet:ip-address;
          description
            "IP address of the MPTED tunnel originator.";
        }
        leaf identifier {
          type uint32;

          description
            "Identifier of the MPTED tunnel.";
        }
        leaf name {
          type string;
          description
            "Name of the MPTED tunnel.";
        }
        leaf description {
          type string;
          description
            "Textual description of the MPTED tunnel.";
        }
        container ingresses {
          description
            "Container for list of MPTED ingresses.";
          list ingress {
            key "ingress-id";
            description
              "MPTED ingress entry.";
            uses mpted-ingress;
          }
        }
        leaf-list egress {
          type inet:ip-address;
          description
            "List of egress nodes associated with the MPTED
             tunnel.";
        }
        leaf type {
          type identityref {
            base mpted-tunnel-type;
          }
          description
            "Type of tunnel.";
        }
        leaf setup-priority {
          type uint8 {
            range "0..7";
          }
          default "7";
          description
            "The priority of the MPTED tunnel with respect to
             taking resources, in the range of 0 to 7.  The
             value 0 is the highest priority.";
        }
        leaf hold-priority {
          type uint8 {
            range "0..7";
          }
          default "7";
          description
            "The priority of the MPTED tunnel with respect to
             holding resources, in the range of 0 to 7.  The
             value 0 is the highest priority.";
        }
        leaf optimization-metric {
          type identityref {
            base mpted-opt-metric-type;
          }
          description
            "Metric type for which the DAG is optimized.";
        }
        leaf metric-margin {
          type uint32;
          description
            "Metric margin for path selection.  A path
             whose metric is within this margin of the
             optimal metric is considered acceptable.";
        }
        uses dag-span-constraints;
        container resource-affinities {
          description
            "Resource-affinity constraints.";
          leaf-list exclude-any {
            type string;
            description
              "Exclude the link if it has any of these
               affinities.";
          }
          leaf-list include-any {
            type string;
            description
              "Include the link if it has any of these
               affinities";
          }
          leaf-list include-all {
            type string;
            description
              "Include the link if it has all these affinities";
          }
        }
        leaf bandwidth-spec-type {
          type identityref {
            base mpted-bw-spec-type;
          }
          description
            "The method used for setting the bandwidth on the
             tunnel, either explicitly specified or automatically
             derived.";
        }
        leaf auto-bandwidth-adjust-interval {
          when "derived-from-or-self(../bandwidth-spec-type, "
             + "'mpted:mpted-bw-spec-auto')" {
            description
              "Applicable only when bandwidth specification
               type is automatic.";
          }
          type uint32;
          units "seconds";

          description
            "Time in seconds between auto-bandwidth adjustments.";
        }
        leaf mpted-computer {
          type inet:ip-address;
          description
            "IP-address of the MPTED computer.";
        }
        leaf signaling-type {
          type identityref {
            base mpted-signaling-type;
          }
          description
            "MPTED tunnel signaling type.";
        }
        leaf signaling-source {
          type inet:ip-address;
          description
            "IP-address of the MPTED tunnel signaling source.";
        }
        container hop {
          description
            "Hop constraint parameters for the MPTED tunnel.";
          uses hop-constraints;
        }
        leaf compute-only {
          type boolean;
          default "false";
          description
            "When set to true, the MPTED DAG is computed
             but not signaled.";
        }
        leaf retry-timer {
          type uint16;
          units "seconds";
          description
            "Timer interval for retrying tunnel setup
             after a failure.";
        }
        leaf optimize-timer {
          type uint16;
          units "seconds";
          description
            "Timer interval for periodic path
             reoptimization.";
        }
        leaf-list exclude-hops {
          type inet:ip-address;
          description
            "List of node addresses to exclude from
             path computation.";
        }
        uses tunnel-status-info;
        container instances {
          config false;
          description
            "Container for list of instances of the MPTED tunnel.";
          list instance {
            key "instance-id";
            description
              "MPTED tunnel instance entry.";
            uses tunnel-instance-status-info;
            container junctions {
              description
                "Container for list of JUNCTIONs associated
                 with the MPTED tunnel instance.";
              list junction {
                key "node-id";
                description
                  "JUNCTION entry.";
                uses junction-status-info;
                container phops {
                  description
                    "Container for associated JCT-PHOPs.";
                  list phop {
                    key "hop-address hop-index hop-version";
                    description
                      "JCT-PHOP entry.";
                    uses mpted-jct-phop-status-info;
                  }

                }
                container nhops {
                  description
                    "Container for associated JCT-NHOPs.";
                  list nhop {
                    key "hop-address hop-index hop-version";
                    description
                      "JCT-NHOP entry.";
                    uses mpted-jct-nhop-status-info;
                  }
                }
              }
            }
          }
        }
      }
    }
  }
}
