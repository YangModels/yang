module ietf-complex-types {

   namespace "urn:ietf:params:xml:ns:yang:ietf-complex-types";
   prefix "ct";

   organization
     "NETMOD WG";

   contact
     "Editor:  Bernd Linowski
               <bernd.linowski@ext.nsn.com>
      Editor:  Mehmet Ersue
               <mehmet.ersue@nsn.com>
      Editor:  Siarhei Kuryla
               <s.kuryla@jacobs-university.de>";

   description
      "YANG extensions for complex types and typed instance
      identifiers.

      Copyright (c) 2010 IETF Trust and the persons identified as
      the document authors. All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC XXXX; see
      the RFC itself for full legal notices.";

   // RFC Ed.: Please replace XXXX with actual RFC number and
   // remove this note

       revision 2010-10-19 {
           description "Initial revision.";
       }

   // RFC Ed.: Please replace the date of the revision statement
   // with RFC publication date and remove this note

        extension complex-type {
            description "Defines a complex-type.";
            reference "section 2.2., complex-type extension statement";
            argument type-identifier {
                yin-element true;
            }
        }

        extension extends {
            description "Defines the base type of a complex-type.";
            reference "section 2.5., extends extension statement";
            argument base-type-identifier {
                yin-element true;
            }
        }

        extension abstract {
            description "Makes the complex-type abstract.";
            reference "section 2.6., abstract extension statement";
            argument status;
        }

        extension instance {
            description "Declares an instance of the given
                 complex type.";
            reference "section 2.3., instance extension statement";
            argument ct-instance-identifier {
                yin-element true;
            }
        }

        extension instance-list {
            description "Declares a list of instances of the given
                 complex type";
            reference "section 2.4., instance-list extension statement";
            argument ct-instance-identifier {
                yin-element true;
            }
        }

        extension instance-type {
            description "Tells to which type instance the instance
                         identifier refers to.";
            reference "section 3.2., instance-type extension statement";
            argument target-type-identifier {
                yin-element true;
            }
        }

        feature complex-types {
            description "This feature indicates that the server supports
                         complex types and instance identifiers.";
        }
   }
