module ietf-ikev2-crypto {
  namespace "urn:ietf:params:xml:ns:yang:ietf-ikev2-crypto";
  prefix ikev2-crypto;

  organization "Ericsson AB.
                Huawei Technologies India Pvt Ltd.";

  contact "Web:   <http://www.ericsson.com>";

  description
    "This YANG module defines the parameters"+
    " for IANA, Internet Key Exchange Version 2 (IKEv2)"+
    " Parameters."+
    " <http://www.rfc-editor.org/info/rfc4301>"+
    " Copyright (c) 2016 Ericsson AB."+
    " All rights reserved.";

  revision 2016-02-26 {
    description
      "First revision.";
    reference
      "RFC 7296: Internet Key Exchange Protocol Version 2.";
  }

  /*--------------------*/
  /* Typedefs           */
  /*--------------------*/

  /* IKEv2 Exchange Types (ET) */
  typedef ikev2-exchange-type-t {
    type enumeration {
      enum et-ike-sa-init {
        value 34;
        description
          "et-ike-sa-init - IKEv2 Exchange Types (ET)";
      }
      enum et-ike-auth {
        value 35;
        description
          "et-ike-auth - IKEv2 Exchange Types (ET)";
      }
      enum et-create-child-sa {
        value 36;
        description
          "et-create-child-sa - IKEv2 Exchange Types (ET)";
      }
      enum et-informational {
        value 37;
        description
          "et-informational - IKEv2 Exchange Types (ET)";
      }
      enum et-ike-session-resume {
        value 38;
        description
          "et-ike-session-resume - IKEv2 Exchange Types (ET)";
      }
      enum et-gsa-auth {
        value 39;
        description
          "et-gsa-auth - IKEv2 Exchange Types (ET)";
      }
      enum et-gsa-registration {
        value 40;
        description
          "et-gsa-registration - IKEv2 Exchange Types (ET)";
      }
      enum et-gsa-rekey {
        value 41;
        description
          "et-gsa-rekey - IKEv2 Exchange Types (ET)";
      }
    }
    description
      "IKEv2 Exchange Types (ET).";
  }

   /* Transform Type Values (TTV), RFC 7296 */
   typedef ikev2-transform-type-value-t {
    type enumeration {
      enum ttv-reserved-0 {
        value 0;
        description
          "ttv-reserved-0 - Transform Type Value (TTV)"+
          " Reserved ";
      }
      enum ttv-encr {
        value 1;
        description
          "ttv-encr - Transform Type Value 1 (TTV),"+
          " Encryption Algorithm "+
          "(ENCR) used in IKE and ESP.";
      }
      enum ttv-prf {
        value 2;
        description
          "ttv-prf - Transform Type Value 2 (TTV),"+
          " Pseudo-Random Function(PRF) used in IKE.";
      }
      enum ttv-integ {
        value 3;
        description
          "ttv-integ - Transform Type Value 3 (TTV),"+
          " Integrity Algorithm"+
          " (INTEG) used in IKE, AH, optional ESP.";
      }
      enum ttv-dh {
        value 4;
        description
          "ttv-dh - Transform Type Value 4 (TTV),"+
          " Diffie-Hellman (DH)"+
          " used in IKE, optional AH and ESP.";
      }
      enum ttv-esn {
        value 5;
        description
          "ttv-esn - Transform Type Value 5 (TTV),"+
          " Extended Sequence"+
          " Numbers (ESN) used in AH and ESP.";
      }
    }
    description
      "IKEv2 Transform Type Values ((TTV).";
  }

   /* IKEv2 Transform Attribute Types (TAT) */
   typedef ikev2-transform-attribute-type-t {
    type enumeration {
      enum tat-reserved-0 {
        value 0;
        description
          "tat-reserved-0 - IKEv2 Transform Attribute "+
          "Type (TAT) Reserved-0";
      }
      enum tat-reserved-1 {
        value 1;
        description
          "tat-reserved-1 - IKEv2 Transform Attribute "+
          "Type (TAT) Reserved-1";
      }
      enum tat-reserved-13 {
        value 13;
        description
          "ikev2-tat-reserved-13 - IKEv2 Transform Attribute "+
          "Type (TAT) Reserved-13";
      }
      enum tat-key-length {
        value 41;
        description
          "ikev2-tat-key-length - IKEv2 Transform Attribute "+
          "Type (TAT) KEY LENGTH (in bits)";
      }
    }
    description
      "IKEv2 Transform Attribute Types (TAT)";
  }

   /* Transform Type 1 (Encryption Algorithm) Transform IDs */
  typedef ikev2-encryption-algorithm-t {
    type enumeration {
      enum encr-reserved-0 {
        value 0;
        description
          "encr-reserved-0 - IKEv2 Encryption Algorithm Transform";
      }
      enum encr-des-iv4 {
        value 1;
        description
          "encr-des-iv4 - IKEv2 Encryption Algorithm Transform";
      }
      enum encr-des {
        value 2;
        description
          "encr-des - IKEv2 Encryption Algorithm Transform";
      }
      enum encr-3des {
        value 3;
        description
          "encr-3des - IKEv2 Encryption Algorithm Transform";
      }
      enum encr-rc5 {
        value 4;
        description
          "encr-rc5 - IKEv2 Encryption Algorithm Transform";
      }
      enum encr-idea {
        value 5;
        description
          "encr-idea - IKEv2 Encryption Algorithm Transform";
      }
      enum encr-cast {
        value 6;
        description
          "encr-cast - IKEv2 Encryption Algorithm Transform";
      }
      enum encr-blowfish {
        value 7;
        description
          "encr-blowfish - IKEv2 Encryption Algorithm Transform";
      }
      enum encr-3idea {
        value 8;
        description
          "encr-3idea - IKEv2 Encryption Algorithm Transform";
      }
      enum encr-des-iv32 {
        value 9;
        description
          "encr-des-iv32 - IKEv2 Encryption Algorithm Transform";
      }
      enum encr-reserved-10 {
        value 10;
        description
          "encr-reserved-10 - IKEv2 Encryption Algorithm"+
          " Transform";
      }
      enum encr-null {
        value 11;
        description
          "encr-null - IKEv2 Encryption Algorithm Transform";
      }
      enum encr-aes-cbc {
        value 12;
        description
          "encr-aes-cbc - IKEv2 Encryption Algorithm Transform";
      }
      enum encr-aes-ctr {
        value 13;
        description
          "encr-aes-ctr - IKEv2 Encryption Algorithm Transform";
      }
      enum encr-aes-ccm-8 {
        value 14;
        description
          "encr-aes-ccm-8 - IKEv2 Encryption Algorithm Transform";
      }
      enum encr-aes-ccm-12 {
        value 15;
        description
          "encr-aes-ccm-12 - IKEv2 Encryption Algorithm"+
          " Transform";
      }
      enum encr-aes-ccm-16 {
        value 16;
        description
          "encr-aes-ccm-16 - IKEv2 Encryption Algorithm"+
          " Transform";
      }
      enum encr-reserved-17 {
        value 17;
        description
          "encr-reserved-17 - IKEv2 Encryption Algorithm"+
          " Transform";
      }
      enum encr-aes-gcm-8-icv {
        value 18;
        description
          "encr-aes-gcm-8-icv - IKEv2 Encryption Algorithm"+
          " Transform";
      }
      enum encr-aes-gcm-12-icv {
        value 19;
        description
          "encr-aes-gcm-12-icv - IKEv2 Encryption Algorithm"+
          " Transform";
      }
      enum encr-aes-gcm-16-icv {
        value 20;
        description
          "encr-aes-gcm-16-icv - IKEv2 Encryption Algorithm"+
          " Transform";
      }
      enum encr-null-auth-aes-gmac {
        value 21;
        description
          "encr-null-auth-aes-gmac - IKEv2 Encryption Algorithm"+
          " Transform";
      }
      enum encr-ieee-p1619-xts-aes {
        value 22;
        description
          "encr-ieee-p1619-xts-aes - IKEv2 Encryption Algorithm"+
          " Transform IEEE P1619 XTS-AES.";
      }
      enum encr-camellia-cbc {
        value 23;
        description
          "encr-camellia-cbc - IKEv2 Encryption Algorithm"+
          " Transform";
      }
      enum encr-camellia-ctr {
        value 24;
        description
          "encr-camellia-ctr - IKEv2 Encryption Algorithm"+
          " Transform";
      }
      enum encr-camellia-ccm-8-icv {
        value 25;
        description
          "encr-camellia-ccm-8-icv - IKEv2 Encryption Algorithm"+
          " Transform";
      }
      enum encr-camellia-ccm-12-icv {
        value 26;
        description
          "encr-camellia-ccm-12-icv - IKEv2 Encryption Algorithm"+
          " Transform";
      }
      enum encr-camellia-ccm-16-icv {
        value 27;
        description
          "encr-camellia-ccm-16-icv - IKEv2 Encryption Algorithm"+
          " Transform";
      }
      enum encr-chacha20-poly1305 {
        value 28;
        description
          "encr-chacha20-poly1305 - IKEv2 Encryption Algorithm"+
          " Transform";
      }
      enum encr-aes-cbc-128 {
        value 1024;
        description
          "encr-aes-cbc-128 - IKEv2 Encryption Algorithm Transform";
      }
      enum encr-aes-cbc-192 {
        value 1025;
        description
          "encr-aes-cbc-192 - IKEv2 Encryption Algorithm Transform";
      }
      enum encr-aes-cbc-256 {
        value 1026;
        description
          "encr-aes-cbc-256 - IKEv2 Encryption Algorithm Transform";
      }
      enum encr-blowfish-128 {
        value 1027;
        description
          "encr-blowfish-128 - IKEv2 Encryption Algorithm"+
          " Transform";
      }
      enum encr-blowfish-192 {
        value 1028;
        description
          "encr-blowfish-192 - IKEv2 Encryption Algorithm"+
          " Transform";
      }
      enum encr-blowfish-256 {
        value 1029;
        description
          "encr-blowfish-256 - IKEv2 Encryption Algorithm"+
          " Transform";
      }
      enum encr-blowfish-448 {
        value 1030;
        description
          "encr-blowfish-448 - IKEv2 Encryption Algorithm"+
          " Transform";
      }
      enum encr-camellia-128 {
        value 1031;
        description
          "encr-camellia-128 - IKEv2 Encryption Algorithm"+
          " Transform";
      }
      enum encr-camellia-192 {
        value 1032;
        description
          "encr-camellia-192 - IKEv2 Encryption Algorithm"+
          " Transform";
      }
      enum encr-camellia-256 {
        value 1033;
        description
          "encr-camellia-256 - IKEv2 Encryption Algorithm"+
          " Transform";
      }
    }
    description
      "Transform Type 1 - IKEv2 Encryption Algorithm Transformm"+
      " IDs";
  }

  /* Transform Type 2 (Pseudo-Random Function PRF) Transform IDs */
  typedef ikev2-pseudo-random-function-t {
    type enumeration {
      enum prf-reserved-0 {
        value 0;
        description
          "prf-reserved-0 - IKEv2 Pseudo-Random Function (PRF)";
      }
      enum prf-hmac-md5 {
        value 1;
        description
          "prf-hmac-md5 - IKEv2 Pseudo-Random Function (PRF)";
      }
      enum prf-hmac-sha1 {
        value 2;
        description
          "prf-hmac-sha1 - IKEv2 Pseudo-Random Function (PRF)";
      }
      enum prf-hmac-tiger {
        value 3;
        description
          "prf-hmac-tiger - IKEv2 Pseudo-Random Function (PRF)";
      }
      enum prf-aes128-xcbc {
        value 4;
        description
          "prf-aes128-xcbc - IKEv2 Pseudo-Random Function (PRF)";
      }
      enum prf-hmac-sha2-256 {
        value 5;
        description
          "prf-hmac-sha2-256 - IKEv2 Pseudo-Random Function (PRF)";
      }
      enum prf-hmac-sha2-384 {
        value 6;
        description
          "prf-hmac-sha2-384 - IKEv2 Pseudo-Random Function (PRF)";
      }
      enum prf-hmac-sha2-512 {
        value 7;
        description
          "prf-hmac-sha2-512 - IKEv2 Pseudo-Random Function (PRF)";
      }
      enum prf-aes128-cmac {
        value 8;
        description
          "prf-aes128-cmac - IKEv2 Pseudo-Random Function (PRF)";
      }
    }
    description
      "Transform Type 2 - IKEv2 Pseudo-Random Function (PRF)"+
      " Transform IDs";
  }
   /* Transform Type 3 (Integrity Algorithm) Transform IDs */
  typedef ikev2-integrity-algorithm-t {
    type enumeration {
      enum auth-none {
        value 0;
        description
          "auth-none - IKEv2 Integrity Algorithm";
      }
      enum auth-hmac-md5-96 {
        value 1;
        description
          "auth-hmac-md5-96 - IKEv2 Integrity Algorithm";
      }
      enum auth-hmac-sha1-96 {
        value 2;
        description
          "auth-hmac-sha1-96 - IKEv2 Integrity Algorithm";
      }
      enum auth-des-mac {
        value 3;
        description
          "auth-des-mac - IKEv2 Integrity Algorithm";
      }
      enum auth-kpdk-md5 {
        value 4;
        description
          "auth-kpdk-md5 - IKEv2 Integrity Algorithm";
      }
      enum auth-aes-xcbc-96 {
        value 5;
        description
          "auth-aes-xcbc-96 - IKEv2 Integrity Algorithm";
      }
      enum auth-hmac-md5-128 {
        value 6;
        description
          "auth-hmac-md5-128 - IKEv2 Integrity Algorithm";
      }
      enum auth-hmac-sha1-160 {
        value 7;
        description
          "auth-hmac-sha1-160 - IKEv2 Integrity Algorithm";
      }
      enum auth-aes-cmac-96 {
        value 8;
        description
          "auth-aes-cmac-96 - IKEv2 Integrity Algorithm";
      }
      enum auth-aes-128-gmac {
        value 9;
        description
          "auth-aes-128-gmac - IKEv2 Integrity Algorithm";
      }
      enum auth-aes-192-gmac {
        value 10;
        description
          "auth-aes-192-gmac - IKEv2 Integrity Algorithm";
      }
      enum auth-aes-256-gmac {
        value 11;
        description
          "auth-aes-256-gmac - IKEv2 Integrity Algorithm";
      }
      enum auth-hmac-sha2-256-128 {
        value 12;
        description
          "auth-hmac-sha2-256-128 - IKEv2 Integrity Algorithm";
      }
      enum auth-hmac-sha2-384-192 {
        value 13;
        description
          "auth-hmac-sha2-384-192 - IKEv2 Integrity Algorithm";
      }
      enum auth-hmac-sha2-512-256 {
        value 14;
        description
          "auth-hmac-sha2-512-256 - IKEv2 Integrity Algorithm";
      }
      enum auth-hmac-sha2-256-96 {
        value 1024;
        description
          "auth-hmac-sha2-256-96 - IKEv2 Integrity Algorithm";
      }
    }
    description
      "Transform Type 3 - IKEv2"+
      " Integrity Algorithms Transform IDs";
  }

  /* Transform Type 4 (Diffie-Hellman Group) Transform IDs */
  typedef ikev2-diffie-hellman-group-t {
    type enumeration {
      enum dh-group-none {
        value 0;
        description
          "dh-group-none - IKEv2 Diffie-Hellman Group (DH)";
      }
      enum dh-modp-768-group-1 {
        value 1;
        description
          "dh-modp-768-group-1 - IKEv2 Diffie-Hellman Group (DH)";
      }
      enum dh-modp-1024-group-2 {
        value 2;
        description
          "dh-modp-1024-group-2 - IKEv2 Diffie-Hellman Group (DH)";
      }
      enum dh-modp-1536-group-5 {
        value 5;
        description
          "dh-modp-1536-group-5 - IKEv2 Diffie-Hellman Group (DH)";
      }
      enum dh-modp-2048-group-14 {
        value 14;
        description
          "dh-modp-2048-group-14 - IKEv2 Diffie-Hellman Group (DH)";
      }
      enum dh-modp-3072-group-15 {
        value 15;
        description
          "dh-modp-3072-group-15 - IKEv2 Diffie-Hellman Group (DH)";
      }
      enum dh-modp-4096-group-16 {
        value 16;
        description
          "dh-modp-4096-group-16 - IKEv2 Diffie-Hellman Group (DH)";
      }
      enum dh-modp-6144-group-17 {
        value 17;
        description
          "dh-modp-6144-group-17 - IKEv2 Diffie-Hellman Group (DH)";
      }
      enum dh-modp-8192-group-18 {
        value 18;
        description
          "dh-modp-8192-group-18 - IKEv2 Diffie-Hellman Group (DH)";
      }
      enum dh-recp-256-group-19 {
        value 19;
        description
          "dh-recp-256-group-19 - IKEv2 Diffie-Hellman Group (DH)";
      }
      enum dh-recp-384-group-20 {
        value 20;
        description
          "dh-recp-384-group-20 - IKEv2 Diffie-Hellman Group (DH)";
      }
      enum dh-recp-521-group-21 {
        value 21;
        description
          "dh-recp-521-group-21 - IKEv2 Diffie-Hellman Group (DH)";
      }
      enum dh-modp-1024-160-pos-group-22 {
        value 22;
        description
          "dh-modp-1024-160-pos-group-22 - IKEv2 Diffie-Hellman"+
          " Group (DH)";
      }
      enum dh-modp-2048-224-pos-group-23 {
        value 23;
        description
          "dh-modp-2048-224-pos-group-23 - IKEv2 Diffie-Hellman"+
          " Group (DH)";
      }
      enum dh-modp-2048-256-pos-group-24 {
        value 24;
        description
          "dh-modp-2048-256-pos-group-24 - IKEv2 Diffie-Hellman"+
          " Group (DH)";
      }
      enum dh-recp-192-group-25 {
        value 25;
        description
          "dh-recp-192-group-25 - IKEv2 Diffie-Hellman Group (DH)";
      }
      enum dh-recp-224-group-26 {
        value 26;
        description
          "dh-recp-224-group-26 - IKEv2 Diffie-Hellman Group (DH)";
      }
      enum dh-brainpool-ip-224-r1 {
        value 27;
        description
          "dh-brainpool-ip-224-r1 - IKEv2 Diffie-Hellman Group"+
          " (DH)";
      }
      enum dh-brainpool-ip-256-r1 {
        value 28;
        description
          "dh-brainpool-ip-256-r1 - IKEv2 Diffie-Hellman Group"+
          " (DH)";
      }
      enum dh-brainpool-ip-384-r1 {
        value 29;
        description
          "dh-brainpool-ip-384-r1 - IKEv2 Diffie-Hellman Group"+
          " (DH)";
      }
      enum dh-brainpool-ip-512-r1 {
        value 30;
        description
          "dh-brainpool-ip-512-r1 - IKEv2 Diffie-Hellman Group"+
          " (DH)";
      }
    }
    description
      "Transform Type 4 - IKEv2"+
      " Diffie-Hellman Groups (DH) Transform IDs";
  }
  /* Transform Type 5 (Extended Sequence Numbers ESN
     Transform IDs) */
  typedef ikev2-extended-sequence-number-t {
    type enumeration {
      enum esn-none {
        value 0;
        description
          "esn-none - IKEv2 Extended Sequence Number";
      }
      enum esn-1 {
        value 1;
        description
          "esn-1 - IKEv2 Extended Sequence Number";
      }
    }
    description
      "Transform Type 5 - IKEv2 Extended Sequence Number (ESN)";
  }
  typedef ikev2-connection-type-t {
    type enumeration {
      enum initiator-only {
        value 0;
        description
          "initiator-only: ME will act as initiator for"+
          " bringing up IKEv2"+
          " session with its IKE peer.";
      }
      enum responder-only {
        value 1;
        description
          "responder-only: ME will act as responder for"+
          " bringing up IKEv2"+
          " session with its IKE peer.";
      }
      enum both {
        value 2;
        description
          "both: ME can act as initiator or responder.";
      }
    }
    description
      "IKEv2 Connection type for IKE session.";
  }
  typedef ikev2-transport-protocol-name-t {
    type enumeration {
      enum tcp {
        value 1;
        description
          "Transmission Control Protocol (TCP) Transport Protocol.";
      }
      enum udp {
        value 2;
        description
          "User Datagram Protocol (UDP) Transport Protocol";
      }
      enum sctp {
        value 3;
        description
          "Stream Control Transmission Protocol (SCTP) Transport "+
          "Protocol";
      }
      enum icmp {
        value 4;
        description
          "Internet Control Message Protocol (ICMP) Transport "+
          "Protocol";
      }
    }
    description
      "Enumeration of well known transport protocols.";
  }

  typedef preshared-key-t {
    type string;
    description
      "Derived string used as Pre-Shared Key.";
  }

  typedef pad-type-t {
    type enumeration {
      enum id-ipv4-addr {
        value 1;
        description
          "A single four (4) octet IPv4 address";
      }
      enum id-fdqn {
        value 2;
        description
          "A fully-qualified domain name string.";
      }
      enum id-rfc822-addr {
        value 3;
        description
          "A fully-qualified RFC 822 email address string";
      }
      enum id-ipv6-addr {
        value 5;
        description
          "A single sixteen (16) octet IPv6 address";
      }
      enum id-der-asn1-dn {
        value 9;
        description
          "The binary Distinguished Encoding Rules (DER) encoding"+
          " of an ASN.1 X.500 Distinguished Name";
      }
      enum id-der-asn1-gn {
        value 10;
        description
          "The binary Distinguished Encoding Rules (DER) encoding"+
          " of an ASN.1 X.509 General Name";
      }
      enum id-key {
        value 11;
        description
          "Key ID (exact match only). An opaque octet stream that"+
          " may be used to pass vendor-specific information"+
          " necessary to do certain proprietary types of"+
          " identification";
      }
      enum id-any {
        value 100;
        description
          "Optional: openIKEv2.conf";
      }
    }
    description
      "Peer Authorization  Database (PAD) Type";
  }

  typedef ikev2-protocol-identifiers-t {
    type enumeration {
      enum "reserved-0" {
        value 0;
        description
          "Reserved IKEv2 Security Protocol Identifier";
      }
      enum "ike" {
        value 1;
        description
          "Internet Key Exchange (IKE) Protocol Identifier";
      }
      enum "ah" {
        value 2;
        description
          "Authentication Header (AH) Protocol Identifier";
      }
      enum "esp" {
        value 3;
        description
          "Encapsulating Security Payload (ESP) Protocol"+
          " Identifier";
      }
      enum "fc_esp_header" {
        value 4;
        description
          "Fibre Channel Encapsulating Security Payload Header";
      }
      enum "fc_ct_authentication" {
        value 5;
        description
          "Fibre Channel Common Transport Authentication";
      }
    }
    description
      "IKEv2 Security Protocol Identifiers";
  }

  typedef ikev2-authentication-method-t {
    type enumeration {
      enum auth-preshared {
        value 0;
        description
          "authorization preshared - IKEv2 Authentication Method";
      }
      enum rsa-digital-signature {
        value 1;
        description
          "rsa-digital-signature - IKEv2 Authentication Method";
      }
      enum shared-key-msg-integrity-code {
        value 2;
        description
          "shared-key-msg-integrity-code - IKEv2 Authentication"+
          " Method";
      }
      enum dss-digital-signature {
        value 3;
        description
          "dss-digital-signature - IKEv2 Authentication Method";
      }
      enum ecdsa-sha-256-p256-curve {
        value 9;
        description
          "ecdsa-sha-256-p256-curve - IKEv2 Authentication Method";
      }
      enum ecdsa-sha-384-p384-curve {
        value 10;
        description
          "ecdsa-sha-384-p384-curve - IKEv2 Authentication Method";
      }
      enum ecdsa-sha-512-p512-curve {
        value 11;
        description
          "ecdsa-sha-512-p512-curve - IKEv2 Authentication Method";
      }
      enum generic-secure-passwd-auth-method {
        value 12;
        description
          "generic-secure-passwd-auth-method - IKEv2"+
          " Authentication Method";
      }
      enum null-auth-method {
        value 13;
        description
          "null-auth-method - IKEv2 Authentication Method";
      }
      enum digital-signature {
        value 14;
        description
          "digital-signature - IKEv2 Authentication Method";
      }
    }
    description "IKEv2 Authentication Methods";
  }

  typedef ikev2-traffic-selector-types-t {
    type enumeration {
      enum "ts-ipv4-addr-range" {
        value 7;
        description
          "ts-ipv4-addr-range - IKEv2 Traffic Selector Type (TS)";
      }
      enum "ts-ipv6-addr-range" {
        value 8;
        description
          "ts-ipv6-addr-range - IKEv2 Traffic Selector Type (TS)";
      }
      enum "ts-fc-addr-range" {
        value 9;
        description
          "ts-fc-addr-range - IKEv2 Traffic Selector Type (TS)";
      }
    }
    description
      "IKEv2 Traffic Selector Types";
  }

  typedef ikev2-cert-encoding-t {
    type enumeration {
      enum cert-pkcs-7-wrapped-x509 {
        value 1;
        description
          "PKCS #7 wrapped X.509 certificate";
      }
      enum cert-pgp {
        value 2;
        description
          "PGP Certificate";
      }
      enum cert-dns-signed-key {
        value 3;
        description
          "DNS Signed Key";
      }
      enum cert-x509-signature {
        value 4;
        description
          "X.509 Certificate - Signature";
      }
      enum cert-kerberos-token {
        value 6;
        description
          "Kerberos Token";
      }
      enum cert-revocation-list {
        value 7;
        description
          "Certificate Revocation List (CRL)";
      }
      enum cert-authority-revocation-list {
        value 8;
        description
          "Authority Revocation List (ARL)";
      }
      enum cert-spki {
        value 9;
        description
          "SPKI Certificate";
      }
      enum cert-x509-attribute {
        value 10;
        description
          "X.509 Certificate - Attribute";
      }
      enum cert-raw-rsa-key {
        value 11;
        description
          "Raw RSA Key";
      }
      enum cert-hash-url-x509 {
        value 12;
        description
          "Hash and URL of X.509 certificate";
      }
      enum cert-hash-url-x509-bundle {
        value 13;
        description
          "Hash and URL of X.509 bundle";
      }
      enum cert-ocsp-content {
        value 14;
        description
          "OCSP Content";
      }
      enum cert-raw-public-key {
        value 15;
        description
          "Raw Public Key";
      }
    }
    description
      "Type of Certificate Encoding";
  }
}
