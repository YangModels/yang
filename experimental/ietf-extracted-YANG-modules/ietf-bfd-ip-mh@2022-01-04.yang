module ietf-bfd-ip-mh {
  yang-version 1.1;
  namespace "urn:ietf:params:xml:ns:yang:ietf-bfd-ip-mh";
  prefix bfd-ip-mh;

  import ietf-bfd-types {
    prefix bfd-types;
    reference
      "RFC XXXX: YANG Data Model for Bidirectional Forwarding
       Detection (BFD)";
  }
  import ietf-bfd {
    prefix bfd;
    reference
      "RFC XXXX: YANG Data Model for Bidirectional Forwarding
       Detection (BFD)";
  }
  import ietf-inet-types {
    prefix inet;
    reference
      "RFC 6991: Common YANG Data Types";
  }
  import ietf-routing {
    prefix rt;
    reference
      "RFC 8349: A YANG Data Model for Routing Management
       (NMDA Version)";
  }

  organization
    "IETF BFD Working Group";
  contact
    "WG Web:   <https://datatracker.ietf.org/wg/bfd/>
     WG List:  <mailto:rtg-bfd@ietf.org>

     Editor:   Reshad Rahman
               <mailto:reshad@yahoo.com>

     Editor:   Lianshu Zheng
               <mailto:veronique_cheng@hotmail.com>

     Editor:   Mahesh Jethanandani
               <mailto:mjethanandani@gmail.com>";
  description
    "This module contains the YANG definition for BFD IP multihop
     as per RFC 5883.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC 9127; see the
     RFC itself for full legal notices.";
  reference
    "RFC 5883: Bidirectional Forwarding Detection (BFD) for
     Multihop Paths
     RFC 9127: YANG Data Model for Bidirectional Forwarding
     Detection (BFD)";

  revision 2022-01-04 {
    description
      "Updating reference to RFC XXXX.";
    reference
      "RFC XXXX: YANG Data Model for Bidirectional Forwarding
       Detection (BFD).";
  }
  revision 2021-10-21 {
    description
      "Initial revision.";
    reference
      "RFC 9127: YANG Data Model for Bidirectional Forwarding
       Detection (BFD)";
  }

  /*
   * Augments
   */

  augment "/rt:routing/rt:control-plane-protocols/"
        + "rt:control-plane-protocol/bfd:bfd" {
    description
      "BFD augmentation for IP multihop.";
    container ip-mh {
      description
        "BFD IP multihop top-level container.";
      uses bfd-types:session-statistics-summary;
      container session-groups {
        description
          "BFD IP multihop session groups.";
        list session-group {
          key "source-addr dest-addr";
          description
            "Group of BFD IP multihop sessions (for ECMP).  A
             group of sessions is between one source and one
             destination.  Each session has a different field
             in the UDP/IP header for ECMP.";
          leaf source-addr {
            type inet:ip-address;
            description
              "Local IP address.";
          }
          leaf dest-addr {
            type inet:ip-address;
            description
              "IP address of the peer.";
          }
          uses bfd-types:common-cfg-parms;
          leaf tx-ttl {
            type bfd-types:hops;
            default "255";
            description
              "Hop count of outgoing BFD control packets.";
          }
          leaf rx-ttl {
            type bfd-types:hops;
            mandatory true;
            description
              "Minimum allowed hop count value for incoming BFD
               control packets.  Control packets whose hop count is
               lower than this value are dropped.";
          }
          list sessions {
            config false;
            description
              "The multiple BFD sessions between a source and a
               destination.";
            uses bfd-types:all-session;
          }
        }
      }
    }
  }

  /*
   * Notifications
   */

  notification multihop-notification {
    description
      "Notification for BFD multihop session state change.  An
       implementation may rate-limit notifications, e.g., when a
       session is continuously changing state.";
    uses bfd-types:notification-parms;
  }
}
