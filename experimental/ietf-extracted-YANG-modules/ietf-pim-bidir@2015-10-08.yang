module ietf-pim-bidir {
  namespace "urn:ietf:params:xml:ns:yang:ietf-pim-bidir";
  // replace with IANA namespace when assigned
  prefix pim-bidir;

  import ietf-routing {
    prefix "rt";
  }

  import ietf-pim-base {
    prefix "pim-base";
  }

  import ietf-pim-rp {
    prefix "pim-rp";
  }

  organization
    "IETF PIM Working Group";

  contact
    "WG Web:   <http://tools.ietf.org/wg/pim/>
     WG List:  <mailto:pim@ietf.org>

     WG Chair: Stig Venaas
               <mailto:stig@venaas.com>

     WG Chair: Mike McBride
               <mailto:mmcbride7@gmail.com>

     Editors:   ";

  description
    "The YANG module defines a BIDIR (Bidirectional) mode PIM
    model.";

  revision 2015-10-08 {
    description
      "Initial revision.";
    reference
      "RFC XXXX: A YANG Data Model for PIM";
  }

  /*
   * Features
   */
  feature intf-df-election {
    description
      "Support configuration of interface DF election.";
  }

  /*
   * Identities
   */
  identity bidir {
    base pim-rp:rp-mode;
    description
      "BIDIR (Bidirectional) mode.";
  }

  /*
   * Groupings
   */
  grouping static-rp-bidir-container {
    description
      "Gouping that contains BIDIR attributes for static RP.";
    container bidir {
      presence
        "Indicate the support of BIDIR mode.";
      description
        "PIM BIDIR configuration data.";

      uses pim-rp:static-rp-attributes;
    } // bidir
  } // static-rp-bidir-container

  /*
   * Configuration data nodes
   */

  augment "/rt:routing/rt:routing-instance/"
    + "rt:routing-protocols/pim-base:pim/"
    + "pim-base:address-family" {
    description "PIM BIDIR augmentation.";

    container bidir {
      description
        "PIM BIDIR configuration data.";
    } // bidir
  } // augment

  augment "/rt:routing/rt:routing-instance/"
    + "rt:routing-protocols/pim-base:pim/"
    + "pim-base:interfaces/pim-base:interface/"
    + "pim-base:address-family" {
    description "PIM BIDIR augmentation.";

    container bidir {
      presence "Present to enable BIDIR mode.";
      description
        "PIM BIDIR configuration data.";

      container df-election {
        if-feature intf-df-election;
        description
          "DF election attributes.";
        leaf offer-interval {
          type uint32;
          description "Offer interval";
        }
        leaf backoff-interval {
          type uint32;
          description "Backoff interval";
        }
        leaf offer-multipler {
          type uint8;
          description "Offer multipler";
        }
      } // df-election
    } // bidir
  } // augment

  augment "/rt:routing/rt:routing-instance/"
    + "rt:routing-protocols/pim-base:pim/"
    + "pim-base:address-family/pim-rp:rp/"
    + "pim-rp:static-rp/pim-rp:ipv4-rp" {
    description "PIM BIDIR augmentation.";

    uses static-rp-bidir-container;
  } // augment

  augment "/rt:routing/rt:routing-instance/"
    + "rt:routing-protocols/pim-base:pim/"
    + "pim-base:address-family/pim-rp:rp/"
    + "pim-rp:static-rp/pim-rp:ipv6-rp" {
    description "PIM BIDIR augmentation.";

    uses static-rp-bidir-container;
  } // augment
  /*
   * Operational state data nodes
   */

  augment "/rt:routing-state/rt:routing-instance/"
    + "rt:routing-protocols/pim-base:pim/"
    + "pim-base:address-family" {
    description
      "PIM BIDIR state.";

    container bidir {
      description
        "PIM BIDIR state data.";
    } // bidir
  } // augment

  /*
   * RPCs
   */

  /*
   * Notifications
   */
}
