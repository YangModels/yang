module ietf-fabric-topology {

yang-version 1;
namespace "urn:ietf:params:xml:ns:yang:ietf-fabric-topology";
prefix fabric;

import ietf-network {
            prefix nw;
    }
    import ietf-network-topology {
            prefix nt;
    }
import ietf-fabric-types {
                    prefix fabrictype;
                    revision-date "2016-02-26";
    }
    organization
"Huawei Technologies";
contact
"shidanian@huawei.com";
description
    "This module contains a collection of YANG definitions for Fabric.";

    revision "2016-04-13"{
            description
                    "intial version";
            reference
                    "";
    }

// typedef statements
 typedef fabric-id {
     type nw:node-id;
     description
         "An identifier for a fabric in a topology.
         The identifier is generated by create-fabric RPC.";
 }
     // grouping statements
      grouping fabric-network-type {
   description "Identify the topology type to be fabric.";
   container fabric-network {
     presence "indicates fabric Network";
     description
     "The presence of the container node indicates
      fabric Topology";
   }
 }

     grouping fabric-network-attributes {
   description "fabric Topology scope attributes";
   container fabric-network-attributes {
     description "Containing fabric network attributes";
     leaf name {
         type string;
                     description "name of the fabric";
     }

             leaf fabric-id {
         type fabric-id;
                     description "fabric id";
     }

     leaf type {
         type fabrictype:underlayer-network-type;
         description "The type of physcial network that implements this fabric.
                     Examples are vlan, and trill.";
     }

     leaf description {
         type string;
                     description "description of the fabric";
     }
     container options {
                     description "options for the fabric";
         uses fabric-options;
     }
   }
 }

 grouping fabric-options {
     description "options for fabric";
     leaf gateway-mode {
         type enumeration {
             enum centralized {
                 description "";
             }
             enum distributed {
                 description "";
             }
         }
         default "distributed";

                     description "gateway mode";
     }

             leaf traffic-behavior {

                     type enumeration {
                             enum normal {
                                     description "";
                             }
                             enum need-acl {
                                     description "";
                             }
                     }
                     default "normal";
                     description "traffic behavior";
             }
 }

 grouping fabric-device-attributes {
     description "fabric node attributes";
     leaf node-ref {
         type fabrictype:node-ref;
                     description "";
     }
             //uses nw:node-ref;
     leaf role {
         type fabrictype:device-role;
                     description "role of the device, such as leaf or spine";
     }
 }

 grouping fabric-link-attributes {
     description "fabric link attribute";
     leaf link-ref {
         type fabrictype:link-ref;
                     description "";
     }
 }

     // augment statements
     augment "/nw:networks/nw:network/nw:network-types" {
 description
   "Introduce new network type for Fabric-based logical topology";
             uses fabric-network-type;
     }
     augment "/nw:networks/nw:network" {
             when "nw:network-types/fabric-network-type" {
                     description
                     "Augmentation parameters apply only for networks with
                     fabric network topo";
             }
             description
     "Configuration parameters for fabric network";
             uses fabric-network-attributes;
}
 augment "/nw:networks/nw:network/nw:node" {
             when "/nw:networks/nw:network/nw:network-types/fabric-network-type"{
                     description "Augmentation parameters apply only for networks with
    fabric topology";
             }
             description "Configuraion parameters for nodes";
         uses fabric-device-attributes;
 }

     augment "/nw:networks/nw:network/nt:link" {
   when "/nw:networks/nw:network/nw:network-types/fabric-network-type" {
     description
       "Augmentation parameters apply only for networks
        with fabric topology";
   }
   description "Augment fabric topology link information";
   uses fabric-link-attributes;
 }

 augment "/nw:networks/nw:network/nw:node/nt:termination-point" {
     when "/nw:networks/nw:network/nw:network-types/fabric-network-type"{
                     description
                     "Augmentation parameters apply only for networks
        with fabric topology";
             }
             description
     "Augment fabric topology termination point configuration";
     container lport-attributes {
                     description "fabric tp configuraiton";
         uses fabrictype:logic-port;
     }
 }

 /*******************************RPC*********************************************/
 rpc get-all-fabric {
     description "get all fabrics";
     output {
         leaf-list fabric-id {
            type fabric-id;
                        description "fabric id";
         }
     }
 }

 rpc compose-fabric {
     description "compose a fabric";
     input {
         uses fabric-network-attributes;
     }
     output {
         leaf fabric-id {
             type fabric-id;
                             description "fabric id";
         }
     }
 }

 rpc decompose-fabric {
     description "decompose a fabric";
     input {
         leaf fabric-id {
             type fabric-id;
                             description "fabric id";
         }
     }
 }

 rpc add-node-to-fabric {
     description "add node to a fabric";
     input {
         leaf fabric-id {
             type fabric-id;
                             description "fabric id";
         }
         uses fabric-device-attributes;
     }
 }

 rpc rm-node-from-fabric {
     description "remove a node from a fabric";
     input {
         leaf fabric-id {
             type fabric-id;
                             description "fabric id";
         }
                     uses nw:node-ref;
     }
 }

 rpc add-link-to-fabric {
     description "add a link to a fabric";
     input {
         leaf fabric-id {
             type fabric-id;
                             description "fabric id";
         }
         uses fabric-link-attributes;
     }
 }

 rpc rm-link-from-fabric {
     description "remove a link from a fabric";
     input {
         leaf fabric-id {
             type fabric-id;
                             description "fabric id";
         }
                     uses nt:link-ref;
     }
 }
}
