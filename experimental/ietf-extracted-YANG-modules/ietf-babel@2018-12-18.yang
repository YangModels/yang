module ietf-babel {
  yang-version 1.1;
  namespace "urn:ietf:params:xml:ns:yang:ietf-babel";
  prefix babel;

  import ietf-yang-types {
    prefix yang;
    reference
      "RFC 6991 - Common YANG Data Types.";
  }
  import ietf-inet-types {
    prefix inet;
    reference
      "RFC 6991 - Common YANG Data Types.";
  }
  import ietf-interfaces {
    prefix if;
    reference
      "RFC 8343 - A YANG Data Model for Interface Management";
  }

  organization
    "IETF Babel routing protocl Working Group";

  contact
    "WG Web: http://tools.ietf.org/wg/babel/
     WG List: babel@ietf.org

     Editor: Mahesh Jethanandani
             mjethanandani@gmail.com
     Editor: Barbara Stark
             bs7652@att.com";

  description
    "This YANG module defines a model for the Babel routing
     protocol.

     Copyright (c) 2018 IETF Trust and the persons identified as
     the document authors.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).

     This version of this YANG module is part of RFC XXXX; see
     the RFC itself for full legal notices.";

  revision 2018-12-18 {
    description
      "Initial version.";
    reference
      "RFC XXX: Babel YANG Data Model.";
  }

  /*
   * Identities
   */
  identity babel-link-type {
    description
      "Base identity from which all Babel Link Types are derived.";
  }

  identity ethernet {
    base "babel-link-type";
    description
      "Ethernet link type for Babel Routing Protocol.";
  }
  identity other {
    base "babel-link-type";
    description
      "Other link type for Babel Routing Protocol.";
  }
  identity tunnel {
    base "babel-link-type";
    description
      "Tunnel link type for Babel Routing Protocol.";
  }
  identity wireless {
    base "babel-link-type";
    description
      "Wireless link type for Babel Routing Protocol.";
  }
  identity moca {
    base "babel-link-type";
    description
      "Multimedia over Coax Alliance.";
  }
  identity g-hn-over-coax {
    base "babel-link-type";
    description
      "G.hn over coax.";
    reference
      "G.9960: Unified high-speed wireline-base home networking
       transceivers.";
  }
  identity g-hn-over-powerline {
    base "babel-link-type";
    description
      "G.hn over powerline.";
    reference
      "G.9960: Unified high-speed wireline-base home networking
       transceivers.";
  }
  identity home-plug {
    base "babel-link-type";
    description
      "HomePlug Power Alliance.";
    reference
      "IEEE 1901: HD-PC";
  }
  identity ieee-802-15 {
    base "babel-link-type";
    description
      "Wireless Personal Area Networks (WPAN).";
    reference
      "IEEE 802.15: Wireless Personal Area Networks (WPAN).";
  }

  identity babel-cost-compute-algorithm {
    description
      "Base identity from which all Babel cost compute algorithms
       are derived.";
  }
  identity k-out-of-j {
    base "babel-cost-compute-algorithm";
    description
      "k-out-of-j algorithm.";
  }
  identity etx {
    base "babel-cost-compute-algorithm";
    description
      "Expected Transmission Count.";
  }

  /*
   * Babel type identities
   */
  identity babel-security-supported {
    description
      "Base identity from which all Babel security types are
       derived.";
  }

  /*
   * Features
   */

  /*
   * Features supported
   */

  /*
   * Typedefs
   */
  typedef base64 {
    type string {
      pattern '(([A-Za-z0-9+/]{4})*([A-Za-z0-9+/]{3}=|'
            + '[A-Za-z0-9+/]{2}==)?){1}';
    }
    description
      "A binary-to-text encoding scheme to represent binary data in
       an ASCII string format.";
    reference
      "RFC 4648, The Base16, Base32, and Base64 Data Encodings";
  }

  /*
   * Groupings
   */
  grouping log {
    leaf log-time {
      type yang:timestamp;
      description
        "The date and time (according to the device internal
         clock setting, which may be a time relative to boot
         time, acquired from NTP, configured by the user, etc.)
         when this log entry was created.";
      reference
        "RFC YYYY, Babel Information Model, Section 4.2.";
    }

    leaf log-entry {
      type string;
      description
        "The logged message, as a string of utf-8 encoded hex
         characters.";
      reference
        "RFC YYYY, Babel Information Model, Section 4.2.";
    }
    description
      "A babel-log-obj list.";
    reference
      "RFC YYYY, Babel Information Model, Section 4.2.";
  }

  grouping credential {
    leaf id {
      type string;
      description
        "An identifier that identifies this credential uniquely.";
    }

    leaf cred {
      type binary;
      description
        "A credential, such as an X.509 certificate, a public key,
         etc. used for signing and/or encrypting babel messages.";
      reference
        "RFC YYYY, Babel Information Model, Section 4.1.";
    }
    description
      "A babel-credential-obj list.";
    reference
      "RFC YYYY, Babel Information Model, Section 4.1.";
  }

  grouping security {
    leaf mechanism {
      type string;
      description
        "The name of the security mechanism this object instance
         is about. The value MUST be the same as one of the
         identities listed as the babel-security-supported
         parameter.";
      reference
        "RFC YYYY, Babel Information Model, Section 3.5.";
    }

    leaf enable {
      type boolean;
      description
        "If true, the security mechanism is running. If false,
         the security mechanism is not currently running.";
      reference
        "RFC YYYY, Babel Information Model, Section 3.5.";
    }
    list self-cred {
      key "id";

      uses credential;
      description
        "Credentials this router presents to participate in the
         enabled security mechanism. Any private key component of
         a credential MUST NOT be readable. Adding and deleting
         credentials MAY be allowed.";
      reference
        "RFC YYYY, Babel Information Model, Section 3.5.";
    }

    list trust {
      key "id";

      uses credential;
      description
        "A list of credential-obj objects that identify the
         credentials of routers whose babel messages may be
         trusted or of a certificate authority (CA) whose signing
         of a router's credentials implies the router credentials
         can be trusted, in the context of this security
         mechanism. How a security mechanism interacts with this
         list is determined by the mechanism. A security algorithm
         may do additional validation of credentials, such as
         checking validity dates or revocation lists, so presence
         in this list may not be sufficient to determine trust.
         Adding and deleting credentials MAY be allowed.";
      reference
        "RFC YYYY, Babel Information Model, Section 3.5.";
    }

    leaf credvalid-log-enable {
      type boolean;
      description
        "If true, logging of messages that include credentials
         used for authentication is enabled. If false, these
         messages are not logged.";
      reference
        "RFC YYYY, Babel Information Model, Section 3.5.";
    }

    list credvalid-log {
      key "log-time";

      uses log;
      description
        "Log entries that have the timestamp a message containing
         credentials used for peer authentication (e.g., DTLS
         Server Hello) was received on a Babel port, and the
         entire received message (including Ethernet frame and IP
         headers, if possible); an implementation must restrict
         the size of this log, but how and what size is
         implementation-specific.";
      reference
        "RFC YYYY, Babel Information Model, Section 3.5.";
    }
    description
      "A babel-security-obj list.";
    reference
      "RFC YYYY, Babel Information Model, Section 3.5.";
  }

  /*
   * Data model
   */
  container babel {
    presence "A Babel container.";
    description
      "This is a top level container for the Babel routing protocol.";

    leaf version {
      type string;
      description
        "This is the version of the babel protocol implemented.";
      reference
        "RFC YYYY, Babel Information Model, Section 3.1.";
    }

    leaf enable {
      type boolean;
      default false;
      description
        "When written, it configures whether the protocol should be
         enabled. A read from the <running> or <intended> datastore
         therefore indicates the configured adminstrative value of
         whether the protocol is enabled or not.

         A read from the <operational> datastore indicates whether
         the protocol is actually running or not, i.e. it indicates
         the operational state of the protocol.";
      reference
        "RFC YYYY, Babel Information Model, Section 3.1.";
    }

    leaf router-id {
      type binary;
      mandatory "true";
      description
        "Every Babel speaker is assigned a router-id, which is an
         arbitrary string of 8 octets that is assumed to be unique
         across the routing domain";
      reference
        "RFC YYYY, Babel Information Model, Section 3.1,
         rfc6126bis, The Babel Routing Protocol. Section 3.";
    }

    leaf-list link-type {
      type identityref {
        base "babel-link-type";
      }
      description
        "Link types supported by this implementation of Babel.";
      reference
        "RFC YYYY, Babel Information Model, Section 3.1.";
    }

    leaf sequence-number {
      type yang:counter32;
      config false;
      description
        "Sequence number included in route updates for routes
         originated by this node.";
      reference
        "RFC YYYY, Babel Information Model, Section 3.1.";
    }

    leaf-list cost-compute-algorithm {
      type identityref {
        base "babel-cost-compute-algorithm";
      }
      description
        "List of cost compute algorithms supported by this
         implementation of Babel.";
      reference
        "RFC YYYY, Babel Information Model, Section 3.1.";
    }

    leaf-list security-supported {
      type identityref {
        base "babel-security-supported";
      }
      description
        "Babel security mechanism used by this implementation or
         per interface.";
      reference
        "RFC YYYY, Babel Information Model, Section 3.1.";
    }

    container transport {
      leaf udp-port {
        type inet:port-number;
        default "6696";
        description
          "UDP port for sending and receiving Babel messages. The
           default port is 6696.";
        reference
          "RFC YYYY, Babel Information Model, Section 3.2.";
      }

      leaf mcast-group {
        type inet:ip-address;
        default "ff02:0:0:0:0:0:1:6";
        description
          "Multicast group for sending and receiving multicast
           announcements on IPv6.";
        reference
          "RFC YYYY, Babel Information Model, Section 3.2.";
      }
      description
        "Babel Transport object.";
      reference
        "RFC YYYY, Babel Information Model, Section 3.1.";
    }
    list interfaces {
      key "reference";

      leaf reference {
        type if:interface-ref;
        description
          "Reference to an interface object as defined by the data
           model (e.g., YANG, BBF TR-181); data model is assumed to
           allow for referencing of interface objects which may be at
           any layer (physical, Ethernet MAC, IP, tunneled IP, etc.).
           Referencing syntax will be specific to the data model. If
           there is no set of interface objects available, this should
           be a string that indicates the interface name used by the
           underlying operating system.";
        reference
          "RFC YYYY, Babel Information Model, Section 3.3.";
      }
      leaf enable {
        type boolean;
        default "true";
        description
          "If true, babel sends and receives messages on this
           interface. If false, babel messages received on this
           interface are ignored and none are sent.";
        reference
          "RFC YYYY, Babel Information Model, Section 3.3.";
      }
      leaf link-type {
        type identityref {
          base babel-link-type;
        }
        description
          "Indicates the type of link. Set of values of supported
           link types where the following enumeration values MUST
           be supported when applicable: 'ethernet', 'wireless',
           'tunnel', and 'other'. Additional values MAY be
           supported.";
        reference
          "RFC YYYY, Babel Information Model, Section 3.3.";
      }
      leaf mcast-hello-seqno {
        type int16;
        config false;
        description
          "The current sequence number in use for multicast hellos
           sent on this interface.";
        reference
          "RFC YYYY, Babel Information Model, Section 3.3.";
      }
      leaf ucast-hello-seqno {
        type int16;
        config false;
        description
          "The current sequence number in use for unicast hellos
           sent on this interface.";
        reference
          "RFC YYYY, Babel Information Model, Section 3.3.";
      }
      leaf mcast-hello-interval {
        type int16;
        config false;
        description
          "The current multicast hello interval in use for hellos
           sent on this interface.";
        reference
          "RFC YYYY, Babel Information Model, Section 3.3.";
      }
      leaf ucast-hello-interval {
        type int16;
        config false;
        description
          "The current unicast hello interval in use for hellos sent
           on this interface.";
        reference
          "RFC YYYY, Babel Information Model, Section 3.3.";
      }
      leaf update-interval {
        type uint32;
        description
          "The current update interval in use for this interface.";
        reference
      "RFC YYYY, Babel Information Model, Section 3.3.";
      }
      leaf external-cost {
        type uint32;
        description
          "External input to cost of link of this interface. If
           supported, this is a value that is added to the metrics
           of routes learned over this interface. How an
           implementation uses the value is up to the implementation,
           which means the use may not be consistent across
           implementations.";
        reference
          "RFC YYYY, Babel Information Model, Section 3.3.";
      }
      leaf message-log-enable {
        type boolean;
        description
          "If true, logging of babel messages received on this
           interface is enabled; if false, babel messages are not
           logged.";
        reference
          "RFC YYYY, Babel Information Model, Section 3.3.";
      }

      list message-log {
        key "log-time";

        uses log;
        description
          "Log entries that have timestamp of a received Babel
           message and the entire received Babel message (including
           Ethernet frame and IP headers, if possible). An
           implementation must restrict the size of this log, but how
           and what size is implementation specific.";
        reference
          "RFC YYYY, Babel Information Model, Section 3.3.";
      }

      list neighbor-objects {
        key "neighbor-address";

        leaf neighbor-address {
          type inet:ip-address;
          description
            "IPv4 or v6 address the neighbor sends messages from.";
          reference
            "RFC YYYY, Babel Information Model, Section 3.4.";
        }

        leaf hello-mcast-history {
          type string;
          description
            "The multicast Hello history of whether or not the
             multicast Hello messages prior to babel-exp-mcast-
             hello-seqno were received, with a '1' for the most
             recent Hello placed in the most significant bit and
             prior Hellos shifted right (with '0' bits placed
             between prior Hellos and most recent Hello for any
             not-received Hellos); represented as a string using
             utf-8 encoded hex digits where a '1' bit = Hello
             received and a '0' bit = Hello not received.";
          reference
            "RFC YYYY, Babel Information Model, Section 3.4.";
        }

        leaf hello-ucast-history {
          type string;
          description
            "The unicast Hello history of whether or not the
             unicast Hello messages prior to babel-exp-ucast-
             hello-seqno were received, with a '1' for the most
             recent Hello placed in the most significant bit and
             prior Hellos shifted right (with '0' bits placed
             between prior Hellos and most recent Hello for any
             not-received Hellos); represented as a string using
             utf-8 encoded hex digits where a '1' bit = Hello
             received and a '0' bit = Hello not received.";
          reference
            "RFC YYYY, Babel Information Model, Section 3.4.";
        }
        leaf txcost {
          type int32;
          description
            "Transmission cost value from the last IHU packet
             received from this neighbor, or maximum value
             (infinity) to indicates the IHU hold timer for this
             neighbor has expired description.";
          reference
            "RFC YYYY, Babel Information Model, Section 3.4.";
        }

        leaf exp-mcast-hello-seqno {
          type int32;
          description
            "Expected multicast Hello sequence number of next Hello
             to be received from this neighbor; if multicast Hello
             messages are not expected, or processing of multicast
             messages is not enabled, this MUST be 0.";
          reference
            "RFC YYYY, Babel Information Model, Section 3.4.";
        }

        leaf exp-ucast-hello-seqno {
          type int32;
          description
            "Expected unicast Hello sequence number of next Hello to
             be received from this neighbor; if unicast Hello
             messages are not expected, or processing of unicast
             messages is not enabled, this MUST be 0.";
          reference
            "RFC YYYY, Babel Information Model, Section 3.4.";
        }

        leaf neighbor-ihu-interval {
          type int32;
          description
            "Current IHU interval for this neighbor.";
          reference
            "RFC YYYY, Babel Information Model, Section 3.4.";
        }

        leaf rxcost {
          type int32;
          description
            "Reception cost calculated for this neighbor. This value
             is usually derived from the Hello history, which may be
             combined with other data, such as statistics maintained
             by the link layer. The rxcost is sent to a neighbour in
             each IHU.";
          reference
            "RFC YYYY, Babel Information Model, Section 3.4.";
        }

        leaf cost {
          type int32;
          description
            "Link cost is computed from the values maintained in
             the neighbour table. The statistics kept in the neighbour
             table about the reception of Hellos, and the txcost
             computed from received IHU packets.";
          reference
            "RFC YYYY, Babel Information Model, Section 3.4.";
        }
        description
          "A set of Babel Neighbor Object.";
        reference
          "RFC YYYY, Babel Information Model, Section 3.3.";
      }

      list security {
        key "mechanism";

        uses security;
        description
          "A security-obj object that applies to this interface. If
           implemented, this allows security to be enabled only on
           specific interfaces or allows different security mechanisms
           to be enabled on different interfaces.";
        reference
          "RFC YYYY, Babel Information Model, Section 3.3.";
      }
      description
        "A set of Babel Interface objects.";
      reference
        "RFC YYYY, Babel Information Model, Section 3.1.";
    }

    list routes {
      key "prefix";

      leaf prefix {
        type inet:ip-address;
        description
          "Prefix (expressed in IP address format) for which this
           route is advertised.";
        reference
          "RFC YYYY, Babel Information Model, Section 3.6.";
      }

      leaf prefix-length {
        type inet:ip-prefix;
        description
          "Length of the prefix for which this route is advertised.";
        reference
          "RFC YYYY, Babel Information Model, Section 3.6.";
      }

      leaf router-id {
        type binary;
        description
          "router-id of the source router for which this route is
           advertised.";
        reference
          "RFC YYYY, Babel Information Model, Section 3.6.";
      }

      leaf neighbor {
        type leafref {
          path "../../interfaces/neighbor-objects/neighbor-address";
        }
        description
          "Reference to the babel-neighbors entry for the neighbor
           that advertised this route.";
        reference
          "RFC YYYY, Babel Information Model, Section 3.6.";
      }

      choice metric {
        mandatory "true";
        leaf received-metric {
          type int32;
          description
            "The metric with which this route was advertised by the
             neighbor, or maximum value (infinity) to indicate a the
             route was recently retracted and is temporarily
             unreachable. this metric will be 0 (zero) if the route
             was not received from a neighbor but was generated
             through other means. Either babel-route-calculated-metric
             or babel-route-received-metric MUST be provided.";
          reference
            "RFC YYYY, Babel Information Model, Section 3.6,
             draft-ietf-babel-rfc6126bis, The Babel Routing Protocol,
             Section 3.5.5.";
        }
        leaf calcuated-metric {
          type int32;
          description
            "A calculated metric for this route. How the metric is
             calculated is implementation-specific. Maximum value
             (infinity) indicates the route was recently retracted
             and is temporarily unreachable. Either
             babel-route-calculated-metric or
             babel-route-received-metric MUST be provided.";
          reference
            "RFC YYYY, Babel Information Model, Section 3.6,
             draft-ietf-babel-rfc6126bis, The Babel Routing Protocol,
             Section 3.5.5.";
        }
        description
          "Either babel-route-calculated-metric or
           babel-route-received-metric MUST be provided.";
        reference
          "RFC YYYY, Babel Information Model, Section 3.6,
           draft-ietf-babel-rfc6126bis, The Babel Routing Protocol,
           Section 3.5.5.";
      }

      leaf seqno {
        type int32;
        description
          "The sequence number with which this route was advertised.";
        reference
          "RFC YYYY, Babel Information Model, Section 3.6.";
      }

      leaf next-hop {
        type inet:ip-address;
        description
          "The next-hop address of this route. This will be empty if
           this route has no next-hop address.";
        reference
          "RFC YYYY, Babel Information Model, Section 3.6.";
      }

      leaf feasible {
        type boolean;
        description
          "A boolean flag indicating whether this route is feasible.";
        reference
          "RFC YYYY, Babel Information Model, Section 3.6,
           draft-ietf-babel-rfc6126bis, The Babel Routing Protocol,
           Section 3.5.1.";
      }

      leaf selected {
        type boolean;
        description
          "A boolean flag indicating whether this route is selected,
           i.e., whether it is currently being used for forwarding and
           is being advertised.";
        reference
          "RFC YYYY, Babel Information Model, Section 3.6.";
      }
      description
        "A set of babel-route-obj objects. Includes received and
         routes routes.";
      reference
        "RFC YYYY, Babel Information Model, Section 3.1.";
    }

    list security {
      key "mechanism";

      uses security;
      description
        "A security-obj object that applies to all interfaces. If this
         object is implemented, it allows a security mechanism to be
         enabled or disabled in a manner that applies to all Babel
         messages on all interfaces";
      reference
        "RFC YYYY, Babel Information Model, Section 3.1.";
    }
  }
}
