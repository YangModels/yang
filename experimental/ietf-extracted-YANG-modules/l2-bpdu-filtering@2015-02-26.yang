module l2-bpdu-filtering {
  namespace "urn:ietf:params:xml:ns:yang:l2-bpdu-filtering";
  prefix bpdu;
  import ietf-interfaces {
    prefix if;
  }

  import iana-if-type {
    prefix ianaift;
  }

  organization
    "Cisco Systems, Inc.
     Customer Service

     Postal: 170 W Tasman Drive
     San Jose, CA 95134

     Tel: +1 1800 553-NETS

     E-mail: cs-yang@cisco.com";

  contact
    "Robert Wilton - rwilton@cisco.com";

  description
    "This YANG module describes the extentions for 802.1Q defined
     filtering of BPDUs via the destination MAC address.";

  revision 2015-02-26 {
    description "Latest revision";

    reference "Internet-Draft draft-ietf-rwilton-vlan-yang-00.txt";
  }

  feature bpdu-filtering {
    description
      "This feature indicates that the device supports standards
       compliant BPDU filtering";
  }

  /*
   * BPDU processing applies to all Etherlike interfaces.
   */
  augment "/if:interfaces/if:interface" {
    when "if:type = 'ianaift:ethernetCsmacd' or
          if:type = 'ianaift:ieee8023adLag'" {
      description "Applies to all Etherlike interfaces";
    }
    description "Add BPDU related configuration to Etherlike
                 interfaces";
    container bpdu {
      description "BPDU related configuration";

      /*
       * The filtering leaf defines the filtering of L2 BPDUs based
       * on their destination MAC address.  If no value has been
       * specified then the default behaviour is that there is no
       * filtering.
       */
      leaf filtering {
        if-feature bpdu-filtering;
        type enumeration {
          enum c-vlan {
            description "C-VLAN ingress frame filtering";
            reference
              "Table 8-1 C-VLAN and MAC Bridge component reserved
               addresses of IEEE 802.1Q (2014)";
          }
          enum s-vlan {
            description "S-VLAN ingress frame filtering";
            reference
              "Table 8-2 S-VLAN component reserved addresses of
               IEEE 802.1Q (2014)";
          }
          enum mac-relay {
            description "2-port MAC relay ingress frame filtering";
            reference
              "Table 8-3 TPMR component Reserved addresses of IEEE
               802.1Q (2014)";
          }
        }
        description "The type of filtering to apply to all ingress
                     BPDU frames on this interface.  If no filtering
                     behavior is specified then frames are forwarded
                     by default unless they have been explicitly
                     peered by protocol specific configuration";
      }
    }
  }
}
