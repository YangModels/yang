module ietf-network-inventory-topology {
  yang-version 1.1;
  namespace "urn:ietf:params:xml:ns:yang:ietf-network-inventory-topology";
  prefix nwit;

  import ietf-network {
    prefix nw;
    reference
      "RFC 8345: A YANG Data Model for Network Topologies";
  }
  import ietf-network-topology {
    prefix nt;
    reference
      "RFC 8345: A YANG Data Model for Network Topologies";
  }

  organization
    "IETF Network Inventory YANG (ivy) Working Group";
  contact
    "WG Web:   <https://datatracker.ietf.org/wg/ivy>
     WG List:  <mailto:inventory-yang@ietf.org>

     Editor: Bo Wu
          <lana.wubo@huawei.com>
     Editor: Cheng Zhou
          <zhouchengyjy@chinamobile.com>
     Editor: Qin Wu
          <bill.wu@huawei.com>
     Editor: Mohamed Boucadair
          <mohamed.boucadair@orange.com>";
  description
    "This YANG module defines XXX.

     Copyright (c) 2023 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.";

  revision 2023-10-18 {
    description
      "Initial revision.";
    reference
      "RFC XXXX: A YANG Data Model for Network Inventory Topology";
  }

  identity node-type {
    description
      "Base identity for node device type.";
  }

  identity switch {
    base node-type;
    description
      "Identity for switch device.";
  }

  identity router {
    base node-type;
    description
      "Identity for router device.";
  }

  identity firewall {
    base node-type;
    description
      "Identity for Firewall device.";
  }

  identity access-controller {
    base node-type;
    description
      "Identity for WIFI access controller device.";
  }

  identity access-point {
    base node-type;
    description
      "Identity for WIFI access point device.";
  }

  identity sdn-controller {
    base node-type;
    description
      "Identity for controller.";
  }

  identity server {
    base node-type;
    description
      "Identity for computing server device.";
  }

  identity vm {
    base node-type;
    description
      "Identity for VM node.";
  }

  identity camera {
    base node-type;
    description
      "Identity for camera device.";
  }

  identity printer {
    base node-type;
    description
      "Identity for camera device.";
  }

  identity cell-phone {
    base node-type;
    description
      "Identity for mobile phone.";
  }

  identity port-type {
    description
      "Base identity for device port type.";
  }

  typedef oper-state {
    type enumeration {
      enum unknown {
        value 1;
        description
          "The resource is unable to report its operational
           state.";
      }
      enum disabled {
        value 2;
        description
          "The resource is totally inoperable.";
      }
      enum enabled {
        value 3;
        description
          "The resource is partially or fully operable.";
      }
      enum testing {
        value 4;
        description
          "The resource is currently being tested and cannot
           therefore report whether or not it is operational.";
      }
    }
    description
      "Represents the possible values of operational states.";
    reference
      "RFC 4268: Entity State MIB - EntityOperState";
  }

  /* Groupings */

  grouping inventory-network-type {
    description
      "Indicates the topology type to be inventory.";
    container network-inventory {
      presence "Indicates Network Inventory.";
      description
        "The presence of the container node indicates
         Network Inventory.";
    }
  }

  grouping system-mount-point {
    container system-mount-point {
      description
        "Container for system configuration or state mount-point.";
    }
  }

  grouping inventory-node-attributes {
    description
      "Augment used to define attach the node configuration";
    leaf name {
      type string;
      description
        "The name of the node.";
    }
    leaf node-type {
      type identityref {
        base node-type;
      }
      config false;
      description
        "Node type.";
    }
    leaf-list network-element-inventory-ref {
      type leafref {
        path "/nwi:network-elements"
           + "/nwi:network-element/nwi:name";
      }
      config false;
      description
        "The reference of the Network Elements (NEs) from which this
         node is abstracted. For example, in the case of cluster device,
         one node can abstract multiple NEs.";
    }
    uses system-mount-point;
    leaf oper-state {
      type oper-state;
      config false;
      description
        "The operational state for this component.
         Note that this node does not follow the administrative
         state.  An administrative state of 'down' does not
         predict an operational state of 'disabled'.
         Note that some implementations may not be able to
         accurately report oper-state while the admin-state node
         has a value other than 'unlocked'.  In these cases, this
         node MUST have a value of 'unknown'.";
      reference
        "RFC 4268: Entity State MIB - entStateOper";
    }
  }

  grouping inventory-termination-point-attributes {
    description
      "Augment used to define attach the termination point
       attributes.";
    leaf tp-name {
      type string;
      config false;
      description
        "The name of the interface.";
    }
    leaf tp-description {
      type string;
      config false;
      description
        "A textual description of the interface.";
    }
    leaf tp-type {
      type identityref {
        base port-type;
      }
      config false;
      description
        "The port type of the interface, e.g. console port";
    }
    leaf port-component-inventory-ref {
      type leafref {
        path "/nwi:network-elements/nwi:network-element/"
           + "nwi:components/nwi:component/nwi:name";
      }
      config false;
      description
        "The reference of the port component from which this
         termination point is abstracted.";
    }
    leaf interface-name {
      type string;
      description
        "Name of the interface.  The name can (but does not
         have to) correspond to an interface reference of a
         containing node's interface, i.e., the path name of a
         corresponding interface data node on the containing
         node is reminiscent of data type interface-ref defined
         in RFC 8343.  It should be noted that data type
         interface-ref of RFC 8343 cannot be used directly,
         as this data type is used to reference an interface
         in a datastore of a single node in the network, not
         to uniquely reference interfaces across a network.";
    }
    uses system-mount-point;
    leaf oper-state {
      type oper-state;
      config false;
      description
        "The operational state for this component.
         Note that this node does not follow the administrative
         state.  An administrative state of 'down' does not
         predict an operational state of 'disabled'.
         Note that some implementations may not be able to
         accurately report oper-state while the admin-state node
         has a value other than 'unlocked'.  In these cases, this
         node MUST have a value of 'unknown'.";
      reference
        "RFC 4268: Entity State MIB - entStateOper";
    }
  }

  grouping inventory-link-attributes {
    description
      "Augment used to define attach the termination point
       attributes.";
    leaf link-name {
      type string;
      config false;
      description
        "The name of the link.";
    }
    leaf cable-ref {
      type leafref {
        path "/nwi:cables/nwi:cable/nwi:name";
      }
      config false;
      description
        "The reference of the cable inventory information from which
         this link is abstracted.";
    }
    leaf link-description {
      type string;
      config false;
      description
        "A textual description of the interface.";
    }
    leaf link-type {
      type string;
      config false;
      description
        "The type of the link.";
    }
    leaf oper-state {
      type oper-state;
      config false;
      description
        "The operational state for this link.";
    }
  }

  /* Main blocks */

  augment "/nw:networks/nw:network/nw:network-types" {
    description
      "Introduces new network type for network inventory.";
    uses inventory-network-type;
  }

  augment "/nw:networks/nw:network/nw:node" {
    when '/nw:networks/nw:network/nw:network-types/
   nwit:network-inventory' {
      description
        "Augmentation parameters apply only for network inventory.";
    }
    description
      "Configuration parameters for inventory at the node
       level.";
    uses inventory-node-attributes;
  }
  augment "/nw:networks/nw:network/nt:link" {
    when '/nw:networks/nw:network/nw:network-types/
     nwit:network-inventory' {
      description
        "Augmentation parameters apply only for network
         inventory.";
    }
    description
      "Augments inventory topology link information.";
    uses inventory-link-attributes;
  }

  augment
    "/nw:networks/nw:network/nw:node/nt:termination-point" {
      when '/nw:networks/nw:network/nw:network-types/
     nwit:network-inventory' {
        description
          "Augmentation parameters apply only for network
           inventory.";
      }
      description
        "Augments inventory termination point information.";
      uses inventory-termination-point-attributes;
  }
}
