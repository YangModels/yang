module ietf-fabric-types {

yang-version 1;
namespace "urn:ietf:params:xml:ns:yang:ietf-fabric-types";
prefix ftypes;

import ietf-inet-types {
            prefix "inet";
    }
import ietf-yang-types {
            prefix "yang";
            revision-date "2013-07-15";
    }
    import ietf-network-topology {
            prefix nt;
    }
    organization
"Huawei Technologies";
    contact
"shidanian@huawei.com";
description
    "This module contains a collection of YANG definitions for Fabric network service.";

revision "2016-02-26" {
    description
        "Initial revision of fabric network service.";
            reference
                    "";
}
    // identity statements
identity fabric-type {
            description "base fabric type";
}
identity vxlan-fabric {
    base fabric-type;
            description "vxlan-fabric fabric";
}
    // typedef statements.
    // ref nodes are all changed to refer to network/network-topology data models.
typedef node-ref {
    type instance-identifier;
            description "A reference to a node in topology";
}
typedef tp-ref {
    type instance-identifier;
            /*type leafref {
        path "/network-topology/topology/node/termination-point/tp-id";
    }*/
    description "A reference to a termination point in topology";
}
typedef link-ref {
    type instance-identifier;
            description "A reference to a link in topology";
}
typedef device-role {

    type enumeration {
        enum SPINE {
            description "";
        }
        enum LEAF {
            description "";
        }
    }
            description "device role type";
}
typedef port-role {

    type enumeration {
        enum NNI {
            description "the port used for fabric intra communiation.";
        }
        enum UNI {
            description "the port used for Endpoint to access fabric.";
        }
    }
            description "port role type";
}
typedef underlayer-network-type {

    type enumeration {
        enum VXLAN {
            description "vxlan";
        }
        enum TRILL {
            description "trill";
        }
    }
            description "";
}
typedef layer2-protocol-type-enum {
    type enumeration {
        enum VLAN{
                            description "vlan";
                    }
        enum VXLAN{
                            description "vxlan";
                    }
        enum TRILL{
                            description "trill";
                    }
        enum NvGRE{
                            description "nvgre";
                    }
    }
            description "l2 protocol type";
}
typedef access-type {
    type enumeration {
        enum exclusive{
                            description "exclusive";
                    }
        enum vlan{
                            description "vlan";
                    }
    }
            description "access type";
}
    // grouping statements
grouping acl-list {

    list fabric-acl {
        key fabric-acl-name;
        leaf fabric-acl-name {
            type string;
                            description "fabric acl name";
        }
                    description "list of fabric acl";
    }
            description "fabric acl list";
}

grouping logic-switch {
    description "logic switch attributes";
    leaf lsw-uuid {
        type yang:uuid;
                    description "logic switch id";
    }
    leaf name {
        type string;
                    description "name of the logic switch";
    }
    leaf segment-id {
        type uint32;
                    description "segement id";
    }
    leaf network {
        type inet:ip-prefix;
                    description "ip prefix";
    }
    uses acl-list;
}
grouping logic-router {
    description "logic router attributes";
    leaf lr-uuid {
        type yang:uuid;
                    description "logic router id";
    }
    leaf name {
        type string;
                    description "logic router name";
    }
    leaf vrf-ctx {
        type uint32;
                    description "vrf-context if vxlan";
    }
    uses acl-list;
}
grouping logic-port {
    description "logic port attributes";
    leaf lport-uuid {
        type yang:uuid;
                    description "logic port id";
    }
    leaf name {
        type string;
                    description "logic port name";
    }
    leaf role {
        type port-role;
                    description "role";
    }
    container layer-1-info {
                    description "layer 1 infor";
        leaf location {
            type tp-ref;
                            description "tp ref to layer 1 topo";
        }
    }
    container layer-2-info {
                    description "layer 2 infor";
        leaf access-type {
            type access-type;
                            description "access type";
        }
        leaf access-segment {
            type uint32;
                            description "access segment";
        }
    }
    container layer-3-info {
                    description "layer 3 info";

        leaf ip {
            type inet:ip-address;
                            description "ip address";
        }
        leaf network {
            type inet:ip-prefix;
                            description "ip prefix";
        }
        leaf mac {
            type yang:phys-address;
                            description "mac address";
        }
        leaf forward-enable {
            type boolean;
                            description "";
        }
    }
    uses acl-list;

            list underlayer-ports {
                    key port-ref;
                    uses nt:tp-ref;
                    description "underlayer-network-type ports infor";
            }
}
}
