module service-function-path-metadata {

  namespace "urn:cisco:params:xml:ns:yang:sfc-md";

  prefix sfc-md;

  organization "Cisco Systems, Inc.";
  contact "Paul Quinn <paulq@cisco.com>";

  description
  "This module contains a collection of YANG definitions metadata
    used in a service function path between participating nodes";

  revision 2014-07-01 {
    description
      "Initial Version";
     reference
      "RFC XXXX: Service Path Metadata";
  }

  // Service Function Path Metadata

  typedef context-metadata-ref {
    type leafref {
      path "/sfc-md:service-function-metadata/" +
        "sfc-md:context-metadata/sfc-md:name";
    }
    description
      "This type is used by data models that need to reference
       configured context metadata headers.";
  }

  typedef variable-metadata-ref {
    type leafref {
      path "/sfc-md:service-function-metadata/" +
        "sfc-md:variable-metadata/sfc-md:name";
    }
    description
      "This type is used by data models that need to reference
       configured variable metadata headers.";
  }

  //Another module would reference these headers like
  //leaf name {
  //  type sfc-md:context-metadata-ref;
  //  description
  //   "A reference to the name of a configured context header";
  //}
  container service-function-metadata {

    description
      "NSH provides a mechanism to carry shared metadata between
       network  devices and service function, and between service
       functions. The semantics of the shared metadata is
       communicated via a control plane to participating
       nodes. Examples of metadata include classification
       information used for policy enforcement and network context
       for forwarding post service delivery.";

    list context-metadata {
      key "name";
      leaf name {
        type string;
        description "A unique name for this set of context headers";
      }
      leaf context-header1 {
        type uint32;
        description "network platform context, bytes 9-12";
      }
      leaf context-header2 {
        type uint32;
        description "network platform context, bytes 13-16";
      }
      leaf context-header3 {
        type uint32;
        description "network platform context, bytes 17-20";
      }
      leaf context-header4 {
        type uint32;
        description "network platform context, bytes 21-24";
      }
      description "Fixed Context metadata headers";
    }
    list variable-metadata {
      key "name";
      leaf name {
        type string;
        description "A unique name for this set of variable length
          metadata";
      }
      list tlv-metadata {
        key "tlv-class tlv-type";
        leaf tlv-class {
          type uint16;
          description "Class of TLV being used, bytes 25-26";
        }
        leaf tlv-type {
          type uint8;
          description "type of tlv for a given class";
        }
        leaf flags {
          type bits {
            bit r1 {
              position 24;
              description "Reserved";
            }
            bit r2 {
              position 25;
              description "Reserved";
            }
            bit r3 {
              position 26;
              description "Reserved";
            }
          }
          description "reserved flag bits";
        }

        leaf length {
          type uint8 {
            range "0..32";
          }
          description "Length of the variable metadata in 4-byte
            words";
        }
        leaf tlv-data {
          type string;
          description "Variable Data";
        }
        description "A set of variable length metadata";
      }
      description "A list that contain sets of variable length
        metadata";
    }
  }
}
