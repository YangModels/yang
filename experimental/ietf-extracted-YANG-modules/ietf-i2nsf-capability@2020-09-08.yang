module ietf-i2nsf-capability {
  yang-version 1.1;
  namespace
    "urn:ietf:params:xml:ns:yang:ietf-i2nsf-capability";
  prefix
    nsfcap;

  organization
    "IETF I2NSF (Interface to Network Security Functions)
     Working Group";

  contact
    "WG Web: <http://tools.ietf.org/wg/i2nsf>
     WG List: <mailto:i2nsf@ietf.org>

     Editor: Jaehoon Paul Jeong
     <mailto:pauljeong@skku.edu>

     Editor: Jinyong Tim Kim
     <mailto:timkim@skku.edu>

     Editor: Susan Hares
     <mailto:shares@ndzh.com>";

  description
    "This module is a YANG module for I2NSF Network Security
     Functions (NSFs)'s Capabilities.

     Copyright (c) 2020 IETF Trust and the persons identified as
     authors of the code. All rights reserved.

     Redistribution and use in source and binary forms, with or
     without modification, is permitted pursuant to, and subject
     to the license terms contained in, the Simplified BSD License
     set forth in Section 4.c of the IETF Trust's Legal Provisions
     Relating to IETF Documents
     http://trustee.ietf.org/license-info).

     This version of this YANG module is part of RFC XXXX; see
     the RFC itself for full legal notices.";

  // RFC Ed.: replace XXXX with an actual RFC number and remove
  // this note.

  revision "2020-09-08"{
    description "Initial revision.";
    reference
      "RFC XXXX: I2NSF Capability YANG Data Model";

    // RFC Ed.: replace XXXX with an actual RFC number and remove
    // this note.
  }

  /*
   * Identities
   */

  identity event {
    description
      "Base identity for I2NSF policy events.";
    reference
      "draft-ietf-i2nsf-nsf-monitoring-data-model-04: I2NSF NSF
       Monitoring YANG Data Model - Event";

    // RFC Ed.: replace the above draft with an actual RFC in the
    // YANG module and remove this note.
  }

  identity system-event-capability {
    base event;
    description
      "Identity for system event";
    reference
      "draft-ietf-i2nsf-nsf-monitoring-data-model-04: I2NSF NSF
       Monitoring YANG Data Model - System event";
  }

  identity system-alarm-capability {
    base event;
    description
      "Identity for system alarm";
    reference
      "draft-ietf-i2nsf-nsf-monitoring-data-model-04: I2NSF NSF
       Monitoring YANG Data Model - System alarm";
  }

  identity access-violation {
    base system-event-capability;
    description
      "Identity for access violation event";
    reference
      "draft-ietf-i2nsf-nsf-monitoring-data-model-04: I2NSF NSF
       Monitoring YANG Data Model - System event for access
       violation";
  }

  identity configuration-change {
    base system-event-capability;
    description
      "Identity for configuration change event";
    reference
      "draft-ietf-i2nsf-nsf-monitoring-data-model-04: I2NSF NSF
       Monitoring YANG Data Model - System event for configuration
       change";
  }

  identity memory-alarm {
    base system-alarm-capability;
    description
      "Identity for memory alarm";
    reference
      "draft-ietf-i2nsf-nsf-monitoring-data-model-04: I2NSF NSF
       Monitoring YANG Data Model - System alarm for memory";
  }

  identity cpu-alarm {
    base system-alarm-capability;
    description
      "Identity for CPU alarm";
    reference
      "draft-ietf-i2nsf-nsf-monitoring-data-model-04: I2NSF NSF
       Monitoring YANG Data Model - System alarm for CPU";
  }

  identity disk-alarm {
    base system-alarm-capability;
    description
      "Identity for disk alarm";
    reference
      "draft-ietf-i2nsf-nsf-monitoring-data-model-04: I2NSF NSF
       Monitoring YANG Data Model - System alarm for disk";
  }

  identity hardware-alarm {
    base system-alarm-capability;
    description
      "Identity for hardware alarm";
    reference
      "draft-ietf-i2nsf-nsf-monitoring-data-model-04: I2NSF NSF
       Monitoring YANG Data Model - System alarm for hardware";
  }

  identity interface-alarm {
    base system-alarm-capability;
    description
      "Identity for interface alarm";
    reference
      "draft-ietf-i2nsf-nsf-monitoring-data-model-04: I2NSF NSF
       Monitoring YANG Data Model - System alarm for interface";
  }

  identity condition {
    description
      "Base identity for policy conditions";
  }

  identity context-capability {
    base condition;
    description
      "Identity for context condition capabilities for an NSF";
    reference
      "draft-ietf-i2nsf-capability-05: Information Model of NSFs
       Capabilities - The operating context of an NSF.";
  }

  identity access-control-list {
    base context-capability;
    description
      "Identity for Access Control List (ACL) condition capability";
    reference
      "draft-ietf-i2nsf-capability-05: Information Model of NSFs
       Capabilities - The context of an NSF.
       RFC 8519: YANG Data Model for Network Access Control Lists
       (ACLs) - A user-ordered set of rules used to configure the
       forwarding behavior in an NSF.";
  }

  identity application-layer-filter {
    base context-capability;
    description
      "Identity for application-layer-filter condition capability";
    reference
      "draft-ietf-i2nsf-capability-05: Information Model of NSFs
       Capabilities - An application-layer filtering (e.g., web
       filter) as an NSF.";
  }

  identity target {
    base context-capability;
    description
      "Identity for target condition capability";
    reference
      "draft-ietf-i2nsf-capability-05: Information Model of NSFs
       Capabilities - A target (or destination) of a policy rule
       to be applied by an NSF.
       RFC 8519: YANG Data Model for Network Access Control Lists
       (ACLs) - An access control for a target (e.g., the
       corresponding IP address) in an NSF.";
  }

  identity user {
    base context-capability;
    description
      "Identity for user condition capability";
    reference
      "draft-ietf-i2nsf-capability-05: Information Model of NSFs
       Capabilities - A user in an application of a policy rule
       to be applied by an NSF.
       RFC 8519: YANG Data Model for Network Access Control Lists
       (ACLs) - An access control for a user (e.g., the
       corresponding IP address) in an NSF.";
  }

  identity group {
    base context-capability;
    description
      "Identity for group condition capability";
    reference
      "draft-ietf-i2nsf-capability-05: Information Model of NSFs
       Capabilities - A group (i.e., a set of users) in an
       application of a policy rule to be applied by an NSF.
       RFC 8519: YANG Data Model for Network Access Control Lists
       (ACLs) - An access control for a group (e.g., the
       corresponding IP address) in an NSF.";
  }

  identity geography {
    base context-capability;
    description
      "Identity for geography condition capability";
    reference
      "draft-ietf-i2nsf-capability-05: Information Model of NSFs
       Capabilities - A group (i.e., a set of users) in an
       application of a policy rule to be applied by an NSF.
       RFC 8519: YANG Data Model for Network Access Control Lists
       (ACLs) - An access control for a geographical location
       i.e., geolocation (e.g., the corresponding IP address) in
       an NSF.
       RFC 8805: A Format for Self-Published IP Geolocation Feeds
       - An IP address with geolocation information.";
  }

  identity ipv4-capability {
    base condition;
    description
      "Identity for IPv4 condition capability";
    reference
      "RFC 791: Internet Protocol";
  }

  identity exact-ipv4-header-length {
    base ipv4-capability;
    description
      "Identity for exact-match IPv4 header-length
      condition capability";
    reference
      "RFC 791: Internet Protocol - Header Length";
  }

  identity range-ipv4-header-length {
    base ipv4-capability;
    description
      "Identity for range-match IPv4 header-length
      condition capability";
    reference
      "RFC 791: Internet Protocol - Header Length";
  }

  identity ipv4-tos {
    base ipv4-capability;
    description
      "Identity for IPv4 Type-Of-Service (TOS)
      condition capability";
    reference
      "RFC 791: Internet Protocol - Type of Service";
  }

  identity exact-ipv4-total-length {
    base ipv4-capability;
    description
      "Identity for exact-match IPv4 total length
      condition capability";
    reference
      "RFC 791: Internet Protocol - Total Length";
  }

  identity range-ipv4-total-length {
    base ipv4-capability;
    description
      "Identity for range-match IPv4 total length
      condition capability";
    reference
      "RFC 791: Internet Protocol - Total Length";
  }

  identity ipv4-id {
    base ipv4-capability;
    description
      "Identity for identification condition capability";
    reference
      "RFC 791: Internet Protocol - Identification";
  }

  identity ipv4-fragment-flags {
    base ipv4-capability;
    description
      "Identity for IPv4 fragment flags condition capability";
    reference
      "RFC 791: Internet Protocol - Fragmentation Flags";
  }

  identity exact-ipv4-fragment-offset {
    base ipv4-capability;
    description
      "Identity for exact-match IPv4 fragment offset
      condition capability";
    reference
      "RFC 791: Internet Protocol - Fragmentation Offset";
  }

  identity range-ipv4-fragment-offset {
    base ipv4-capability;
    description
      "Identity for range-match IPv4 fragment offset
      condition capability";
    reference
      "RFC 791: Internet Protocol - Fragmentation Offset";
  }

  identity exact-ipv4-ttl {
    base ipv4-capability;
    description
      "Identity for exact-match IPv4 Time-To-Live (TTL)
      condition capability";
    reference
      "RFC 791: Internet Protocol - Time To Live (TTL)";
  }

  identity range-ipv4-ttl {
    base ipv4-capability;
    description
      "Identity for range-match IPv4 Time-To-Live (TTL)
      condition capability";
    reference
      "RFC 791: Internet Protocol - Time To Live (TTL)";
  }

  identity ipv4-protocol {
    base ipv4-capability;
    description
      "Identity for IPv4 protocol condition capability";
    reference
      "IANA Website: Assigned Internet Protocol Numbers
       - Protocol Number for IPv4
       RFC 791: Internet Protocol - Protocol";
  }

  identity exact-ipv4-address {
    base ipv4-capability;
    description
      "Identity for exact-match IPv4 address
      condition capability";
    reference
      "RFC 791: Internet Protocol - Address";
  }

  identity range-ipv4-address {
    base ipv4-capability;
    description
      "Identity for range-match IPv4 address condition
       capability";
    reference
      "RFC 791: Internet Protocol - Address";
  }

  identity ipv4-ip-opts {
    base ipv4-capability;
    description
      "Identity for IPv4 option condition capability";
    reference
      "RFC 791: Internet Protocol - Options";
  }

  identity ipv4-geo-ip {
    base ipv4-capability;
    description
      "Identity for geography condition capability";
    reference
      "draft-ietf-i2nsf-capability-05: Information Model
       of NSFs Capabilities - Geo-IP";
  }

  identity ipv6-capability {
    base condition;
    description
      "Identity for IPv6 condition capabilities";
    reference
      "RFC 8200: Internet Protocol, Version 6 (IPv6)
      Specification";
  }

  identity ipv6-traffic-class {
    base ipv6-capability;
    description
      "Identity for IPv6 traffic class
      condition capability";
    reference
      "RFC 8200: Internet Protocol, Version 6 (IPv6)
      Specification - Traffic Class";
  }

  identity exact-ipv6-flow-label {
    base ipv6-capability;
    description
      "Identity for exact-match IPv6 flow label
      condition capability";
    reference
      "RFC 8200: Internet Protocol, Version 6 (IPv6)
      Specification - Flow Label";
  }

  identity range-ipv6-flow-label {
    base ipv6-capability;
    description
      "Identity for range-match IPv6 flow label
      condition capability";
    reference
      "RFC 8200: Internet Protocol, Version 6 (IPv6)
      Specification - Flow Label";
  }

  identity exact-ipv6-payload-length {
    base ipv6-capability;
    description
      "Identity for exact-match IPv6 payload length
      condition capability";
    reference
      "RFC 8200: Internet Protocol, Version 6 (IPv6)
      Specification - Payload Length";
  }

  identity range-ipv6-payload-length {
    base ipv6-capability;
    description
      "Identity for range-match IPv6 payload length
      condition capability";
    reference
      "RFC 8200: Internet Protocol, Version 6 (IPv6)
      Specification - Payload Length";
  }

  identity ipv6-next-header {
    base ipv6-capability;
    description
      "Identity for IPv6 next header condition capability";
    reference
      "RFC 8200: Internet Protocol, Version 6 (IPv6)
      Specification - Next Header";
  }

  identity exact-ipv6-hop-limit {
    base ipv6-capability;
    description
      "Identity for exact-match IPv6 hop limit condition
      capability";
    reference
      "RFC 8200: Internet Protocol, Version 6 (IPv6)
      Specification - Hop Limit";
  }

  identity range-ipv6-hop-limit {
    base ipv6-capability;
    description
      "Identity for range-match IPv6 hop limit condition
      capability";
    reference
      "RFC 8200: Internet Protocol, Version 6 (IPv6)
      Specification - Hop Limit";
  }

  identity ipv6-protocol {
    base ipv6-capability;
    description
      "Identity for IPv6 protocol condition capability";
    reference
      "IANA Website: Assigned Internet Protocol Numbers
       - Protocol Number for IPv6
       RFC 8200: Internet Protocol, Version 6 (IPv6)
       Specification - Protocol";
  }

  identity exact-ipv6-address {
    base ipv6-capability;
    description
      "Identity for exact-match IPv6 address condition
       capability";
    reference
      "RFC 8200: Internet Protocol, Version 6 (IPv6)
      Specification - Address";
  }

  identity range-ipv6-address {
    base ipv6-capability;
    description
      "Identity for range-match IPv6 address condition
      capability";
    reference
      "RFC 8200: Internet Protocol, Version 6 (IPv6)
      Specification - Address";
  }

  identity tcp-capability {
    base condition;
    description
      "Identity for TCP condition capabilities";
    reference
      "RFC 793: Transmission Control Protocol";
  }

  identity exact-tcp-port-num {
    base tcp-capability;
    description
      "Identity for exact-match TCP port number condition
       capability";
    reference
      "RFC 793: Transmission Control Protocol - Port Number";
  }

  identity range-tcp-port-num {
    base tcp-capability;
    description
      "Identity for range-match TCP port number condition
       capability";
    reference
      "RFC 793: Transmission Control Protocol - Port Number";
  }

  identity exact-tcp-seq-num {
    base tcp-capability;
    description
      "Identity for exact-match TCP sequence number condition
      capability";
    reference
      "RFC 793: Transmission Control Protocol - Sequence Number";
  }

  identity range-tcp-seq-num {
    base tcp-capability;
    description
      "Identity for range-match TCP sequence number condition
       capability";
    reference
      "RFC 793: Transmission Control Protocol - Sequence Number";
  }

  identity exact-tcp-ack-num {
    base tcp-capability;
    description
      "Identity for exact-match TCP acknowledgement number condition
       capability";
    reference
      "RFC 793: Transmission Control Protocol - Acknowledgement Number";
  }

  identity range-tcp-ack-num {
    base tcp-capability;
    description
      "Identity for range-match TCP acknowledgement number condition
       capability";
    reference
      "RFC 793: Transmission Control Protocol - Acknowledgement Number";
  }

  identity exact-tcp-window-size {
    base tcp-capability;
    description
      "Identity for exact-match TCP window size condition capability";
    reference
      "RFC 793: Transmission Control Protocol - Window Size";
  }

  identity range-tcp-window-size {
    base tcp-capability;
    description
      "Identity for range-match TCP window size condition capability";
    reference
      "RFC 793: Transmission Control Protocol - Window Size";
  }

  identity tcp-flags {
    base tcp-capability;
    description
      "Identity for TCP flags condition capability";
    reference
      "RFC 793: Transmission Control Protocol - Flags";
  }

  identity udp-capability {
    base condition;
    description
      "Identity for UDP condition capabilities";
    reference
      "RFC 768: User Datagram Protocol";
  }

  identity exact-udp-port-num {
    base udp-capability;
    description
      "Identity for exact-match UDP port number condition capability";
    reference
      "RFC 768: User Datagram Protocol - Port Number";
  }

  identity range-udp-port-num {
    base udp-capability;
    description
      "Identity for range-match UDP port number condition capability";
    reference
      "RFC 768: User Datagram Protocol - Port Number";
  }

  identity exact-udp-total-length {
    base udp-capability;
    description
      "Identity for exact-match UDP total-length condition capability";
    reference
      "RFC 768: User Datagram Protocol - Total Length";
  }

  identity range-udp-total-length {
    base udp-capability;
    description
      "Identity for range-match UDP total-length condition capability";
    reference
      "RFC 768: User Datagram Protocol - Total Length";
  }

  identity icmp-capability {
    base condition;
    description
      "Identity for ICMP condition capability";
    reference
      "RFC 792: Internet Control Message Protocol";
  }

  identity icmp-type {
    base icmp-capability;
    description
      "Identity for ICMP type condition capability";
    reference
      "RFC 792: Internet Control Message Protocol";
  }

  identity icmpv6-capability {
    base condition;
    description
      "Identity for ICMPv6 condition capability";
    reference
      "RFC 4443: Internet Control Message Protocol (ICMPv6)
       for the Internet Protocol Version 6 (IPv6) Specification
       - ICMPv6";
  }

  identity icmpv6-type {
    base icmpv6-capability;
    description
      "Identity for ICMPv6 type condition capability";
    reference
      "RFC 4443: Internet Control Message Protocol (ICMPv6)
       for the Internet Protocol Version 6 (IPv6) Specification
       - ICMPv6";
  }

  identity url-capability {
    base condition;
    description
      "Identity for URL condition capability";
  }

  identity pre-defined {
    base url-capability;
    description
      "Identity for URL pre-defined condition capability";
  }

  identity user-defined {
    base url-capability;
    description
      "Identity for URL user-defined condition capability";
  }

  identity log-action-capability {
    description
      "Identity for log-action capability";
  }

  identity rule-log {
    base log-action-capability;
    description
      "Identity for rule log log-action capability";
  }

  identity session-log {
    base log-action-capability;
    description
      "Identity for session log log-action capability";
  }

  identity ingress-action-capability {
    description
      "Identity for ingress-action capability";
    reference
      "RFC 8329: Framework for Interface to Network Security
       Functions - Ingress action";
  }

  identity egress-action-capability {
    description
      "Base identity for egress-action capability";
    reference
      "RFC 8329: Framework for Interface to Network Security
       Functions - Egress action";
  }

  identity default-action-capability {
    description
      "Identity for default-action capability";
    reference
      "draft-ietf-i2nsf-capability-05: Information Model of
       NSFs Capabilities - Default action";
  }

  identity pass {
    base ingress-action-capability;
    base egress-action-capability;
    base default-action-capability;
    description
      "Identity for pass action capability";
    reference
      "RFC 8329: Framework for Interface to Network Security
       Functions - Ingress, egress, and pass actions.
       draft-ietf-i2nsf-capability-05: Information Model of
       NSFs Capabilities - Actions and default action.";
  }
  identity drop {
    base ingress-action-capability;
    base egress-action-capability;
    base default-action-capability;
    description
      "Identity for drop action capability";
    reference
      "RFC 8329: Framework for Interface to Network Security
       Functions - Ingress, egress, and drop actions.
       draft-ietf-i2nsf-capability-05: Information Model of
       NSFs Capabilities - Actions and default action.";
  }

  identity alert {
    base ingress-action-capability;
    base egress-action-capability;
    base default-action-capability;
    description
      "Identity for alert action capability";
    reference
      "RFC 8329: Framework for Interface to Network Security
       Functions - Ingress, egress, and alert actions.
       draft-ietf-i2nsf-nsf-monitoring-data-model-04: I2NSF
       NSF Monitoring YANG Data Model - Alarm (i.e., alert).
       draft-ietf-i2nsf-capability-05: Information Model of
       NSFs Capabilities - Actions and default action.";
  }

  identity mirror {
    base ingress-action-capability;
    base egress-action-capability;
    base default-action-capability;
    description
      "Identity for mirror action capability";
    reference
      "RFC 8329: Framework for Interface to Network Security
       Functions - Ingress, egress, and mirror actions.
       draft-ietf-i2nsf-capability-05: Information Model of
       NSFs Capabilities - Actions and default action.";
  }

  identity invoke-signaling {
    base egress-action-capability;
    description
      "Identity for invoke signaling action capability";
    reference
      "RFC 8329: Framework for Interface to Network Security
       Functions - Invoke-signaling action";
  }

  identity tunnel-encapsulation {
    base egress-action-capability;
    description
      "Identity for tunnel encapsulation action capability";
    reference
      "RFC 8329: Framework for Interface to Network Security
       Functions - Tunnel-encapsulation action";
  }

  identity forwarding {
    base egress-action-capability;
    description
      "Identity for forwarding action capability";
    reference
      "RFC 8329: Framework for Interface to Network Security
       Functions - Forwarding action";
  }

  identity redirection {
    base egress-action-capability;
    description
      "Identity for redirection action capability";
    reference
      "RFC 8329: Framework for Interface to Network Security
       Functions - Redirection action";
  }

  identity resolution-strategy-capability {
    description
      "Base identity for resolution strategy capability";
    reference
      "draft-ietf-i2nsf-capability-05: Information Model of
       NSFs Capabilities - Resolution Strategy";
  }

  identity fmr {
    base resolution-strategy-capability;
    description
      "Identity for First Matching Rule (FMR) resolution
       strategy capability";
    reference
      "draft-ietf-i2nsf-capability-05: Information Model of
       NSFs Capabilities - Resolution Strategy";
  }

  identity lmr {
    base resolution-strategy-capability;
    description
      "Identity for Last Matching Rule (LMR) resolution
       strategy capability";
    reference
      "draft-ietf-i2nsf-capability-05: Information Model of
       NSFs Capabilities - Resolution Strategy";
  }

  identity pmr {
    base resolution-strategy-capability;
    description
      "Identity for Prioritized Matching Rule (PMR) resolution
       strategy capability";
    reference
      "draft-ietf-i2nsf-capability-05: Information Model of
       NSFs Capabilities - Resolution Strategy";
  }

  identity pmre {
    base resolution-strategy-capability;
    description
      "Identity for Prioritized Matching Rule with Errors (PMRE)
       resolution strategy capability";
    reference
      "draft-ietf-i2nsf-capability-05: Information Model of NSFs
       Capabilities - Resolution Strategy";
  }

  identity pmrn {
    base resolution-strategy-capability;
    description
      "Identity for Prioritized Matching Rule with No Errors (PMRN)
       resolution strategy capability";
    reference
      "draft-ietf-i2nsf-capability-05: Information Model of NSFs
       Capabilities - Resolution Strategy";
  }

  identity advanced-nsf-capability {
    description
      "Base identity for advanced Network Security Function (NSF)
       capability.  This can be used for advanced NSFs such as
       Anti-Virus, Anti-DDoS Attack, IPS, and VoIP/VoLTE Security
       Service.";
    reference
      "RFC 8329: Framework for Interface to Network Security
       Functions - Advanced NSF capability";
  }

  identity anti-virus-capability {
    base advanced-nsf-capability;
    description
      "Identity for advanced NSF Anti-Virus capability.
       This can be used for an extension point for Anti-Virus
       as an advanced NSF.";
       reference
      "RFC 8329: Framework for Interface to Network Security
       Functions - Advanced NSF Anti-Virus capability";
  }

  identity anti-ddos-capability {
    base advanced-nsf-capability;
    description
      "Identity for advanced NSF Anti-DDoS Attack capability.
       This can be used for an extension point for Anti-DDoS
       Attack as an advanced NSF.";
    reference
      "RFC 8329: Framework for Interface to Network Security
       Functions - Advanced NSF Anti-DDoS Attack capability";
  }

  identity ips-capability {
    base advanced-nsf-capability;
    description
      "Identity for advanced NSF IPS capabilities.  This can be
       used for an extension point for IPS as an advanced NSF.";
    reference
      "RFC 8329: Framework for Interface to Network Security
       Functions - Advanced NSF IPS capability";
  }

  identity voip-volte-capability {
    base advanced-nsf-capability;
    description
      "Identity for advanced NSF VoIP/VoLTE Security Service
       capability.  This can be used for an extension point
       for VoIP/VoLTE Security Service as an advanced NSF.";
    reference
      "RFC 3261: SIP: Session Initiation Protocol
       RFC 8329: Framework for Interface to Network Security
       Functions - Advanced NSF VoIP/VoLTE security service
       capability";
  }

  identity detect {
    base anti-virus-capability;
    description
      "Identity for advanced NSF Anti-Virus Detection capability.
       This can be used for an extension point for Anti-Virus
       Detection as an advanced NSF.";
    reference
      "RFC 8329: Framework for Interface to Network Security
       Functions - Advanced NSF Anti-Virus Detection capability";
  }

  identity exception-application {
    base anti-virus-capability;
    description
      "Identity for advanced NSF Anti-Virus Exception Application
       capability.  This can be used for an extension point for
       Anti-Virus Exception Application as an advanced NSF.";
    reference
      "RFC 8329: Framework for Interface to Network Security
       Functions - Advanced NSF Anti-Virus Exception Application
       capability";
  }

  identity exception-signature {
    base anti-virus-capability;
    description
      "Identity for advanced NSF Anti-Virus Exception Signature
       capability.  This can be used for an extension point for
       Anti-Virus Exception Signature as an advanced NSF.";
    reference
      "RFC 8329: Framework for Interface to Network Security
       Functions - Advanced NSF Anti-Virus Exception Signature
       capability";
  }

  identity allow-list {
    base anti-virus-capability;
    description
      "Identity for advanced NSF Anti-Virus Allow List capability.
       This can be used for an extension point for Anti-Virus
       Allow List as an advanced NSF.";
    reference
      "RFC 8329: Framework for Interface to Network Security
       Functions - Advanced NSF Anti-Virus Allow List capability";
  }

  identity syn-flood-action {
    base anti-ddos-capability;
    description
      "Identity for advanced NSF Anti-DDoS SYN Flood Action
       capability.  This can be used for an extension point for
       Anti-DDoS SYN Flood Action as an advanced NSF.";
    reference
      "RFC 8329: Framework for Interface to Network Security
       Functions - Advanced NSF Anti-DDoS SYN Flood Action
       capability";
  }

  identity udp-flood-action {
    base anti-ddos-capability;
    description
      "Identity for advanced NSF Anti-DDoS UDP Flood Action
       capability.  This can be used for an extension point for
       Anti-DDoS UDP Flood Action as an advanced NSF.";
    reference
      "RFC 8329: Framework for Interface to Network Security
       Functions - Advanced NSF Anti-DDoS UDP Flood Action
       capability";
  }

  identity http-flood-action {
    base anti-ddos-capability;
    description
      "Identity for advanced NSF Anti-DDoS HTTP Flood Action
       capability.  This can be used for an extension point for
       Anti-DDoS HTTP Flood Action as an advanced NSF.";
    reference
      "RFC 8329: Framework for Interface to Network Security
       Functions - Advanced NSF Anti-DDoS HTTP Flood Action
       capability";
  }

  identity https-flood-action {
    base anti-ddos-capability;
    description
      "Identity for advanced NSF Anti-DDoS HTTPS Flood Action
       capability.  This can be used for an extension point for
       Anti-DDoS HTTPS Flood Action as an advanced NSF.";
    reference
      "RFC 8329: Framework for Interface to Network Security
       Functions - Advanced NSF Anti-DDoS HTTPS Flood Action
       capability";
  }

  identity dns-request-flood-action {
    base anti-ddos-capability;
    description
      "Identity for advanced NSF Anti-DDoS DNS Request Flood
       Action capability.  This can be used for an extension
       point for Anti-DDoS DNS Request Flood Action as an
       advanced NSF.";
    reference
      "RFC 8329: Framework for Interface to Network Security
       Functions - Advanced NSF Anti-DDoS DNS Request Flood
       Action capability";
  }

  identity dns-reply-flood-action {
    base anti-ddos-capability;
    description
      "Identity for advanced NSF Anti-DDoS DNS Reply Flood
       Action capability.  This can be used for an extension
       point for Anti-DDoS DNS Reply Flood Action as an
       advanced NSF.";
    reference
      "RFC 8329: Framework for Interface to Network Security
       Functions - Advanced NSF Anti-DDoS DNS Reply Flood
       Action capability";
  }

  identity icmp-flood-action {
    base anti-ddos-capability;
    description
      "Identity for advanced NSF Anti-DDoS ICMP Flood Action
       capability.  This can be used for an extension point
       for Anti-DDoS ICMP Flood Action as an advanced NSF.";
    reference
      "RFC 8329: Framework for Interface to Network Security
       Functions - Advanced NSF Anti-DDoS ICMP Flood Action
       capability";
  }

  identity icmpv6-flood-action {
    base anti-ddos-capability;
    description
      "Identity for advanced NSF Anti-DDoS ICMPv6 Flood Action
       capability.  This can be used for an extension point
       for Anti-DDoS ICMPv6 Flood Action as an advanced NSF.";
    reference
      "RFC 8329: Framework for Interface to Network Security
       Functions - Advanced NSF Anti-DDoS ICMPv6 Flood Action
       capability";
  }

  identity sip-flood-action {
    base anti-ddos-capability;
    description
      "Identity for advanced NSF Anti-DDoS SIP Flood Action
       capability.  This can be used for an extension point
       for Anti-DDoS SIP Flood Action as an advanced NSF.";
    reference
      "RFC 8329: Framework for Interface to Network Security
       Functions - Advanced NSF Anti-DDoS SIP Flood Action
       capability";
  }

  identity detect-mode {
    base anti-ddos-capability;
    description
      "Identity for advanced NSF Anti-DDoS Detection Mode
       capability.  This can be used for an extension point
       for Anti-DDoS Detection Mode as an advanced NSF.";
    reference
      "RFC 8329: Framework for Interface to Network Security
       Functions - Advanced NSF Anti-DDoS Detection Mode
       capability";
  }

  identity baseline-learning {
    base anti-ddos-capability;
    description
      "Identity for advanced NSF Anti-DDoS Baseline Learning
       capability.  This can be used for an extension point
       for Anti-DDoS Baseline Learning as an advanced NSF.";
    reference
      "RFC 8329: Framework for Interface to Network Security
       Functions - Advanced NSF Anti-DDoS Baseline Learning
       capability";
  }

  identity signature-set {
    base ips-capability;
    description
      "Identity for advanced NSF IPS Signature Set capability.
       This can be used for an extension point for IPS Signature
       Set as an advanced NSF.";
    reference
      "RFC 8329: Framework for Interface to Network Security
       Functions - Advanced NSF IPS Signature Set capability";
  }

  identity ips-exception-signature {
    base ips-capability;
    description
      "Identity for advanced NSF IPS Exception Signature
       capability.  This can be used for an extension point for
       IPS Exception Signature as an advanced NSF.";
    reference
      "RFC 8329: Framework for Interface to Network Security
       Functions - Advanced NSF IPS Exception Signature Set
       capability";
  }

  identity voice-id {
    base voip-volte-capability;
    description
      "Identity for advanced NSF VoIP/VoLTE Voice-ID capability.
       This can be used for an extension point for VoIP/VoLTE
       Voice-ID as an advanced NSF.";
    reference
      "RFC 3261: SIP: Session Initiation Protocol
       RFC 8329: Framework for Interface to Network Security
       Functions - Advanced NSF VoIP/VoLTE Security Service
       capability";

  }

  identity user-agent {
    base voip-volte-capability;
    description
      "Identity for advanced NSF VoIP/VoLTE User Agent capability.
       This can be used for an extension point for VoIP/VoLTE
       User Agent as an advanced NSF.";
    reference
      "RFC 3261: SIP: Session Initiation Protocol
       RFC 8329: Framework for Interface to Network Security
       Functions - Advanced NSF VoIP/VoLTE Security Service
       capability";
  }

  identity ipsec-capability {
    description
      "Base identity for an IPsec capability";
    reference
      "draft-ietf-i2nsf-sdn-ipsec-flow-protection-08:
       Software-Defined Networking (SDN)-based IPsec Flow
       Protection - IPsec methods such as IKE and IKE-less";
  }

  identity ike {
    base ipsec-capability;
    description
      "Identity for an IPsec Internet Key Exchange (IKE)
      capability";
    reference
      "draft-ietf-i2nsf-sdn-ipsec-flow-protection-08:
       Software-Defined Networking (SDN)-based IPsec Flow
       Protection - IPsec method with IKE.
       RFC 7296: Internet Key Exchange Protocol Version 2
       (IKEv2) - IKE as a component of IPsec used for
       performing mutual authentication and establishing and
       maintaining Security Associations (SAs).";
  }

  identity ikeless {
    base ipsec-capability;
    description
      "Identity for an IPsec without Internet Key Exchange (IKE)
      capability";
    reference
      "draft-ietf-i2nsf-sdn-ipsec-flow-protection-08:
       Software-Defined Networking (SDN)-based IPsec Flow
       Protection - IPsec method without IKE";
  }

  /*
   *  Grouping
   */

  grouping nsf-capabilities {
    description
      "Network Security Function (NSF) Capabilities";
    reference
      "RFC 8329: Framework for Interface to Network Security
       Functions - I2NSF Flow Security Policy Structure.
       draft-ietf-i2nsf-capability-05: Information Model of
       NSFs Capabilities - Capability Information Model Design.";

    leaf-list time-capabilities {
      type enumeration {
        enum absolute-time {
          description
            "absolute time capabilities.
             If a network security function has the absolute time
             capability, the network security function supports
             rule execution according to absolute time.";
        }
        enum periodic-time {
          description
            "periodic time capabilities.
             If a network security function has the periodic time
             capability, the network security function supports
             rule execution according to periodic time.";
        }
      }
      description
        "Time capabilities";
    }

    container event-capabilities {
      description
        "Capabilities of events.
         If a network security function has the event capabilities,
         the network security function supports rule execution
         according to system event and system alarm.";

      reference
        "RFC 8329: Framework for Interface to Network Security
         Functions - I2NSF Flow Security Policy Structure.
         draft-ietf-i2nsf-capability-05: Information Model of
         NSFs Capabilities - Design Principles and ECA Policy
         Model Overview.
         draft-ietf-i2nsf-nsf-monitoring-data-model-04: I2NSF
         NSF Monitoring YANG Data Model - System Alarm and
         System Events.";

      leaf-list system-event-capability {
        type identityref {
          base system-event-capability;
        }
        description
          "System event capabilities";
      }

      leaf-list system-alarm-capability {
        type identityref {
          base system-alarm-capability;
        }
        description
          "System alarm capabilities";
      }
    }

    container condition-capabilities {
      description
        "Conditions capabilities.";

      container generic-nsf-capabilities {
        description
          "Conditions capabilities.
           If a network security function has the condition
           capabilities, the network security function
           supports rule execution according to conditions of
           IPv4, IPv6, TCP, UDP, ICMP, ICMPv6, and payload.";
        reference
          "RFC 791: Internet Protocol - IPv4.
           RFC 792: Internet Control Message Protocol - ICMP.
           RFC 793: Transmission Control Protocol - TCP.
           RFC 768: User Datagram Protocol - UDP.
           RFC 8200: Internet Protocol, Version 6 (IPv6)
           Specification - IPv6.
           RFC 4443: Internet Control Message Protocol (ICMPv6)
           for the Internet Protocol Version 6 (IPv6) Specification
           - ICMPv6.
           RFC 8329: Framework for Interface to Network Security
           Functions - I2NSF Flow Security Policy Structure.
           draft-ietf-i2nsf-capability-05: Information Model of
           NSFs Capabilities - Design Principles and ECA Policy
           Model Overview.";

        leaf-list ipv4-capability {
          type identityref {
            base ipv4-capability;
          }
          description
            "IPv4 packet capabilities";
          reference
            "RFC 791: Internet Protocol";
        }

        leaf-list icmp-capability {
          type identityref {
            base icmp-capability;
          }
          description
            "ICMP packet capabilities";
          reference
            "RFC 792: Internet Control Message Protocol - ICMP";
        }

        leaf-list ipv6-capability {
          type identityref {
            base ipv6-capability;
          }
          description
            "IPv6 packet capabilities";
          reference
            "RFC 8200: Internet Protocol, Version 6 (IPv6)
             Specification - IPv6";
        }

        leaf-list icmpv6-capability {
          type identityref {
            base icmpv6-capability;
          }
          description
            "ICMPv6 packet capabilities";
          reference
            "RFC 4443: Internet Control Message Protocol (ICMPv6)
             for the Internet Protocol Version 6 (IPv6) Specification
             - ICMPv6";
        }

        leaf-list tcp-capability {
          type identityref {
            base tcp-capability;
          }
          description
            "TCP packet capabilities";
          reference
            "RFC 793: Transmission Control Protocol - TCP";
        }

        leaf-list udp-capability {
          type identityref {
            base udp-capability;
          }
          description
            "UDP packet capabilities";
          reference
            "RFC 768: User Datagram Protocol - UDP";
        }
      }

      container advanced-nsf-capabilities {
        description
          "Advanced Network Security Function (NSF) capabilities,
           such as Anti-Virus, Anti-DDoS, IPS, and VoIP/VoLTE.
           This container contains the leaf-lists of advanced
           NSF capabilities";
        reference
          "RFC 8329: Framework for Interface to Network Security
           Functions - Advanced NSF capabilities";
        leaf-list anti-virus-capability {
          type identityref {
            base anti-virus-capability;
          }
          description
            "Anti-Virus capabilities";
          reference
            "RFC 8329: Framework for Interface to Network Security
             Functions - Advanced NSF Anti-Virus capabilities";
          }

        leaf-list anti-ddos-capability {
          type identityref {
            base anti-ddos-capability;
          }
          description
            "Anti-DDoS Attack capabilities";
          reference
            "RFC 8329: Framework for Interface to Network Security
             Functions - Advanced NSF Anti-DDoS Attack capabilities";
        }

        leaf-list ips-capability {
          type identityref {
            base ips-capability;
          }
          description
            "IPS capabilities";
          reference
            "RFC 8329: Framework for Interface to Network Security
             Functions - Advanced NSF IPS capabilities";
        }

        leaf-list url-capability {
          type identityref {
            base url-capability;
          }
          description
            "URL capabilities";
          reference
            "RFC 8329: Framework for Interface to Network Security
             Functions - Advanced NSF URL capabilities";
        }

        leaf-list voip-volte-capability {
          type identityref {
            base voip-volte-capability;
         }
          description
            "VoIP/VoLTE capabilities";
          reference
            "RFC 8329: Framework for Interface to Network Security
             Functions - Advanced NSF VoIP/VoLTE capabilities";
        }
      }

      leaf-list context-capabilities {
        type identityref {
          base context-capability;
        }
        description
          "Security context capabilities";
      }
    }

    container action-capabilities {
      description
        "Action capabilities.
         If a network security function has the action capabilities,
         the network security function supports the attendant
         actions for policy rules.";

      leaf-list ingress-action-capability {
        type identityref {
          base ingress-action-capability;
        }
        description
          "Ingress-action capabilities";
      }

      leaf-list egress-action-capability {
        type identityref {
          base egress-action-capability;
        }
        description
          "Egress-action capabilities";
      }

      leaf-list log-action-capability {
        type identityref {
          base log-action-capability;
        }
        description
          "Log-action capabilities";
      }
    }
    leaf-list resolution-strategy-capabilities {
      type identityref {
        base resolution-strategy-capability;
      }
      description
        "Resolution strategy capabilities.
         The resolution strategies can be used to specify how
         to resolve conflicts that occur between the actions
         of the same or different policy rules that are matched
         for the same packet and by particular NSF";
      reference
        "draft-ietf-i2nsf-capability-05: Information Model of
         NSFs Capabilities - Resolution strategy capabilities";
    }

    leaf-list default-action-capabilities {
      type identityref {
        base default-action-capability;
      }
      description
        "Default action capabilities.
         A default action is used to execute I2NSF policy rules
         when no rule matches a packet. The default action is
         defined as pass, drop, alert, or mirror.";
      reference
        "RFC 8329: Framework for Interface to Network Security
         Functions - Ingress and egress actions.
         draft-ietf-i2nsf-capability-05: Information Model of
         NSFs Capabilities - Default action capabilities.";
    }

    leaf-list ipsec-method {
      type identityref {
        base ipsec-capability;
      }
      description
        "IPsec method capabilities";
      reference
        "draft-ietf-i2nsf-sdn-ipsec-flow-protection-08:
         Software-Defined Networking (SDN)-based IPsec Flow
         Protection - IPsec methods such as IKE and IKE-less";
    }
  }

  /*
   * Data nodes
   */

  list nsf {
    key "nsf-name";
    description
      "The list of Network Security Functions (NSFs)";
    leaf nsf-name {
      type string;
      mandatory true;
      description
        "The name of Network Security Function (NSF)";
    }
  }
}
