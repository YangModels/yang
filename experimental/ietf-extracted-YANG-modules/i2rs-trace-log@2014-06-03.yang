module i2rs-trace-log {
        yang-version 1;
        namespace "urn:TBD:params:xml:ns:yang:i2rs:trace-log";
        // This namespace should be considered with other I2RS YANG
        // models.
        prefix i2rslog;

        import ietf-yang-types {
                prefix "yang";
        }

        import ietf-inet-types {
                prefix "inet";
        }

        organization "TBD";

        contact
           "Joe Clarke jclarke@cisco.com
           Gonzalo Salgueiro gsalguei@cisco.com
           Carlos Pignataro cpignata@cisco.com";

        description
            "This module defines the model for I2RS traceability
        based on the I2RS architecture as defined in
    draft-ietf-i2rs-architecture.

    Copyright (c) 2014 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).";

        reference
            "draft-ietf-i2rs-architecture: An Architecture for the
        Interface to the Routing System";

        revision "2014-06-03" {
                description "Initial revision";
                reference "TBD";
        }

        typedef log-entry-id {
                type uint64;
                description
                    "A unique identifier for I2RS log entries.";
        }

        typedef timestamp {
                type yang:date-and-time;
                description
                    "Timestamp for I2RS transactions.";
        }

        typedef client-id {
                type yang:uuid;
                description
                    "The I2RS Client identifier used to authenticate
                the Client to the I2RS Agent.";
        }

        typedef actor-id {
                type union {
                        type string {
                                pattern "[^\r\n]+";
                        }
                        type enumeration {
                                enum UNAVAILABLE {
                                        description
                                            "The Actor ID was not
                                        specified by the Client.";
                                }
                        }
                }
                description
                    "Identifier used to trace the northbound actor
                driving the actions of the Client.";
        }

        typedef client-addr {
                type inet:ip-address;
                description
                    "IP address of the client that connected to the
                Agent.";
        }

        typedef operation {
                type string {
                        pattern "[a-zA-Z] [a-zA-Z_\-\(\)]*";
                    }
                description
                    "This is the I2RS operation performed.";
        }

        typedef operation-data {
                type union {
                        type string;
                        type enumeration {
                                enum NULL {
                                        description
                                            "No additional operation
                                        data was required.";
                                }
                        }
                }
                description
                    "Data passed to the Agent to complete the desired
                operation.";
        }

        typedef result-code {
                type string {
                        pattern "[a-zA-Z0-9_\-\(\)]+";
                }
                description
                    "Result code for the operation.";
        }

        container i2rs-trace-log {
                description
                    "This is the model for I2RS traceability.  An
                I2RS log is comprised of the following mandatory
                fields.  Each field MUST be identified by a unique
                log-entry-id.";
                leaf log-enable {
                        type boolean;
                        default "true";
                        description
                            "Enable/Disable I2RS logging.";
                }
                list log-entry {
                        key "log-entry-id";
                        config false;
                        description
                            "Each element in an I2RS trace log is
                        discrete and identified by its unique log
                        entry ID.";
                        leaf log-entry-id {
                                type log-entry-id;
                                config false;
                                description
                                    "This is a unique identifier for
                                each entry in the I2RS trace log.
                                Since multiple operations can occur
                                from the same client at the same
                                time, it is important to have an
                                identifier that can be unambiguously
                                associated to a specific entry.";
                        }
                        leaf timestamp {
                                type timestamp;
                                config false;
                                mandatory true;
                                description
                                    "The specific time, adhering to
                                RFC3339 format, at which the I2RS
                                transaction occurred. Given that
                                many I2RS transactions can occur in
                                rapid succession, the use of
                                fractional seconds MUST be used to
                                provide adequate granularity.";
                                reference
                                    "RFC 3339: Date and Time on the
                                Internet: Timestamps";
                        }
                        leaf client-id {
                                type client-id;
                                config false;
                                mandatory true;
                                description
                                    "The I2RS Client identifier used
                                to authenticate the Client to the
                                I2RS Agent.";
                        }
                        leaf actor-id {
                                type actor-id;
                                config false;
                                mandatory true;
                                description
                                    "This is an opaque identifier
                                 that may be known to the Client
                                 from a northbound controlling
                                 application. This is used to
                                 trace the northbound actor
                                 driving the actions of the
                                 Client. The Client may not
                                 provide this identifier to the
                                 Agent if there is no external
                                 actor driving the Client. In
                                 that case, the special value,
                                 UNAVAILABLE is used to denote no
                                 Actor ID.";
                        }
                        leaf client-addr {
                                type client-addr;
                                config false;
                                mandatory true;
                                description
                                    "This is the IP address of the
                                client that connected to the Agent.";
                        }
                        leaf operation {
                                type operation;
                                config false;
                                mandatory true;
                                description
                                    "This is the I2RS operation
                                performed.";
                        }
                        leaf operation-data {
                                type operation-data;
                                config false;
                                mandatory true;
                                description
                                    "This field comprises the data
                                passed to the Agent to complete the
                                desired operation.  If no additional
                                operation data is required, then this
                                field should be set to the special
                                value, NULL.";
                        }
                        leaf result-code {
                                type result-code;
                                config false;
                                mandatory true;
                                description
                                    "This field holds the result of
                                the operation. In the case of RIB
                                operations, this MUST be the return
                                code as specified in Section 4 of
                                draft-nitinb-i2rs-rib-info-model.
                                The operation may not complete with
                                a result code in the case of a
                                timeout. If the operation fails to
                                complete, it MUST still log the
                                attempted operation with an
                                appropriate result code (e.g., a
                                result code indicating a timeout).";
                                reference
                                "draft-nitinb-i2rs-rib-info-model:
                                Routing Information Base Info Model";
                        }
                }
        }
}
