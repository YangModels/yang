module ietf-nat-sctp {
  yang-version 1.1;
  namespace "urn:ietf:params:xml:ns:yang:ietf-nat-sctp";
  prefix nat-sctp;

  import ietf-nat {
    prefix nat;
    reference
      "RFC 8512: A YANG Module for Network Address Translation
                 (NAT) and Network Prefix Translation (NPT)";
  }

  organization
    "IETF TSVWG Working Group";
  contact
    "WG Web:   <https://datatracker.ietf.org/wg/tsvwg/>
     WG List:  <mailto:tsvwg@ietf.org>

     Author:  Mohamed Boucadair
              <mailto:mohamed.boucadair@orange.com>";
  description
    "This module augments NAT YANG module with Stream Control
     Transmission Protocol (SCTP) specifics. The extension supports
     both a classical SCTP NAT (that is, rewrite port numbers)
     and a, SCTP-specific variant where the ports numbers are
     not altered.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2019-11-18 {
    description
      "Initial revision.";
    reference
      "RFC XXXX: Stream Control Transmission Protocol (SCTP)
                 Network Address Translation Support";
  }

  feature sctp-nat {
    description
      "This feature means that SCTP-specific variant of NAT
       is supported. That is, avoid rewriting port numbers.";
    reference
      "Section 4.3 of RFC XXXX.";
  }

  augment "/nat:nat/nat:instances/nat:instance"
        + "/nat:policy/nat:timers" {
    when "/nat:nat/nat:instances/nat:instance"
       + "/nat:policy/nat:transport-protocols"
       + "/nat:protocol-id = 132";
    description
      "Extends NAT policy with a timeout for SCTP mapping
       entries.";
    leaf sctp-timeout {
      type uint32;
      units "seconds";
      description
        "SCTP inactivity timeout. That is, the time an SCTP
         mapping entry will stay active without packets
         traversing the NAT.";
    }
  }

  augment "/nat:nat/nat:instances/nat:instance"
        + "/nat:mapping-table/nat:mapping-entry" {
    when "nat:transport-protocol = 132";
    if-feature "sctp-nat";
    description
      "Extends the mapping entry with SCTP specifics.";

    leaf int-VTag {
       type uint32;
       description
         "The Internal Verification Tag that the internal
          host has chosen for this communication.";
    }
    leaf rem-VTag {
      type uint32;
      description
         "The Remote Verification Tag that the remote
          peer has chosen for this communication.";
    }
  }
}
