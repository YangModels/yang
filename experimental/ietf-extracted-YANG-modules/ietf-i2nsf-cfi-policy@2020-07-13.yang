module ietf-i2nsf-cfi-policy {
  yang-version 1.1;
  namespace
    "urn:ietf:params:xml:ns:yang:ietf-i2nsf-cfi-policy";
  prefix
    i2nsf-cfi;

  import ietf-inet-types{
    prefix inet;
  }

  import ietf-yang-types{
    prefix yang;
  }

  import ietf-netconf-acm {
    prefix nacm;
  }

  organization
    "IETF I2NSF (Interface to Network Security Functions)
     Working Group";
  contact
    "WG Web: <http://tools.ietf.org/wg/i2nsf>
    WG List: <mailto:i2nsf@ietf.org>

     WG Chair: Linda Dunbar
     <mailto:linda.dunbar@futurewei.com>

     WG Chair: Yoav Nir
     <mailto:ynir.ietf@gmail.com>

     Editor: Jaehoon Paul Jeong
     <mailto:pauljeong@skku.edu>

     Editor: Chaehong Chung
     <mailto:darkhong@skku.edu>";

  description
    "This module is a YANG module for Consumer-Facing Interface.
     Copyright (c) 2020 IETF Trust and the persons
     identified as authors of the code. All rights reserved.
     Redistribution and use in source and binary forms, with or
     without modification, is permitted pursuant to, and subject
     to the license terms contained in, the Simplified BSD License
     set forth in Section 4.c of the IETF Trust's Legal Provisions
     Relating to IETF Documents
     http://trustee.ietf.org/license-info).
     This version of this YANG module is part of RFC XXXX; see
     the RFC itself for full legal notices.";

  revision "2020-07-13"{
    description "The latest revision";
    reference
      "draft-ietf-consumer-facing-interface-dm-08";
  }

  identity malware-file-type {
    description
      "Base identity for malware file types.";
  }

  identity executable-file {
    base malware-file-type;
    description
      "Identity for executable file types.";
  }

  identity doc-file {
    base malware-file-type;
    description
      "Identity for Microsoft document file types.";
  }

  identity html-app-file {
    base malware-file-type;
    description
      "Identity for html application file types.";
  }

  identity javascript-file {
    base malware-file-type;
    description
      "Identity for Javascript file types.";
  }

  identity pdf-file {
    base malware-file-type;
    description
      "Identity for pdf file types.";
  }

  identity dll-file {
    base malware-file-type;
    description
      "Identity for dll file types.";
  }

  identity msi-file {
    base malware-file-type;
    description
      "Identity for Microsoft installer file types.";
  }

  identity security-event-type {
    description
      "Base identity for security event types.";
  }

  identity ddos {
    base security-event-type;
    description
      "Identity for DDoS event types.";
  }

  identity spyware {
    base security-event-type;
    description
      "Identity for spyware event types.";
  }

  identity trojan {
    base security-event-type;
    description
      "Identity for Trojan infection event types.";
  }

  identity ransomware {
    base security-event-type;
    description
      "Identity for ransomware infection event types.";
  }

  identity i2nsf-ipsec {
    description
      "Base identity for IPsec method types.";
    reference
      "draft-ietf-i2nsf-sdn-ipsec-flow-protection-07";
  }

  identity ipsec-ike {
    base i2nsf-ipsec;
    description
      "Identity for ipsec-ike.";
    reference
      "draft-ietf-i2nsf-sdn-ipsec-flow-protection-07";
  }

  identity ipsec-ikeless {
    base i2nsf-ipsec;
    description
      "Identity for ipsec-ikeless.";
    reference
      "draft-ietf-i2nsf-sdn-ipsec-flow-protection-07";
  }

  identity continent {
    description
      "Base Identity for continent types.";
  }

  identity africa {
    base continent;
    description
      "Identity for africa.";
  }
  identity asia {
    base continent;
    description
      "Identity for asia.";
  }

  identity europe {
    base continent;
    description
      "Identity for europe.";
  }

  identity north-america {
    base continent;
    description
      "Identity for north-america.";
  }

  identity south-america {
    base continent;
    description
      "Identity for south-america.";
  }

  identity oceania {
    base continent;
    description
      "Identity for Oceania";
  }

  identity protocol-type {
    description
      "This identity represents the protocol types.";
  }

  identity ftp {
    base protocol-type;
    description
      "The identity for ftp protocol.";
    reference
      "RFC 959: File Transfer Protocol (FTP)";
  }

  identity ssh {
    base protocol-type;
    description
      "The identity for ssh protocol.";
    reference
      "RFC 4250: The Secure Shell (SSH) Protocol";
  }

  identity telnet {
    base protocol-type;
    description
      "The identity for telnet.";
    reference
      "RFC 854: Telnet Protocol";
  }

  identity smtp {
    base protocol-type;
    description
      "The identity for smtp.";
    reference
      "RFC 5321: Simple Mail Transfer Protocol (SMTP)";
  }

  identity sftp {
    base protocol-type;
    description
      "The identity for sftp.";
    reference
      "RFC 913: Simple File Transfer Protocol (SFTP)";
  }

  identity http {
    base protocol-type;
    description
      "The identity for http.";
    reference
      "RFC 2616: Hypertext Transfer Protocol (HTTP)";
  }

  identity https {
    base protocol-type;
    description
      "The identity for https.";
    reference
      "RFC 2818: HTTP over TLS (HTTPS)";
  }

  identity pop3 {
    base protocol-type;
    description
      "The identity for pop3.";
    reference
      "RFC 1081: Post Office Protocol -Version 3 (POP3)";
  }

  identity nat {
    base protocol-type;
    description
      "The identity for nat.";
    reference
      "RFC 1631: The IP Network Address Translator (NAT)";
  }

  identity primary-action {
    description
      "This identity represents the primary actions, such as
       PASS, DROP, ALERT, RATE-LIMIT, and MIRROR.";
  }

  identity pass {
    base primary-action;
    description
      "The identity for pass.";
  }

  identity drop {
    base primary-action;
    description
      "The identity for drop.";
  }

  identity alert {
    base primary-action;
    description
      "The identity for alert.";
  }

  identity rate-limit {
    base primary-action;
    description
      "The identity for rate-limit.";
  }

  identity mirror {
    base primary-action;
    description
      "The identity for mirroring.";
  }

  identity secondary-action {
    description
      "This field identifies additional actions if a rule is
       matched. This could be one of 'LOG', 'SYSLOG',
       'SESSION-LOG', etc.";
  }

  identity log {
    base secondary-action;
    description
      "The identity for logging.";
  }

  identity syslog {
    base secondary-action;
    description
      "The identity for system logging.";
  }

  identity session-log {
    base secondary-action;
    description
      "The identity for session logging.";
  }

  identity signature-type {
    description
      "This represents the base identity for signature types.";
  }

  identity signature-yara {
    base signature-type;
    description
      "This represents the YARA signatures.";
  }

  identity signature-snort {
    base signature-type;
    description
      "This represents the SNORT signatures.";
  }

  identity signature-suricata {
    base signature-type;
    description
      "This represents the SURICATA signatures.";
  }

  identity threat-feed-type {
    description
      "This represents the base identity for threat-feed.";
  }

  identity day {
    description
      "This represents the base for days.";
  }

  identity monday {
    base day;
    description
      "This represents monday.";
  }

  identity tuesday {
    base day;
    description
      "This represents tuesday.";
  }

  identity wednesday {
    base day;
    description
      "This represents wednesday.";
  }

  identity thursday {
    base day;
    description
      "This represents thursday.";
  }

  identity friday {
    base day;
    description
      "This represents friday.";
  }

  identity saturday {
    base day;
    description
      "This represents saturday.";
  }

  identity sunday {
    base day;
    description
      "This represents sunday.";
  }

  /*
  * Typedefs
  */
  typedef time{
    type string {
      pattern '\d{2}:\d{2}:\d{2}(\.\d+)?'
        + '(Z|[\+\-]\d{2}:\d{2})';
    }
    description
      "This is the format of time.";
  }

  /*
  * Groupings
  */

  grouping ipv4-list {
    description
      "Grouping for ipv4 based ip-addresses.";
    leaf-list ipv4 {
      type inet:ipv4-address;
      description
        "This is the entry for the ipv4 ip-addresses.";
    }
  }

  grouping ipv6-list {
    description
      "Grouping for ipv6 based ip-addresses.";
    leaf-list ipv6 {
      type inet:ipv6-address;
      description
        "This is the entry for the ipv6 ip-addresses.";
    }
  }

  grouping ipv4 {
    description
      "Grouping for ipv4 based ip-address.";
    leaf ipv4 {
      type inet:ipv4-address;
      description
        "This is the entry for the ipv4 ip-address.";
    }
  }

  grouping ipv6 {
    description
      "Grouping for ipv6 based ip-address.";
    leaf ipv6 {
      type inet:ipv6-address;
      description
        "This is the entry for the ipv6 ip-address.";
    }
  }

  grouping ip-address-info {
    description
      "There are two types to configure a security policy
      for IPv4 address, such as exact match and range match.";
    choice match-type {
      description
        "User can choose between 'exact match' and 'range match'.";
      case exact-match-ipv4 {
        uses ipv4;
        description
          "Exact ip-address match for ipv4 type addresses";
      }
      case exact-match-ipv6 {
        uses ipv6;
        description
          "Exact ip-address match for ipv6 type addresses";
      }
      case range-match-ipv4 {
        container range-ipv4-address {
          leaf start-ipv4-address {
            type inet:ipv4-address;
            description
              "Start IPv4 address for a range match.";
          }
          leaf end-ipv4-address {
            type inet:ipv4-address;
            description
              "End IPv4 address for a range match.";
          }
          description
            "Range match for an IP-address.";
        }
      }
      case range-match-ipv6 {
        container range-ipv6-address {
          leaf start-ipv6-address {
            type inet:ipv6-address;
            description
              "Start IPv6 address for a range match.";
          }
          leaf end-ipv6-address {
            type inet:ipv6-address;
            description
              "End IPv6 address for a range match.";
          }
          description
            "Range match for an IP-address.";
        }
      }
    }
  }

  grouping ipsec-based-method {
    description
      "This represents the ipsec-based method.";
    list ipsec-method {
      key "method";
      description
        "This represents the list of IPsec method types.";
      leaf method {
        type identityref {
          base i2nsf-ipsec;
        }
        description
          "This represents IPsec IKE and IPsec IKEless cases.
          If this is not set, it cannot support IPsec IKE or
          IPsec IKEless.";
        reference
          "draft-ietf-i2nsf-sdn-ipsec-flow-protection-07";
      }
    }
  }

  grouping user-group {
    description
      "The grouping for user-group entities, and contains
      information such as name & ip-address.";
    leaf name {
      type string;
      description
        "This represents the name of a user-group.
        A user-group name is used to map a user-group's
        name (e.g., employees) to an ip address.
        It is implementation dependent";
    }
    uses ip-address-info{
      refine match-type{
        mandatory true;
      }
      description
        "This represent the IP address of a user-group.";
    }
  }

  grouping device-group {
    description
      "This group represents device group information
      such as ip-address protocol.";
    leaf name {
      type string;
      description
      "This represents the name of a device-group.";
    }
    uses ip-address-info{
      refine match-type{
        mandatory true;
      }
    }
    leaf-list protocol {
      type identityref {
        base protocol-type;
      }
      description
        "This represents the communication protocols of
        devices.
        If this is not set, it cannot support the
        appropriate protocol";
    }
  }

  grouping location-group {
    description
      "This group represents location-group information
      such as geo-ip and continent.";
    leaf name {
      type string;
      description
        "This represents the name of a location.";
    }
    list geo-ip-ipv4 {
      key "ipv4-address";
      description
        "This represents the list of IPv4 address based on
        a location.";
      leaf ipv4-address{
        type inet:ipv4-address;
        description
          "This represents an IPv4 geo-ip of a location.";
      }
      leaf ipv4-prefix{
        type inet:ipv4-prefix;
        description
          "This represents the prefix for the IPv4-address.";
      }
    }
    list geo-ip-ipv6 {
      key "ipv6-address";
      description
        "This represents the list of IPv6 address based on
        a location.";
      leaf ipv6-address{
        type inet:ipv6-address;
        description
          "This represents an IPv6 geo-ip of a location.";
      }
      leaf ipv6-prefix{
        type inet:ipv6-prefix;
        description
          "This represents the prefix for the IPv6-address.";
      }
    }
    leaf continent {
      type identityref {
        base continent;
      }
      default asia;
      description
        "location-group-based on geo-ip of
        respective continent.";
    }
  }

  grouping threat-feed-info {
    description
      "This is the grouping for the threat-feed-list";
    leaf threat-type {
      type identityref {
        base threat-feed-type;
      }
      description
        "This represents the type of the threat-feed.";
    }
    leaf server-ipv4 {
      type inet:ipv4-address;
      description
        "The IPv4 ip-address for the threat-feed server.";
    }
    leaf server-ipv6 {
      type inet:ipv6-address;
      description
        "The IPv6 ip-address for the threat-feed server.";
    }
    leaf description {
      type string;
      description
        "This represents the descriptions of a threat-feed.
        The description should include information, such as
        the type, related threat, method, and file type.
        Structured Threat Information Expression (STIX) can
        be used for description of a threat [STIX].";
    }
  }

  grouping payload-string {
    description
      "The grouping for payload-string content.
      It contains information such as name and string
      content.";
    leaf description {
      type string;
      description
        "This represents the description of a payload.
        If this is not set, it cannot support the
        description of how the payload content is
        related to a security attack.";
    }
    leaf-list content {
      type string;
      description
        "This represents the string of the payload
        contents. This content leaf-list contains the
        payload of a packet to analyze a threat.
        Due to the types of threats, the type of the
        content is defined as string to accommodate
        any kind of a payload type such as HTTP, HTTPS,
        and SIP.
        If this is not set, it cannot support the
        payload contents involved in a security attack
        as strings";
    }
  }

  list i2nsf-cfi-policy {
    key "policy-name";
    description
      "This is the security policy list. Each policy in
      the list contains a list of security rules, and is
      a policy instance to have complete information
      such as where and when a policy needs to be
      applied.";
    leaf policy-name {
      type string;
      description
        "The name which identifies the policy.";    }
    container rules{
      description
        "This container is for rules.";
      nacm:default-deny-write;
      list rule {
        key "rule-name";
        ordered-by user;
        leaf rule-name {
          type string;
          description
            "This represents the name for the rule.";
        }
        description
          "There can be a single or multiple number of
          rules.";

        container event {
          description
            "This represents the event (e.g., a security
            event, for which a security rule is made.)";
          leaf security-event {
            type identityref {
              base security-event-type;
            }
            description
              "This contains the description of security
              events. If this is not set, it cannot
              support which security event is enforced";
          }

          container time-information {
            description
              "The time information when the security
              rule should be applied.";
            leaf start-date-time {
              type yang:date-and-time;
              description
                "This is the start date and time
                for policy.";
            }
            leaf end-date-time {
              type yang:date-and-time;
              description
                "This is the end date and time
                for policy. The policy will stop
                working after the specified
                end-date-time";
            }
            container period{
              when
                "/i2nsf-cfi-policy/rules/rule/event/frequency!='only-once'";
              description
                "This represents the repetition time.
                In case of frequency is weekly, the days
                can be set.";
              leaf start-time {
                type time;
                description
                  "This is period start time for event.";
              }
              leaf end-time {
                type time;
                description
                  "This is period end time for event.";
              }
              leaf-list day {
                when
                  "/i2nsf-cfi-policy/rules/rule/event/frequency='weekly'";
                type identityref{
                  base day;
                }
                description
                  "This represents the repeated day of
                  every week (e.g., monday and tuesday).
                  More than one day can be specified";
              }
              leaf-list date {
                when
                  "/i2nsf-cfi-policy/rules/rule/event/frequency='monthly'";
                type int32{
                  range "1..31";
                }
                description
                  "This represents the repeated date of
                  every month. More than one date can be
                  specified.";
              }
              leaf-list month {
                when
                  "/i2nsf-cfi-policy/rules/rule/event/frequency='yearly'";
                type string{
                  pattern '\d{2}-\d{2}';
                }
                description
                  "This represents the repeated date and month
                  of every year. More than one can be specified.
                  Pattern used is Month-Date (MM-DD).";
              }
            }
          }

          leaf frequency {
            type enumeration {
              enum only-once {
                description
                  "This represents the rule is enforced
                  only once immediately and not repeated.
                  The policy will continuously active from
                  start time and terminated at end-time.";
              }
              enum daily {
                description
                  "This represents the rule is enforced
                  on a daily basis. The policy will be
                  repeated daily until the end-date.";
              }
              enum weekly {
                description
                  "This represents the rule is enforced
                  on a weekly basis. The policy will be
                  repeated weekly until the end-date. The
                  repeated days can be specified.";
              }
              enum monthly {
                description
                  "This represents the rule is enforced
                  on a monthly basis. The policy will be
                  repeated monthly until the end-date.";
              }
              enum yearly {
                description
                  "This represents the rule is enforced
                  on a yearly basis. The policy will be
                  repeated yearly until the end-date.";
              }
            }
            default only-once;
            description
              "This represents how frequent the rule
              should be enforced.";
          }
        }

        container condition {
          description
          "The conditions for general security policies.";
          container firewall-condition {
            description
              "The general firewall condition.";
            leaf source {
              type leafref {
                path
                  "/i2nsf-cfi-policy/endpoint-groups/user-group/name";
              }
              description
              "This describes the paths to the source reference.";
            }

            leaf-list destination {
              type leafref {
                path
                  "/i2nsf-cfi-policy/endpoint-groups/user-group/name";
              }
              description
                "This describes the paths to the destination
                target reference.";
            }
          }

          container ddos-condition {
            description
              "The condition for DDoS mitigation.";
            leaf-list source {
              type leafref {
                path
                  "/i2nsf-cfi-policy/endpoint-groups/device-group/name";
              }
              description
                "This describes the path to the
                source target references.";
            }
            leaf-list destination {
              type leafref {
                path
                  "/i2nsf-cfi-policy/endpoint-groups/device-group/name";
              }
              description
                "This describes the path to the destination target
                references.";
            }
            container rate-limit {
              description
                "This describes the rate-limit.";
              leaf packet-threshold-per-second {
                type uint32;
                description
                  "This is a trigger value for the condition.";
              }
            }
          }

          container location-condition {
            description
              "The condition for location based connection";
            leaf-list source {
              type leafref {
                path
                  "/i2nsf-cfi-policy/endpoint-groups/location-group/name";
              }
              description
                "This describes the path to the location
                source reference.";
            }
            leaf-list destination {
              type leafref {
                path
                  "/i2nsf-cfi-policy/endpoint-groups/location-group/name";
              }
              description
                "This describes the path to the location
                destination reference.";
            }
          }
          container custom-condition {
            description
              "The condition based on packet contents.";
            leaf-list source {
              type leafref {
               path
                "/i2nsf-cfi-policy/threat-preventions/payload-content/name";
              }
              description
                "Describes the payload string content condition
                source.";
            }
            leaf destination {
              type leafref {
               path
               "/i2nsf-cfi-policy/threat-preventions/payload-content/name";
              }
              description
                "Describes the payload string content condition
                destination.";
            }
          }

          container threat-feed-condition {
            description
              "The condition based on the threat-feed information.";
            leaf-list source {
              type leafref {
               path
               "/i2nsf-cfi-policy/threat-preventions/threat-feed-list/name";
              }
              description
                "Describes the threat-feed condition source.";
            }
            leaf destination {
              type leafref {
               path
               "/i2nsf-cfi-policy/threat-preventions/threat-feed-list/name";
              }
              description
                "Describes the threat-feed condition destination.";
            }
          }
        }

        container actions {
          description
            "This is the action container.";
          leaf primary-action {
            type identityref {
              base primary-action;
            }
            description
              "This represent the primary actions (e.g.,
              PASS, DROP, ALERT, and MIRROR) to be
              applied a condition.
              If this is not set, it cannot support
              the primary actions.";
          }
          leaf secondary-action {
            type identityref {
              base secondary-action;
            }
            description
              "This represents the secondary actions
              (e.g., log and syslog) to be applied
              if needed.
              If this is not set, it cannot support
              the secondary actions.";
          }
        }

        container ipsec-method {
          description
            "This container represents the IPsec IKE
            and IKEless cases.";
          leaf method {
            type identityref {
              base i2nsf-ipsec;
            }
            description
              "This references the IPsec method types,
              which includes IPsec IKE and IPsec IKEless
              cases.
              If this is not set, it cannot support
              IPsec IKE or IPsec IKEless.";
            reference
              "draft-ietf-i2nsf-sdn-ipsec-flow-protection-07";
          }
        }
      }
    }
    container endpoint-groups {
      description
        "A logical entity in their business
        environment, where a security policy
        is to be applied.";
      list user-group{
        uses user-group;
        key "name";
        description
          "This represents the user group.";
      }
      list device-group {
        key "name";
        uses device-group;
        description
          "This represents the device group.";
      }
      list location-group{
        key "name";
        uses location-group;
        description
          "This represents the location group.";
      }
    }

    container threat-preventions {
      description
        "this describes the list of threat-prevention.";
      list threat-feed-list {
        key "name";
        description
          "There can be a single or multiple number of
          threat-feeds.";
        leaf name {
          type string;
          description
            "This represents the name of the threat-feed.";
        }
        uses threat-feed-info;
        leaf-list threat-file-types {
          type identityref {
            base malware-file-type;
          }
          default executable-file;
          description
            "This contains a list of file types needed to
            be scanned for the virus.";
        }
        leaf-list signatures {
          type identityref {
            base signature-type;
          }
          default signature-suricata;
          description
            "This contains a list of signatures or hashes
            of the threats.";
        }
      }
      list payload-content {
        key "name";
        leaf name {
          type string;
          description
            "This represents the name of payload-content.
            It should give an idea of why specific payload
            content is marked as threat. For example, the
            name 'backdoor' indicates the payload content
            is related to backdoor attack.";
        }
        description
          "This represents the payload-string group.";
        uses payload-string;
      }
    }
  }
}
