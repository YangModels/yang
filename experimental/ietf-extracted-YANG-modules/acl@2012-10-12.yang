module acl {
    namespace "urn:cisco:params:xml:ns:yang:acl";
    // replace with IANA namespace when assigned
    prefix acl;

    import ietf-inet-types {
        prefix "inet";
    }

    import ietf-yang-types {
        prefix "yang";
    }

    organization
       "IETF NETMOD (NETCONF Data Modeling Language) Working Group";

    contact
         "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com

        Editor: Alexander Clemm
        alex@cisco.com

        Editor: Andy Bierman
        andy@yumaworks.com";

    description
        "This YANG module defines a component that describing the
        configuration of Access Control Lists (ACLs).

        An ACL is an ordered set of rules and actions used to filter
        traffic.  Each set of rules and actions is represented
        as an Access Control Entries (ACE). Each ACE is evaluated
        sequentially. When the rule matches then action for that
        rule is applied to the packet.

        There are three types of ACL.

        IP ACLs - IP ACLs are ordered sets of rules that can use to
            filter traffic based on IP information in the Layer 3
            header of packets.
            The device applies IP ACLs only to IP traffic. IP ACL
            can be IPv4 or IPv6.
        MAC ACLs - MAC ACLs are used to filter traffic using the
            information in the Layer 2 header of each packet.
            MAC ACLs are by default only applied to non-IP
            traffic; however, Layer 2 interfaces can be configured
            to apply MAC ACLs to all traffic.
        ARP ACLs - The device applies ARP ACLs to IP traffic.

        This module should be used with acl-ip, acl-arp, or acl-mac
        depends on what feature the device supports.

        This YANG module also includes auxiliary definitions that
        are needed in conjunction with configuration of ACLs, such as
        reusable containers and references for ports and IP.

        Terms and Acronyms
         ACE (ace): Access Control Entry

         ACL (acl): Access Control List

         AFI (afi): Authority and Format Identifier (Address
             Field Identifier)

         ARP (arp): Address Resolution Protocol

         IP (ip): Internet Protocol

         IPv4 (ipv4):Internet Protocol Version 4

         IPv6 (ipv6): Internet Protocol Version 6

         MAC: Media Access Control

         TCP (tcp): Transmission Control Protocol

         TTL (ttl): Time to Live

         VLAN (vlan): Virtual Local Area Network
       ";
    reference
        "Access List Commands on Cisco IOS XR Software,
        Cisco Nexus 7000 Series NX-OS Security Configuration Guide,
        Catalyst 6500 Release 12.2SX Software Configuration Guide,
        ACL TCP Flags Filtering";

    revision 2012-10-12 {
        description "Initial revision. ";
    }

    /* Features */

    feature capture-session-id {
        if-feature packet-capture;
        description
            "The ability to configure ACL capture in order to
            selectively monitor traffic on an interface or VLAN.
            When the capture option for an ACL rule
            is enabled, packets that match this rule are
            either forwarded or dropped based on the specified permit
            or deny action and may also be copied to an alternate
            destination port for further analysis.
            An ACL rule with the capture option can be applied
            as follows:
                On a VLAN
                In the ingress direction on all interfaces
                In the egress direction on all Layer 3 interfaces
            The statistics data for the capture-session are capture
            in the device where the ACL rule applied to.";
    }

    feature host-by-name {
        description
            "The capability to reference a host by DNS name.";
    }

    feature ip-address-groups {
        description
            "The ability to define named groups for lists of
            ip addresses. ";
    }

    feature logging {
        description
            "The ability to log messages upon the matching of ACLs.";
    }

    feature match-counter {
        description
            "The ability to maintain global or local match statistics
            for each ACL rules.";
    }

    feature packet-capture {
        description "The ability to capture packets that
          match the filter.";
    }

    feature packet-length {
        description "The ability to filter packets by packet length";
    }

    feature port-groups {
        description
            "The ability to define named groups for lists of ports. ";
    }

    /* Identities */

    identity acl-type {
        description "Base acl type for all ACL type identifiers.";
    }

    /* Types */

    typedef acl-comparator {
        description "A data type used to express comparator string";
        type enumeration {
            enum "eq" {
                value 0;
                description "match only equal to any giving number.";
            }
            enum "gt" {
                value 1;
                description
                    "match only greater than any giving number.";
            }
            enum "lt" {
                value 2;
                description
                    "match only lower than any giving number.";
            }
            enum "neq" {
                value 3;
                description
                    "match only not equal to any giving number";
            }
        }
    }

    typedef acl-action {
        description "An enumeration data type to express acl
            action when match.";
        type enumeration {
            enum deny {
                description "Apply deny action to the traffic";
            }
            enum permit {
                description "Apply permit action to the traffic";
            }

        }

    }

    typedef acl-remark {
        type string {
            length "0..100";
        }
        description
          "A remark is a comment that can be
           associated with an ACE in order to make
           the access list easier for the network
           administrator to understand.
           It is retained to facilitate
           co-existence with CLI.";
    }

    typedef acl-type-ref {
        description
            "This type is used to refer to an Access Control List
            (ACL) type";
        type identityref {
            base "acl-type";
        }
    }

    typedef acl-ref {
        description "This type refers to an ACL.";
        type leafref {
            path  "/acl:acls/acl:acl/acl:name";
        }
    }

    typedef port-group-ref {
        description
            "This type is used to refer to a Portgroup object.";
        type leafref {
            path "/acls/port-groups/port-group/name";
        }

    }

    typedef ip-address-group-ref {
        description
            "This type is used to refer to a time range object.";
        type leafref {
            path "/acls/ip-address-groups/ip-address-group/name";
        }
    }

    typedef time-range-ref {
        description
            "This type is used to refer to a time range object.";
        type leafref {
            path "/acls/timerange-groups/timerange-group/name";
        }

    }

    typedef weekdays {
      type bits {
        bit Sunday {
          position 0;
        }
        bit Monday {
          position 1;
        }
        bit Tuesday {
          position 2;
        }
        bit Wednesday {
          position 3;
        }
        bit Thursday {
          position 4;
        }
        bit Friday {
          position 5;
        }
        bit Saturday {
          position 6;
        }
      }
    }

    typedef acl-name-string {
      type string {
        length "1 .. 64";
      }
    }

    /* Groupings */

    grouping ACE-COMMON {
        description
          "A collection of nodes that should be added to
           every ACE list entry";

        container actions {
          leaf action {
            type acl:acl-action;
            mandatory true;
            description "Permit/deny action.";
          }

          leaf log {
           if-feature acl:logging;
           type empty;
           description
             "Causes an informational logging message about the
              packet that matches the entry to be sent to the
              console.";
          }
        }

        leaf match {
          if-feature acl:match-counter;
          config false;
          type yang:counter64;
          description
            "The total packet that have matched for the
             particular ACE";
        }
    }

    grouping FILTER-COMMON {
        description
          "A collection of nodes that should be added to
           every 'filters' container within each
           ACE list entry";

        leaf enable-capture {
            if-feature acl:packet-capture;
            type boolean;
            description
              "Enable packet capture on this filter
               for this session.";
        }

        leaf capture-session-id {
            if-feature acl:capture-session-id;
            when "../enable-capture = 'true'";
            type uint32 {
                range "1..48";
            }
            description
                "Enable packet capture on this filter
                for this session id.";
        }
    }

    /* Data Nodes */

    container acls {
        description
            "This is the top container that contains a list of
            named ACL and reusable acl object groups.";
        list acl {
            key name;
            leaf name {
                description "ACL/access group name.";
                type acl-name-string;
            }

            leaf acl-type {
                type acl-type-ref;
                description "Type of ACL";
                mandatory true;
            }
            leaf enable-capture-global {
                if-feature packet-capture;
                type boolean;
                description "Enable packet capture on this filter
                    for this session. Session ID range is 1 to 48";
                default "false";
            }
            leaf capture-session-id-global {
                if-feature capture-session-id;
                when "../enable-capture-global = 'true'";
                type uint32 {
                    range "1..48";
                }
                description "Enable packet capture on this filter
                    for this session. Session ID range is 1 to 48";
            }
            choice enable-match-counter-choices {
                if-feature match-counter;
                case match {
                    leaf enable-match-counter {
                        type boolean;
                        description
                            "Enable to collect statistics for the ACL";
                        default false;
                    }
                }
                case per-entry-match {
                    leaf enable-per-entry-match-counter {
                        type boolean;
                        description "Enable to collect match
                            statistics for each ACL entry(ACE).";
                        default false;
                    }
                }
            }

            leaf match {
                if-feature match-counter;
                config false;
                type yang:counter64;
                description
                    "The total packet that have matched for the
                    particular access list";
            }

        }

        container port-groups {
            if-feature port-groups;
            list port-group {
                key "name";
                leaf name {
                    type acl-name-string;
                }
                list port-group-entry {
                   key "name";
                   ordered-by user;
                   leaf name {
                     type acl-name-string;
                    }
                    //unique "comparator port-number
                    //port-lower port-upper";

                    choice port-number-or-range {
                      case port-number-range {
                        description
                         "Port group includes all ports between
                         port-lowerand port-upper (including those)";
                        leaf port-lower {
                          type inet:port-number;
                          description "Lower Port number.";
                          mandatory true;
                        }
                        leaf port-upper {
                          type inet:port-number;
                          description "Upper Port number.";
                          mandatory true;
                          must "../port-lower <= ../port-upper";
                        }
                      }
                      case port-number {
                       description
                        "Port group includes all ports that are greater
                         than, greater or equal, less than, less or
                         equal, or not equal the port, per the
                         indicated comparator.
                         It is possible for the port group to be empty
                         (for example, in case a port group that
                         is less than the minimum port number is
                         specified).";
                       leaf comparator {
                         type acl-comparator;
                         mandatory true;
                       }
                       leaf port {
                         type inet:port-number;
                         description "Port number.";
                         mandatory true;
                       }
                     }
                   } // choice port-number-or-range
                 }  // list port-group-entry
            }  // list port-group
        }  // container port-groups

        container timerange-groups {
            description "Define time range entries to restrict
                the access. The time range is identified by a name
                and then referenced by a function, so that those
                time restrictions are imposed on the function itself.";
            list timerange-group {
                key "name";
                leaf name {
                    type acl-name-string;
                }
                list time-range {
                  key "name";
                  ordered-by user;
                  leaf name {
                    type acl-name-string;
                  }

                  leaf remark {
                    type acl-remark;
                  }

                  choice range-type {
                    // abosolute or periodic time range
                    container absolute {
                    description
                      "Absolute time and date that
                       the associated function starts
                       going into effect.";
                    leaf start {
                      type yang:date-and-time;
                      description
                        "Absolute start time and date";
                    }
                    leaf end {
                      type yang:date-and-time;
                      description "Absolute end time and date";
                    }
                  }
                  container periodic {
                    description
                      "To specify a periodic time and date.";
                    leaf weekdays {
                      type weekdays;
                    }
                    leaf start {
                      type yang:timestamp;
                      description "Start time";
                    }
                    leaf end {
                      type yang:timestamp;
                      description "End time";
                    }
                  }
                } // choice range-type
              } // list time-range
            } // list timerange-group
        }  // container timerange-groups

        container ip-address-groups {
            if-feature ip-address-groups;
            description
                "This contains a list of named ip address group. Each
                group defines a range of address and mask pair.";
            list ip-address-group {
                key "name";
                leaf name {
                    type acl-name-string;
                }
                leaf afi {
                    default "ipv4";
                    type inet:ip-version;
                    description "Address Field Identifier (AFI).";
                }
                list ip-address {
                  key "name";
                  ordered-by user;
                  leaf name {
                    type acl-name-string;
                  }
                  //unique "ip-address ip-mask";
                  //unique "ip-host-address";

                  grouping IP-HOST {
                    description
                      "Choice within a case not allowed so need
                       this grouping.";
                    choice address-or-name {
                      mandatory true;
                      leaf ip-host-address {
                        type inet:ip-address;
                      }
                      leaf ip-host-name {
                        if-feature acl:host-by-name;
                        type inet:domain-name;
                      }
                    }
                  }

                  choice ip-network-kind {
                    mandatory true;

                    case ip {
                      leaf ip-address {
                        type inet:ip-address;
                      }
                      leaf ip-mask {
                        type inet:ip-prefix;
                         mandatory true;
                      }
                    }
                    leaf ip-any {
                      type empty;
                      description "To express Any network or address.
                        Use the any keyword as an abbreviation
                        for an address and a mask of 0.0.0.0
                        255.255.255.255. For example:
                        0.0.0.0/255.255.255.255 means 'any'";
                    }
                    case host {
                      description
                        "Use the host address combination as an
                         abbreviation for an address and wildcard
                         of address 0.0.0.0";

                      uses IP-HOST;
                    }
                    // case group not allowed here!
                  }

                }  // list ip-address
            }  // list ip-address-group
        } // container ip-address-groups
    } // container acls

}
