module ietf-semver-extension {
  yang-version 1.1;
  namespace "urn:ietf:params:xml:ns:yang:ietf-semver-extension";
  prefix semver-ext;

  organization
    "IETF NETMOD (Network Modeling) Working Group";
  contact
    "WG Web:   <https://datatracker.ietf.org/wg/netmod/>
     WG List:  <mailto:netmod@ietf.org>

     Author:   Benoit Claise
               <mailto:bclaise@cisco.com>

     Author:   Joe Clarke
               <mailto:jclarke@cisco.com>

     Author:   Kevin D'Souza
               <mailto:kd6913@att.com>";
  description
    "This module contains a defintion for a YANG 1.1 extension to
     express the semantic version of YANG modules.";

  revision 2017-11-10 {
    description
      "Initial revision.";
    reference "draft-clacla-netmod-yang-model-update: New YANG Module Update Procedure";
  }

  extension module-version {
    argument semver;
    description
      "The version number for the module. This is
       expressed as a semantic version number of the form:
        x.y.z
       where:
        * x corresponds to the major version,
        * y corresponds to a minor version,
        * z corresponds to a patch version.
       This version corresponds to the model file within which it is
       defined.

       A major version number of 0 indicates that this model is still
       in development, and is potentially subject to change.

       Following a release of major version 1, all modules will
       increment major revision number where backwards incompatible
       changes to the model are made.

       The minor version is changed when features are added to the
       model that do not impact current clients use of the model.

       The patch-level version is incremented when non-feature changes
       (such as bugfixes or clarifications to human-readable
       descriptions that do not impact model functionality) are made
       that maintain backwards compatibility.

       The version number is stored in the module meta-data.

       By comparing the module-version between two revisions of a given
       module, one can know if revision N+1 is backwards compatible or
       not relative to revision N, as well as whether or not new features
       have been added to revision N+1.";
    reference "http://semver.org/ : Semantic Versioning 2.0.0";
  }
}
