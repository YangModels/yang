submodule ietf-netconf-tls {

  belongs-to ietf-netconf-config {
    prefix ncconf;
  }

  import ietf-yang-types {
    prefix yang;
  }
  import ietf-inet-types {
    prefix inet;
  }
  import ietf-netconf-acm {
    prefix nacm;
  }
  import ietf-x509-cert-to-name {
    prefix x509c2n;
  }

  include ietf-netconf-common;

  organization
   "IETF NETCONF (Network Configuration) Working Group";

  contact
   "WG Web:   <http://tools.ietf.org/wg/netconf/>
    WG List:  <mailto:netconf@ietf.org>

    WG Chair: Mehmet Ersue
              <mailto:mehmet.ersue@nsn.com>

    WG Chair: Bert Wijnen
              <mailto:bertietf@bwijnen.net>

    Editor:   Mohamad Badra
              <mailto:mbadra@gmail.com>

              Alan Luchuk
              <mailto:luchuk@snmp.com>

              Juergen Schoenwaelder
              <mailto:j.schoenwaelder@jacobs-university.de>";

  description
   "This submodule applies to NETCONF over TLS.  It specifies how
    NETCONF servers transform X.509 certificates presented by
    NETCONF clients into NETCONF usernames.  It also specifies
    how NETCONF servers transform pre-shared TLS keys into NETCONF
    usernames.

    Copyright (c) 2013 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";
  // RFC Ed.: replace XXXX with actual RFC number and
  // remove this note

  // RFC Ed.: please update the date to the date of publication

  revision "2013-10-21" {
    description
     "Initial version";
    reference
     "RFC XXXX: NETCONF over Transport Layer Security (TLS)";
  }

  feature tls {
    description
     "A server implements this feature if it supports NETCONF
      over Transport Layer Security (TLS).";
    reference
     "RFC XXXX: NETCONF over Transport Layer Security (TLS)";
  }

  feature tls-map-certificates {
    description
     "The tls-map-certificates feature indicates that the
      server implements mapping X.509 certificates to NETCONF
      usernames.";
  }

  feature tls-map-pre-shared-keys {
    description
     "The tls-map-pre-shared-keys feature indicates that the
      server implements mapping TLS pre-shared keys to NETCONF
      usernames.";
  }

  feature tls-call-home {
    description
     "The tls-call-home feature indicates that the server can
      connect to a client.";
  }

  augment /ncconf:netconf {
    if-feature tls;

    container tls {

      leaf enabled {
        type boolean;
        default "false";
        description
         "Enables NETCONF over Transport Layer Security (TLS).";
      }

      // Objects for deriving NETCONF usernames from X.509
      // certificates.

      container cert-maps {
        if-feature tls-map-certificates;
        uses x509c2n:cert-to-name;
        description
         "The cert-maps container is used by a NETCONF server to
          map the NETCONF client's presented X.509 certificate to
          a NETCONF username.

          If no matching and valid cert-to-name list entry can be
          found, then the NETCONF server MUST close the connection,
          and MUST NOT accept NETCONF messages over it.";
      }

      //  Objects for deriving NETCONF usernames from TLS
      //  pre-shared keys.

      container psk-maps {
        if-feature tls-map-pre-shared-keys;
        description
         "During the TLS Handshake, the client indicates which
          key to use by including a PSK identity in the TLS
          ClientKeyExchange message. On the server side, this
          PSK identity is used to look up an entry in the psk-map
          list. If such an entry is found, and the pre-shared keys
          match, then the client is authenticated. The server uses
          the value from the user-name leaf in the psk-map list as
          the NETCONF username.  If the server cannot find an entry
          in the psk-map list, or if the pre-shared keys do not
          match, then the server terminates the connection.";
        reference
         "RFC 4279: Pre-Shared Key Ciphersuites for Transport Layer
                    Security (TLS)";

        list psk-map {
          key psk-identity;

          leaf psk-identity {
            type string;
            description
             "The PSK identity encoded as a UTF-8 string. For
              details how certain common PSK identity formats can
              be encoded in UTF-8, see section 5.1. of RFC 4279.";
            reference
             "RFC 4279: Pre-Shared Key Ciphersuites for Transport
                        Layer Security (TLS)";
          }
          leaf user-name {
            type nacm:user-name-type;
            mandatory true;
            description
             "The NETCONF username associated with this PSK
              identity.";
          }
          leaf not-valid-before {
            type yang:date-and-time;
            description
             "This PSK identity is not valid before the given date
              and time.";
          }
          leaf not-valid-after {
            type yang:date-and-time;
            description
             "This PSK identity is not valid after the given date
              and time.";
          }
          leaf key {
            type yang:hex-string;
            mandatory true;
            nacm:default-deny-all;
            description
             "The key associated with the PSK identity";
            reference
             "RFC 4279: Pre-Shared Key Ciphersuites for Transport
                        Layer Security (TLS)";
          }
        }  // list psk-map
      }  // container psk-maps

      //  XXX
      //  Objects for determining where to connect to, how frequently,
      //  and how to reconnect should a connection break. This ideally
      //  would be a common grouping for both NETCONF over TLS and
      //  NETCONF over SSH.

      container call-home {
        if-feature tls-call-home;
        description
         "Provides the configuration of the NETCONF call-home
          clients to connect to, the overall call-home policy,
          and the reconnect strategy.";

        list client {
          key "address port";

          leaf address {
            type inet:host;
            description
             "The address of the call-home client to connect to.";
          }

          leaf port {
            type inet:port-number;
            // default 8888;
            description
             "The port number of the call-home client to connect to.";
          }

          choice connection-type {
            case persistent {
              leaf persistent-connection {
                type empty;
                description
                 "Maintain a persistent connection to the call-home
                  client.";
              }
            }
            case periodic {
              container periodic {
                leaf interval {
                  type uint16;            // ssh had uint8 ?
                  units minutes;
                  default 5;
                  description
                   "The maximum amount of unconnected time the device
                    will wait until establishing a connection to the
                    call-home client again. The device may establish
                    a connection before this time.";
                }

                leaf linger {
                  type uint16;            // ssh had uint8 ?
                  units seconds;
                  default 30;
                  description
                   "The amount of time the device should wait after
                    last receiving data from or sending data to the
                    call-home client before closing the connection.";
                }
              }
            }
          }

          // XXX
          // Should we have something smarter as the reconnect
          // strategy, e.g. an exponential backoff? What about
          // a persistent connection that fails for say a week?
          // One would hope that the box still attempts to
          // connect so that it can recover once it comes back
          // online.

          container reconnect-strategy {
            leaf retry-interval {
              type uint16;              // ssh had uint8 ?
              units seconds;
              default 5;
              description
               "Time delay between two subsequent connection
                attempts to the call-home client.";
            }
            leaf max-attempts {
              type uint16;              // ssh had uint8 ?
              default 3;
              description
               "Number of times to try to connect to a call-home
                client.";
            }
          }
          // XXX
          // Do we need objects to configure which cert / psk
          // to expect to use when attempting a call-home?
        }
      } // container call-home

    }
  }
}
