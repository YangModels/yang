module ietf-isis {
  yang-version 1.1;
  namespace "urn:ietf:params:xml:ns:yang:ietf-isis";

  prefix isis;

  import ietf-routing {
    prefix "rt";
    reference "RFC 8349 - A YANG Data Model for Routing
               Management (NMDA Version)";
  }

  import ietf-inet-types {
    prefix inet;
    reference "RFC 6991 - Common YANG Data Types";
  }

  import ietf-yang-types {
    prefix yang;
    reference "RFC 6991 - Common YANG Data Types";
  }

  import ietf-interfaces {
    prefix "if";
    reference "RFC 8343 - A YANG Data Model for Interface
               Management (NDMA Version)";
  }

  import ietf-key-chain {
    prefix "key-chain";
    reference "RFC 8177 - YANG Data Model for Key Chains";
  }

  import ietf-routing-types {
    prefix "rt-types";
    reference "RFC 8294 - Common YANG Data Types for the
               Routing Area";
  }

  import iana-routing-types {
    prefix "iana-rt-types";
    reference "RFC 8294 - Common YANG Data Types for the
               Routing Area";
  }

  import ietf-bfd-types {
    prefix "bfd-types";
    reference "RFC XXXX - YANG Data Model for Bidirectional
               Forwarding Detection (BFD).Please replace YYYY with
                                                         published RFC 
number for draft-ietf-bfd-yang.";
  }

  organization
    "IETF LSR Working Group";

  contact
    "WG List:  &lt;mailto:lsr@ietf.org&gt;

    Editor:    Stephane Litkowski
          &lt;mailto:stephane.litkowski@orange.com&gt;

        Derek Yeung
          &lt;mailto:derek@arrcus.com&gt;
        Acee Lindem
          &lt;mailto:acee@cisco.com&gt;
        Jeffrey Zhang
          &lt;mailto:zzhang@juniper.net&gt;
        Ladislav Lhotka
          &lt;mailto:llhotka@nic.cz&gt;
        Yi Yang
          &lt;mailto:yiya@cisco.com&gt;
        Dean Bogdanovic
          &lt;mailto:deanb@juniper.net&gt;
        Kiran Agrahara Sreenivasa
          &lt;mailto:kkoushik@brocade.com&gt;
        Yingzhen Qu
          &lt;mailto:yiqu@cisco.com&gt;
        Jeff Tantsura
          &lt;mailto:jefftant.ietf@gmail.com&gt;

    ";

  description
    "This YANG module defines the generic configuration and
      operational state for the IS-IS protocol.
                        It is intended that the module
      will be extended by vendors to define vendor-specific
      IS-IS configuration parameters and policies,
      for example route maps or route policies.
      This YANG model conforms to the Network Management
      Datastore Architecture (NDMA) as described in RFC 8242.

      Copyright (c) 2018 IETF Trust and the persons identified as
      authors of the code.  All rights reserved.

       Redistribution and use in source and binary forms, with or
       without modification, is permitted pursuant to, and subject
       to the license terms contained in, the Simplified BSD License
       set forth in Section 4.c of the IETF Trust's Legal Provisions
       Relating to IETF Documents
       (http://trustee.ietf.org/license-info).

       This version of this YANG module is part of RFC XXXX;
       see the RFC itself for full legal notices.";

  revision 2018-11-26 {
    description
      "Initial revision.";
    reference "RFC XXXX";
  }

  /* Identities */

  identity isis {
    base rt:routing-protocol;
    description "Identity for the IS-IS routing protocol.";
  }

  identity lsp-log-reason {
    description "Base identity for an LSP change log reason.";
  }

  identity refresh {
    base lsp-log-reason;
    description
      "Identity used when the LSP log reason is
       a refresh LSP received.";
  }

  identity content-change {
    base lsp-log-reason;
    description
      "Identity used when the LSP log reason is
       a change in the content of the LSP.";
  }

  /* Feature definitions */

  feature poi-tlv {
    description "Support of Purge Originator Identification.";
    reference "RFC 6232 - Purge Originator Identification TLV
               for IS-IS";
  }
  feature ietf-spf-delay {
    description
      "Support for IETF SPF delay algorithm.";
    reference "RFC 8405 - SPF Back-off algorithm for link
               state IGPs";
  }
  feature bfd {
    description
      "Support for BFD detection of IS-IS neighbor reachability.";
    reference "RFC 5880 - Bidirectional Forwarding Detection (BFD)
               RFC 5881 - Bidirectional Forwarding Detection
               (BFD) for IPv4 and IPv6 (Single Hop)";
  }
  feature key-chain {
    description
      "Support of keychain for authentication.";
    reference "RFC8177 - YANG Data Model for Key Chains";
  }
  feature node-flag {
    description
      "Support for node-flag for IS-IS prefixes.";
    reference "RFC7794 - IS-IS Prefix Attributes for
               Extended IP and IPv6 Reachability";
  }
  feature node-tag {
    description
      "Support for node admin tag for IS-IS routing instances.";
    reference "RFC7917 - Advertising Node Administrative Tags
               in IS-IS";
  }
  feature ldp-igp-sync {
    description
      "LDP IGP synchronization.";
    reference "RFC5443 - LDP IGP Synchronization.";
  }
  feature fast-reroute {
    description
      "Support for IP Fast Reroute (IP-FRR).";
  }
  feature nsr {
    description
      "Non-Stop-Routing (NSR) support.";
  }
  feature lfa {
    description
      "Support for Loop-Free Alternates (LFAs).";
    reference "RFC5286 - Basic Specification of IP Fast-Reroute:
               Loop-free Alternates";
  }
  feature remote-lfa {
    description
      "Support for Remote Loop-Free Alternates (R-LFAs).";
    reference "RFC7490 - Remote Loop-Free Alternate Fast Reroute";
  }

  feature overload-max-metric {
    description
      "Support of overload by setting
       all links to max metric.";
  }
  feature prefix-tag {
    description
      "Support for 32-bit prefix tags";
    reference "RFC5130 - A Policy Control Mechanism in
               IS-IS Using Administrative Tags";
  }
  feature prefix-tag64 {
    description
      "Support for 64-bit prefix tags";
    reference "RFC5130 - A Policy Control Mechanism in
               IS-IS Using Administrative Tags";
  }
  feature auto-cost {
    description
      "Calculate IS-IS interface metric according to
       reference bandwidth.";
  }

  feature te-rid {
    description
      "Traffic-Engineering Router-ID.";
    reference "RFC5305 - IS-IS Extensions for Traffic Engineering
               RFC6119 - IPv6 Traffic Engineering in IS-IS";
  }
  feature max-ecmp {
    description
      "Setting maximum number of ECMP paths.";
  }
  feature multi-topology {
    description
      "Support for Multiple-Topology Routing (MTR).";
    reference "RFC5120 - M-IS-IS: Multi Topology Routing in IS-IS";
  }
  feature nlpid-control {
    description
      "This feature controls the advertisement
       of support NLPID within IS-IS configuration.";
  }
  feature graceful-restart {
    description
      "IS-IS Graceful restart support.";
    reference "RFC5306 - Restart Signaling in IS-IS";
  }

  feature lsp-refresh {
    description
      "Configuration of LSP refresh interval.";
  }

  feature maximum-area-addresses {
    description
      "Support of maximum-area-addresses config.";
  }

  feature admin-control {
    description
      "Administrative control of the protocol state.";
  }

  /* Type definitions */

  typedef circuit-id {
    type uint8;
    description
      "This type defines the circuit ID
       associated with an interface.";
  }

  typedef extended-circuit-id {
    type uint32;
    description
      "This type defines the extended circuit ID
       associated with an interface.";
  }

  typedef interface-type {
    type enumeration {
      enum broadcast {
        description
          "Broadcast interface type.";
      }
      enum point-to-point {
        description
          "Point-to-point interface type.";
      }
    }
    description
      "This type defines the type of adjacency
       to be established on the interface.
       The interface-type determines the type
       of hello message that is used.";

  }

  typedef level {
    type enumeration {
      enum "level-1" {
        description
          "This enum indicates L1-only capability.";
      }
      enum "level-2" {
        description
          "This enum indicates L2-only capability.";
      }
      enum "level-all" {
        description
          "This enum indicates capability for both levels.";
      }
    }
    default "level-all";
    description
      "This type defines IS-IS level of an object.";

  }

  typedef adj-state-type {
    type enumeration {
      enum "up" {
        description
          "State indicates the adjacency is established.";
      }
      enum "down" {
        description
          "State indicates the adjacency is NOT established.";
      }
      enum "init" {
        description
          "State indicates the adjacency is establishing.";
      }
      enum "failed" {
        description
          "State indicates the adjacency is failed.";
      }
    }
    description
      "This type defines states of an adjacency";
  }

  typedef if-state-type {
    type enumeration {
      enum "up" {
        description "Up state.";

      }
      enum "down" {
        description "Down state";
      }
    }
    description
      "This type defines the state of an interface";
  }

  typedef level-number {
    type uint8 {
      range "1 .. 2";
    }
    description
      "This type defines the current IS-IS level.";
  }

  typedef lsp-id {
    type string {
      pattern
        '[0-9A-Fa-f]{4}\.[0-9A-Fa-f]{4}\.[0-9A-Fa-f]'
        +'{4}\.[0-9][0-9]-[0-9][0-9]';
    }
    description
      "This type defines the IS-IS LSP ID format using a
       pattern, An example LSP ID is 0143.0438.AEF0.02-01";
  }

  typedef area-address {
    type string {
      pattern '[0-9A-Fa-f]{2}(\.[0-9A-Fa-f]{4}){0,3}';
    }
    description
      "This type defines the area address format.";
  }

  typedef snpa {
    type string {
      length "0 .. 20";
    }
    description
      "This type defines the Subnetwork Point
       of Attachement (SNPA) format.";
  }

  typedef system-id {
    type string {
      pattern
        '[0-9A-Fa-f]{4}\.[0-9A-Fa-f]{4}\.[0-9A-Fa-f]{4}';
    }
    description
      "This type defines IS-IS system-id using pattern,
       An example system-id is 0143.0438.AEF0";
  }
        typedef extended-system-id {
    type string {
      pattern
        '[0-9A-Fa-f]{4}\.[0-9A-Fa-f]{4}\.[0-9A-Fa-f]{4}\.[0-9][0-9]';
    }
    description
      "This type defines IS-IS system-id using pattern. The extended
                         system id contains the pseudonode number in 
addition to the
                         system id.
       An example system-id is 0143.0438.AEF0.00";
  }

  typedef wide-metric {
    type uint32 {
      range "0 .. 16777215";
    }
    description
      "This type defines wide style format of IS-IS metric.";
  }

  typedef std-metric {
    type uint8 {
      range "0 .. 63";
    }
    description
      "This type defines old style format of IS-IS metric.";
  }

  typedef mesh-group-state {
    type enumeration {
      enum "mesh-inactive" {
        description
          "Interface is not part of a mesh group.";
      }
      enum "mesh-set" {
        description
          "Interface is part of a mesh group.";
      }
      enum "mesh-blocked" {
        description
          "LSPs must not be flooded over this interface.";
      }
    }
    description
      "This type describes mesh group state of an interface";
  }

  /* Grouping for notifications */

  grouping notification-instance-hdr {
    description
      "Instance specific IS-IS notification data grouping";
    leaf routing-protocol-name {
      type leafref {
        path "/rt:routing/rt:control-plane-protocols/"
           + "rt:control-plane-protocol/rt:name";
      }
      description "Name of the IS-IS instance.";
    }
    leaf isis-level {
      type level;
      description "IS-IS level of the instance.";
    }
  }

  grouping notification-interface-hdr {
    description
      "Interface specific IS-IS notification data grouping";
    leaf interface-name {
      type if:interface-ref;
      description "IS-IS interface name";
    }
    leaf interface-level {
      type level;
      description "IS-IS level of the interface.";
    }
    leaf extended-circuit-id {
      type extended-circuit-id;
      description "Eextended circuit-id of the interface.";
    }
  }

 /* Groupings for IP Fast Reroute */

 grouping instance-fast-reroute-config {
    description
      "This group defines global configuration of IP
       Fast ReRoute (FRR).";
    container fast-reroute {
      if-feature fast-reroute;
      description
        "This container may be augmented with global
         parameters for IP-FRR.";
      container lfa {
        if-feature lfa;
        description
          "This container may be augmented with
           global parameters for Loop-Free Alternatives (LFA).
           Container creation has no effect on LFA activation.";
      }
    }
  }

 grouping interface-lfa-config {
    leaf candidate-enable {
      type boolean;
      default true;
      description
        "Enable the interface to be used as backup.";
    }
    leaf enable {
      type boolean;
      default false;
      description
        "Activates LFA - Per-prefix LFA computation
         is assumed.";
    }
    container remote-lfa {
      if-feature remote-lfa;
      leaf enable {
        type boolean;
        default false;
        description
          "Activates Remote LFA (R-LFA).";
      }
      description
        "Remote LFA configuration.";
    }
    description "Grouping for LFA interface configuration";
  }
  grouping interface-fast-reroute-config {
    description
      "This group defines interface configuration of IP-FRR.";
    container fast-reroute {
      if-feature fast-reroute;
      container lfa {
        if-feature lfa;
        uses interface-lfa-config;
        container level-1 {
          uses interface-lfa-config;
          description
            "LFA level 1 config";
        }
        container level-2 {
        uses interface-lfa-config;
         description
          "LFA level 2 config";
        }
        description
          "LFA configuration.";
      }
      description
        "Interface IP Fast-reroute configuration.";
    }
  }
  grouping instance-fast-reroute-state {
    description "IPFRR state data grouping";

    container protected-routes {
      config false;
      list address-family-stats {
        key "address-family prefix alternate";

        leaf address-family {
          type iana-rt-types:address-family;
          description
            "Address-family";
        }
        leaf prefix {
          type string;
          description
            "Protected prefix.";
        }
        leaf alternate {
          type string;
          description
            "Alternate nexthop for the prefix.";
        }
        leaf alternate-type {
          type enumeration {
            enum equal-cost {
              description
                "ECMP alternate.";
            }
            enum lfa {
              description
                "LFA alternate.";
            }
            enum remote-lfa {
              description
                "Remote LFA alternate.";
            }
            enum tunnel {
              description
                "Tunnel based alternate
                 (like RSVP-TE or GRE).";
            }
            enum ti-lfa {
              description
                "TI-LFA alternate.";
            }
            enum mrt {
              description
                "MRT alternate.";
            }
            enum other {
              description
                "Unknown alternate type.";
            }
          }
          description
            "Type of alternate.";
        }
        leaf best {
          type boolean;
          description
            "Indicates if the alternate is the preferred.";
        }
        leaf non-best-reason {
          type string;
          description
            "Information field to describe why the alternate
             is not best.";
        }
        leaf protection-available {
          type bits {
            bit node-protect {
              position 0;
              description
                "Node protection available.";
            }
            bit link-protect {
              position 1;
              description
                "Link protection available.";
            }
            bit srlg-protect {
              position 2;
              description
                "SRLG protection available.";
            }
            bit downstream-protect {
              position 3;
              description
                "Downstream protection available.";
            }
            bit other {
              position 4;
              description
                "Other protection available.";
            }
          }
          description "Protection provided by the alternate.";
        }
        leaf alternate-metric1 {
          type uint32;
          description
            "Metric from Point of Local Repair (PLR) to
             destination through the alternate path.";
        }
        leaf alternate-metric2 {
          type uint32;
          description
            "Metric from PLR to the alternate node";
        }
        leaf alternate-metric3 {
          type uint32;
          description
            "Metric from alternate node to the destination";
        }
        description
          "Per-AF protected prefix statistics.";
      }
      description
        "List of prefixes that are protected.";
    }

    container unprotected-routes {
      config false;
      list address-family-stats {
        key "address-family prefix";

        leaf address-family {
          type iana-rt-types:address-family;

          description "Address-family";
        }
        leaf prefix {
          type string;
          description "Unprotected prefix.";
        }
        description
          "Per AF unprotected prefix statistics.";
      }
      description
        "List of prefixes that are not protected.";
    }

    list protection-statistics {
      key frr-protection-method;
      config false;
      leaf frr-protection-method {
        type string;
        description "Protection method used.";
      }
      list address-family-stats {
        key address-family;

        leaf address-family {
          type iana-rt-types:address-family;

          description "Address-family";
        }
        leaf total-routes {
          type uint32;
          description "Total prefixes.";
        }
        leaf unprotected-routes {
          type uint32;
          description
            "Total prefixes that are not protected.";
        }
        leaf protected-routes {
          type uint32;
          description
            "Total prefixes that are protected.";
        }
        leaf linkprotected-routes {
          type uint32;
          description
            "Total prefixes that are link protected.";
        }
        leaf nodeprotected-routes {
          type uint32;
          description
            "Total prefixes that are node protected.";
        }
        description
          "Per AF protected prefix statistics.";
      }

      description "Global protection statistics.";
    }
  }

        /* Route table and local RIB groupings */

  grouping local-rib {
    description "Local-rib - RIB for Routes computed by the local
                 IS-IS routing instance.";
    container local-rib {
      config false;
      description "Local-rib.";
      list route {
        key "prefix";
        description "Routes";
        leaf prefix {
          type inet:ip-prefix;
          description "Destination prefix.";
        }
        container next-hops {
          description "Next hops for the route.";
          list next-hop {
            key "next-hop";
            description "List of next hops for the route";
            leaf outgoing-interface {
              type if:interface-ref;
              description
                "Name of the outgoing interface.";
            }
            leaf next-hop {
             type inet:ip-address;
             description "Nexthop address.";
            }
          }
        }
        leaf metric {
          type uint32;
          description "Metric for this route.";
        }
        leaf level {
          type level-number;
          description "Level number for this route.";
        }
        leaf route-tag {
          type uint32;
          description "Route tag for this route.";
        }
      }
    }
  }

  grouping route-content {
    description
      "IS-IS protocol-specific route properties grouping.";
    leaf metric {
      type uint32;
      description "IS-IS metric of a route.";
    }
    leaf-list tag {
      type uint64;
      description
        "List of tags associated with the route. The leaf
         describes both 32-bit and 64-bit tags.";
    }
    leaf route-type {
      type enumeration {
        enum l2-up-internal {
          description "Level 2 internal route
                       and not leaked to a lower level";
        }
        enum l1-up-internal {
          description "Level 1 internal route
                       and not leaked to a lower level";
        }
        enum l2-up-external {
          description "Level 2 external route
                       and not leaked to a lower level";
        }
        enum l1-up-external {
          description "Level 1 external route
                       and not leaked to a lower level";
        }
        enum l2-down-internal {
          description "Level 2 internal route
                       and leaked to a lower level";
        }
        enum l1-down-internal {
          description "Level 1 internal route
                       and leaked to a lower level";
        }
        enum l2-down-external {
          description "Level 2 external route
                       and leaked to a lower level";
        }
        enum l1-down-external {
          description "Level 1 external route
                       and leaked to a lower level";
        }
      }
      description "IS-IS route type.";
    }
  }

        /* Grouping definitions for configuration and ops state */

  grouping adjacency-state {
    container adjacencies {
      config false;
      list adjacency {
        leaf neighbor-sys-type {
          type level;
          description
            "Level capability of neighboring system";
        }
        leaf neighbor-sysid {
          type system-id;
          description
            "The system-id of the neighbor";
        }
        leaf neighbor-extended-circuit-id {
          type extended-circuit-id;
          description
            "Circuit ID of the neighbor";
        }
        leaf neighbor-snpa {
          type snpa;
          description
            "SNPA of the neighbor";
        }
        leaf usage {
          type level;
          description
            "Define the level(s) activated on the adjacency.
             On a p2p link this might be level 1 and 2,
             but on a LAN, the usage will be level 1
             between peers at level 1 or level 2 between
             peers at level 2.";
        }
        leaf hold-timer {
          type rt-types:timer-value-seconds16;
          units seconds;
          description
            "The holding time in seconds for this
             adjacency. This value is based on
             received hello PDUs and the elapsed
             time since receipt.";
        }
        leaf neighbor-priority {
          type uint8 {
            range "0 .. 127";
          }
          description
            "Priority of the neighboring IS for becoming
             the DIS.";
        }
        leaf lastuptime {
          type yang:timestamp;
          description
            "When the adjacency most recently entered
             state 'up', measured in hundredths of a
             second since the last reinitialization of
             the network management subsystem.
             The value is 0 if the adjacency has never
             been in state 'up'.";
        }
        leaf state {
          type adj-state-type;
          description
            "This leaf describes the state of the interface.";
        }

        description
          "List of operational adjacencies.";
      }
      description
        "This container lists the adjacencies of
         the local node.";
    }
    description
      "Adjacency state";
  }

  grouping admin-control {
    leaf enable {
      if-feature admin-control;
      type boolean;
      default true;
      description
        "Enable/Disable the protocol.";
    }
    description
      "Grouping for admin control.";
  }

  grouping ietf-spf-delay {
    leaf initial-delay {
      type rt-types:timer-value-milliseconds;
      units msec;
      description
        "Delay used while in QUIET state (milliseconds).";
    }
    leaf short-delay {
      type rt-types:timer-value-milliseconds;
      units msec;
      description
        "Delay used while in SHORT_WAIT state (milliseconds).";
    }
    leaf long-delay {
      type rt-types:timer-value-milliseconds;
      units msec;
      description
        "Delay used while in LONG_WAIT state (milliseconds).";
    }

    leaf hold-down {
      type rt-types:timer-value-milliseconds;
      units msec;
      description
        "Timer used to consider an IGP stability period
                                 (milliseconds).";
    }
    leaf time-to-learn {
      type rt-types:timer-value-milliseconds;
      units msec;
      description
        "Duration used to learn all the IGP events
         related to a single component failure (milliseconds).";
    }
    leaf current-state {
      type enumeration {
        enum "quiet" {
          description "QUIET state";
        }
        enum "short-wait" {
          description "SHORT_WAIT state";
        }
        enum "long-wait" {
          description "LONG_WAIT state";
        }
      }
      config false;
      description
        "Current SPF backoff algorithm state.";
    }
    leaf remaining-time-to-learn {
      type rt-types:timer-value-milliseconds;
      units "msec";
      config false;
      description
        "Remaining time until time-to-learn timer fires.";
    }
    leaf remaining-hold-down {
      type rt-types:timer-value-milliseconds;
      units "msec";
      config false;
      description
        "Remaining time until hold-down timer fires.";
    }
    leaf last-event-received {
      type yang:timestamp;
      config false;
      description
        "Time of last IGP event received";
    }
    leaf next-spf-time {
      type yang:timestamp;
      config false;
      description
        "Time when next SPF has been scheduled.";
    }
    leaf last-spf-time {
      type yang:timestamp;
      config false;
      description
        "Time of last SPF computation.";
    }
    description
      "Grouping for IETF SPF delay configuration and state.";
  }

  grouping node-tag-config {
    description
      "IS-IS node tag config state.";
    container node-tags {
      if-feature node-tag;
      list node-tag {
        key tag;
        leaf tag {
          type uint32;
            description
              "Node tag value.";
        }
        description
          "List of tags.";
      }
      description
        "Container for node admin tags.";
    }
  }

  grouping authentication-global-cfg {
    choice authentication-type {
      case key-chain {
        if-feature key-chain;
        leaf key-chain {
          type key-chain:key-chain-ref;
          description
            "Reference to a key-chain.";
        }
      }
      case password {
        leaf key {
          type string;
          description
            "This leaf specifies the authentication key.";
        }
        leaf crypto-algorithm {
          type identityref {
            base key-chain:crypto-algorithm;
          }
          description
            "Cryptographic algorithm associated with key.";
        }
      }
      description "Choice of authentication.";
    }
    description "Grouping for global authentication config.";
  }

  grouping metric-type-global-cfg {
    leaf value {
      type enumeration {
        enum wide-only {
          description
            "Advertise new metric style only (RFC5305)";
        }
        enum old-only {
          description
            "Advertise old metric style only (RFC1195)";
        }
        enum both {
          description "Advertise both metric styles";
        }
      }
      default wide-only;
      description
        "Type of metric to be generated:
         - wide-only means only new metric style
            is generated,
         - old-only means that only old style metric
           is generated,
         - both means that both are advertised.
         This leaf is only affecting IPv4 metrics.";
    }
    description
      "Grouping for global metric style config.";
  }

  grouping default-metric-global-cfg {
    leaf value {
      type wide-metric;
      default "10";
      description  "Value of the metric";
    }
    description
      "Global default metric config grouping.";
  }

  grouping overload-global-cfg {
    leaf status {
      type boolean;
      default false;
      description
        "This leaf specifies the overload status.";
    }
    description "Grouping for overload bit config.";
  }

  grouping overload-max-metric-global-cfg {
    leaf timeout {
      type rt-types:timer-value-seconds16;
      units "seconds";
      description
        "Timeout (in seconds) of the overload condition.";
    }
    description
      "Overload maximum metric configuration grouping";
  }

  grouping route-preference-global-cfg {
    choice granularity {
      case detail {
        leaf internal {
          type uint8;
          description
            "Protocol preference for internal routes.";
        }
        leaf external {
          type uint8;
          description
            "Protocol preference for external routes.";
        }
      }
      case coarse {
        leaf default {
          type uint8;
          description
            "Protocol preference for all IS-IS routes.";
        }
      }
      description
        "Choice for implementation of route preference.";
    }
    description
      "Global route preference grouping";
  }

  grouping hello-authentication-cfg {
    choice authentication-type {
      case key-chain {
        if-feature key-chain;
        leaf key-chain {
          type key-chain:key-chain-ref;
          description "Reference to a key-chain.";
        }
      }
      case password {
        leaf key {
          type string;
          description "Authentication key specification";
        }
        leaf crypto-algorithm {
          type identityref {
            base key-chain:crypto-algorithm;
          }
          description
            "Cryptographic algorithm associated with key.";
        }
      }
      description "Choice of authentication.";
    }
    description "Grouping for hello authentication.";
  }

  grouping hello-interval-cfg {
    leaf value {
      type rt-types:timer-value-seconds16;
      units "seconds";
      default 10;
      description
        "Interval (in seconds) between successive hello
         messages.";
    }

    description "Interval between hello messages.";
  }

  grouping hello-multiplier-cfg {
    leaf value {
      type uint16;
      default 3;
      description
        "Number of missed hello messages prior to
         declaring the adjacency down.";
    }
    description
        "Number of missed hello messages prior to
         adjacency down grouping.";
  }

  grouping priority-cfg {
    leaf value {
      type uint8 {
        range "0 .. 127";
      }
      default 64;
      description
        "Priority of interface for DIS election.";
    }

    description "Interface DIS election priority grouping";
  }

  grouping metric-cfg {
    leaf value {
      type wide-metric;
      default "10";
      description "Metric value.";
    }
    description "Interface metric grouping";
  }

  grouping metric-parameters {
    container metric-type {
      uses metric-type-global-cfg;
      container level-1 {
        uses metric-type-global-cfg;
        description "level-1 specific configuration";
      }
      container level-2 {
        uses metric-type-global-cfg;
        description "level-2 specific configuration";
      }
      description "Metric style global configuration";
    }

    container default-metric {
      uses default-metric-global-cfg;
      container level-1 {
        uses default-metric-global-cfg;
        description "level-1 specific configuration";
      }
      container level-2 {
        uses default-metric-global-cfg;
        description "level-2 specific configuration";
      }
      description "Default metric global configuration";
    }
    container auto-cost {
      if-feature auto-cost;
      description
        "Interface Auto-cost configuration state.";
      leaf enable {
        type boolean;
        description
          "Enable/Disable interface auto-cost.";
      }
      leaf reference-bandwidth {
        when "../enable = 'true'" {
          description "Only when auto cost is enabled";
        }
        type uint32 {
          range "1..4294967";
        }
        units Mbits;
        description
          "Configure reference bandwidth used to automatically
           determine interface cost (Mbits). The cost is the
           reference bandwidth divided by the interface speed
           with 1 being the minimum cost.";
      }
    }

    description "Grouping for global metric parameters.";
  }

  grouping high-availability-parameters {
    container graceful-restart {
      if-feature graceful-restart;
      leaf enable {
        type boolean;
        default false;
        description "Enable graceful restart.";
      }
      leaf restart-interval {
        type rt-types:timer-value-seconds16;
        units "seconds";
        description
          "Interval (in seconds) to attempt graceful restart prior
           to failure.";
      }
      leaf helper-enable {
        type boolean;
        default true;
        description
          "Enable local IS-IS router as graceful restart helper.";
      }
      description "Graceful-Restart Configuration.";
    }
    container nsr {
      if-feature nsr;
      description "Non-Stop Routing (NSR) configuration.";
      leaf enable {
        type boolean;
        default false;
        description "Enable/Disable Non-Stop Routing (NSR).";
      }
    }
    description "Grouping for High Availability parameters.";
  }

  grouping authentication-parameters {
    container authentication {
      uses authentication-global-cfg;

      container level-1 {
        uses authentication-global-cfg;
        description "level-1 specific configuration";
      }
      container level-2 {
        uses authentication-global-cfg;
        description "level-2 specific configuration";
      }
      description "Authentication global configuration for
                   both LSPs and SNPs.";
    }
    description "Grouping for authentication parameters";
  }
  grouping address-family-parameters {
    container address-families {
      if-feature nlpid-control;
      list address-family-list {
        key address-family;
        leaf address-family {
          type iana-rt-types:address-family;
          description "Address-family";
        }
        leaf enable {
          type boolean;
          description "Activate the address family.";
        }
        description
          "List of address families and whether or not they
           are activated.";
      }
      description "Address Family configuration";
    }
    description "Grouping for address family parameters.";
  }

  grouping mpls-parameters {
    container mpls {
      container te-rid {
        if-feature te-rid;
        description
          "Stable ISIS Router IP Address used for Traffic
           Engineering";
        leaf ipv4-router-id {
          type inet:ipv4-address;
          description
            "Router ID value that would be used in TLV 134.";
        }
        leaf ipv6-router-id {
          type inet:ipv6-address;
          description
            "Router ID value that would be used in TLV 140.";
        }
      }
      container ldp {
        container igp-sync {
          if-feature ldp-igp-sync;
          description
            "This container may be augmented with global
             parameters for igp-ldp-sync.";
        }
        description "LDP configuration.";
      }
      description "MPLS configuration";
    }
    description "Grouping for MPLS global parameters.";
  }

  grouping lsp-parameters {
    leaf lsp-mtu {
      type uint16;
      units "bytes";
      default 1492;
      description
        "Maximum size of an LSP PDU in bytes.";
    }
    leaf lsp-lifetime {
      type uint16 {
        range "1..65535";
      }
      units "seconds";
      description
        "Lifetime of the router's LSPs in seconds.";
    }
    leaf lsp-refresh {
      if-feature lsp-refresh;
      type rt-types:timer-value-seconds16;
      units "seconds";
      description
        "Refresh interval of the router's LSPs in seconds.";
    }
    leaf poi-tlv {
      if-feature poi-tlv;
      type boolean;
      default false;
      description
        "Enable advertisement of IS-IS purge TLV.";
    }
    description "Grouping for LSP global parameters.";
  }
  grouping spf-parameters {
    container spf-control {
        leaf paths {
          if-feature max-ecmp;
          type uint16 {
            range "1..32";
          }
          description
            "Maximum number of Equal-Cost Multi-Path (ECMP) paths.";
        }
        container ietf-spf-delay {
          if-feature ietf-spf-delay;
          uses ietf-spf-delay;
          description "IETF SPF delay algorithm configuration.";
        }
        description
          "SPF calculation control.";
    }
                description "Grouping for SPF global parameters.";
  }
  grouping instance-config {
    description "IS-IS global configuration grouping";

    uses admin-control;

    leaf level-type {
      type level;
      default "level-all";
      description
        "Level of an IS-IS node - can be level-1-only,
         level-2-only or level-1-2.";
    }

    leaf system-id {
      type system-id;
      description "System-id of the node.";
    }

    leaf maximum-area-addresses {
      if-feature maximum-area-addresses;
      type uint8;
      default 3;
      description "Maximum areas supported.";
    }

    leaf-list area-address {
      type area-address;
      description
        "List of areas supported by the protocol instance.";
    }

    uses lsp-parameters;
    uses high-availability-parameters;
    uses node-tag-config;
    uses metric-parameters;
    uses authentication-parameters;
    uses address-family-parameters;
    uses mpls-parameters;
    uses spf-parameters;
    uses instance-fast-reroute-config;

    container preference {
      uses route-preference-global-cfg;
      description "Router preference configuration for IS-IS
                   protocol instance route installation";
    }

    container overload {
      uses overload-global-cfg;
      description "Router protocol instance overload state
                   configuration";
    }

    container overload-max-metric {
      if-feature overload-max-metric;
      uses overload-max-metric-global-cfg;
      description
        "Router protocol instance overload maximum
         metric advertisement configuration.";
    }
  }

  grouping instance-state {
      description
       "IS-IS instance operational state.";
     uses spf-log;
      uses lsp-log;
      uses hostname-db;
      uses lsdb;
      uses local-rib;
      uses system-counters;
      uses instance-fast-reroute-state;
  }

  grouping multi-topology-config {
    description "Per-topology configuration";
    container default-metric {
      uses default-metric-global-cfg;
      container level-1 {
        uses default-metric-global-cfg;
        description "level-1 specific configuration";
      }
      container level-2 {
        uses default-metric-global-cfg;
        description "level-2 specific configuration";
      }
      description "Default metric per-topology configuration";
    }
    uses node-tag-config;
  }

  grouping interface-config {
    description "Interface configuration grouping";
    leaf level-type {
      type level;
      default "level-all";
      description "IS-IS level of the interface.";
    }
    leaf lsp-pacing-interval {
      type rt-types:timer-value-milliseconds;
      units "milliseconds";
      default 33;
      description
        "Interval (in milli-seconds) between LSP
         transmissions.";
    }
    leaf lsp-retransmit-interval {
      type rt-types:timer-value-seconds16;
      units "seconds";
      description
        "Interval (in seconds) between LSP
         retransmissions.";
    }
    leaf passive {
      type boolean;
      default "false";
      description
        "Indicates whetherthe interface is in passive mode (IS-IS
         not running but network is advertised).";
    }
    leaf csnp-interval {
      type rt-types:timer-value-seconds16;
      units "seconds";
      default 10;
      description
         "Interval (in seconds) between CSNP messages.";
    }
    container hello-padding {
      leaf enable {
        type boolean;
        default "true";
        description
          "IS-IS Hello-padding activation - enabled by default.";
      }
      description "IS-IS hello padding configuration.";
    }
    leaf mesh-group-enable {
      type mesh-group-state;
      description "IS-IS interface mesh-group state";
    }
    leaf mesh-group {
      when "../mesh-group-enable = 'mesh-set'" {
        description
          "Only valid when mesh-group-enable equals meshset";
      }
      type uint8;
      description "IS-IS interface mesh-group ID.";
    }
    leaf interface-type {
      type interface-type;
      default "broadcast";
      description
        "Type of adjacency to be established on the interface. This
         dictates the type of hello messages that are used.";
    }

    uses admin-control;

    leaf-list tag {
      if-feature prefix-tag;
      type uint32;
      description
        "List of tags associated with the interface.";
    }
    leaf-list tag64 {
      if-feature prefix-tag64;
      type uint64;
      description
        "List of 64-bit tags associated with the interface.";
    }
    leaf node-flag {
      if-feature node-flag;
      type boolean;
      default false;
      description
        "Set prefix as a node representative prefix.";
    }
    container hello-authentication {
      uses hello-authentication-cfg;
      container level-1 {
        uses hello-authentication-cfg;
        description "level-1 specific configuration";
      }
      container level-2 {
        uses hello-authentication-cfg;
        description "level-2 specific configuration";
      }
      description
        "Authentication type to be used in hello messages.";
    }
    container hello-interval {
      uses hello-interval-cfg;
      container level-1 {
        uses hello-interval-cfg;
        description "level-1 specific configuration";
      }
      container level-2 {
        uses hello-interval-cfg;
        description "level-2 specific configuration";
      }
      description "Interval between hello messages.";
    }
    container hello-multiplier {
      uses hello-multiplier-cfg;
      container level-1 {
        uses hello-multiplier-cfg;
        description "level-1 specific configuration";
      }
      container level-2 {
        uses hello-multiplier-cfg;
        description "level-2 specific configuration";
      }
      description "Hello multiplier configuration.";
    }
    container priority {
      must '../interface-type = "broadcast"' {
        error-message
          "Priority only applies to broadcast interfaces.";
        description "Check for broadcast interface.";
      }
      uses priority-cfg;
      container level-1 {
        uses priority-cfg;
        description "level-1 specific configuration";
      }
      container level-2 {
        uses priority-cfg;
        description "level-2 specific configuration";
      }
      description "Priority for DIS election.";
    }
    container metric {
      uses metric-cfg;
      container level-1 {
        uses metric-cfg;
        description "level-1 specific configuration";
      }
      container level-2 {
        uses metric-cfg;
        description "level-2 specific configuration";
      }
      description "Metric configuration.";
    }
    container bfd {
      if-feature bfd;
      description "BFD Client Configuration.";
      uses bfd-types:client-cfg-parms;

      reference "draft-ietf-bfd-yang-xx.txt:
                 YANG Data Model for Bidirectional Forwarding
                 Detection (BFD)";
    }
    container address-families {
      if-feature nlpid-control;
      list address-family-list {
        key address-family;
        leaf address-family {
          type iana-rt-types:address-family;
          description  "Address-family";
        }
        description "List of AFs.";
      }
      description "Interface address-families";
    }
    container mpls {
      container ldp {
        leaf igp-sync {
          if-feature ldp-igp-sync;
          type boolean;
          default false;
          description "Enables IGP/LDP synchronization";
        }
        description "LDP protocol related configuration.";
      }
      description "MPLS configuration for IS-IS interfaces";
    }
    uses interface-fast-reroute-config;
  }

  grouping multi-topology-interface-config {
    description "IS-IS interface topology configuration.";
    container metric {
      uses metric-cfg;
      container level-1 {
        uses metric-cfg;
        description "level-1 specific configuration";
      }
      container level-2 {
        uses metric-cfg;
        description "level-2 specific configuration";
      }
      description "Metric IS-IS interface configuration.";
    }
  }
  grouping interface-state {
    description
      "IS-IS interface operational state.";
    uses adjacency-state;
    uses event-counters;
    uses packet-counters;
  }

 /* Grouping for the hostname database */

  grouping hostname-db {
    container hostnames {
      config false;
      list hostname {
        key system-id;
        leaf system-id {
          type system-id;
          description
            "System-id associated with the hostname.";
        }
        leaf hostname {
          type string;
          description
            "Hostname associated with the system ID.";
        }
        description
          "List of system-id/hostname associations.";
      }
      description
        "Hostname to system-id mapping database.";
    }
    description
      "Grouping for hostname to system-id mapping database.";
  }

  /* Groupings for counters */

  grouping system-counters {
    container system-counters {
      config false;
      list level {
        key level;

        leaf level {
          type level-number;
          description "IS-IS level.";
        }
        leaf corrupted-lsps {
          type uint32;
          description
            "Number of corrupted in-memory LSPs detected.
             LSPs received from the wire with a bad
             checksum are silently dropped and not counted.
             LSPs received from the wire with parse errors
             are counted by lsp-errors.";
        }
        leaf authentication-type-fails {
          type uint32;
          description
             "Number of authentication type mismatches.";
        }
        leaf authentication-fails {
          type uint32;
          description
            "Number of authentication key failures.";
        }
        leaf database-overload {
          type uint32;
          description
            "Number of times the database has become
             overloaded.";
        }
        leaf own-lsp-purge {
          type uint32;
          description
            "Number of times a zero-aged copy of the system's
             own LSP is received from some other IS-IS node.";
        }
        leaf manual-address-drop-from-area {
          type uint32;
          description
            "Number of times a manual address
             has been dropped from the area.";
        }
        leaf max-sequence {
          type uint32;
          description
            "Number of times the system has attempted
             to exceed the maximum sequence number.";
        }
        leaf sequence-number-skipped {
          type uint32;
          description
            "Number of times a sequence number skip has
             occured.";
        }
        leaf id-len-mismatch {
          type uint32;
          description
            "Number of times a PDU is received with a
             different value for the ID field length
             than that of the receiving system.";
        }
        leaf partition-changes {
          type uint32;
          description
            "Number of partition changes detected.";
        }
        leaf lsp-errors {
          type uint32;
          description
            "Number of LSPs with errors we have received.";
        }
        leaf spf-runs {
          type uint32;
          description
            "Number of times we ran SPF at this level.";
        }
        description
          "List of supported levels.";
      }
      description
        "List counters for the IS-IS protocol instance";
    }
    description "System counters grouping.";
  }

  grouping event-counters {
    container event-counters {
      config false;
      leaf adjacency-changes {
        type uint32;
        description
          "The number of times an adjacency state change has
           occured on this interface.";
      }
      leaf adjacency-number {
        type uint32;
        description
          "The number of adjacencies on this interface.";
      }
      leaf init-fails {
        type uint32;
        description
          "The number of times initialization of this
           interface has failed. This counts events such
           as PPP NCP failures. Failures to form an
           adjacency are counted by adjacency-rejects.";
      }
      leaf adjacency-rejects {
        type uint32;
        description
          "The number of times an adjacency has been
           rejected on this interface.";
      }
      leaf id-len-mismatch {
        type uint32;
        description
          "The number of times an IS-IS PDU with an ID
           field length different from that for this
           system has been received on this interface.";
      }
      leaf max-area-addresses-mismatch {
        type uint32;
        description
          "The number of times an IS-IS PDU has been
           received on this interface with the
           max area address field differing from that of
           this system.";
      }
      leaf authentication-type-fails {
        type uint32;
        description
          "Number of authentication type mismatches.";
      }
      leaf authentication-fails {
        type uint32;
        description
          "Number of authentication key failures.";
      }
      leaf lan-dis-changes {
        type uint32;
        description
          "The number of times the DIS has changed on this
           interface at this level. If the interface type is
           point-to-point,the count is zero.";
      }
      description "IS-IS interface event counters.";
    }
    description
      "Grouping for IS-IS interface event counters";
  }

  grouping packet-counters {
    container packet-counters {
      config false;
      list level {
        key level;

        leaf level {
          type level-number;
          description "IS-IS level.";
        }
        container iih {
          leaf in {
            type uint32;
            description "Received IIH PDUs.";
          }
          leaf out {
            type uint32;
            description "Sent IIH PDUs.";
          }
          description "Number of IIH PDUs received/sent.";
        }
        container ish {
          leaf in {
            type uint32;
            description "Received ISH PDUs.";
          }
          leaf out {
            type uint32;
            description "Sent ISH PDUs.";
          }
          description
            "ISH PDUs received/sent.";
        }
        container esh {
          leaf in {
            type uint32;
            description "Received ESH PDUs.";
          }
          leaf out {
            type uint32;
            description "Sent ESH PDUs.";
          }
          description "Number of ESH PDUs received/sent.";
        }
        container lsp {
          leaf in {
            type uint32;
            description "Received LSP PDUs.";
          }
          leaf out {
            type uint32;
            description "Sent LSP PDUs.";
          }
          description "Number of LSP PDUs received/sent.";
        }
        container psnp {
          leaf in {
            type uint32;
            description "Received PSNP PDUs.";
          }
          leaf out {
            type uint32;
            description "Sent PSNP PDUs.";
          }
          description "Number of PSNP PDUs received/sent.";
        }
        container csnp {
          leaf in {
            type uint32;
            description "Received CSNP PDUs.";
          }
          leaf out {
            type uint32;
            description "Sent CSNP PDUs.";
          }
          description "Number of CSNP PDUs received/sent.";
        }
        container unknown {
          leaf in {
            type uint32;
            description "Received unknown PDUs.";
          }
          leaf out {
            type uint32;
            description "Sent unknown PDUs.";
          }
          description "Number of unknown PDUs received/sent.";
        }
        description
          "List of packet counter for supported llevels.";
      }
      description "Packet counters per IS-IS level.";
    }
    description
      "Grouping for per IS-IS Level packet counters.";
  }

        /* Groupings for various log buffers */
  grouping spf-log {
    container spf-log {
      config false;
      list event {
        key id;

        leaf id {
          type uint32;
          description
            "Event identifier -  purely internal value.";
        }
        leaf spf-type {
          type enumeration {
            enum full {
              description "Full SPF computation.";
            }
            enum route-only {
              description
                "Route reachability only SPF computation";
            }
          }
          description "Type of SPF computation performed.";
        }
        leaf level {
          type level-number;
          description
            "IS-IS level number for SPF computation";
        }
        leaf schedule-timestamp {
          type yang:timestamp;
          description
            "Timestamp of when the SPF computation was
             scheduled.";
        }
        leaf start-timestamp {
          type yang:timestamp;
          description
            "Timestamp of when the SPF computation started.";
        }
        leaf end-timestamp {
          type yang:timestamp;
          description
            "Timestamp of when the SPF computation ended.";
        }
        list trigger-lsp {
          key "lsp";
          leaf lsp {
            type lsp-id;
            description
              "LSPID of the LSP triggering SPF computation.";
          }
          leaf sequence {
            type uint32;
            description
              "Sequence number of the LSP triggering SPF
               computation";
          }
          description
            "This list includes the LSPs that triggered the
             SPF computation.";
        }
        description
          "List of computation events - implemented as a
           wrapping buffer.";
      }

      description
        "This container lists the SPF computation events.";
    }
    description "Grouping for spf-log events.";
  }

  grouping lsp-log {
    container lsp-log {
      config false;
      list event {
        key id;

        leaf id {
          type uint32;
          description
            "Event identifier -  purely internal value.";
        }
        leaf level {
          type level-number;
          description
            "IS-IS level number for LSP";
        }
        container lsp {
          leaf lsp {
            type lsp-id;
            description
              "LSPID of the LSP.";
          }
          leaf sequence {
            type uint32;
            description
              "Sequence number of the LSP.";
          }
          description
            "LSP identification container - either the received
             LSP or the locally generated LSP.";
        }

        leaf received-timestamp {
          type yang:timestamp;
          description
            "This is the timestamp when the LSA was received.
             In case of local LSA update, the timestamp refers
             to the LSA origination time.";
        }

        leaf reason {
          type identityref {
            base lsp-log-reason;
          }
          description "Type of LSP change.";
        }

        description
          "List of LSP events - implemented as a
           wrapping buffer.";
      }

      description
        "This container lists the LSP log.
         Local LSP modifications are also included
         in the list.";

    } description "Grouping for LSP log.";
  }

  /* Groupings for the LSDB description */

  /* Unknown TLV and subTLV description */
  grouping tlv {
    description
      "Type-Length-Value (TLV)";
    leaf type {
      type uint16;
      description "TLV type.";
    }
    leaf length {
      type uint16;
      description "TLV length (octets).";
    }
    leaf value {
      type yang:hex-string;
      description "TLV value.";
    }
  }

  grouping unknown-tlvs {
    description
      "Unknown TLVs grouping - Used for unknown TLVs or
       unknown sub-TLVs.";
    container unknown-tlvs {
      description "All unknown TLVs.";
      list unknown-tlv {
        description "Unknown TLV.";
        uses tlv;
      }
    }
  }

  /* TLVs and subTLVs for prefixes */

  grouping prefix-reachability-attributes {
    description
      "Grouping for extended reachability attributes of an
       IPv4 or IPv6 prefix.";

    leaf external-prefix-flag {
      type boolean;
      description "External prefix flag.";
    }
    leaf readvertisement-flag {
      type boolean;
      description "Readvertisement flag.";
    }
    leaf node-flag {
      type boolean;
      description "Node flag.";
    }
  }

  grouping prefix-ipv4-source-router-id {
    description
      "Grouping for the IPv4 source router ID of a prefix
       advertisement.";

    leaf ipv4-source-router-id {
      type inet:ipv4-address;
      description "IPv4 Source router ID address.";
    }
  }

  grouping prefix-ipv6-source-router-id {
    description
      "Grouping for the IPv6 source router ID of a prefix
       advertisement.";

    leaf ipv6-source-router-id {
      type inet:ipv6-address;
      description "IPv6 Source router ID address.";
    }
  }

  grouping prefix-attributes-extension {
    description "Prefix extended attributes.";

    uses prefix-reachability-attributes;
    uses prefix-ipv4-source-router-id;
    uses prefix-ipv6-source-router-id;
  }

  grouping prefix-ipv4-std {
    description
      "Grouping for attributes of an IPv4 standard prefix.";
    leaf up-down {
      type boolean;
      description "Value of up/down bit.";
    }
    leaf i-e {
      type boolean;
      description "Value of I/E bit.";
    }
    leaf ip-prefix {
      type inet:ipv4-address;
      description "IPv4 prefix address";
    }
    leaf prefix-len {
      type uint8;
      description "IPv4 prefix length (in bits)";
    }
    leaf default-metric {
      type std-metric;
      description "Default IS-IS metric for IPv4 prefix";
    }
    container delay-metric {
      leaf metric {
        type std-metric;
        description "IS-IS delay metric for IPv4 prefix";
      }
      leaf supported {
        type boolean;
        default "false";
        description
          "Indicates whether IS-IS delay metric is supported.";
      }
      description "IS-IS delay metric container.";
    }
    container expense-metric {
      leaf metric {
        type std-metric;
        description "IS-IS expense metric for IPv4 prefix";
      }
      leaf supported {
        type boolean;
        default "false";
        description
          "Indicates whether IS-IS delay metric is supported.";
      }
      description "IS-IS expense metric container.";
    }
    container error-metric {
      leaf metric {
        type std-metric;
        description
          "This leaf describes the IS-IS error metric value";
      }
      leaf supported {
        type boolean;
        default "false";
        description "IS-IS error metric for IPv4 prefix";
      }
      description "IS-IS error metric container.";
    }
  }

  grouping prefix-ipv4-extended {
    description
      "Grouping for attributes of an IPv4 extended prefix.";
    leaf up-down {
      type boolean;
      description  "Value of up/down bit.";
    }
    leaf ip-prefix {
      type inet:ipv4-address;
      description "IPv4 prefix address";
    }
    leaf prefix-len {
      type uint8;
      description "IPv4 prefix length (in bits)";
    }

    leaf metric {
      type wide-metric;
      description "IS-IS wide metric value";
    }
    leaf-list tag {
      type uint32;
      description
        "List of 32-bit tags associated with the IPv4 prefix.";
    }
    leaf-list tag64 {
      type uint64;
      description
        "List of 32-bit tags associated with the IPv4 prefix.";
    }
    uses prefix-attributes-extension;
  }

  grouping prefix-ipv6-extended {
    description "Grouping for attributes of an IPv6 prefix.";
    leaf up-down {
      type boolean;
      description "Value of up/down bit.";
    }
    leaf ip-prefix {
      type inet:ipv6-address;
      description "IPv6 prefix address";
    }
    leaf prefix-len {
      type uint8;
      description  "IPv4 prefix length (in bits)";
    }
    leaf metric {
      type wide-metric;
      description  "IS-IS wide metric value";
    }
    leaf-list tag {
      type uint32;
      description
        "List of 32-bit tags associated with the IPv4 prefix.";
    }
    leaf-list tag64 {
      type uint64;
      description
        "List of 32-bit tags associated with the IPv4 prefix.";
    }
    uses prefix-attributes-extension;
  }

        /* TLVs and subTLVs for neighbors */

        grouping neighbor-link-attributes {
                description
                        "Grouping for link attributes as defined
                        in RFC5029";
                leaf link-attributes-flags {
                        type uint16;
                        description
                                "Flags for the link attributes";
                }
        }
        grouping neighbor-gmpls-extensions {
                description
                        "Grouping for GMPLS attributes of a neighbor as 
defined
                        in RFC5307";
                leaf link-local-id {
                        type uint32;
                        description
                                "Local identifier of the link.";
                }
                leaf remote-local-id {
                        type uint32;
                        description
                                "Remote identifier of the link.";
                }
                leaf protection-capability {
                        type uint8;
                        description
                                "Describes the protection capabilities
                                of the link. This is the value of the
                                first octet of the sub-TLV type 20 
value.";
                }
                container interface-switching-capability {
                        description
                                "Interface switching capabilities of 
the link.";
                        leaf switching-capability {
                                type uint8;
                                description
                                        "Switching capability of the 
link.";
                        }
                        leaf encoding {
                                type uint8;
                                description
                                        "Type of encoding of the LSP 
being used.";
                        }
                        container max-lsp-bandwidths {
                                description "Per priority max LSP 
bandwidths.";
                                list max-lsp-bandwidth {
                                        leaf priority {
                                                type uint8 {
                                                        range "0 .. 7";
                                                }
                                                description "Priority 
from 0 to 7.";
                                        }
                                        leaf bandwidth {
                                                type 
rt-types:bandwidth-ieee-float32;
                                                description "max LSP 
bandwidth.";
                                        }
                                        description
                                                "List of max LSP 
bandwidths for different
                                                 priorities.";
                                }
                        }
                        container tdm-specific {
                                when "switching-capability = 100";
                                description
                                        "Switching Capability-specific 
information applicable
                                        when switching type is TDM.";

                                leaf minimum-lsp-bandwidth {
                                        type 
rt-types:bandwidth-ieee-float32;
                                        description "minimum LSP 
bandwidth.";
                                }
                                leaf indication {
                                        type uint8;
                                        description
                                                "The indication whether 
the interface supports Standard or Arbitrary
                                                SONET/SDH.";
                                }
                        }
                        container psc-specific {
                                when "switching-capability >= 1 and 
switching-capability <= 4";
                                description
                                        "Switching Capability-specific 
information applicable
                                        when switching type is 
PSC1,PSC2,PSC3 or PSC4.";

                                leaf minimum-lsp-bandwidth {
                                        type 
rt-types:bandwidth-ieee-float32;
                                        description "minimum LSP 
bandwidth.";
                                }
                                leaf mtu {
                                        type uint16;
                                        units bytes;
                                        description
                                                "Interface MTU";
                                }
                        }
                }
        }

        grouping neighbor-extended-te-extensions {
                description
                        "Grouping for TE attributes of a neighbor as 
defined
                        in RFC7810";
                container unidirectional-link-delay {
                        description
                                "Container for the average delay
                                from the local neighbor to the remote 
one.";
                        leaf flags {
                                type bits {
                                        bit A {
                                                position 7;
                                                description
                                                        "The A bit 
represents the Anomalous (A) bit.
                                                        The A bit is 
set when the measured value of
                                                        this parameter 
exceeds its configured
                                                        maximum 
threshold.
                                                        The A bit is 
cleared when the measured value
                                                        falls below its 
configured reuse threshold.
                                                        If the A bit is 
clear,
                                                        the value 
represents steady-state link performance.";
                                        }
                                }
                                description
                                        "Flags.";
                        }
                        leaf value {
                                type uint32;
                                units usec;
                                description
                                        "Delay value expressed in 
microseconds.";
                        }
                }
                container min-max-unidirectional-link-delay {
                        description
                                "Container for the min and max delay
                                from the local neighbor to the remote 
one.";
                        leaf flags {
                                type bits {
                                        bit A {
                                                position 7;
                                                description
                                                        "The A bit 
represents the Anomalous (A) bit.
                                                        The A bit is 
set when the measured value of
                                                        this parameter 
exceeds its configured
                                                        maximum 
threshold.
                                                        The A bit is 
cleared when the measured value
                                                        falls below its 
configured reuse threshold.
                                                        If the A bit is 
clear,
                                                        the value 
represents steady-state link performance.";
                                        }
                                }
                                description
                                        "Flags.";
                        }
                        leaf min-value {
                                type uint32;
                                units usec;
                                description
                                        "Minimum delay value expressed 
in microseconds.";
                        }
                        leaf max-value {
                                type uint32;
                                units usec;
                                description
                                        "Maximum delay value expressed 
in microseconds.";
                        }
                }
                container unidirectional-link-delay-variation {
                        description
                                "Container for the average delay 
variation
                                from the local neighbor to the remote 
one.";
                        leaf value {
                                type uint32;
                                units usec;
                                description
                                        "Delay variation value 
expressed in microseconds.";
                        }
                }
                container unidirectional-link-loss{
                        description
                                "Container for the packet loss
                                from the local neighbor to the remote 
one.";
                        leaf flags {
                                type bits {
                                        bit A {
                                                position 7;
                                                description
                                                        "The A bit 
represents the Anomalous (A) bit.
                                                        The A bit is 
set when the measured value of
                                                        this parameter 
exceeds its configured
                                                        maximum 
threshold.
                                                        The A bit is 
cleared when the measured value
                                                        falls below its 
configured reuse threshold.
                                                        If the A bit is 
clear,
                                                        the value 
represents steady-state link performance.";
                                        }
                                }
                                description
                                        "Flags.";
                        }
                        leaf value {
                                type uint32;
                                units percent;
                                description
                                        "Link packet loss expressed as 
a percentage
                                        of the total traffic sent over 
a configurable interval.";
                        }
                }
                container unidirectional-link-residual-bandwidth {
                        description
                                "Container for the residual bandwidth
                                from the local neighbor to the remote 
one.";
                        leaf value {
                                type rt-types:bandwidth-ieee-float32;
                                units Bps;
                                description
                                        "Residual bandwidth.";
                        }
                }
                container unidirectional-link-available-bandwidth {
                        description
                                "Container for the available bandwidth
                                from the local neighbor to the remote 
one.";
                        leaf value {
                                type rt-types:bandwidth-ieee-float32;
                                units Bps;
                                description
                                        "Available bandwidth.";
                        }
                }
                container unidirectional-link-utilized-bandwidth {
                        description
                                "Container for the utilized bandwidth
                                from the local neighbor to the remote 
one.";
                        leaf value {
                                type rt-types:bandwidth-ieee-float32;
                                units Bps;
                                description
                                        "Utilized bandwidth.";
                        }
                }
        }

        grouping neighbor-te-extensions {
                description
                        "Grouping for TE attributes of a neighbor as 
defined
                        in RFC5305";
                leaf admin-group {
                        type uint32;
                        description
                                "Administrative group/Resource 
Class/Color.";
                }
                container local-if-ipv4-addrs {
                        description "All local interface IPv4 
addresses.";
                        leaf-list local-if-ipv4-addr {
                                type inet:ipv4-address;
                                description
                                        "List of local interface IPv4 
addresses.";
                        }
                }
                container remote-if-ipv4-addrs {
                        description "All remote interface IPv4 
addresses.";
                        leaf-list remote-if-ipv4-addr {
                                type inet:ipv4-address;
                                description
                                        "List of remote interface IPv4 
addresses.";
                        }
                }
                leaf te-metric {
                        type uint32;
                        description "TE metric.";
                }
                leaf max-bandwidth {
                        type rt-types:bandwidth-ieee-float32;
                        description "Maximum bandwidth.";
                }
                leaf max-reservable-bandwidth {
                        type rt-types:bandwidth-ieee-float32;
                        description "Maximum reservable bandwidth.";
                }
                container unreserved-bandwidths {
                        description "All unreserved bandwidths.";
                        list unreserved-bandwidth {
                                leaf priority {
                                        type uint8 {
                                                range "0 .. 7";
                                        }
                                        description "Priority from 0 to 
7.";
                                }
                                leaf unreserved-bandwidth {
                                        type 
rt-types:bandwidth-ieee-float32;
                                        description "Unreserved 
bandwidth.";
                                }
                                description
                                        "List of unreserved bandwidths 
for different
                                         priorities.";
                        }
                }
        }

  grouping neighbor-extended {
    description
     "Grouping for attributes of an IS-IS extended neighbor.";
    leaf neighbor-id {
      type extended-system-id;
      description "System-id of the extended neighbor.";
    }
   container instances {
      description "List of all adjacencies between the local
                   system and the neighbor system-id.";
      list instance {
        key id;

        leaf id {
          type uint32;
          description "Unique identifier of an instance of a
                       particular neighbor.";
        }
        leaf metric {
          type wide-metric;
          description "IS-IS wide metric for extended neighbor";
        }
        uses neighbor-gmpls-extensions;
        uses neighbor-te-extensions;
        uses neighbor-extended-te-extensions;
        uses neighbor-link-attributes;
        uses unknown-tlvs;
        description "Instance of a particular adjacency.";
      }
    }
  }

  grouping neighbor {
    description  "IS-IS standard neighbor grouping.";
    leaf neighbor-id {
      type extended-system-id;
      description "IS-IS neighbor system-id";
    }
   container instances {
      description "List of all adjacencies between the local
                   system and the neighbor system-id.";
      list instance {
        key id;
        leaf id {
          type uint32;
          description "Unique identifier of an instance of a
                       particular neighbor.";
        }
        leaf i-e {
          type boolean;
          description
            "Internal or External (I/E) Metric bit value";
        }
        leaf default-metric {
          type std-metric;
          description "IS-IS default metric value";
        }
        container delay-metric {
          leaf metric {
            type std-metric;
            description "IS-IS delay metric value";
          }
          leaf supported {
            type boolean;
            default "false";
            description "IS-IS delay metric supported";
          }
          description "IS-IS delay metric container";
        }
        container expense-metric {
          leaf metric {
            type std-metric;
            description "IS-IS delay expense metric value";
          }
          leaf supported {
            type boolean;
            default "false";
            description "IS-IS delay expense metric supported";
          }
          description "IS-IS delay expense metric container";
        }
        container error-metric {
          leaf metric {
            type std-metric;
            description "IS-IS error metric value";
          }
          leaf supported {
            type boolean;
            default "false";
            description "IS-IS error metric supported";
          }
          description "IS-IS error metric container";
        }
        description "Instance of a particular adjacency.";
      }
    }
  }

  /* Top level TLVs */

  grouping tlv132-ipv4-addresses {
    leaf-list ipv4-addresses {
      type inet:ipv4-address;
      description
        "List of IPv4 addresses of the IS-IS node - IS-IS
         reference is TLV 132.";
    }
    description "Grouping for TLV132.";
  }
  grouping tlv232-ipv6-addresses {
    leaf-list ipv6-addresses {
      type inet:ipv6-address;
      description
        "List of IPv6 addresses of the IS-IS node - IS-IS
         reference is TLV 232.";
    }
    description "Grouping for TLV232.";
  }
  grouping tlv134-ipv4-te-rid {
    leaf ipv4-te-routerid {
      type inet:ipv4-address;
      description
        "IPv4 Traffic Engineering router ID of the IS-IS node -
         IS-IS reference is TLV 134.";
    }
    description "Grouping for TLV134.";
  }
  grouping tlv140-ipv6-te-rid {
    leaf ipv6-te-routerid {
      type inet:ipv6-address;
      description
        "IPv6 Traffic Engineering router ID of the IS-IS node -
         IS-IS reference is TLV 140.";
    }
    description "Grouping for TLV140.";
  }
  grouping tlv129-protocols {
    leaf-list protocol-supported {
      type uint8;
      description
      "List of supported protocols of the IS-IS node -
       IS-IS reference is TLV 129.";
    }
    description "Grouping for TLV129.";
  }
  grouping tlv137-hostname {
    leaf dynamic-hostname {
      type string;
      description
        "Host Name of the IS-IS node - IS-IS reference
         is TLV 137.";
    }
    description "Grouping for TLV137.";
  }
  grouping tlv10-authentication {
    container authentication {
      leaf authentication-type {
        type string;
        description
          "Authentication type to be used with IS-IS node.";
      }
      leaf authentication-key {
        type string;
        description
          "Authentication keyto be used. For security reasons,
           the authentication key MUST NOT be presented in
           plaintext format. It is recommended to use an MD5
           hash to present the authentication-key.";
      }
      description
        "IS-IS node authentication information container -
         IS-IS reference is TLV 10.";
    }
    description "Grouping for TLV10.";
  }
  grouping tlv229-mt {
    container mt-entries {
      list topology {
        description
          "List of topologies supported";

        leaf mt-id {
          type uint16 {
            range "0 .. 4095";
          }
          description
            "Multi-Topology identifier of topology.";
        }

        leaf attributes {
          type bits {
            bit overload {
              description
                "If set, the originator is overloaded,
                 and must be avoided in path calculation.";
            }
            bit attached {
              description
                "If set, the originator is attached to
                another area using the referred metric.";
            }
          }
          description
            "Attributes of the LSP for the associated
             topology.";
        }
      }
      description
        "IS-IS node topology information container -
         IS-IS reference is TLV 229.";
    }
    description "Grouping for TLV229.";
  }

  grouping tlv242-router-capabilities {
    container router-capabilities {
      list router-capability {
          leaf flags {
            type bits {
              bit flooding {
                position 0;
                description
                  "If the S bit is set, the IS-IS Router CAPABILITY
                   TLV MUST be flooded across the entire routing
                   domain. If the S bit is clear, the TLV MUST NOT
                   be leaked between levels. This bit MUST NOT
                    be altered during the TLV leaking.";
              }
              bit down {
                position 1;
                description
                  "When the IS-IS Router CAPABILITY TLV is leaked
                   from level-2 to level-1, the D bit MUST be set.
                   Otherwise, this bit MUST be clear.  IS-IS Router
                   capability TLVs with the D bit set MUST NOT be
                   leaked from level-1 to level-2 in to prevent
                   TLV looping.";
              }
            }
            description "Router Capability Flags";
          }
          container node-tags {
            if-feature node-tag;
            list node-tag {
              leaf tag {
                type uint32;
                description "Node tag value.";
              }
              description "List of tags.";
            }
            description "Container for node admin tags";
          }

          uses unknown-tlvs;

          leaf binary {
            type binary;
            description
              "Binary encoding of the IS-IS node capabilities";
          }
          description
            "IS-IS node capabilities. This list element may
             be extended with detailed information -  IS-IS
             reference is TLV 242.";
        }
        description "List of router capability TLVs.";
      }
      description "Grouping for TLV242.";
  }

  grouping tlv138-srlg {
    description
      "Grouping for TLV138.";
    container links-srlgs {
      list links {
        leaf neighbor-id {
          type extended-system-id;
          description "System-id of the extended neighbor.";
        }
        leaf flags {
          type uint8;
          description
            "Flags associated with the link.";
        }
        leaf link-local-id {
          type union {
            type inet:ip-address;
            type uint32;
          }
          description
            "Local identifier of the link.
            It could be an IPv4 address or a local identifier.";
        }
        leaf link-remote-id {
          type union {
            type inet:ip-address;
            type uint32;
          }
          description
            "Remote identifier of the link.
            It could be an IPv4 address or a remotely learned
            identifier.";
        }
        container srlgs {
          description "List of SRLGs.";
          leaf-list srlg {
            type uint32;
            description
              "SRLG value of the link.";
          }
        }
        description
          "SRLG attribute of a link.";
      }
      description
        "List of links with SRLGs";
    }
  }

  /* Grouping for LSDB description */

  grouping lsp-entry {
    description "IS-IS LSP database entry groupting";

    leaf decoded-completed {
      type boolean;
      description "IS-IS LSP body fully decoded.";
    }
    leaf raw-data {
      type yang:hex-string;
      description
        "The hexadecial representation of the complete LSP in
         network-byte order (NBO) as received or originated.";
    }
    leaf lsp-id {
      type lsp-id;
      description "LSP ID of the LSP";
    }
    leaf checksum {
      type uint16;
      description "LSP checksum";
    }
    leaf remaining-lifetime {
      type uint16;
      units "seconds";
      description
        "Remaining lifetime (in seconds) until LSP expiration.";
    }
    leaf sequence {
      type uint32;
      description
        "This leaf describes the sequence number of the LSP.";
    }
    leaf attributes {
      type bits {
        bit partitioned {
          description "Originator partition repair supported";
        }
        bit attached-error {
          description
            "If set, the originator is attached to
             another area using the referred metric.";
        }
        bit attached-expense {
          description
            "If set, the originator is attached to
             another area using the referred metric.";
        }
        bit attached-delay {
          description
            "If set, the originator is attached to
             another area using the referred metric.";
        }
        bit attached-default {
          description
            "If set, the originator is attached to
             another area using the referred metric.";
        }
        bit overload {
          description
            "If set, the originator is overloaded,
             and must be avoided in path calculation.";
        }
      }
      description "LSP attributes";
    }

    uses tlv132-ipv4-addresses;
    uses tlv232-ipv6-addresses;
    uses tlv134-ipv4-te-rid;
    uses tlv140-ipv6-te-rid;
    uses tlv129-protocols;
    uses tlv137-hostname;
    uses tlv10-authentication;
    uses tlv229-mt;
    uses tlv242-router-capabilities;
    uses tlv138-srlg;
    uses unknown-tlvs;

    container is-neighbor {
      list neighbor {
        key neighbor-id;

        uses neighbor;
        description "List of neighbors.";
      }
      description
        "Standard IS neighbors container - IS-IS reference is
         TLV 2.";
    }

    container extended-is-neighbor {
      list neighbor {
        key neighbor-id;

        uses neighbor-extended;
        description
          "List of extended IS neighbors";
      }
      description
        "Standard IS extended neighbors container - IS-IS
         reference is TLV 22";
    }

    container ipv4-internal-reachability {
      list prefixes {
        uses prefix-ipv4-std;
        description "List of prefixes.";
      }
      description
      "IPv4 internal reachability information container - IS-IS
       reference is TLV 128.";
    }

    container ipv4-external-reachability {
      list prefixes {
        uses prefix-ipv4-std;
        description "List of prefixes.";
      }
      description
        "IPv4 external reachability information container -
         IS-IS reference is TLV 130.";
    }

    container extended-ipv4-reachability {
      list prefixes {
        uses prefix-ipv4-extended;
        uses unknown-tlvs;
        description "List of prefixes.";
      }
      description
        "IPv4 extended reachability information container -
         IS-IS reference is TLV 135.";
    }

    container mt-is-neighbor {
      list neighbor {
        leaf mt-id {
          type uint16 {
            range "0 .. 4095";
          }
          description "Multi-topology (MT) identifier";
        }
        uses neighbor-extended;
        description "List of neighbors.";
      }
      description
        "IS-IS multi-topology neighbor container - IS-IS
         reference is TLV 223.";
    }

    container mt-extended-ipv4-reachability {
      list prefixes {
        leaf mt-id {
          type uint16 {
            range "0 .. 4095";
          }
          description  "Multi-topology (MT) identifier";
        }
        uses prefix-ipv4-extended;
        uses unknown-tlvs;
        description "List of extended prefixes.";
      }
      description
        "IPv4 multi-topolgy (MT) extended reachability
         information container - IS-IS reference is TLV 235.";
    }

    container mt-ipv6-reachability {
      list prefixes {
        leaf MT-ID {
          type uint16 {
            range "0 .. 4095";
          }
          description "Multi-topology (MT) identifier";
        }
        uses prefix-ipv6-extended;
        uses unknown-tlvs;
        description "List of IPv6 extended prefixes.";
      }
      description
        "IPv6 multi-topolgy (MT) extended reachability
         information container - IS-IS reference is TLV 237.";
    }

    container ipv6-reachability {
      list prefixes {
        uses prefix-ipv6-extended;
        uses unknown-tlvs;
        description "List of IPv6 prefixes.";
      }
      description
        "IPv6 reachability information container - IS-IS
         reference is TLV 236.";
    }
  }

  grouping lsdb {
    description "Link State Database (LSDB) grouping";
    container database {
      config false;
      list level-db {
        key level;
        leaf level {
          type level-number;
          description "LSDB level number (1 or 2)";
        }
        list lsp {
          key lsp-id;
          uses lsp-entry;
          description "List of LSPs in LSDB";
        }
        description "LSP list for LSDB level container";
      }
      description "IS-IS Link State database container";
    }
  }

  /* Augmentations */

  augment "/rt:routing/"
    +"rt:ribs/rt:rib/rt:routes/rt:route" {
    when "rt:source-protocol = 'isis:isis'" {
      description "IS-IS-specific route attributes.";
    }
    uses route-content;
    description
      "This augments route object in RIB with IS-IS-specific
       attributes.";
  }

  augment "/if:interfaces/if:interface" {
    leaf clns-mtu {
      type uint16;
      description "CLNS MTU of the interface";
    }
    description "ISO specific interface parameters.";
  }

  augment "/rt:routing/rt:control-plane-protocols/"
    +"rt:control-plane-protocol" {
    when "rt:type = 'isis:isis'" {
      description
        "This augment is only valid when routing protocol
         instance type is 'isis'";
    }
    description
      "This augments a routing protocol instance with IS-IS
       specific parameters.";
    container isis {
      must "count(area-address) > 0" {
        error-message
          "At least one area-address must be configured.";
        description
          "Enforce configuration of at least one area.";
      }

      uses instance-config;
      uses instance-state;

      container topologies {
        if-feature multi-topology;
        list topology {
          key "name";
          leaf enable {
            type boolean;
            description "Topology enable configuration";
          }
          leaf name {
            type leafref {
              path "../../../../../../rt:ribs/rt:rib/rt:name";
            }
            description
              "Routing Information Base (RIB) corresponding
               to topology.";
          }

          uses multi-topology-config;

          description "List of topologies";
        }
        description "Multi-topology container";
      }
      container interfaces {
        list interface {
          key "name";
          leaf name {
            type if:interface-ref;

            description
              "Reference to the interface within
               the routing-instance.";
          }
          uses interface-config;
          container topologies {
            if-feature multi-topology;
            list topology {
              key name;

              leaf name {
                type leafref {
                  path "../../../../../../../../"+
                    "rt:ribs/rt:rib/rt:name";
                }

                description
                  "Routing Information Base (RIB) corresponding
                   to topology.";
              }
              uses multi-topology-interface-config;
              description "List of interface topologies";
            }
            description "Multi-topology container";
          }
          description "List of IS-IS interfaces.";
        }
        description
          "IS-IS interface specific configuration container";
      }

      description
        "IS-IS configuration/state top-level container";
    }
  }

  /* RPC methods */

  rpc clear-adjacency {
    description
      "This RPC request clears a particular set of IS-IS
       adjacencies. If the operation fails due to an internal
       reason, then the error-tag and error-app-tag should be
       set indicating the reason for the failure.";
    input {

      leaf routing-protocol-instance-name {
        type leafref {
          path "/rt:routing/rt:control-plane-protocols/"
             + "rt:control-plane-protocol/rt:name";
        }
        mandatory "true";
        description
          "Name of the IS-IS protocol instance whose IS-IS
           information is being queried.

           If the corresponding IS-IS instance doesn't exist,
           then the operation will fail with an error-tag of
           'data-missing' and an error-app-tag of
           'routing-protocol-instance-not-found'.";
      }
      leaf level {
        type level;
        description
          "IS-IS level of the adjacency to be cleared. If the
           IS-IS level is level-1-2, both level 1 and level 2
           adjacencies would be cleared.

           If the value provided is different from the one
           authorized in the enum type, then the operation
           SHALL fail with an error-tag of 'data-missing' and
           an error-app-tag of 'bad-isis-level'.";
      }
      leaf interface {
        type if:interface-ref;
        description
          "IS-IS interface name.

           If the corresponding IS-IS interface doesn't exist,
           then the operation SHALL fail with an error-tag of
           'data-missing' and an error-app-tag of
           'isis-interface-not-found'.";
      }
    }
  }

  rpc clear-database {
    description
      "This RPC request clears a particular  IS-IS database. If
       the operation fails for an IS-IS internal reason, then
       the error-tag and error-app-tag should be set
       indicating the reason for the failure.";
    input {
      leaf routing-protocol-instance-name {
        type leafref {
          path "/rt:routing/rt:control-plane-protocols/"
             + "rt:control-plane-protocol/rt:name";
        }
        mandatory "true";
        description
          "Name of the IS-IS protocol instance whose IS-IS
           database(s) is/are being cleared.

           If the corresponding IS-IS instance doesn't exist,
           then the operation will fail with an error-tag of
           'data-missing' and an error-app-tag of
           'routing-protocol-instance-not-found'.";
      }
      leaf level {
        type level;
        description
          "IS-IS level of the adjacency to be cleared. If the
           IS-IS level is level-1-2, both level 1 and level 2
           databases would be cleared.

           If the value provided is different from the one
           authorized in the enum type, then the operation
           SHALL fail with an error-tag of 'data-missing' and
           an error-app-tag of 'bad-isis-level'.";
      }
    }
  }

  /* Notifications */

  notification database-overload {
    uses notification-instance-hdr;

    leaf overload {
      type enumeration {
        enum off {
          description
            "Indicates IS-IS instance has left overload state";
        }
        enum on {
          description
            "Indicates IS-IS instance has entered overload state";
        }

      }
      description "New overload state of the IS-IS instance";
    }
    description
      "This notification is sent when an IS-IS instance
       overload state changes.";
  }

  notification lsp-too-large {
    uses notification-instance-hdr;
    uses notification-interface-hdr;

    leaf pdu-size {
      type uint32;
      description "Size of the LSP PDU";
    }
    leaf lsp-id {
      type lsp-id;
      description "LSP ID";
    }
    description
      "This notification is sent when we attempt to propagate
       an LSP that is larger than the dataLinkBlockSize for the
       circuit.  The notification generation must be throttled
       with at least 5 seconds betweeen successive
       notifications.";
  }

  notification if-state-change {
    uses notification-instance-hdr;
    uses notification-interface-hdr;

    leaf state {
      type if-state-type;
      description "Interface state.";
    }
    description
      "This notification is sent when an interface
       state change is detected.";
  }

  notification corrupted-lsp-detected {
    uses notification-instance-hdr;
    leaf lsp-id {
      type lsp-id;
      description "LSP ID";
    }
    description
      "This notification is sent when we find that
       an LSP that was stored in memory has become
       corrupted.";
  }

  notification attempt-to-exceed-max-sequence {
    uses notification-instance-hdr;
    leaf lsp-id {
      type lsp-id;
      description "LSP ID";
    }
    description
      "This notification is sent when the system
       wraps the 32-bit sequence counter of an LSP.";
  }

  notification id-len-mismatch {
    uses notification-instance-hdr;
    uses notification-interface-hdr;

    leaf pdu-field-len {
      type uint8;
      description "Size of the ID length in the received PDU";
    }
    leaf raw-pdu {
      type binary;
      description "Received raw PDU.";
    }
    description
      "This notification is sent when we receive a PDU
       with a different value for the System ID length.
       The notification generation must be throttled
       with at least 5 seconds betweeen successive
       notifications.";
  }

  notification max-area-addresses-mismatch {
    uses notification-instance-hdr;
    uses notification-interface-hdr;

    leaf max-area-addresses {
      type uint8;
      description "Received number of supported areas";
    }
    leaf raw-pdu {
      type binary;
      description "Received raw PDU.";
    }
    description
      "This notification is sent when we receive a PDU
       with a different value for the Maximum Area Addresses.
       The notification generation must be throttled
       with at least 5 seconds betweeen successive
       notifications.";
  }

  notification own-lsp-purge {
    uses notification-instance-hdr;
    uses notification-interface-hdr;
    leaf lsp-id {
      type lsp-id;
      description "LSP ID";
    }
    description
      "This notification is sent when the system receives
       a PDU with its own system ID and zero age.";
  }

  notification sequence-number-skipped {
    uses notification-instance-hdr;
    uses notification-interface-hdr;
    leaf lsp-id {
      type lsp-id;
      description "LSP ID";
    }
    description
      "This notification is sent when the system receives a
       PDU with its own system ID and different contents. The
       system has to reoriginate the LSP with a higher sequence
       number.";
  }

  notification authentication-type-failure {
    uses notification-instance-hdr;
    uses notification-interface-hdr;
    leaf raw-pdu {
      type binary;
      description "Received raw PDU.";
    }
    description
      "This notification is sent when the system receives a
       PDU with the wrong authentication type field.
       The notification generation must be throttled
       with at least 5 seconds betweeen successive
       notifications.";
  }

  notification authentication-failure {
    uses notification-instance-hdr;
    uses notification-interface-hdr;
    leaf raw-pdu {
      type binary;
      description "Received raw PDU.";
    }
    description
      "This notification is sent when the system receives
       a PDU with the wrong authentication information.
       The notification generation must be throttled with
       with at least 5 seconds betweeen successive
       notifications.";
  }

  notification version-skew {
    uses notification-instance-hdr;
    uses notification-interface-hdr;
    leaf protocol-version {
      type uint8;
      description "Protocol version received in the PDU.";
    }
    leaf raw-pdu {
      type binary;
      description "Received raw PDU.";
    }
    description
      "This notification is sent when the system receives a
       PDU with a different protocol version number.
       The notification generation must be throttled
       with at least 5 seconds betweeen successive
       notifications.";
  }

  notification area-mismatch {
    uses notification-instance-hdr;
    uses notification-interface-hdr;
    leaf raw-pdu {
      type binary;
      description "Received raw PDU.";
    }
    description
      "This notification is sent when the system receives a
       Hello PDU from an IS that does not share any area
       address. The notification generation must be throttled
       with at least 5 seconds betweeen successive
       notifications.";
  }

  notification rejected-adjacency {
    uses notification-instance-hdr;
    uses notification-interface-hdr;
    leaf raw-pdu {
      type binary;
      description
        "Received raw PDU.";
    }
    leaf reason {
      type string;
      description
        "The system may provide a reason to reject the
         adjacency. If the reason is not available,
         an empty string will be returned.";
    }
    description
      "This notification is sent when the system receives a
       Hello PDU from an IS but does not establish an adjacency
       for some reason. The notification generation must be
       throttled with at least 5 seconds betweeen successive
       notifications.";
  }

  notification protocols-supported-mismatch {
    uses notification-instance-hdr;
    uses notification-interface-hdr;
    leaf raw-pdu {
      type binary;
      description "Received raw PDU.";
    }
    leaf-list protocols {
      type uint8;
      description
        "List of protocols supported by the remote system.";
    }
    description
      "This notification is sent when the system receives a
       non-pseudonode LSP that has no matching protocols
       supported. The notification generation must be throttled
       with at least 5 seconds betweeen successive
       notifications.";
  }

  notification lsp-error-detected {
    uses notification-instance-hdr;
    uses notification-interface-hdr;
    leaf lsp-id {
      type lsp-id;
      description "LSP ID.";
    }
    leaf raw-pdu {
      type binary;
      description "Received raw PDU.";
    }
    leaf error-offset {
      type uint32;
      description
        "If the problem is a malformed TLV, the error-offset
         points to the start of the TLV. If the problem is with
         the LSP header, the error-offset points to the errant
         byte";
    }
    leaf tlv-type {
      type uint8;
      description
        "If the problem is a malformed TLV, the tlv-type is set
         to the type value of the suspicious TLV. Otherwise,
         this leaf is not present.";
    }
    description
      "This notification is sent when the system  receives an
       LSP with a parse error. The notification generation must
       be throttled with at least 5 seconds betweeen successive
       notifications.";
  }

  notification adjacency-state-change {
    uses notification-instance-hdr;
    uses notification-interface-hdr;
    leaf neighbor {
      type string;
      description
        "Name of the neighbor. If the name of the neighbor is
         not available, it is not returned.";
    }
    leaf neighbor-system-id {
      type system-id;
      description "Neighbor system-id";
    }
    leaf state {
      type adj-state-type;

      description "New state of the IS-IS adjacency.";
    }
    leaf reason {
      type string;
      description
        "If the adjacency is going to DOWN,  this leaf provides
         a reason for the adjacency going down. The reason is
         provided as a text. If the adjacency is going to UP, no
         reason is provided.";
    }
    description
      "This notification is sent when an IS-IS adjacency
       moves to Up state or to Down state.";
  }

  notification lsp-received {
    uses notification-instance-hdr;
    uses notification-interface-hdr;

    leaf lsp-id {
      type lsp-id;
      description "LSP ID";
    }
    leaf sequence {
      type uint32;
      description "Sequence number of the received LSP.";
    }
    leaf received-timestamp {
      type yang:timestamp;

      description "Timestamp when the LSP was received.";
    }
    leaf neighbor-system-id {
      type system-id;
      description "Neighbor system-id of LSP sender";
    }
    description
      "This notification is sent when an LSP is received.
       The notification generation must be throttled with at
       least 5 seconds betweeen successive notifications.";
   }

  notification lsp-generation {
    uses notification-instance-hdr;

    leaf lsp-id {
      type lsp-id;
      description "LSP ID";
    }
    leaf sequence {
      type uint32;
      description "Sequence number of the received LSP.";
    }
    leaf send-timestamp {
      type yang:timestamp;

      description "Timestamp when our LSP was regenerated.";
    }
    description
      "This notification is sent when an LSP is regenerated.
       The notification generation must be throttled with at
       least 5 seconds betweeen successive notifications.";
  }
}
