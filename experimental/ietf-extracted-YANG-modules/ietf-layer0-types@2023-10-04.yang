module ietf-layer0-types {
  yang-version 1.1;
  namespace "urn:ietf:params:xml:ns:yang:ietf-layer0-types";
  prefix l0-types;

  organization
    "IETF CCAMP Working Group";
  contact
    "WG Web:  <https://datatracker.ietf.org/wg/ccamp/>
     WG List: <mailto:ccamp@ietf.org>

     Editor:  Dieter Beller
              <mailto:Dieter.Beller@nokia.com>

     Editor:  Sergio Belotti
              <mailto:Sergio.Belotti@nokia.com>

     Editor:  Italo Busi
              <mailto:Italo.Busi@huawei.com>

     Editor:  Haomian Zheng
              <mailto:zhenghaomian@huawei.com>";
  description
    "This module defines Optical Layer 0 types.  This module
     provides groupings that can be applicable to Layer 0
     Fixed Optical Networks (e.g., CWDM (Coarse Wavelength
     Division Multiplexing) and DWDM (Dense Wavelength Division
     Multiplexing)) and flexi-grid optical networks.

     Copyright (c) 2023 IETF Trust and the persons identified
     as authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

// RFC Ed.: replace XXXX with actual RFC number and remove
// this note

// replace the revision date with the module publication date
// the format is (year-month-day)
  revision 2023-10-04 {
    description
      "To be updated";
    reference
      "RFC XXXX: A YANG Data Model for Layer 0 Types";
  }
  revision 2021-08-13 {
    description
      "Initial version";
    reference
      "RFC 9093: A YANG Data Model for Layer 0 Types";
  }

/*
 * Identities
 */

  identity l0-grid-type {
    description
      "Layer 0 grid type";
    reference
      "RFC 6205: Generalized Labels for Lambda-Switch-Capable
      (LSC), Label Switching Routers,

       ITU-T G.694.2 (12/2003): Spectral grids for WDM applications:
       CWDM wavelength grid";
  }

    identity wson-grid-cwdm {
      base l0-grid-type;
      description
        "CWDM grid";
      reference
        "RFC 6205: Generalized Labels for Lambda-Switch-Capable (LSC)
        Label Switching Routers,

        ITU-T G.694.2 (12/2003): Spectral grids for WDM applications:
        CWDM wavelength grid";
    }

    identity wson-grid-dwdm {
      base l0-grid-type;
      description
        "DWDM grid";
      reference
        "RFC 6205: Generalized Labels for Lambda-Switch-Capable
        (LSC), Label Switching Routers,

        ITU-T G.694.1 (10/2020): Spectral grids for WDM applications:
        DWDM frequency grid";
    }

    identity flexi-grid-dwdm {
      base l0-grid-type;
      description
        "Flexi-grid";
      reference
        "RFC 7699: Generalized Labels for the Flexi-Grid in Lambda
        Switch Capable (LSC) Label Switching Routers,

        ITU-T G.694.1 (10/2020): Spectral grids for WDM applications:
        DWDM frequency grid";
    }

  identity cwdm-ch-spc-type {
    description
      "CWDM channel-spacing type";
    reference
      "RFC 6205: Generalized Labels for Lambda-Switch-Capable (LSC)
       Label Switching Routers,

       ITU-T G.694.2 (12/2003): Spectral grids for WDM applications:
       CWDM wavelength grid";
  }

    identity cwdm-20nm {
      base cwdm-ch-spc-type;
      description
        "20nm channel spacing";
    }

  identity dwdm-ch-spc-type {
    description
      "DWDM channel-spacing type";
    reference
      "RFC 6205: Generalized Labels for Lambda-Switch-Capable (LSC)
       Label Switching Routers,

       ITU-T G.694.1 (10/2020): Spectral grids for WDM applications:
       DWDM frequency grid";
  }

    identity dwdm-100ghz {
      base dwdm-ch-spc-type;
      description
        "100 GHz channel spacing";
    }

    identity dwdm-50ghz {
      base dwdm-ch-spc-type;
      description
        "50 GHz channel spacing";
    }
    identity dwdm-25ghz {
      base dwdm-ch-spc-type;
      description
        "25 GHz channel spacing";
    }

    identity dwdm-12p5ghz {
      base dwdm-ch-spc-type;
      description
        "12.5 GHz channel spacing";
    }

  identity flexi-ch-spc-type {
    status deprecated;
    description
      "Flexi-grid channel-spacing type";
  }

    identity flexi-ch-spc-6p25ghz {
      base flexi-ch-spc-type;
      status deprecated;
      description
        "6.25 GHz channel spacing";
    }

  identity flexi-ncfg-type {
    description
      "Flexi-grid Nominal Central Frequency Granularity (NCFG)
      type";
    reference
      "RFC 7699: Generalized Labels for the Flexi-Grid in Lambda
      Switch Capable (LSC) Label Switching Routers,

      ITU-T G.694.1 (10/2020): Spectral grids for WDM applications:
      DWDM frequency grid";
  }

    identity flexi-ncfg-6p25ghz {
      base flexi-ncfg-type;
      description
        "6.25 GHz Nominal Central Frequency Granularity (NCFG)";
    }

  identity flexi-slot-width-granularity {
    description
      "Flexi-grid slot width granularity";
  }

    identity flexi-swg-12p5ghz {
      base flexi-slot-width-granularity;
      description
        "12.5 GHz slot width granularity";
    }

  identity modulation {
    description "base identity for modulation type";
  }

    identity DPSK {
      base modulation;
      description
        "DPSK (Differential Phase Shift Keying) modulation";
    }

    identity QPSK {
      base modulation;
      description
        "QPSK (Quadrature Phase Shift Keying) modulation";
    }

    identity DP-QPSK {
      base modulation;
      description
        "DP-QPSK (Dual Polarization Quadrature
        Phase Shift Keying) modulation";
    }

    identity QAM8 {
      base modulation;
      description
        "8QAM (8 symbols Quadrature Amplitude Modulation)";
    }

    identity DP-QAM8 {
      base modulation;
      description
        "DP-QAM8 (8 symbols Dual Polarization Quadrature Amplitude
        Modulation)";
    }

    identity QAM16 {
      base modulation;
      description
        "QAM16 (16 symbols Quadrature Amplitude Modulation)";
    }

    identity DP-QAM16 {
      base modulation;
      description
        "DP-QAM16 (16 symbols Dual Polarization Quadrature Amplitude
        Modulation)";
    }

    identity QAM32 {
      base modulation;
      description
        "QAM32 (32 symbols Quadrature Amplitude Modulation)";
    }

    identity DP-QAM32 {
      base modulation;
      description
        "DP-QAM32 (32 symbols Dual Polarization Quadrature Amplitude
        Modulation)";
    }

    identity QAM64 {
      base modulation;
      description
        "QAM64 (64 symbols Quadrature Amplitude Modulation)";
    }

    identity DP-QAM64 {
      base modulation;
      description
        "DP-QAM64 (64 symbols Dual Polarization Quadrature Amplitude
        Modulation)";
    }

  identity fec-type {
    description
      "Base identity from which specific FEC
      (Forward Error Correction) type identities are derived.";
  }

    identity g-fec {
      base fec-type;
      description
        "Generic Forward Error Correction (G-FEC).";
      reference
        "ITU-T G.975 v2.0 (10/2000): Forward error correction for
        submarine systems.";
    }

    identity super-fec {
      base fec-type;
      description
        "Super Forward Error Correction (S-FEC).";
      reference
        "ITU-T G.975.1 v1.2 (07/2013): Forward error correction for
        high bit-rate DWDM submarine systems.";
    }

    identity no-fec {
      base fec-type;
      description
        "No FEC";
    }

    identity sc-fec {
      base fec-type;
      description
        "Staircase Forward Error Correction (SC-FEC).";
      reference
        "Annex A of ITU-T G.709.2 v1.1 (09/2020):OTU4 long-reach
        interface.";
    }

    identity o-fec {
      base fec-type;
      description
        "Open Forward Error Correction (O-FEC) which reuses the
        Bose, Chaudhuri and Hocquenghem (BCH) FEC.";
      reference
        "Clause 16.4.4 of ITU-T G.709.3 v2.1 (11/2022): Flexible OTN
        long-reach interfaces;

        Annex E of ITU-T G.709.3 v2.1 (11/2022): Flexible OTN
        long-reach interfaces.";
    }

    identity c-fec {
      base fec-type;
      description
        "Concatenated FEC (C-FEC) that combines an outer Staircase
        Forward Error Correction (SC-FEC) code and an inner
        double-extended SD-FEC (128,119) Hamming code.

        More details are provided in clause 15/G.709.3 where it is
        called DSH instead of concatenated FEC.";
      reference
        "Annex A of ITU-T G.709.2 v1.1 (09/2020):OTU4 long-reach
        interface;

        Annex D of ITU-T G.709.3 v2.1 (11/2022): Flexible OTN
        long-reach interfaces;

        Clause 15 of ITU-T G.709.3 v2.1 (11/2022): Flexible OTN
        long-reach interfaces.";
    }

  identity line-coding {
    description
      "Base identity to defined the bit rate/line coding of optical
      tributary signals.";
    reference
      "Section 7.1.2 of ITU-T G.698.2 v3.0 (11/2018).";
  }

    identity line-coding-NRZ-2p5G {
      base line-coding;
      description
        "The non return to zero (NRZ) bit rate/line coding used by
        the optical tributary signal class NRZ 2.5G";
      reference
        "Section 3.2.6 of ITU-T G.959.1 v8.0 (07/2018).";
    }

    identity line-coding-NRZ-OTU1 {
      base line-coding;
      description
        "The non return to zero (NRZ) bit rate/line coding used by
        the Optical channel Transport Unit order 1 (OTU1) optical
        tributary signals";
      reference
        "Section 7.2.1.2 of ITU-T G.959.1 v8.0 (07/2018).";
    }

    identity line-coding-NRZ-10G {
      description
        "The non return to zero (NRZ) bit rate/line coding used by
        the optical tributary signal class NRZ 10G";
      reference
        "Section 3.2.7 of ITU-T G.959.1 v8.0 (07/2018).";
    }

    identity line-coding-NRZ-OTU2 {
      base line-coding;
      description
        "The non return to zero (NRZ) bit rate/line coding used by
        the Optical channel Transport Unit order 2 (OTU2) optical
        tributary signals";
      reference
        "Section 7.2.1.2 of ITU-T G.959.1 v8.0 (07/2018).";
    }

    identity line-coding-OTL4.4-SC {
      base line-coding;
      description
        "The bit rate/line coding used by optical tributary
        signals carrying a 100G Optical Transport Unit order 4
        (OTU4) with Staircase Forward Error Correction (SC FEC)
        from a group of four Optical Transport Lanes (OTL).";
      reference
        "Section 3.2.1 of ITU-T G.698.2 v3.0 (11/2018).";
    }

    identity line-coding-FOIC1.4-SC {
      base line-coding;
      description
        "The bit rate/line coding used by optical tributary signals
        carrying a FlexO Interface of order C1 with 4 lanes
        (FOIC1.1) with Staircase Forward Error Correction
        (SC FEC).";
      reference
        "Section 3.2.1 of ITU-T G.698.2 v3.0 (11/2018).";
    }

  identity wavelength-assignment {
    description
      "Wavelength selection base";
    reference
      "RFC 7689: Signaling Extensions for Wavelength Switched
      Optical Networks";
  }

    identity first-fit-wavelength-assignment {
      base wavelength-assignment;
      description
        "All the available wavelengths are numbered,
        and this WA (Wavelength Assignment) method chooses
        the available wavelength with the lowest index";
    }

    identity random-wavelength-assignment {
      base wavelength-assignment;
      description
        "This WA method chooses an available
        wavelength randomly";
    }

    identity least-loaded-wavelength-assignment {
      base wavelength-assignment;
      description
        "This WA method selects the wavelength that
        has the largest residual capacity on the most loaded
        link along the route (in multi-fiber networks)";
    }

  identity term-type {
    description
      "Termination type";
    reference
      "ITU-T G.709: Interfaces for the Optical Transport Network";
  }

    identity term-phys {
      base term-type;
      description
        "Physical layer termination";
    }

    identity term-otu {
      base term-type;
      description
        "OTU (Optical Transport Unit) termination";
    }

    identity term-odu {
      base term-type;
      description
        "ODU (Optical Data Unit) termination";
    }

    identity term-opu {
      base term-type;
      description
        "OPU (Optical Payload Unit) termination";
    }

  identity otu-type {
    description
      "Base identity from which specific OTU identities are derived";
    reference
      "ITU-T G.709: Interfaces for the Optical Transport Network";
  }
    identity OTU1 {
      base otu-type;
      description
        "OTU1 (2.66 Gb/s)";
    }

    identity OTU1e {
      base otu-type;
      description
        "OTU1e (11.04 Gb/s)";
    }

    identity OTU1f {
      base otu-type;
      description
        "OTU1f (11.27 Gb/s)";
    }

    identity OTU2 {
      base otu-type;
      description
        "OTU2 (10.70 Gb/s)";
    }

    identity OTU2e {
      base otu-type;
      description
        "OTU2e (11.09 Gb/s)";
    }

    identity OTU2f {
      base otu-type;
      description
        "OTU2f (11.31G)";
    }

    identity OTU3 {
      base otu-type;
      description
        "OTU3 (43.01 Gb/s)";
    }

    identity OTU3e1 {
      base otu-type;
      description
        "OTU3e1 (44.57 Gb/s)";
    }

    identity OTU3e2 {
      base otu-type;
      description
        "OTU3e2 (44.58 Gb/s)";
    }

    identity OTU4 {
      base otu-type;
      description
        "OTU4 (111.80 Gb/s)";
    }

    identity OTUCn {
      base otu-type;
      description
        "OTUCn (n x 105.25 Gb/s)";
    }

  identity type-power-mode {
    description
      "power equalization mode used within the
       OMS and its elements";
  }

    identity power-spectral-density {
      base type-power-mode;
      description
        "all elements must use power spectral density (W/Hz)";
    }

    identity carrier-power {
      base type-power-mode;
      description
        "all elements must use power (dBm)";
    }

  identity operational-mode {
    description
      "Base identity to be used when defining organization/vendor
      specific modes.

      The format of the derived identities has to be defined by the
      organization which is responsible for defining the
      corresponding optical interface specification.";
    reference
      "Section 2.5.2 of RFC YYYY: A YANG Data Model for Optical
      Impairment-aware Topology.";
  }
// RFC Ed.: replace YYYY with actual RFC number and remove
// this note after draft-ietf-ccamp-optical-impairment-topology-yang
// is published as an RFC

/*
 * Typedefs
 */

  typedef dwdm-n {
    type int16;
    description
      "The given value 'N' is used to determine the nominal central
       frequency.

       The nominal central frequency, 'f', is defined by:
         f = 193100.000 GHz + N x channel spacing (measured in GHz),

       where 193100.000 GHz (193.100000 THz) is the ITU-T 'anchor
       frequency' for transmission over the DWDM grid, and where
       'channel spacing' is defined by the dwdm-ch-spc-type.";
    reference
      "RFC6205: Generalized Labels for Lambda-Switch-Capable (LSC)
       Label Switching Routers,

       ITU-T G.694.1 (10/2020): Spectral grids for WDM applications:
       DWDM frequency grid";
  }

  typedef cwdm-n {
    type int16;
    description
      "The given value 'N' is used to determine the nominal central
       wavelength.

       The nominal central wavelength is defined by:
         Wavelength = 1471 nm + N x channel spacing (measured in nm)

       where 1471 nm is the conventional 'anchor wavelength' for
       transmission over the CWDM grid, and where 'channel spacing'
       is defined by the cwdm-ch-spc-type.";
    reference
      "RFC 6205: Generalized Labels for Lambda-Switch-Capable (LSC)
       Label Switching Routers,

       ITU-T G.694.2 (12/2003): Spectral grids for WDM applications:
       CWDM wavelength grid";
  }

  typedef flexi-n {
    type int16;
    description
      "The given value 'N' is used to determine the nominal central
       frequency.

       The nominal central frequency, 'f', is defined by:
         f = 193100.000 GHz + N x NCFG (measured in GHz),

       where 193100.000 GHz (193.100000 THz) is the ITU-T 'anchor
       frequency' for transmission over the DWDM grid, and where
       NCFG is defined by the flexi-ncfg-type, or by the deprecated
       flexi-ch-spc-type.";
    reference
      "RFC 7699: Generalized Labels for the Flexi-Grid in Lambda
      Switch Capable (LSC) Label Switching Routers,

       ITU-T G.694.1 (10/2020): Spectral grids for WDM applications:
       DWDM frequency grid";
  }

  typedef flexi-m {
    type uint16;
    description
      "The given value 'M' is used to determine the slot width.

       A slot width is defined by:
         slot width = M x SWG (measured in GHz),

       where SWG is defined by the flexi-slot-width-granularity.";
    reference
      "RFC 7699: Generalized Labels for the Flexi-Grid in Lambda
      Switch Capable (LSC) Label Switching Routers,

       ITU-T G.694.1 (10/2020): Spectral grids for WDM applications:
       DWDM frequency grid";
  }

  typedef standard-mode {
    type string;
    description
      "Identifies an ITU-T G.698.2 standard application code.

      It MUST be a string with a format that follows the
      nomenclature defined in section 5.3 of ITU-T G.698.2.";
    reference
      "ITU-T G.698.2 (11/2018)";
  }
  typedef organization-identifier {
    type string;
    description
      "vendor/organization identifier that uses a private mode
      out of already defined in G.698.2 ITU-T application-code";
    reference
      "Section 2.5.2 of RFC YYYY: A YANG Data Model for Optical
      Impairment-aware Topology.";
  }
// RFC Ed.: replace YYYY with actual RFC number and remove
// this note after draft-ietf-ccamp-optical-impairment-topology-yang
// is published as an RFC

  typedef operational-mode {
    type identityref {
      base operational-mode;
    }
    description
      "Identifies an organization (e.g., vendor) specific mode.

      The format of these identities has to be defined by the
      organization which is responsible for defining the
      corresponding optical interface specification.";
    reference
      "Section 2.5.2 of RFC YYYY: A YANG Data Model for Optical
      Impairment-aware Topology.";
  }
// RFC Ed.: replace YYYY with actual RFC number and remove
// this note after draft-ietf-ccamp-optical-impairment-topology-yang
// is published as an RFC

  typedef frequency-thz {
    type decimal64 {
      fraction-digits 9;
    }
    units "THz";
    description
      "The DWDM frequency in THz, e.g., 193.112500000";
  }
  typedef frequency-ghz {
    type decimal64 {
      fraction-digits 6;
    }
    units "GHz";
    description
      "The DWDM frequency in GHz, e.g., 193112.500000";
  }

  typedef snr {
    type decimal64 {
      fraction-digits 2;
    }
    units "dB@0.1nm";
    description
      "(Optical) Signal to Noise Ratio measured over 0.1 nm
      resolution bandwidth";
  }

  typedef snr-or-null {
    type union {
      type snr;
      type empty;
    }
    description
      "(Optical) Signal to Noise Ratio measured over 0.1 nm
      resolution bandwidth, when known, or an empty value when
      unknown.";
  }

  typedef fiber-type {
    type enumeration {
      enum G.652 {
      description "G.652 Standard Singlemode Fiber";
      }
      enum G.654 {
        description "G.654 Cutoff Shifted Fiber";
      }
      enum G.653 {
        description "G.653 Dispersion Shifted Fiber";
      }
      enum G.655 {
        description "G.655 Non-Zero Dispersion Shifted Fiber";
      }
      enum G.656 {
        description "G.656 Non-Zero Dispersion for Wideband
               Optical Transport";
      }
      enum G.657 {
        description "G.657 Bend-Insensitive Fiber";
      }
    }
    description
      "ITU-T based fiber-types";
  }

  typedef decimal-2-digits {
    type decimal64 {
      fraction-digits 2;
    }
    description
      "A decimal64 value with two digits.";
  }

  typedef decimal-2-digits-or-null {
    type union {
      type decimal-2-digits;
      type empty;
    }
    description
      "A decimal64 value with two digits, when the value is known or
      an empty value when the value is not known.";
  }

  typedef gain-in-db {
    type decimal-2-digits {
      range "0..max";
    }
    units "dB";
    description
      "The gain in dB.";
  }

  typedef gain-in-db-or-null {
    type union {
      type gain-in-db;
      type empty;
    }
    description
      "The gain in dB, when it is known or an empty
      value when the power gain/loss is not known.";
  }

  typedef loss-in-db {
    type decimal-2-digits {
      range "0..max";
    }
    units "dB";
    description
      "The power attenuation in dB.";
  }

  typedef loss-in-db-or-null {
    type union {
      type loss-in-db;
      type empty;
    }
    description
      "The power attenuation in dB, when it is known or an empty
      value when the loss is not known.";
  }

  typedef power-in-dbm {
    type decimal-2-digits;
    units "dBm";
    description
      "The power in dBm.";
  }

  typedef power-in-dbm-or-null {
    type union {
      type power-in-dbm;
      type empty;
    }
    description
      "The power in dBm, when it is known or an empty value when the
      power is not known.";
  }

  typedef decimal-5-digits {
    type decimal64 {
      fraction-digits 5;
    }
    description
      "A decimal64 value with five digits.";
  }

  typedef decimal-5-digits-or-null {
    type union {
      type decimal-5-digits;
      type empty;
    }
    description
      "A decimal64 value with five digits, when the value is known
      or an empty value when the value is not known.";
  }

  typedef decimal-16-digits {
    type decimal64 {
      fraction-digits 16;
    }
    description
      "A decimal64 value with sixteen digits.";
  }

  typedef decimal-16-digits-or-null {
    type union {
      type decimal-5-digits;
      type empty;
    }
    description
      "A decimal64 value with sixteen digits, when the value is
      known or an empty value when the value is not known.";
  }

/*
 * Groupings
 */
  grouping wdm-label-start-end {
    description
      "The WDM label-start or label-end used to specify DWDM and
       CWDM label range.";

    choice grid-type {
      description
        "Label for fixed & flexi-DWDM or CWDM grid";
      case fixed-dwdm {
        leaf dwdm-n {
          when "derived-from-or-self(../../../grid-type,
                \"wson-grid-dwdm\")" {
            description
              "Valid only when grid type is DWDM.";
          }
          type l0-types:dwdm-n;
          description
            "The given value 'N' is used to determine the
             nominal central frequency.";
          reference
            "RFC 6205: Generalized Labels for Lambda-Switch-Capable
             (LSC) Label Switching Routers";
        }
      }
      case cwdm {
        leaf cwdm-n {
          when "derived-from-or-self(../../../grid-type,
                \"wson-grid-cwdm\")" {
            description
              "Valid only when grid type is CWDM.";
          }
          type l0-types:cwdm-n;
          description
            "The given value 'N' is used to determine the nominal
             central wavelength.";
          reference
            "RFC 6205: Generalized Labels for Lambda-Switch-Capable
             (LSC) Label Switching Routers";
        }
      }
      case flexi-grid {
        uses l0-types:flexi-grid-label-start-end;
      }
    }
    reference
      "RFC 6205: Generalized Labels for Lambda-Switch-Capable (LSC)
       Label Switching Routers";
  }

  grouping wdm-label-step {
    description
      "Label step information for fixed & flexi-DWDM or CWDM grid";
    choice l0-grid-type {
      description
        "Grid type: DWDM, CWDM, etc.";
      case fixed-dwdm {
        leaf wson-dwdm-channel-spacing {
          when "derived-from-or-self(../../grid-type,
                \"wson-grid-dwdm\")" {
            description
              "Valid only when grid type is DWDM.";
          }
          type identityref {
            base dwdm-ch-spc-type;
          }
          description
            "Label-step is the channel spacing (GHz), e.g., 100.000,
             50.000, 25.000, or 12.500 GHz for DWDM.";
          reference
            "RFC 6205: Generalized Labels for Lambda-Switch-Capable
             (LSC) Label Switching Routers";
        }
      }
      case cwdm {
        leaf wson-cwdm-channel-spacing {
          when "derived-from-or-self(../../grid-type,
                \"wson-grid-cwdm\")" {
            description
              "Valid only when grid type is CWDM.";
          }
          type identityref {
            base cwdm-ch-spc-type;
          }
          description
            "Label-step is the channel spacing (nm), i.e., 20 nm
             for CWDM, which is the only value defined for CWDM.";
          reference
            "RFC 6205: Generalized Labels for Lambda-Switch-Capable
             (LSC) Label Switching Routers";
        }
      }
      case flexi-grid {
        uses flexi-grid-label-step;
      }
    }
    reference
      "RFC 6205: Generalized Labels for Lambda-Switch-Capable (LSC)
       Label Switching Routers,
       ITU-T G.694.2 (12/2003): Spectral grids for WDM applications:
       CWDM wavelength grid,
       RFC 8363: GMPLS OSPF-TE Extensions in Support of Flexi-Grid
       Dense Wavelength Division Multiplexing (DWDM) Networks";
  }

  grouping wdm-label-hop {
    description
      "Generic label-hop information for fixed & flexi-DWDM or
       CWDM grid";
    choice grid-type {
      description
        "Label for DWDM or CWDM grid";
      case fixed-dwdm {
        choice fixed-single-or-super-channel {
          description
            "single or super channel";
          case single {
            leaf dwdm-n {
              type l0-types:dwdm-n;
              description
                "The given value 'N' is used to determine the
                 nominal central frequency.";
            }
          }
          case multi {
            leaf-list subcarrier-dwdm-n {
              type l0-types:dwdm-n;
              min-elements 2;
              description
                "The given values 'N' are used to determine the
                 nominal central frequency for each subcarrier
                 channel.";
              reference
                "ITU-T Recommendation G.694.1: Spectral grids for
                 WDM applications: DWDM frequency grid";
            }
          }
        }
      }
      case cwdm {
        leaf cwdm-n {
          type l0-types:cwdm-n;
          description
            "The given value 'N' is used to determine the nominal
             central wavelength.";
          reference
            "RFC 6205: Generalized Labels for Lambda-Switch-Capable
             (LSC) Label Switching Routers";
        }
      }
      case flexi-grid {
        uses l0-types:flexi-grid-label-hop;
      }
    }
    reference
      "RFC 6205: Generalized Labels for Lambda-Switch-Capable (LSC)
       Label Switching Routers";
  }

  grouping wdm-label-range-info {
    description
      "WDM label range related information";
    uses l0-label-range-info;
    container flexi-grid {
      when "derived-from-or-self(../grid-type,
                \"flexi-grid-dwdm\")" {
        description
          "Applicable only when the grid type is flexi-grid-dwdm.";
      }
      description
        "flexi-grid definition";
      leaf slot-width-granularity {
        type identityref {
          base flexi-slot-width-granularity;
        }
        default "flexi-swg-12p5ghz";
        description
          "Minimum space between slot widths. Default is 12.500
           GHz.";
        reference
          "RFC 7698: Framework and Requirements for GMPLS-Based
           Control of Flexi-Grid Dense Wavelength Division
           Multiplexing (DWDM) Networks";
      }
      leaf min-slot-width-factor {
        type uint16 {
          range "1..max";
        }
        default "1";
        description
          "A multiplier of the slot width granularity, indicating
           the minimum slot width supported by an optical port.

           Minimum slot width is calculated by:
             Minimum slot width (GHz) =
               min-slot-width-factor * slot-width-granularity.";
        reference
          "RFC 8363: GMPLS OSPF-TE Extensions in Support of Flexi-
           Grid Dense Wavelength Division Multiplexing (DWDM)
           Networks";
      }

      leaf max-slot-width-factor {
        type uint16 {
          range "1..max";
        }
        must '. >= ../min-slot-width-factor' {
          error-message
            "Maximum slot width must be greater than or equal to
             minimum slot width.";
        }
        description
          "A multiplier of the slot width granularity, indicating
           the maximum slot width supported by an optical port.

           Maximum slot width is calculated by:
             Maximum slot width (GHz) =
               max-slot-width-factor * slot-width-granularity

           If specified, maximum slot width must be greater than or
           equal to minimum slot width.  If not specified, maximum
           slot width is equal to minimum slot width.";
        reference
          "RFC 8363: GMPLS OSPF-TE Extensions in Support of Flexi-
           Grid Dense Wavelength Division Multiplexing (DWDM)
           Networks";
      }
    }
  }

  grouping wson-label-start-end {
    description
      "The WSON label-start or label-end used to specify WSON label
       range.";
    choice grid-type {
      description
        "Label for DWDM or CWDM grid";
      case dwdm {
        leaf dwdm-n {
          when "derived-from-or-self(../../../grid-type,
                \"wson-grid-dwdm\")" {
            description
              "Valid only when grid type is DWDM.";
          }
          type l0-types:dwdm-n;
          description
            "The central frequency of DWDM.";
          reference
            "RFC 6205: Generalized Labels for Lambda-Switch-Capable
             (LSC) Label Switching Routers";
        }
      }
      case cwdm {
        leaf cwdm-n {
          when "derived-from-or-self(../../../grid-type,
                \"wson-grid-cwdm\")" {
            description
              "Valid only when grid type is CWDM.";
          }
          type l0-types:cwdm-n;
          description
            "Channel wavelength computing input.";
          reference
            "RFC 6205: Generalized Labels for Lambda-Switch-Capable
             (LSC) Label Switching Routers";
        }
      }
    }
    reference
      "RFC 6205: Generalized Labels for Lambda-Switch-Capable (LSC)
       Label Switching Routers";
  }

  grouping wson-label-hop {
    description
      "Generic label-hop information for WSON";
    choice grid-type {
      description
        "Label for DWDM or CWDM grid";
      case dwdm {
        choice single-or-super-channel {
          description
            "single or super channel";
          case single {
            leaf dwdm-n {
              type l0-types:dwdm-n;
              description
                "The given value 'N' is used to determine the
                 nominal central frequency.";
            }
          }
          case super {
            leaf-list subcarrier-dwdm-n {
              type l0-types:dwdm-n;
              description
                "The given values 'N' are used to determine the
                 nominal central frequency for each subcarrier
                 channel.";
              reference
                "ITU-T Recommendation G.694.1: Spectral grids for
                 WDM applications: DWDM frequency grid";
            }
          }
        }
      }
      case cwdm {
        leaf cwdm-n {
          type l0-types:cwdm-n;
          description
            "The given value 'N' is used to determine the nominal
             central wavelength.";
          reference
            "RFC 6205: Generalized Labels for Lambda-Switch-Capable
             (LSC) Label Switching Routers";
        }
      }
    }
    reference
      "RFC 6205: Generalized Labels for Lambda-Switch-Capable (LSC)
       Label Switching Routers";
  }

  grouping l0-label-range-info {
    description
      "Information about Layer 0 label range.";
    leaf grid-type {
      type identityref {
        base l0-grid-type;
      }
      description
        "Grid type";
    }
    leaf priority {
      type uint8;
      description
        "Priority in Interface Switching Capability Descriptor
         (ISCD).";
      reference
        "RFC 4203: OSPF Extensions in Support of Generalized
         Multi-Protocol Label Switching (GMPLS)";
    }
    reference
      "RFC 6205: Generalized Labels for Lambda-Switch-Capable (LSC)
       Label Switching Routers";
  }

  grouping wson-label-step {
    description
      "Label step information for WSON";
    choice l0-grid-type {
      description
        "Grid type: DWDM, CWDM, etc.";
      case dwdm {
        leaf wson-dwdm-channel-spacing {
          when "derived-from-or-self(../../grid-type,
                \"wson-grid-dwdm\")" {
            description
              "Valid only when grid type is DWDM.";
          }
          type identityref {
            base dwdm-ch-spc-type;
          }
          description
            "Label-step is the channel spacing (GHz), e.g., 100.000,
             50.000, 25.000, or 12.500 GHz for DWDM.";
          reference
            "RFC 6205: Generalized Labels for Lambda-Switch-Capable
             (LSC) Label Switching Routers";
        }
      }
      case cwdm {
        leaf wson-cwdm-channel-spacing {
          when "derived-from-or-self(../../grid-type,
                \"wson-grid-cwdm\")" {
            description
              "Valid only when grid type is CWDM.";
          }
          type identityref {
            base cwdm-ch-spc-type;
          }
          description
            "Label-step is the channel spacing (nm), i.e., 20 nm
             for CWDM, which is the only value defined for CWDM.";
          reference
            "RFC 6205: Generalized Labels for Lambda-Switch-Capable
             (LSC) Label Switching Routers";
        }
      }
    }
    reference
      "RFC 6205: Generalized Labels for Lambda-Switch-Capable (LSC)
       Label Switching Routers,

       ITU-T G.694.2 (12/2003): Spectral grids for WDM applications:
       CWDM wavelength grid";
  }

  grouping flexi-grid-label-start-end {
    description
      "The flexi-grid label-start or label-end used to specify
       flexi-grid label range.";
    leaf flexi-n {
      type l0-types:flexi-n;
      description
        "The given value 'N' is used to determine the nominal
        central frequency.

        As described in section 3.1 of RFC 8363, the range of
        available nominal central frequencies are advertised for
        m=1, which means that for an available central frequency n,
        the frequency slot from central frequency n-1 to central
        frequency n+1 is available.";
    }
    reference
      "RFC 7699: Generalized Labels for the Flexi-Grid in Lambda
      Switch Capable (LSC) Label Switching Routers,

      RFC 8363: GMPLS OSPF-TE Extensions in Support of Flexi-Grid
      Dense Wavelength Division Multiplexing (DWDM) Networks";
  }

  grouping flexi-grid-frequency-slot {
    description
      "Flexi-grid frequency slot grouping.";
    uses flexi-grid-label-start-end;
    leaf flexi-m {
      type l0-types:flexi-m;
      description
        "The given value 'M' is used to determine the slot width.";
    }
    reference
      "RFC 7699: Generalized Labels for the Flexi-Grid in Lambda
      Switch Capable (LSC) Label Switching Routers";
  }

  grouping flexi-grid-label-hop {
    description
      "Generic label-hop information for flexi-grid";
    choice single-or-super-channel {
      description
        "single or super channel";
      case single {
        uses flexi-grid-frequency-slot;
      }
      case super {
        status deprecated;
        list subcarrier-flexi-n {
          key "flexi-n";
          uses flexi-grid-frequency-slot;
          description
            "List of subcarrier channels for flexi-grid super
             channel.";
        }
      }
      case multi {
        container frequency-slots {
          description
            "The top level container for the list of frequency
            slots used for flexi-grid super channel.";
          list frequency-slot {
            key "flexi-n";
            min-elements 2;
            uses flexi-grid-frequency-slot;
            description
              "List of frequency slots used for flexi-grid super
              channel.";
          }
        }
      }
    }
    reference
      "RFC 8363: GMPLS OSPF-TE Extensions in Support of Flexi-Grid
      Dense Wavelength Division Multiplexing (DWDM) Networks";
  }

  grouping flexi-grid-label-range-info {
    description
      "Flexi-grid-specific label range related information";
    uses l0-label-range-info;
    container flexi-grid {
      description
        "flexi-grid definition";
      leaf slot-width-granularity {
        type identityref {
          base flexi-slot-width-granularity;
        }
        default "flexi-swg-12p5ghz";
        description
          "Minimum space between slot widths. Default is 12.500
           GHz.";
        reference
          "RFC 8363: GMPLS OSPF-TE Extensions in Support of
          Flexi-Grid Dense Wavelength Division Multiplexing (DWDM)
          Networks";
      }
      leaf min-slot-width-factor {
        type uint16 {
          range "1..max";
        }
        default "1";
        description
          "A multiplier of the slot width granularity, indicating
           the minimum slot width supported by an optical port.

           Minimum slot width is calculated by:
             Minimum slot width (GHz) =
               min-slot-width-factor * slot-width-granularity.";
        reference
          "RFC 8363: GMPLS OSPF-TE Extensions in Support of Flexi-
           Grid Dense Wavelength Division Multiplexing (DWDM)
           Networks";
      }

      leaf max-slot-width-factor {
        type uint16 {
          range "1..max";
        }
        must '. >= ../min-slot-width-factor' {
          error-message
            "Maximum slot width must be greater than or equal to
             minimum slot width.";
        }
        description
          "A multiplier of the slot width granularity, indicating
           the maximum slot width supported by an optical port.

           Maximum slot width is calculated by:
             Maximum slot width (GHz) =
               max-slot-width-factor * slot-width-granularity

           If specified, maximum slot width must be greater than or
           equal to minimum slot width.  If not specified, maximum
           slot width is equal to minimum slot width.";
        reference
          "RFC 8363: GMPLS OSPF-TE Extensions in Support of Flexi-
           Grid Dense Wavelength Division Multiplexing (DWDM)
           Networks";
      }
    }
  }

  grouping flexi-grid-label-step {
    description
      "Label step information for flexi-grid";
    leaf flexi-grid-channel-spacing {
      type identityref {
        base flexi-ch-spc-type;
      }
      default "flexi-ch-spc-6p25ghz";
      status deprecated;
      description
        "Label-step is the nominal central frequency granularity
         (GHz), e.g., 6.25 GHz.";
      reference
        "RFC 7699: Generalized Labels for the Flexi-Grid in Lambda
         Switch Capable (LSC) Label Switching Routers";
    }
    leaf flexi-ncfg {
      type identityref {
        base flexi-ncfg-type;
      }
      default "flexi-ncfg-6p25ghz";
      description
        "Label-step is the nominal central frequency granularity
         (GHz), e.g., 6.25 GHz.";
      reference
        "RFC 7699: Generalized Labels for the Flexi-Grid in Lambda
         Switch Capable (LSC) Label Switching Routers";
    }
    leaf flexi-n-step {
      type uint8;
      description
        "This attribute defines the multiplier for the supported
         values of 'N'.

         For example, given a grid with a nominal central frequency
         granularity of 6.25 GHz, the granularity of the supported
         values of the nominal central frequency could be 12.5 GHz.
         In this case, the values of flexi-n should be even and this
         constraint is reported by setting the flexi-n-step to 2.

         This attribute is also known as central frequency
         granularity in RFC 8363.";
      reference
        "RFC 8363: GMPLS OSPF-TE Extensions in Support of Flexi-Grid
         Dense Wavelength Division Multiplexing (DWDM) Networks";
    }
  }

 /* supported inverse multiplexing capabilities such as
    max. OTSiG:OTSi cardinality
    It is a transponder attribute not transceiver
  */

 /*    leaf multiplexing-cap {
      type uint32;
    config false;
      description "supported inverse multiplexing capabilities
       such as max. OTSiG:OTSi cardinality";
    }
  */

  grouping transceiver-mode {
    description
      "This grouping is intended to be used for reporting the
       information of a transceiver's mode.

       The compatible-modes container shall be augmented with the
       proper leafrefs when used: see for example the
       transceiver-capabilities grouping below.";
    choice mode {
      mandatory true;
      description
        "Indicates whether the transceiver's mode is a standard
          mode, an organizational mode or an explicit mode.";
      case G.698.2 {
        uses standard-mode;
        uses common-standard-organizational-mode;
      }
      case organizational-mode {
        container organizational-mode {
          config false;
          description
            "The set of attributes for an organizational mode";
          uses organizational-mode;
          uses common-standard-organizational-mode;
          uses common-organizational-explicit-mode;
        }  // container organizational-mode
      }
      case explicit-mode {
        container explicit-mode {
          config false;
          description
            "The set of attributes for an explicit mode";
          uses common-explicit-mode;
          uses common-organizational-explicit-mode;
          container compatible-modes {
            description
              "Container for all the standard and organizational
                modes supported by the transceiver's explicit
                mode.";
          }  // container compatible-modes
        }  // container explicit-mode
      } // end of case explicit-mode
    } // end of choice
  }

  grouping transceiver-capabilities {
    description
      "This grouping is intended to be used for reporting the
       capabilities of a transceiver.";

    container supported-modes {
      presence
        "When present, it indicates that the modes supported by a
        transceiver are reported.";
      description
        "The top level container for the list supported
        transceiver's modes.";
      list supported-mode {
        key "mode-id";
        config false;
        min-elements 1;
        description "The list of supported transceiver's modes.";
        leaf mode-id {
          type string {
            length "1..255";
          }
          description "ID for the supported transceiver's mode.";
        }
        uses transceiver-mode {
          augment "mode/explicit-mode/explicit-mode/"
                + "compatible-modes" {
            description
              "Augments the compatible modes with the proper
              leafrefs.";
            leaf-list supported-application-codes {
              type leafref {
                path "../../../mode-id";
              }
              must "../../../../"
                  + "supported-mode[mode-id=current()]/"
                  + "standard-mode" {
                description
                  "The pointer is only for application codes
                    supported by transceiver.";
              }
              description
                "List of pointers to the application codes
                  supported by the transceiver's explicit mode.";
            }
            leaf-list supported-organizational-modes {
              type leafref {
                path "../../../mode-id";
              }
              must "../../../../"
                  + "supported-mode[mode-id=current()]/"
                  + "organizational-mode" {
                description
                  "The pointer is only for organizational modes
                    supported by transceiver.";
              }
              description
                "List of pointers to the organizational modes
                  supported by the transceiver's explicit mode.";
            }
          }
        }
      }  // list supported-modes
    }  // container supported-modes
  }  // grouping transceiver-capabilities

  grouping standard-mode {
    description
      "ITU-T G.698.2 standard mode that guarantees interoperability.
       It must be an string with the following format:
       B-DScW-ytz(v) where all these attributes are conformant
       to the ITU-T recomendation";

    leaf standard-mode {
      type standard-mode;
      config false;
      description
        "G.698.2 standard mode";
    }
  }

  grouping organizational-mode {
    description
      "Transponder operational mode supported by organizations or
       vendor";

    leaf operational-mode {
      type operational-mode;
      config false;
      description
        "configured organization- or vendor-specific
         application identifiers (AI) supported by the transponder";
    }
    leaf organization-identifier {
      type organization-identifier;
      config false;
      description
        "organization identifier that uses organizational
         mode";
    }
  }

  grouping penalty-value {
    description
      "A common definition of the penalty value used for describing
      multiple penalty types (.e.g, CD, PMD, PDL).";

    leaf penalty-value {
      type union {
        type decimal64 {
          fraction-digits 2;
          range "0..max";
        }
        type empty;
      }
      units "dB";
      config false;
      mandatory true;
      description
        "The OSNR penalty associated with the related optical
        impairment at the receiver, when the value is known or an
        empty value when the value is not known.";
    }
  }

/*
 * This grouping represent the list of attributes related to
 * optical impairment limits for explicit mode
 * (min OSNR, max PMD, max CD, max PDL, Q-factor limit, etc.)
 * In case of standard and operational mode the attributes are
 * implicit
 */

  grouping common-explicit-mode {
    description "Attributes capabilities related to
    explicit mode of an optical transceiver";
    leaf line-coding-bitrate {
      type identityref {
        base line-coding;
      }
      config false;
      description
        "Bit rate/line coding of the optical tributary signal.";
      reference
        "ITU-T G.698.2 section 7.1.2";
    }
    leaf bitrate {
      type uint16;
      units "Gbit/sec";
      config false;
      description
        "The gross bitrate (e.g., 100, 200) of the optical tributary
        signal.";
    }
    leaf max-diff-group-delay  {
      type uint32;
      units "ps";
      config false;
      description
        "Maximum Differential group delay of this mode for this
        lane";
    }
    leaf max-chromatic-dispersion {
      type decimal64 {
        fraction-digits 2;
        range "0..max";
      }
      units "ps/nm";
      config false;
      description
        "Maximum acceptable accumulated chromatic dispersion (CD)
        on the receiver";
    }
    list cd-penalty {
      config false;
      description
        "Optional penalty associated with a given accumulated
        chromatic dispersion (CD) value.

        This list of pair cd and penalty values can be used to
        sample the function penalty = f(CD).";
      leaf cd-value {
        type union {
          type decimal64 {
            fraction-digits 2;
            range "0..max";
          }
          type empty;
        }
        units "ps/nm";
        config false;
        mandatory true;
        description
          "The Chromatic Dispersion (CD), when the value is known
          or an empty value when the value is not known.";
      }
      uses penalty-value;
    }
    leaf max-polarization-mode-dispersion {
      type decimal64 {
        fraction-digits 2;
        range "0..max";
      }
      units "ps";
      config false;
      description
        "Maximum acceptable accumulated polarization mode
         dispersion (PMD) on the receiver";
    }
    list pmd-penalty {
      config false;
      description
        "Optional penalty associated with a given accumulated
        polarization mode dispersion (PMD) value.

        This list of pair pmd and penalty can be used to
        sample the function penalty = f(PMD).";
      leaf pmd-value {
        type union {
          type decimal64 {
            fraction-digits 2;
            range "0..max";
          }
          type empty;
        }
        units "ps";
        config false;
        mandatory true;
        description
          "The Polarization Mode Dispersion (PMD), when the value
          is known or an empty value when the value is not known.";
      }
      uses penalty-value;
    }
    leaf max-polarization-dependant-loss {
      type loss-in-db-or-null;
      config false;
      mandatory true;
      description
        "Maximum acceptable accumulated accumulated polarization
        dependent loss (PDL) on the receiver";
    }
    list pdl-penalty {
      config false;
      description
        "Optional penalty associated with a given accumulated
        polarization dependent loss (PDL) value.

        This list of pair pdl and penalty values can be used to
        sample the function PDL = f(penalty).";
      leaf pdl-value {
        type loss-in-db-or-null;
        config false;
        mandatory true;
        description
          "Maximum acceptable accumulated polarization dependent
          loss.";
      }
      uses penalty-value;
    }
    leaf available-modulation-type {
      type identityref {
        base modulation;
      }
      config false;
      description
        "Modulation type the specific transceiver in the list
         can support";
    }
    leaf min-OSNR {
      type snr;
      units "dBm";
      config false;
      description
        "min OSNR measured over 0.1 nm resolution bandwidth:
        if received OSNR at Rx-power reference point
        (rx-ref-channel-power) is lower than MIN-OSNR, an increased
        level of bit-errors post-FEC needs to be expected";
    }
    leaf rx-ref-channel-power {
      type power-in-dbm;
      config false;
      description
        "The channel power used as reference for defining penalties
        and min-OSNR";
    }
    list rx-channel-power-penalty {
      config false;
      description
        "Optional penalty associated with a received power
          lower than rx-ref-channel-power.
          This list of pair power and penalty can be used to
          sample the function penalty = f(rx-channel-power).";
      leaf rx-channel-power-value {
        type power-in-dbm-or-null;
        units "dBm";
        config false;
        mandatory true;
        description
          "The Received Power, when the value is known or an empty
          value when the value is not known.";
      }
      uses penalty-value;
    }
    leaf min-Q-factor {
      type int32;
      units "dB";
      config false;
      description "min Qfactor at FEC threshold";
    }
    leaf available-baud-rate {
      type uint32;
      units "Bd";
      config false;
      description
        "Baud-rate the specific transceiver in
        the list can support.
         Baud-rate is the unit for
         symbol rate or modulation rate
         in symbols per second or
         pulses per second.
         It is the number of distinct symbol
         changes (signal events) made to the
         transmission medium
         per second in a digitally
         modulated signal or a line code";
    }
    leaf roll-off {
      type decimal64 {
        fraction-digits 4;
        range "0..1";
      }
      config false;
      description
        "the roll-off factor (beta with values from 0 to 1)
        identifies how the real signal shape exceed
        the baud rate. If=0 it is exactly matching
        the baud rate.If=1 the signal exceeds the
        50% of the baud rate at each side.";
    }
    leaf min-carrier-spacing {
      type frequency-ghz;
      config false;
      description
        "This attribute specifies the minimum nominal difference
        between the carrier frequencies of two homogeneous OTSis
        (which have the same optical characteristics but the central
        frequencies) such that if they are placed next to each other
        the interference due to spectrum overlap between them can be
        considered negligible.

        In case of heterogeneous OTSi it is up to path computation
        engine to determine the minimum distance between the carrier
        frequency of the two adjacent OTSi.";
    }
    leaf available-fec-type {
      type identityref {
        base fec-type;
      }
      config false;
      description "Available FEC";
    }
    leaf fec-code-rate {
      type decimal64 {
        fraction-digits 8;
        range "0..max";
      }
      config false;
      description "FEC-code-rate";
    }
    leaf fec-threshold {
      type decimal64 {
        fraction-digits 8;
        range "0..max";
      }
      config false;
      description
        "Threshold on the BER, for which FEC
         is able to correct errors";
    }
    leaf in-band-osnr {
      type snr;
      config false;
      description
        "The OSNR defined within the bandwidth of the transmit
        spectral excursion (i.e.,  between the nominal central
        frequency of the channel and the -3.0dB points of the
        transmitter spectrum furthest from the nominal central
        frequency) measured at reference point Ss.

        The in-band OSNR is referenced to an optical bandwidth of
        0.1nm @ 193.7 THz or 12.5 GHz.";
      reference
        "OIF-400ZR-01.0: Implementation Agreement 400ZR";
    }
    leaf out-of-band-osnr {
      type snr;
      config false;
      description
        "The ratio of the peak transmitter power to the integrated
        power outside the transmitter spectral excursion.

        The spectral resolution of the measurement shall be better
        than the maximum spectral width of the peak.

        The out-of-band OSNR is referenced to an optical bandwidth
        of 0.1nm @ 193.7 THz or 12.5 GHz";
      reference
        "OIF-400ZR-01.0: Implementation Agreement 400ZR";
    }
    leaf tx-polarization-power-difference {
      type decimal-2-digits;
      units "dB";
      config false;
      description
        "The transmitter polarization dependent power difference
        defined as the power difference between X and Y
        polarizations";
      reference
        "OIF-400ZR-01.0: Implementation Agreement 400ZR";
    }
    leaf polarization-skew {
      type decimal64 {
        fraction-digits 2;
      }
      units "ps";
      config false;
      description
        "The X-Y skew, included as a fixed value in the receiver
        polarization mode dispersion (PMD) tolerance limits.";
      reference
        "OIF-400ZR-01.0: Implementation Agreement 400ZR";
    }
  } // grouping common-explicit-mode

  grouping common-standard-organizational-mode {
    description
      "Common attributes used by standard and organizational
      modes.";

    leaf-list line-coding-bitrate {
      type identityref {
        base line-coding;
      }
      config false;
      description
        "The list of the bit rate/line coding of the optical
        tributary signal supported by the transceiver.

        Reporting this list is optional when the standard or
        organization mode supports only one bit rate/line coding.";
      reference
        "ITU-T G.698.2 section 7.1.2";
    }
  } // grouping common-standard-organizational-mode

  grouping transmitter-tuning-range {
    description
      "Transmitter tuning range (f_tx-min, f_tx-max)";

    leaf min-central-frequency {
      type frequency-thz;
      description
        "This parameter indicates the minimum frequency for the
        transmitter tuning range.";
    }
    leaf max-central-frequency {
      type frequency-thz;
      description
        "This parameter indicates the maximum frequency for the
        transmitter tuning range.";
    }

    leaf transceiver-tunability {
      type frequency-ghz;
      description
        "This parameter indicates the transmitter frequency fine
        tuning steps e.g 3.125GHz or 0.001GHz.";
    }
  } // grouping transmitter-tuning-range

  grouping common-organizational-explicit-mode {
    description "Common capability attributes limit range
    in case of operational mode and explicit mode.
    These attributes are supported separately in
    case of application codes";

/* transmitter tuning range (f_tx-min, f_tx-max) */
    uses transmitter-tuning-range;

/* supported transmitter power range [p_tx-min, p_tx_max] */

    leaf tx-channel-power-min {
      type power-in-dbm;
      config false;
      description "The minimum output power of this interface";
    }
    leaf tx-channel-power-max {
      type power-in-dbm;
      config false;
      description "The maximum output power of this interface";
    }

/* supported receiver power range [p_rx-min, p_rx_max] */

     leaf rx-channel-power-min {
      type power-in-dbm;
      config false;
      description "The minimum input power of this interface";
    }
    leaf rx-channel-power-max {
      type power-in-dbm;
      config false;
      description "The maximum input power of this interface";
    }

    leaf rx-total-power-max {
      type power-in-dbm;
      config false;
      description "Maximum rx optical power for
      all the channels";
    }
  } // grouping common-organizational-explicit-mode

/* This grouping represent the list of configured parameters */
/* values independent of operational mode */

  grouping common-transceiver-configured-param {
    description "Capability of an optical transceiver";

    leaf line-coding-bitrate {
      type identityref {
        base line-coding;
      }
      config false;
      description
        "Bit rate/line coding of the optical tributary signal.

        Reporting this attribute is optional when the configured
        mode supports only one bit rate/line coding.";
      reference
        "ITU-T G.698.2 section 7.1.2";
    }
    leaf tx-channel-power {
      type power-in-dbm-or-null;
      description
        "The current channel transmit power, when the value is
        known or an empty value when the value is not known.

        The empty value MUST NOT be used when this attribute is
        configured.";
    }
    leaf rx-channel-power {
      type power-in-dbm-or-null;
      config false;
      description
        "The current channel received power, when the value is
        known or an empty value when the value is not known.";
    }
    leaf rx-total-power {
      type power-in-dbm-or-null;
      config false;
      description
        "The current total received power, when the value is known
        or an empty value when the value is not known.";
    }
  } // grouping for configured attributes out of mode

  grouping l0-tunnel-attributes {
    description
      "Parameters for Layer0 (WSON or Flexi-Grid) Tunnels.";
    leaf bit-stuffing {
      type boolean;
      description
        "Bit stuffing enabled/disabled.";
    }
    leaf wavelength-assignment {
      type identityref {
        base wavelength-assignment;
      }
      description "Wavelength Allocation Method";
    }
  }

  grouping frequency-range {
    description
      "This grouping defines the lower and upper bounds of a
      frequency range (e.g., a band).
      This grouping SHOULD NOT be used to define a frequency slot,
      which SHOULD be defined using the n and m values instead.";
    leaf lower-frequency {
      type frequency-thz;
      mandatory true;
      description
        "The lower frequency boundary of the
        frequency range.";
    }
    leaf upper-frequency {
      type frequency-thz;
      must '. > ../lower-frequency' {
        error-message
          "The upper frequency must be greater than the lower
          frequency.";
      }
      mandatory true;
      description
        "The upper frequency boundary of the
        frequency range.";
    }
  }

  grouping l0-path-constraints {
    description
      "Common attribute for Layer 0 path constraints to be used by
      Layer 0 computation.";
    leaf gsnr-margin {
      type snr {
        range 0..max;
      }
      default 0;
      description
        "An additional margin to be added to the OSNR-min of the
        transceiver when checking the estimated received Generalized
        SNR (GSNR).";
    }
  }

  grouping l0-path-properties {
    description
      "Common attribute for reporting the Layer 0 computed path
      properties.";
    leaf estimated-gsnr {
      type snr;
      config false;
      description
        "The estimate received GSNR for the computed path.";
    }
    leaf estimated-eol-gsnr {
      type snr;
      config false;
      description
        "The estimate received GSNR for the computed path
         degraded at the end of life.";
    }
    leaf estimated-lowest-gsnr {
      type snr;
      config false;
      description
        "The estimate lowest received GSNR for the computed path
         among all possible wavelength channels along the same
         path.";
    }
  }
}
