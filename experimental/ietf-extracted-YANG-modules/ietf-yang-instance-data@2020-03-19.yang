module ietf-yang-instance-data {
  yang-version 1.1;
  namespace "urn:ietf:params:xml:ns:yang:ietf-yang-instance-data";
  prefix yid;

  import ietf-yang-structure-ext {
    prefix sx;
    reference
      "YANG Data Structure Extensions:
       draft-ietf-netmod-yang-data-ext-05";
  }
  import ietf-datastores {
    prefix ds;
    reference
      "RFC 8342: Network Management Datastore Architecture (NMDA)";
  }
  import ietf-inet-types {
    prefix inet;
      reference
      "RFC 6991: Common YANG Data Types";
}
  import ietf-yang-types {
    prefix yang;
    reference
      "RFC 6991: Common YANG Data Types";
  }

  organization
    "IETF NETMOD Working Group";
  contact
    "WG Web:   <https://datatracker.ietf.org/wg/netmodf/>
     WG List:  <mailto:netmod@ietf.org>

     Author:  Balazs Lengyel
        <mailto:balazs.lengyel@ericsson.com>";
  description
    "The module defines the structure and content of YANG
     instance data sets.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2020-03-19 {
    description
      "Initial revision.";
    reference
      "RFC XXXX: YANG Instance Data Format";
  }

  feature inline-content-schema {
    description
      "This feature indicates that inline content-schema
          option is supported.";
  }

  sx:structure "instance-data-set" {
    description
      "A data structure to define a format for
       YANG instance data sets. Consists of meta-data about
       the instance data set and the real content-data.";
    leaf name {
      type string;
      description
        "An arbitrary name for the YANG instance data set.  This
         value is primarily used for descriptive purposes.  However,
         when the instance data set is saved to a file, then the
         filename MUST encode the name's value, per Section 3
         of RFC XXXX.";
    }
    leaf format-version {
      type string {
        pattern '\d{4}-(1[0-2]|0[1-9])-(0[1-9]|[1|2][0-9]|3[0-1])';
      }
      default "2020-03-19";
      description
        "Version of the 'YANG Instance Data format'.

         It SHALL contain the revision date of the
         ietf-yang-instance-data module used when creating the
         instance data set in a YYYY-MM-DD format";
    }
    container content-schema {
      description
        "The content schema used to create the instance data set.
         If not present the user needs to obtain the information
         through external documents.";
      choice content-schema-spec {
        description
          "Specification of the content-schema.";
        case simplified-inline {
          leaf-list module {
            type string;
            description
              "The list of content defining YANG modules.

               The value SHALL start with the module name.
               If the module contains a revision statement the
               revision date SHALL be included in the leaf-list
               entry. If other methods (e.g., revision-label) are
               defined to identify individual module revisions
               those MAY be used instead of using a revision date.

               E.g., ietf-yang-library@2016-06-21

               Usage of this leaf-list implies the modules are
               used without any deviations and with all features
               supported. Multiple revisions of the same module
               MUST NOT be specified.";
          }
        }
        case inline {
          if-feature "inline-content-schema";
          leaf-list inline-module {
            type string;
            min-elements 1;
            ordered-by user;
            description
              "Indicates that content defining YANG modules
               are specified inline.

               The value SHALL start with the module name.
               If the module contains a revision statement the
               revision date SHALL be included in the leaf-list
               entry. If other methods (e.g., revision-label) are
               defined to identify individual module revisions
               those MAY be used instead of using a revision date.

               E.g., ietf-yang-library@2016-06-21

               The first item is either ietf-yang-library or some
               other YANG module that contains a list of YANG modules
               with their name, revision-date, supported-features,
               and deviations. The usage of
               ietf-yang-library@2019-01-04 MUST be supported.
               Using other modules, module versions MAY also be
               supported.

               As some versions of ietf-yang-library MAY contain
               different module-sets for different datastores, if
               multiple module-sets are included, the instance data
               set's meta-data MUST contain the datastore information
               and instance data for the ietf-yang-library MUST also
               contain information specifying the module-set for the
               relevant datastore.

               Subsequent items MAY specify YANG modules augmenting
               the first module with useful data
               (e.g., revision label).";
          }
          anydata inline-schema {
            mandatory true;
            description
              "Instance data corresponding to the YANG modules
               specified in the inline-module nodes defining the set
               of content defining YANG modules for this
               instance-data-set.";
          }
        }
        case uri {
          leaf same-schema-as-file {
            type inet:uri;
            description
              "A reference to another YANG instance data file.
               This instance data file uses the same
               content schema as the referenced file.";
          }
        }
      }
    }
    leaf-list description {
      type string;
      description
        "Description of the instance data set.";
    }
    leaf contact {
      type string;
      description
        "Contact information for the person or
         organization to whom queries concerning this
         instance data set should be sent.";
    }
    leaf organization {
      type string;
      description
        "Organization responsible for the instance
         data set.";
    }
    leaf datastore {
      type ds:datastore-ref;
      description
        "The identity of the datastore with which the
         instance data set is associated, e.g., the datastore from
         where the data was read or the datastore into which the data
         may be loaded or the datastore which is being documented.
         If a single specific datastore cannot be specified, the
         leaf MUST be absent.

         If this leaf is absent, then the datastore to which the
         instance data belongs is undefined.";
    }
    list revision {
      key "date";
      description
        "Instance data sets that are produced as
         a result of some sort of specification or design effort
         SHOULD have at least one revision entry.  For every
         published editorial change, a new one SHOULD be added
         in front of the revisions sequence so that all
         revisions are in reverse chronological order.

         For instance data sets that are read from
         or produced by a server or otherwise
         subject to frequent updates or changes, revision
         SHOULD NOT be present";
      leaf date {
        type string {
        pattern '\d{4}-(1[0-2]|0[1-9])-(0[1-9]|[1|2][0-9]|3[0-1])';
        }
        description
          "Specifies the date the instance data set
           was last modified. Formatted as YYYY-MM-DD";
      }
      leaf description {
        type string;
        description
          "Description of this revision of the instance data set.";
      }
    }
    leaf timestamp {
      type yang:date-and-time;
      description
        "The date and time when the instance data set
         was last modified.

         For instance data sets that are read from or produced
         by a server or otherwise subject to frequent
         updates or changes, timestamp SHOULD be present";
    }
    anydata content-data {
      description
        "Contains the real instance data.
         The data MUST conform to the relevant YANG Modules specified
         either in the content-schema-spec or in some other
         implementation specific manner.";
    }
  }
}
