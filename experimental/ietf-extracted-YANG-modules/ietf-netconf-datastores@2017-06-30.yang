module ietf-netconf-datastores {
  yang-version 1.1;
  namespace "urn:ietf:params:xml:ns:yang:ietf-netconf-datastores";
  prefix ncds;

  import ietf-inet-types {
    prefix inet;
  }
  import ietf-datastores {
    prefix ds;
  }
  import ietf-netconf {
    prefix nc;
  }
  import ietf-netconf-with-defaults {
    prefix ncwd;
  }

  organization
    "IETF NETCONF Working Group";
  contact
    "WG Web:   <https://datatracker.ietf.org/wg/netconf/>

     WG List:  <mailto:netconf@ietf.org>

     Author:   Martin Bjorklund
           <mailto:mbj@tail-f.com>

     Author:   Juergen Schoenwaelder
           <mailto:j.schoenwaelder@jacobs-university.de>

     Author:   Phil Shafer
           <mailto:phil@juniper.net>

     Author:   Kent Watsen
           <mailto:kwatsen@juniper.net>

     Author:   Rob Wilton
           <rwilton@cisco.com>";
  description
    "This YANG module defines a set of NETCONF operations for the
     Network Management Datastore Architecture (NMDA).

     Copyright (c) 2017 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX
     (http://www.rfc-editor.org/info/rfcxxxx); see the RFC itself
     for full legal notices.";

  revision 2017-06-30 {
    description
      "Initial revision.";
    reference "RFC XXXX: NETCONF Support for NMDA";
  }

  typedef datastore {
    type identityref {
      base ds:datastore;
    }
    description
      "An NMDA datastore.";
    reference "RFC XXXX: Network Management Datastore Architecture";
  }

  rpc get-data {
    description
      "Get data from an NMDA datastore";
    input {
      leaf source {
        type ncds:datastore;
        description
          "Datastore from which to retrieve data.";
      }
      anydata filter {
        description
          "Subtree or XPath filter to use.";
        nc:get-filter-element-attributes;
      }
    }
    output {
      anydata data {
        description
          "Copy of the source datastore subset which matched
           the filter criteria (if any).  An empty data
           container indicates that the request did not
           produce any results.";
      }
    }
  }
  rpc edit-data {
    description
      "Edit data in an NMDA datastore.";
    input {
      leaf target {
        type ncds:datastore;
        description
          "Datastore which data affects.";
      }
      leaf default-operation {
        type enumeration {
          enum "merge" {
            description
              "The default operation is merge.";
          }
          enum "replace" {
            description
              "The default operation is replace.";
          }
          enum "none" {
            description
              "There is no default operation.";
          }
        }
        default "merge";
        description
          "The default operation to use.";
      }
      uses ncwd:with-defaults-parameters;
      choice edit-content {
        mandatory true;
        description
          "The content for the edit operation.";

        anydata config {
          description
            "Inline Config content.";
        }
        leaf url {
          if-feature nc:url;
          type inet:uri;
          description
            "URL based config content.";
        }
      }
    }
  }

  /*
   * Augment the lock and unlock operations with a
   * "datastore" parameter.
   */

  augment "/nc:lock/nc:input/nc:target/nc:config-target" {
    description
      "Add NMDA Datastore as target.";
    leaf datastore {
      type ncds:datastore;
      description
        "Datastore to lock.";
    }
  }
  augment "/nc:unlock/nc:input/nc:target/nc:config-target" {
    description
      "Add NMDA Datastore as target.";
    leaf datastore {
      type ncds:datastore;
      description
        "Datastore to unlock.";
    }
  }

  /*
   * Augment the validate operation with a
   * "datastore" parameter.
   */

  augment "/nc:validate/nc:input/nc:source/nc:config-source" {
    description
      "Add NMDA Datastore as source.";
    leaf datastore {
      type ncds:datastore;
      description
        "Datastore to validate.";
    }
  }
}
