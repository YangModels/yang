module ietf-cmis-monitor {
  yang-version 1.1;
  namespace "urn:ietf:params:xml:ns:yang:ietf-cmis-monitor";
  prefix cmis-mon;

  import ietf-interfaces {
    prefix if;
  }
  import ietf-yang-types {
    prefix yang;
  }

  organization
    "IETF CCAMP Working Group";

  contact
    "WG Web:   <https://datatracker.ietf.org/wg/ccamp/>
     WG List:  <mailto:ccamp@ietf.org>

    Editor:   Shunsuke Homma
      <mailto:shunsuke.homma.ietf@gmail.com>

    Editor:   Hitoshi Irino
      <mailto:hitoshi.irino.ntt@gmail.com>";

  description
    "This module provides monitoring capabilities for CMIS-based
     optical modules. Users can define monitor rules for CMIS
     registers identified by page/bank/offset/size. Notifications
     are generated when threshold or delta-rate conditions are met.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.

    Copyright (c) 2026 IETF Trust and the persons identified
    as authors of the code.  All rights reserved.

    Redistribution and use in source and binary forms, with or
    without modification, is permitted pursuant to, and
    subject to the license terms contained in, the Revised
    BSD License set forth in Section 4.c of the IETF Trust's
    Legal Provisions Relating to IETF Documents
    (http://trustee.ietf.org/license-info).

    This version of this YANG module is part of RFC XXXX
    (https://www.rfc-editor.org/info/rfcXXXX); see the RFC itself
    for full legal notices.";

  revision "2025-10-11" {
    description "Initial revision.";
    reference
      "RFC XXXX: A YANG Data Model for CMIS Access and Control";
  }

  grouping monitor-target {
    description
      "Target CMIS register to monitor.";
    leaf page {
      type uint8;
      mandatory true;
      description "The number of the CMIS page.";
    }
    leaf bank {
      type uint8;
      mandatory true;
      description "The bank of the CMIS page.";
    }
    leaf offset {
      type uint8;
      mandatory true;
      description "The memory address of the value.";
    }
    leaf size {
      type uint8 {
        range "1 .. 128";
      }
      description "The memory size of the monitored value.";
    }
  }

  container monitors {
    description "Container for all monitor rules.";

    list monitor-rule {
      key "id";
      description "Monitoring rule.";

      leaf id {
        type string;
        description "Unique identifier of the rule.";
      }

      leaf interface-name {
        type leafref {
          path "/if:interfaces/if:interface/if:name";
        }
        mandatory true;
        description "Target interface of the monitored CMIS module.";
      }

      container monitor-target {
        description "Target CMIS register details.";
        uses monitor-target;
      }

      container condition {
        description "Condition to trigger notification.";
        leaf condition-type {
          type enumeration {
            enum threshold {
              description "Condition based on crossing a threshold.";
            }
            enum delta-rate {
              description "Condition based on a rate of change.";
            }
          }
          mandatory true;
          description "Type of condition.";
        }
        leaf threshold {
          type decimal64 {
            fraction-digits 2;
          }
          description
            "Threshold value for triggering notification
            (only used for threshold type).";
        }
        leaf delta-rate {
          type decimal64 {
            fraction-digits 2;
          }
          description
            "Maximum allowed change per interval (only used for
            delta-rate type).";
        }
      }

      leaf interval-ms {
        type uint32;
        default 1000;
        description "Monitoring interval in milliseconds.";
      }

      leaf enabled {
        type boolean;
        default true;
        description "Enable or disable this monitor rule.";
      }
    }
  }

  notification cmis-monitor-event {
    description
      "Notification raised when monitor rule condition is met.";
    leaf interface-name {
      type string;
      description "Interface name of the monitored module.";
    }

    leaf rule-id {
      type string;
      description "ID of the rule that triggered this notification.";
    }

    container monitor-target {
      description "Target CMIS register that triggered the event.";
      uses monitor-target;
    }

    leaf condition-type {
      type enumeration {
        enum threshold {
          description "Triggered by crossing a threshold.";
        }
        enum delta-rate {
          description "Triggered by a rate of change.";
        }
      }
      description "The type of condition that was met.";
    }

    leaf current-value {
      type binary;
      description "Current value of the monitored register.";
    }

    leaf threshold {
      type decimal64 {
        fraction-digits 2;
      }
      description "Threshold value (present if threshold type).";
    }

    leaf delta-rate {
      type decimal64 {
        fraction-digits 2;
      }
      description "Delta-rate value (present if delta-rate type).";
    }

    leaf timestamp {
      type yang:date-and-time;
      description "Time when the notification was generated.";
    }
  }
}
