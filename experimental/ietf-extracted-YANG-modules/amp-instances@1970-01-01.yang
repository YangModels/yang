submodule "amp-instances" {
        belongs-to "amp-adm" {
                prefix "amp";
        }

        description
                "This submodule contains the extensions necessary to "
                +"define AMP data instances directly in an ADM.";
        reference "draft Asynchronous Management Protocol";

        extension number-instance {
                argument "value";
                description
                        "Instantiate a value of BYTE, INT, UINT, VAST, UVAST, "
                        +"SDNV, REAL32, or REAL64 within an ADM.";
        }
        extension number-type {
                argument "name";
                description
                        "The type name of a number-instance.";
        }

        extension string-instance {
                argument "value";
                description
                        "Instantiate a value of STR from a text value.";
        }

        extension TS-instance {
                argument "value";
                description
                        "Instantiate a value of TS from a text value. "
                        +"The value is encoded according to RFC3339.";
        }

        extension MID-instance {
                description
                        "Instantiate a value of MID from substatements "
                        +"specializing the MID.";
                /// Must contain instance-identifer, amp:fulloid, or amp:compressoid
                /// May also contain DC-instance for parameterized OID
        }
        /// are type and cat necessary?
        extension MID-type {
                argument "value";
                description "One of data, control, literal, or operator. "
                        +"Default is data.";
        }
        extension MID-category {
                argument "value";
                description "One of atomic, computed, or collection. "
                        +"Default is atomic.";
        }
        extension MID-issuer {
                argument "value";
                description "A numeric value identifying an issuer.";
        }
        extension MID-tag {
                argument "value";
                description "A numeric value identifying a tag.";
        }

        extension BLOB-instance {
                argument "value";
                description
                        "Instantiate a value of BLOB from a text value. "
                        +"The value is encoded in Base-64 per RFC3548. ";
        }

        extension DC-instance {
                description
                        "Instantiate a value of DC from BLOB-instance substatements.";
        }
        extension TDC-instance {
                description
                        "Instantiate a value of TDC from *-instance substatements.";
        }
        extension MC-instance {
                description
                        "Instantiate a value of MC from MID-instance substatements.";
        }

        /// Really is just MC-instance
        extension MACRO-instance {
                description
                        "Instantiate a value of MACRO from MID-instance substatements.";
        }

}
