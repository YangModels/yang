module ietf-pm-interval-capabilities {
  yang-version 1.1;
  namespace
    "urn:ietf:params:xml:ns:yang:ietf-pm-interval-capabilities";
  prefix ipc;

  import ietf-pm-collection {
    prefix pm-coll;
    reference "draft-ietf-ccamp-pm-measurements-yang";
  }

  organization
    "IETF Common Control and Measurement Plane (ccamp)
     Working Group";
  contact
    "WG Web: <https://datatracker.ietf.org/wg/ccamp/>
     Editor: Bin Yeong Yoon <mailto:byyun@etri.re.kr>";
  description
    "This YANG module defines a data model for discovering and
     expressing performance management (PM) interval capabilities
     in network equipment. The module enables clients to discover
     what sampling and measurement intervals a server can support
     for different performance parameters within various
     parameter profiles.

     This module provides hierarchical interval capability
     discovery where measurement intervals must be multiples of
     their corresponding sampling intervals, and each parameter
     can have different interval capabilities within parameter
     profiles.

     This module is designed to work with ietf-pm-collection for
     complete PM streaming solutions and supports both real-time
     monitoring and long-term trend analysis.";

  revision 2026-05-02 {
    description
      "Companion module ietf-pm-collection replaces measurement
       methods with collection types (counts, snapshot,
       tidemarks) and renames the grouping and container to
       collection-types per ITU-T G.7710; this module continues
       to describe interval capabilities for that design.";
    reference
      "RFC XXXX: A YANG Data Model of Performance Management
       Streaming";
  }

  /*
   * TYPEDEFs
   */
  typedef interval-unit {
    type enumeration {
      enum millisecond {
        description "Time interval in milliseconds.";
      }
      enum second {
        description "Time interval in seconds.";
      }
      enum minute {
        description "Time interval in minutes.";
      }
      enum hour {
        description "Time interval in hours.";
      }
      enum day {
        description "Time interval in days.";
      }
    }
    description "Supported units for expressing time intervals.";
  }

  /*
   * IDENTITIES
   */
  identity interval-capability-type {
    description
      "Base identity for different types of interval
       capabilities.";
  }

  identity sampling-interval-capability {
    base interval-capability-type;
    description
      "Capability for sampling intervals - how frequently data
       is collected.";
  }

  identity measurement-interval-capability {
    base interval-capability-type;
    description
      "Capability for measurement intervals - how long
       measurements are aggregated.";
  }

  /*
   * GROUPINGS
   */
  grouping interval-constraints {
    description
      "Constraints for supported intervals including min/max
       values and supported units. This grouping defines the
       capability constraints for both sampling and measurement
       intervals, allowing devices to express their supported
       interval ranges, units, and granularity.";
    leaf min-value {
      type uint32;
      description
        "Minimum supported value for this interval type.";
    }
    leaf max-value {
      type uint32;
      description
        "Maximum supported value for this interval type.";
    }
    leaf-list units {
      type interval-unit;
      description
        "List of supported time units for this interval type.";
    }
    leaf default-value {
      type uint32;
      description
        "Default value recommended for this interval type.";
    }
    leaf default-unit {
      type interval-unit;
      description
        "Default unit recommended for this interval type.";
    }
    leaf granularity {
      type uint32;
      description
        "Granularity step for interval values. For example, if
         granularity is 5, then only values that are multiples
         of 5 are supported.";
    }
  }

  grouping parameter-interval-capabilities {
    description
      "Interval capabilities for a specific parameter within a
       profile. This grouping defines the complete interval
       capability information for a single performance
       parameter, including its name and hierarchical interval
       relationships. The structure uses mapping-based discovery
       where all interval information is contained within the
       sampling-interval structure.";
    leaf name {
      type string;
      description
        "Name of the performance parameter (e.g., es, ses,
         bbe).";
    }
    container interval-relationships {
      description
        "Defines hierarchical relationships between sampling and
         measurement intervals for this parameter. Measurement
         intervals must be multiples of their corresponding
         sampling intervals.";
      list sampling-interval {
        key "id";
        description
          "Maps sampling intervals to their compatible
           measurement intervals with complete capability
           information.";
        leaf id {
          type string;
          description
            "Unique identifier for this sampling interval
             capability.";
        }
        uses interval-constraints;
        list measurement-interval {
          key "id";
          description
            "Detailed information for each compatible
             measurement interval within the sampling interval
             structure.";
          leaf id {
            type string;
            description
              "Unique identifier for this measurement interval
               capability.";
          }
          uses interval-constraints;
        }
      }
    }
  }

  grouping profile-parameter-capabilities {
    description
      "Capabilities for all parameters within a specific
       parameter profile. This grouping defines the complete
       capability information for a parameter profile, including
       the profile name and all performance parameters with
       their respective interval capabilities.";
    leaf name {
      type pm-coll:profile-names;
      description
        "Name of the parameter profile (e.g.,
         itu-transport-maintenance-15min).";
    }
    list pm-parameter {
      key "name";
      description
        "List of parameters with their specific interval
         capabilities within this profile.";
      uses parameter-interval-capabilities;
    }
  }

  /*
   * MAIN CONTAINER
   */
  container pm-interval-capabilities {
    description
      "Main container for hierarchical PM interval capabilities.
       This container provides comprehensive information about
       the sampling and measurement intervals that a server can
       support for different parameters within different
       parameter profiles.";
    config false;

    list parameter-profile {
      key "name";
      description
        "List of parameter profiles with their parameter-
         specific interval capabilities. Each profile represents
         a collection of parameters that share common
         measurement requirements but may have different
         interval capabilities.";
      uses profile-parameter-capabilities;
    }
  }
}
