module ietf-pcep {
  yang-version 1.1;
  namespace "urn:ietf:params:xml:ns:yang:ietf-pcep";
  prefix pcep;

  import ietf-inet-types {
    prefix inet;
    reference
      "RFC 6991: Common YANG Data Types";
  }
  import ietf-yang-types {
    prefix yang;
    reference
      "RFC 6991: Common YANG Data Types";
  }
  import ietf-te-types {
    prefix te-types;
    reference
      "RFC 8776: Common YANG Data Types for Traffic Engineering";
  }
  import ietf-key-chain {
    prefix key-chain;
    reference
      "RFC 8177: YANG Data Model for Key Chains";
  }
  import ietf-netconf-acm {
    prefix nacm;
    reference
      "RFC 8341: Network Configuration Protocol (NETCONF) Access
       Control Model";
  }
  import ietf-tls-server {
    prefix tlss;
    reference
      "I-D.ietf-netconf-tls-client-server: YANG Groupings for TLS
       Clients and TLS Servers";
  }
  import ietf-tls-client {
    prefix tlsc;
    reference
      "I-D.ietf-netconf-tls-client-server: YANG Groupings for TLS
       Clients and TLS Servers";
  }
  import ietf-ospf {
    prefix ospf;
    reference
      "I-D.ietf-ospf-yang: YANG Data Model for OSPF Protocol";
  }
  import ietf-isis {
    prefix isis;
    reference
      "I-D.ietf-isis-yang-isis-cfg: YANG Data Model for IS-IS
       Protocol";
  }

  organization
    "IETF PCE (Path Computation Element) Working Group";
  contact
    "WG Web:  <https://tools.ietf.org/wg/pce/>
     WG List:  <mailto:pce@ietf.org>
     Editor:   Dhruv Dhody
              <mailto:dhruv.ietf@gmail.com>";
  description
    "The YANG module defines a generic configuration and
     operational model for PCEP.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).

     This version of this YANG module is part of RFC XXXX; see the
     RFC itself for full legal notices.";

  revision 2021-02-22 {
    description
      "Initial revision.";
    reference
      "RFC XXXX:  A YANG Data Model for Path Computation
       Element Communications Protocol (PCEP)";
  }

  /*
   * Typedefs
   */

  typedef pcep-role {
    type enumeration {
      enum unknown {
        value 0;
        description
          "An unknown role";
      }
      enum pcc {
        value 1;
        description
          "The role of a Path Computation Client";
      }
      enum pce {
        value 2;
        description
          "The role of Path Computation Element";
      }
      enum pcc-and-pce {
        value 3;
        description
          "The role of both Path Computation Client and
           Path Computation Element";
      }
    }
    description
      "The role of a PCEP speaker.
       Takes one of the following values
       - unknown(0): the role is not known.
       - pcc(1): the role is of a Path Computation
        Client (PCC).
       - pce(2): the role is of a Path Computation
        Server (PCE).
       - pccAndPce(3): the role is of both a PCC and
        a PCE.";
    reference
      "RFC 5440: Path Computation Element (PCE) Communication
       Protocol (PCEP)";
  }

  typedef pcep-oper-status {
    type enumeration {
      enum oper-status-up {
        value 1;
        description
          "The PCEP entity is active";
      }
      enum oper-status-down {
        value 2;
        description
          "The PCEP entity is inactive";
      }
      enum oper-status-going-up {
        value 3;
        description
          "The PCEP entity is activating";
      }
      enum oper-status-going-down {
        value 4;
        description
          "The PCEP entity is deactivating";
      }
      enum oper-status-failed {
        value 5;
        description
          "The PCEP entity has failed and will recover
           when possible.";
      }
      enum oper-status-failed-perm {
        value 6;
        description
          "The PCEP entity has failed and will not recover
           without operator intervention";
      }
    }
    description
      "The operational status of the PCEP entity.
       Takes one of the following values
       - oper-status-up(1): Active
       - oper-status-down(2): Inactive
       - oper-status-going-up(3): Activating
       - oper-status-going-down(4): Deactivating
       - oper-status-failed(5): Failed
       - oper-status-failed-perm(6): Failed Permanantly";
    reference
      "RFC 5440: Path Computation Element (PCE) Communication
       Protocol (PCEP)";
  }

  typedef pcep-initiator {
    type enumeration {
      enum local {
        value 1;
        description
          "The local PCEP entity initiated the session";
      }
      enum remote {
        value 2;
        description
          "The remote PCEP peer initiated the session";
      }
    }
    description
      "The initiator of the session, that is, whether the TCP
       connection was initiated by the local PCEP entity or
       the remote peer.
       Takes one of the following values
       - local(1): Initiated locally
       - remote(2): Initiated remotely";
  }

  typedef pcep-sess-state {
    type enumeration {
      enum tcp-pending {
        value 1;
        description
          "The tcp-pending state of PCEP session.";
      }
      enum open-wait {
        value 2;
        description
          "The open-wait state of PCEP session.";
      }
      enum keep-wait {
        value 3;
        description
          "The keep-wait state of PCEP session.";
      }
      enum session-up {
        value 4;
        description
          "The session-up state of PCEP session.";
      }
    }
    description
      "The current state of the session.
       The set of possible states excludes the idle state
       since entries do not exist in the idle state.
       Takes one of the following values
       - tcp-pending(1): PCEP TCP Pending state
       - open-wait(2): PCEP Open Wait state
       - keep-wait(3): PCEP Keep Wait state
       - session-up(4): PCEP Session Up state";
    reference
      "RFC 5440: Path Computation Element (PCE) Communication
       Protocol (PCEP)";
  }

  typedef domain-ospf-area {
    type ospf:area-id-type;
    description
      "OSPF Area ID.";
    reference
      "I-D.ietf-ospf-yang: YANG Data Model for OSPF Protocol";
  }

  typedef domain-isis-area {
    type isis:area-address;
    description
      "IS-IS Area ID.";
    reference
      "I-D.ietf-isis-yang-isis-cfg: YANG Data Model for IS-IS
       Protocol";
  }

  typedef domain-as {
    type inet:as-number;
    description
      "Autonomous System number.";
  }

  typedef domain {
    type union {
      type domain-ospf-area;
      type domain-isis-area;
      type domain-as;
    }
    description
      "The Domain Information";
  }

  typedef operational-state {
    type enumeration {
      enum down {
        value 0;
        description
          "not active.";
      }
      enum up {
        value 1;
        description
          "signalled.";
      }
      enum active {
        value 2;
        description
          "up and carrying traffic.";
      }
      enum going-down {
        value 3;
        description
          "LSP is being torn down, resources are
           being released.";
      }
      enum going-up {
        value 4;
        description
          "LSP is being signalled.";
      }
    }
    description
      "The operational status of the LSP";
    reference
      "RFC 8231: Path Computation Element Communication Protocol
       (PCEP) Extensions for Stateful PCE";
  }

  typedef sync-state {
    type enumeration {
      enum pending {
        value 0;
        description
          "The state synchronization
           has not started.";
      }
      enum ongoing {
        value 1;
        description
          "The state synchronization
           is ongoing.";
      }
      enum finished {
        value 2;
        description
          "The state synchronization
           is finished.";
      }
    }
    description
      "The LSP-DB state synchronization operational
       status.";
    reference
      "RFC 8231: Path Computation Element Communication Protocol
       (PCEP) Extensions for Stateful PCE";
  }

  /*
   * Features
   */

  feature svec {
    description
      "Support synchronized path computation.";
    reference
      "RFC 5440: Path Computation Element (PCE) Communication
       Protocol (PCEP)";
  }

  feature gmpls {
    description
      "Support GMPLS.";
    reference
      "RFC 8779: PCEP extensions for GMPLS";
  }

  feature objective-function {
    description
      "Support OF as per RFC 5541.";
    reference
      "RFC 5541: Encoding of Objective Functions in the Path
       Computation Element Communication Protocol (PCEP)";
  }

  feature global-concurrent {
    description
      "Support GCO as per RFC 5557.";
    reference
      "RFC 5557: Path Computation Element Communication Protocol
       (PCEP) Requirements and Protocol Extensions in Support of
       Global Concurrent Optimization";
  }

  feature path-key {
    description
      "Support path-key as per RFC 5520.";
    reference
      "RFC 5520: Preserving Topology Confidentiality in Inter-
       Domain Path Computation Using a Path-Key-Based Mechanism";
  }

  feature p2mp {
    description
      "Support P2MP as per RFC 8306.";
    reference
      "RFC 8306: Extensions to the Path Computation Element
       Communication Protocol (PCEP) for Point-to-Multipoint
       Traffic Engineering Label Switched Paths";
  }

  feature stateful {
    description
      "Support stateful PCE as per RFC 8231.";
    reference
      "RFC 8231: Path Computation Element Communication Protocol
       (PCEP) Extensions for Stateful PCE";
  }

  feature sync-opt {
    description
      "Support stateful sync optimization
       as per RFC 8232";
    reference
      "RFC 8232: Optimizations of Label Switched Path State
       Synchronization Procedures for a Stateful PCE";
  }

  feature pce-initiated {
    description
      "Support PCE-Initiated LSP as per
       RFC 8281.";
    reference
      "RFC 8281: Path Computation Element Communication Protocol
       (PCEP) Extensions for PCE-Initiated LSP Setup in a Stateful
       PCE Model";
  }

  feature tls {
    description
      "Support PCEP over TLS as per
       RFC 8253.";
    reference
      "RFC 8253: PCEPS: Usage of TLS to Provide a Secure Transport
       for the Path Computation Element Communication Protocol
       (PCEP)";
  }

  feature sr {
    description
      "Support Segment Routing for PCE.";
    reference
      "RFC 8664: Path Computation Element Communication Protocol
       (PCEP) Extensions for Segment Routing";
  }

  feature association {
    description
      "Support Association in PCEP.";
    reference
      "RFC 8697: Path Computation Element Communication Protocol
       (PCEP) Extensions for Establishing Relationships between
       Sets of Label Switched Paths (LSPs)";
  }

  /*
   * Identities
   */

  identity domain-type {
    description
      "Base Domain Type for PCE";
  }

  identity ospf-area {
    base domain-type;
    description
      "The OSPF area.";
  }

  identity isis-area {
    base domain-type;
    description
      "The IS-IS area.";
  }

  identity autonomous-system {
    base domain-type;
    description
      "The Autonomous System (AS).";
  }

  identity lsp-error {
    if-feature "stateful";
    description
      "Base LSP error";
    reference
      "RFC 8231: Path Computation Element Communication Protocol
       (PCEP) Extensions for Stateful PCE";
  }

  identity no-error-lsp-error {
    if-feature "stateful";
    base lsp-error;
    description
      "No error, LSP is fine.";
    reference
      "RFC 8231: Path Computation Element Communication Protocol
       (PCEP) Extensions for Stateful PCE";
  }

  identity unknown-lsp-error {
    if-feature "stateful";
    base lsp-error;
    description
      "Unknown reason.";
    reference
      "RFC 8231: Path Computation Element Communication Protocol
       (PCEP) Extensions for Stateful PCE";
  }

  identity limit-lsp-error {
    if-feature "stateful";
    base lsp-error;
    description
      "Limit reached for PCE-controlled LSPs.";
    reference
      "RFC 8231: Path Computation Element Communication Protocol
       (PCEP) Extensions for Stateful PCE";
  }

  identity pending-lsp-error {
    if-feature "stateful";
    base lsp-error;
    description
      "Too many pending LSP update requests.";
    reference
      "RFC 8231: Path Computation Element Communication Protocol
       (PCEP) Extensions for Stateful PCE";
  }

  identity unacceptable-lsp-error {
    if-feature "stateful";
    base lsp-error;
    description
      "Unacceptable parameters.";
    reference
      "RFC 8231: Path Computation Element Communication Protocol
       (PCEP) Extensions for Stateful PCE";
  }

  identity internal-lsp-error {
    if-feature "stateful";
    base lsp-error;
    description
      "Internal error.";
    reference
      "RFC 8231: Path Computation Element Communication Protocol
       (PCEP) Extensions for Stateful PCE";
  }

  identity admin-lsp-error {
    if-feature "stateful";
    base lsp-error;
    description
      "LSP administratively brought down.";
    reference
      "RFC 8231: Path Computation Element Communication Protocol
       (PCEP) Extensions for Stateful PCE";
  }

  identity preempted-lsp-error {
    if-feature "stateful";
    base lsp-error;
    description
      "LSP preempted.";
    reference
      "RFC 8231: Path Computation Element Communication Protocol
       (PCEP) Extensions for Stateful PCE";
  }

  identity rsvp-lsp-error {
    if-feature "stateful";
    base lsp-error;
    description
      "RSVP signaling error.";
    reference
      "RFC 8231: Path Computation Element Communication Protocol
       (PCEP) Extensions for Stateful PCE";
  }

  /*
   * Groupings
   */

  grouping pce-scope {
    description
      "This grouping defines PCE path computation scope
       information which maybe relevant to PCE selection.
       This information corresponds to PCE auto-discovery
       information.";
    reference
      "RFC 5088: OSPF Protocol Extensions for Path
       Computation Element (PCE) Discovery
       RFC 5089: IS-IS Protocol Extensions for Path
       Computation Element (PCE) Discovery";
    leaf path-scope {
      type bits {
        bit intra-area-scope {
          description
            "PCE can compute intra-area paths.";
        }
        bit inter-area-scope {
          description
            "PCE can compute inter-area paths.";
        }
        bit inter-area-scope-default {
          description
            "PCE can act as a default PCE for inter-area
             path computation.";
        }
        bit inter-as-scope {
          description
            "PCE can compute inter-AS paths.";
        }
        bit inter-as-scope-default {
          description
            "PCE can act as a default PCE for inter-AS
             path computation.";
        }
        bit inter-layer-scope {
          description
            "PCE can compute inter-layer paths.";
        }
      }
      description
        "The field corresponding to the path scope bits";
    }
    leaf intra-area-pref {
      type uint8 {
        range "0..7";
      }
      description
        "The PCE's preference for intra-area TE LSP
         computation.";
    }
    leaf inter-area-pref {
      type uint8 {
        range "0..7";
      }
      description
        "The PCE's preference for inter-area TE LSP
         computation.";
    }
    leaf inter-as-pref {
      type uint8 {
        range "0..7";
      }
      description
        "The PCE's preference for inter-AS TE LSP
         computation.";
    }
    leaf inter-layer-pref {
      type uint8 {
        range "0..7";
      }
      description
        "The PCE's preference for inter-layer TE LSP
         computation.";
    }
  }

  //pce-scope

  grouping domain {
    description
      "This grouping specifies a Domain where the
       PCEP speaker has topology visibility.";
    leaf domain-type {
      type identityref {
        base domain-type;
      }
      description
        "The domain type.";
    }
    leaf domain {
      type domain;
      description
        "The domain Information.";
    }
  }

  //domain

  grouping info {
    description
      "This grouping specifies all information which
       maybe relevant to both PCC and PCE.
       This information corresponds to PCE auto-discovery
       information.";
    container domain {
      description
        "The local domain for the PCEP entity";
      list domain {
        key "domain-type domain";
        description
          "The local domain.";
        uses domain {
          description
            "The local domain for the PCEP entity.";
        }
      }
    }
    container capability {
      description
        "The PCEP entity capability information of local
         PCEP entity. This maybe relevant to PCE selection
         as well. This information corresponds to PCE auto-
         discovery information.";
      reference
        "RFC 5088: OSPF Protocol Extensions for Path
         Computation Element (PCE) Discovery
         RFC 5089: IS-IS Protocol Extensions for Path
         Computation Element (PCE) Discovery";
      leaf capability {
        type bits {
          bit gmpls {
            if-feature "gmpls";
            description
              "Path computation with GMPLS link
               constraints.";
          }
          bit bi-dir {
            description
              "Bidirectional path computation.";
          }
          bit diverse {
            description
              "Diverse path computation.";
          }
          bit load-balance {
            description
              "Load-balanced path computation.";
          }
          bit synchronize {
            if-feature "svec";
            description
              "Synchronized paths computation.";
          }
          bit objective-function {
            if-feature "objective-function";
            description
              "Support for multiple objective functions.";
          }
          bit add-path-constraint {
            description
              "Support for additive path constraints (max
               hop count, etc.).";
          }
          bit prioritization {
            description
              "Support for request prioritization.";
          }
          bit multi-request {
            description
              "Support for multiple requests per message.";
          }
          bit global-concurrent {
            if-feature "global-concurrent";
            description
              "Support for Global Concurrent Optimization
               (GCO).";
          }
          bit p2mp {
            if-feature "p2mp";
            description
              "Support for P2MP path computation.";
          }
          bit active {
            if-feature "stateful";
            description
              "Support for active stateful PCE.";
          }
          bit passive {
            if-feature "stateful";
            description
              "Support for passive stateful PCE.";
          }
          bit p2mp-active {
            if-feature "stateful";
            if-feature "p2mp";
            description
              "Support for active stateful PCE for P2MP.";
          }
          bit p2mp-passive {
            if-feature "stateful";
            if-feature "p2mp";
            description
              "Support for passive stateful PCE for P2MP.";
          }
          bit p2mp-pce-initiated {
            if-feature "stateful";
            if-feature "pce-initiated";
            if-feature "p2mp";
            description
              "Support for PCE-initiated LSP for P2MP.";
          }
        }
        description
          "The bits string indicating the capabiliies";
        reference
          "RFC 5088: OSPF Protocol Extensions for Path
           Computation Element (PCE) Discovery
           RFC 5089: IS-IS Protocol Extensions for Path
           Computation Element (PCE) Discovery";
      }
      leaf pce-initiated {
        if-feature "pce-initiated";
        type boolean;
        description
          "Set to true if PCE-initiated LSP capability is
           enabled.";
        reference
          "RFC 8281: Path Computation Element Communication
           Protocol (PCEP) Extensions for PCE-Initiated LSP
           Setup in a Stateful PCE Model";
      }
      leaf include-db-ver {
        if-feature "stateful";
        if-feature "sync-opt";
        type boolean;
        description
          "Support inclusion of LSP-DB-VERSION
           in LSP object";
        reference
          "RFC 8232: Optimizations of Label Switched Path State
           Synchronization Procedures for a Stateful PCE";
      }
      leaf trigger-resync {
        if-feature "stateful";
        if-feature "sync-opt";
        type boolean;
        description
          "Support PCE triggered re-synchronization";
        reference
          "RFC 8232: Optimizations of Label Switched Path State
           Synchronization Procedures for a Stateful PCE";
      }
      leaf trigger-initial-sync {
        if-feature "stateful";
        if-feature "sync-opt";
        type boolean;
        description
          "PCE triggered initial synchronization";
        reference
          "RFC 8232: Optimizations of Label Switched Path State
           Synchronization Procedures for a Stateful PCE";
      }
      leaf incremental-sync {
        if-feature "stateful";
        if-feature "sync-opt";
        type boolean;
        description
          "Support incremental (delta) sync";
        reference
          "RFC 8232: Optimizations of Label Switched Path State
           Synchronization Procedures for a Stateful PCE";
      }
      container sr {
        if-feature "sr";
        description
          "If segment routing is supported";
        reference
          "RFC 8664: Path Computation Element Communication Protocol
           (PCEP) Extensions for Segment Routing";
        leaf enabled {
          type boolean;
          description
            "Set to true if SR is enabled";
        }
        leaf msd-limit {
          type boolean;
          default "false";
          description
            "True indicates no limit on MSD, the
             leaf msd is ignored";
        }
        leaf nai {
          type boolean;
          default "false";
          description
            "True indicates capability to resolve NAI
             to SID";
        }
      }
      //sr
    }
    //capability
    leaf msd {
      if-feature "sr";
      type uint8;
      description
        "Maximum SID Depth for SR";
      reference
        "RFC 8664: Path Computation Element Communication Protocol
         (PCEP) Extensions for Segment Routing";
    }
  }

  //info

  grouping pce-info {
    description
      "This grouping specifies all PCE information
       which maybe relevant to the PCE selection.
       This information corresponds to PCE auto-discovery
       information.";
    container scope {
      description
        "The path computation scope";
      uses pce-scope;
    }
    container neigh-domains {
      description
        "The list of neighbour PCE-Domain
         toward which a PCE can compute
         paths";
      list domain {
        key "domain-type domain";
        description
          "The neighbour domain.";
        uses domain {
          description
            "The PCE neighbour domain.";
        }
      }
    }
  }

  //pce-info

  grouping notification-instance-hdr {
    description
      "This group describes common instance specific data
       for notifications.";
    leaf peer-addr {
      type leafref {
        path "/pcep/entity/peers/peer/addr";
      }
      description
        "Reference to peer address";
    }
  }

  // notification-instance-hdr

  grouping notification-session-hdr {
    description
      "This group describes common session instance specific
       data for notifications.";
    leaf session-initiator {
      type leafref {
        path "/pcep/entity/peers/peer/sessions/"
           + "session/initiator";
      }
      description
        "Reference to pcep session initiator leaf";
    }
  }

  // notification-session-hdr

  grouping of-list {
    description
      "List of OF";
    reference
      "RFC 5541: Encoding of Objective Functions in the Path
       Computation Element Communication Protocol (PCEP)";
    list objective-function {
      key "of";
      description
        "The list of authorized OF";
      leaf of {
        type identityref {
          base te-types:objective-function-type;
        }
        description
          "The OF authorized";
      }
    }
  }

  /*
   * Configuration data nodes
   */

  container pcep {
    presence "The PCEP is enabled";
    description
      "Parameters for list of configured PCEP entities
       on the device.";
    container entity {
      description
        "The configured PCEP entity on the device.";
      leaf addr {
        type inet:ip-address;
        mandatory true;
        description
          "The local Internet address of this PCEP entity.
           If operating as a PCE server, the PCEP entity
           listens on this address. If operating as a PCC,
           the PCEP entity binds outgoing TCP connections
           to this address. It is possible for the PCEP entity
           to operate both as a PCC and a PCE Server, in which
           case it uses this address both to listen for incoming
           TCP connections and to bind outgoing TCP connections.";
      }
      leaf enabled {
        type boolean;
        default "true";
        description
          "The administrative status of this PCEP
           Entity.";
      }
      leaf role {
        type pcep-role;
        mandatory true;
        description
          "The role that this entity can play.
           Takes one of the following values.
           - unknown(0): this PCEP Entity role is not
           known.
           - pcc(1): this PCEP Entity is a PCC.
           - pce(2): this PCEP Entity is a PCE.
           - pcc-and-pce(3): this PCEP Entity is both
           a PCC and a PCE.";
      }
      leaf description {
        type string;
        description
          "Description of the PCEP entity configured
           by the user";
      }
      leaf speaker-entity-id {
        if-feature "sync-opt";
        type string;
        description
          "The Speaker Entity Identifier";
        reference
          "RFC 8232: Optimizations of Label Switched
           Path State  Synchronization Procedures for
           a Stateful PCE";
      }
      leaf admin-status {
        type boolean;
        default "true";
        description
          "The administrative status of this PCEP Entity.
           The value true represents admin status as up.
           This is the desired operational status as
           currently set by an operator or by default in
           the implementation. The value of oper-status
           represents the current status of an attempt to
           reach this desired status.";
      }
      leaf index {
        type uint32;
        config false;
        description
          "The index of the operational PECP entity";
      }
      leaf oper-status {
        type pcep-oper-status;
        config false;
        description
          "The operational status of the PCEP entity.
           Takes one of the following values.
           - oper-status-up(1): the PCEP entity is active.
           - oper-status-down(2): the PCEP entity is inactive.
           - oper-status-going-up(3): the PCEP entity is
           activating.
           - oper-status-going-down(4): the PCEP entity is
           deactivating.
           - oper-status-failed(5): the PCEP entity has
           failed and will recover when possible.
           - oper-status-failed-perm(6): the PCEP entity
           has failed and will not recover without
           operator intervention.";
      }
      uses info {
        description
          "Local PCEP entity information";
      }
      container pce-info {
        when "../role = 'pce'"
           + "or "
           + "../role = 'pcc-and-pce'" {
          description
            "These fields are applicable when the role is PCE.";
        }
        description
          "The Local PCE Entity PCE information";
        uses pce-info {
          description
            "Local PCE information";
        }
        container path-key {
          if-feature "path-key";
          description
            "Path-Key Configuration";
          reference
            "RFC 5520: Preserving Topology Confidentiality in Inter-
             Domain Path Computation Using a Path-Key-Based Mechanism";
          leaf enabled {
            type boolean;
            description
              "Enabled or Disabled";
          }
          leaf discard-timer {
            type uint32;
            units "minutes";
            default "10";
            description
              "A timer to discard unwanted path-keys";
          }
          leaf reuse-time {
            type uint32;
            units "minutes";
            default "30";
            description
              "A time after which the path-keys could be reused";
          }
          leaf pce-id {
            type inet:ip-address;
            description
              "PCE Address to be used in each Path-Key Subobject
               (PKS)";
          }
        }
      }
      leaf connect-timer {
        type uint16 {
          range "1..65535";
        }
        units "seconds";
        default "60";
        description
          "The time in seconds that the PCEP entity will wait
           to establish a TCP connection with a peer.  If a
           TCP connection is not established within this time
           then PCEP aborts the session setup attempt.";
        reference
          "RFC 5440: Path Computation Element (PCE) Communication
           Protocol (PCEP)";
      }
      leaf connect-max-retry {
        type uint32;
        default "5";
        description
          "The maximum number of times the system tries to
           establish a TCP connection to a peer before the
           session with the peer transitions to the idle
           state.";
        reference
          "RFC 5440: Path Computation Element (PCE) Communication
           Protocol (PCEP)";
      }
      leaf init-backoff-timer {
        type uint16 {
          range "1..65535";
        }
        units "seconds";
        description
          "The initial back-off time in seconds for retrying
           a failed session setup attempt to a peer.
           The back-off time increases for each failed
           session setup attempt, until a maximum back-off
           time is reached.  The maximum back-off time is
           max-backoff-timer.";
        reference
          "RFC 5440: Path Computation Element (PCE) Communication
           Protocol (PCEP)";
      }
      leaf max-backoff-timer {
        type uint32;
        units "seconds";
        description
          "The maximum back-off time in seconds for retrying
           a failed session setup attempt to a peer.
           The back-off time increases for each failed session
           setup attempt, until this maximum value is reached.
           Session setup attempts then repeat periodically
           without any further increase in back-off time.";
        reference
          "RFC 5440: Path Computation Element (PCE) Communication
           Protocol (PCEP)";
      }
      leaf open-wait-timer {
        type uint16;
        units "seconds";
        default "60";
        config false;
        description
          "The time in seconds that the PCEP entity will wait
           to receive an Open message from a peer after the
           TCP connection has come up.
           If no Open message is received within this time then
           PCEP terminates the TCP connection and deletes the
           associated sessions.";
        reference
          "RFC 5440: Path Computation Element (PCE) Communication
           Protocol (PCEP)";
      }
      leaf keep-wait-timer {
        type uint16;
        units "seconds";
        default "60";
        config false;
        description
          "The time in seconds that the PCEP entity will wait
           to receive a Keepalive or PCErr message from a peer
           during session initialization after receiving an
           Open message.  If no Keepalive or PCErr message is
           received within this time then PCEP terminates the
           TCP connection and deletes the associated
           sessions.";
        reference
          "RFC 5440: Path Computation Element (PCE) Communication
           Protocol (PCEP)";
      }
      leaf keep-alive-timer {
        type uint8;
        units "seconds";
        default "30";
        description
          "The keep alive transmission timer that this PCEP
           entity will propose in the initial OPEN message of
           each session it is involved in.  This is the
           maximum time between two consecutive messages sent
           to a peer. Zero means that the PCEP entity prefers
           not to send Keepalives at all.
           Note that the actual Keepalive transmission
           intervals, in either direction of an active PCEP
           session, are determined by negotiation between the
           peers as specified by RFC 5440, and so may differ
           from this configured value.";
        reference
          "RFC 5440: Path Computation Element (PCE) Communication
           Protocol (PCEP)";
      }
      leaf dead-timer {
        type uint8;
        units "seconds";
        must '(. > ../keep-alive-timer)' {
          error-message "The dead timer must be "
                      + "larger than the keep alive timer";
        }
        default "120";
        description
          "The dead timer that this PCEP entity will propose
           in the initial OPEN message of each session it is
           involved in. This is the time after which a peer
           should declare a session down if it does not
           receive any PCEP messages. Zero suggests that the
           peer does not run a dead timer at all.";
        reference
          "RFC 5440: Path Computation Element (PCE) Communication
           Protocol (PCEP)";
      }
      leaf allow-negotiation {
        type boolean;
        description
          "Whether the PCEP entity will permit negotiation of
           session parameters.";
      }
      leaf max-keep-alive-timer {
        type uint8;
        units "seconds";
        description
          "In PCEP session parameter negotiation in seconds,
           the maximum value that this PCEP entity will
           accept from a peer for the interval between
           Keepalive transmissions. Zero means that the PCEP
           entity will allow no Keepalive transmission at
           all.";
      }
      leaf max-dead-timer {
        type uint8;
        units "seconds";
        description
          "In PCEP session parameter negotiation in seconds,
           the maximum value that this PCEP entity will accept
           from a peer for the Dead timer.  Zero means that
           the PCEP entity will allow not running a Dead
           timer.";
      }
      leaf min-keep-alive-timer {
        type uint8;
        units "seconds";
        description
          "In PCEP session parameter negotiation in seconds,
           the minimum value that this PCEP entity will
           accept for the interval between Keepalive
           transmissions. Zero means that the PCEP entity
           insists on no Keepalive transmission at all.";
      }
      leaf min-dead-timer {
        type uint8;
        units "seconds";
        description
          "In PCEP session parameter negotiation in
           seconds, the minimum value that this PCEP entity
           will accept for the Dead timer.  Zero means that
           the PCEP entity insists on not running a Dead
           timer.";
      }
      leaf sync-timer {
        if-feature "svec";
        type uint16;
        units "seconds";
        default "60";
        description
          "The value of SyncTimer in seconds is used in the
           case of synchronized path computation request
           using the SVEC object. Consider the case where a
           PCReq message is received by a PCE that contains
           the SVEC object referring to M synchronized path
           computation requests.  If after the expiration of
           the SyncTimer all the M path computation requests
           have not been, received a protocol error is
           triggered and the PCE must cancel the whole set
           of path computation requests.
           The aim of the SyncTimer is to avoid the storage
           of unused synchronized requests should one of
           them get lost for some reasons (for example, a
           misbehaving PCC).
           Zero means that the PCEP entity does not use the
           SyncTimer.";
        reference
          "RFC 5440: Path Computation Element (PCE)
           Communication Protocol (PCEP)";
      }
      leaf request-timer {
        type uint16 {
          range "1..65535";
        }
        units "seconds";
        description
          "The maximum time that the PCEP entity will wait
           for a response to a PCReq message.";
      }
      leaf max-sessions {
        type uint32;
        description
          "Maximum number of sessions involving this PCEP
           entity that can exist at any time.";
      }
      leaf max-unknown-reqs {
        type uint32;
        default "5";
        description
          "The maximum number of unrecognized requests and
           replies that any session on this PCEP entity is
           willing to accept per minute before terminating
           the session.
           A PCRep message contains an unrecognized reply
           if it contains an RP object whose request ID
           does not correspond to any in-progress request
           sent by this PCEP entity.
           A PCReq message contains an unrecognized request
           if it contains an RP object whose request ID is
           zero.";
        reference
          "RFC 5440: Path Computation Element (PCE)
           Communication Protocol (PCEP)";
      }
      leaf max-unknown-msgs {
        type uint32;
        default "5";
        description
          "The maximum number of unknown messages that any
           session on this PCEP entity is willing to accept
           per minute before terminating the session.";
        reference
          "RFC 5440: Path Computation Element (PCE)
           Communication Protocol (PCEP)";
      }
      leaf pcep-notification-max-rate {
        type uint32;
        mandatory true;
        description
          "This variable indicates the maximum number of
           notifications issued per second. If events
           occur more rapidly, the implementation may
           simply fail to emit these notifications during
           that period, or may queue them until an
           appropriate time. A value of 0 means no
           notifications are emitted and all should be
           discarded (that is, not queued).";
      }
      container stateful-parameter {
        if-feature "stateful";
        description
          "The configured stateful PCE parameters";
        leaf state-timeout {
          type uint32;
          units "seconds";
          description
            "When a PCEP session is terminated, a PCC
             waits for this time period before flushing
             LSP state associated with that PCEP session
             and reverting to operator-defined default
             parameters or behaviours.";
        }
        leaf redelegation-timeout {
          when "../../role = 'pcc'"
             + "or "
             + "../../role = 'pcc-and-pce'" {
            description
              "This field is applicable when the role is
               PCC";
          }
          type uint32;
          units "seconds";
          description
            "When a PCEP session is terminated, a PCC
             waits for this time period before revoking
             LSP delegation to a PCE and attempting to
             redelegate LSPs associated with the
             terminated PCEP session to an alternate
             PCE.";
        }
        leaf rpt-non-pcep-lsp {
          when "../../role = 'pcc'"
             + "or "
             + "../../role = 'pcc-and-pce'" {
            description
              "This field is applicable when the role is
               PCC";
          }
          type boolean;
          default "true";
          description
            "If set, a PCC reports LSPs that are not
             controlled by any PCE (for example, LSPs
             that are statically configured at the
             PCC). ";
        }
        reference
          "RFC 8231: Path Computation Element Communication Protocol
           (PCEP) Extensions for Stateful PCE";
      }
      container of-list {
        when "../role = 'pce'"
           + "or "
           + "../role = 'pcc-and-pce'" {
          description
            "These field are applicable when the role is
             PCE";
        }
        if-feature "objective-function";
        uses of-list;
        description
          "The authorized OF-List at PCE for all peers";
      }
      container lsp-db {
        if-feature "stateful";
        config false;
        description
          "The LSP-DB";
        leaf db-ver {
          when "../../role = 'pcc'"
             + "or "
             + "../../role = 'pcc-and-pce'" {
            description
              "This field is applicable when the role is
               PCC";
          }
          if-feature "sync-opt";
          type uint64;
          description
            "The LSP State Database Version Number";
        }
        list association-list {
          if-feature "association";
          key "type id source global-source extended-id";
          description
            "List of all PCEP associations";
          reference
            "RFC 8697: Path Computation Element Communication
             Protocol (PCEP) Extensions for Establishing
             Relationships between Sets of Label Switched
             Paths (LSPs)";
          leaf type {
            type identityref {
              base te-types:association-type;
            }
            description
              "The PCEP association type";
          }
          leaf id {
            type uint16;
            description
              "PCEP Association ID";
          }
          leaf source {
            type inet:ip-address;
            description
              "PCEP Association Source.";
          }
          leaf global-source {
            type uint32;
            description
              "PCEP Association Global Source.";
          }
          leaf extended-id {
            type string;
            description
              "Additional information to support unique
               identification.";
          }
          list lsp {
            key "plsp-id pcc-id lsp-id";
            description
              "List of all LSP in this association";
            leaf plsp-id {
              type leafref {
                path "/pcep/entity/lsp-db/"
                   + "lsp/plsp-id";
              }
              description
                "Reference to PLSP-ID in LSP-DB";
            }
            leaf pcc-id {
              type leafref {
                path "/pcep/entity/lsp-db/"
                   + "lsp/pcc-id";
              }
              description
                "Reference to PCC-ID in LSP-DB";
            }
            leaf lsp-id {
              type leafref {
                path "/pcep/entity/lsp-db/"
                   + "lsp/lsp-id";
              }
              description
                "Reference to LSP ID in LSP-DB";
            }
          }
        }
        list lsp {
          key "plsp-id pcc-id lsp-id";
          description
            "List of all LSPs in LSP-DB";
          leaf plsp-id {
            type uint32 {
              range "1..1048575";
            }
            description
              "A PCEP-specific identifier for the LSP.  A PCC
               creates a unique PLSP-ID for each LSP that is
               constant for the lifetime of a PCEP session.
               PLSP-ID is 20 bits with 0 and 0xFFFFF are
               reserved";
          }
          leaf pcc-id {
            type inet:ip-address;
            description
              "The local internet address of the PCC, that
               generated the PLSP-ID.";
          }
          leaf source {
            type inet:ip-address;
            description
              "Tunnel sender address extracted from
               LSP-IDENTIFIERS TLV";
            reference
              "RFC 8231: Path Computation Element
               Communication Protocol (PCEP) Extensions
               for Stateful PCE";
          }
          leaf destination {
            type inet:ip-address;
            description
              "Tunnel endpoint address extracted from
               LSP-IDENTIFIERS TLV";
            reference
              "RFC 8231: Path Computation Element
               Communication Protocol (PCEP) Extensions
               for Stateful PCE";
          }
          leaf tunnel-id {
            type uint16;
            description
              "Tunnel identifier used in the LSP-IDENTIFIERS
               TLV that remains constant over the life
               of the tunnel.";
            reference
              "RFC 8231: Path Computation Element
               Communication Protocol (PCEP) Extensions
               for Stateful PCE";
          }
          leaf lsp-id {
            type uint16;
            description
              "Identifier used in the LSP-IDENTIFIERS TLV
               that can be changed to allow a sender to share
               resources with itself.";
            reference
              "RFC 8231: Path Computation Element
               Communication Protocol (PCEP) Extensions
               for Stateful PCE";
          }
          leaf extended-tunnel-id {
            type inet:ip-address;
            description
              "Extended Tunnel ID of the LSP in LSP-IDENTIFIERS
               TLV.";
            reference
              "RFC 8231: Path Computation Element
               Communication Protocol (PCEP) Extensions
               for Stateful PCE";
          }
          leaf admin-state {
            type boolean;
            default "true";
            description
              "The desired operational state";
          }
          leaf operational-state {
            type operational-state;
            description
              "The operational status of the LSP";
          }
          container delegated {
            description
              "The delegation related parameters";
            leaf enabled {
              type boolean;
              default "false";
              description
                "LSP is delegated or not";
            }
            leaf peer {
              type leafref {
                path "/pcep/entity/peers/peer/addr";
              }
              must '(../enabled = true())' {
                error-message "The LSP must be delegated";
              }
              description
                "At the PCC, the reference to the PCEP peer to
                 which LSP is delegated; At the PCE, the
                 reference to the PCEP peer which delegated this
                 LSP";
            }
            leaf srp-id {
              type uint32;
              description
                "The last SRP-ID-number associated with this
                 LSP.";
            }
          }
          container initiation {
            if-feature "pce-initiated";
            description
              "The PCE initiation related parameters";
            reference
              "RFC 8281: Path Computation Element Communication
               Protocol (PCEP) Extensions for PCE-Initiated LSP
               Setup in a Stateful PCE Model";
            leaf enabled {
              type boolean;
              default "false";
              description
                "Set to true if this LSP is initiated by a PCE";
            }
            leaf peer {
              type leafref {
                path "/pcep/entity/peers/peer/addr";
              }
              must '(../enabled = true())' {
                error-message "The LSP must be PCE-Initiated";
              }
              description
                "At the PCC, the reference to the PCEP peer
                 that initiated this LSP; At the PCE, the
                 reference to the PCEP peer where the LSP
                 is initiated";
            }
          }
          leaf symbolic-path-name {
            type string;
            description
              "The symbolic path name associated with the LSP.";
            reference
              "RFC 8231: Path Computation Element Communication
               Protocol (PCEP) Extensions for Stateful PCE";
          }
          leaf last-error {
            type identityref {
              base lsp-error;
            }
            description
              "The last error for the LSP.";
          }
          leaf pst {
            type identityref {
              base te-types:path-signaling-type;
            }
            default "te-types:path-setup-rsvp";
            description
              "The Path Setup Type";
            reference
              "RFC 8408: Conveying Path Setup Type in PCE
               Communication Protocol (PCEP) Messages";
          }
          list association-list {
            if-feature "association";
            key "type id source global-source extended-id";
            description
              "List of all PCEP associations";
            leaf type {
              type leafref {
                path "/pcep/entity/lsp-db/"
                   + "association-list/type";
              }
              description
                "PCEP Association Type";
            }
            leaf id {
              type leafref {
                path "/pcep/entity/lsp-db/"
                   + "association-list/id";
              }
              description
                "PCEP Association ID";
            }
            leaf source {
              type leafref {
                path "/pcep/entity/lsp-db/"
                   + "association-list/source";
              }
              description
                "PCEP Association Source.";
            }
            leaf global-source {
              type leafref {
                path "/pcep/entity/lsp-db/"
                   + "association-list/global-source";
              }
              description
                "PCEP Association Global Source.";
            }
            leaf extended-id {
              type leafref {
                path "/pcep/entity/lsp-db/"
                   + "association-list/extended-id";
              }
              description
                "Additional information to
                 support unique identification.";
            }
            reference
              "RFC 8697: Path Computation Element Communication
               Protocol (PCEP) Extensions for Establishing
               Relationships between Sets of Label Switched
               Paths (LSPs)";
          }
        }
      }
      container path-keys {
        when "../role = 'pce' or ../role = 'pcc-and-pce'" {
          description
            "These fields are applicable when the role is
             PCE";
        }
        if-feature "path-key";
        config false;
        description
          "The path-keys generated by the PCE";
        reference
          "RFC 5520: Preserving Topology Confidentiality
           in Inter-Domain Path Computation Using a Path-
           Key-Based Mechanism";
        list path-keys {
          key "path-key";
          description
            "The list of path-keys generated by the PCE";
          leaf path-key {
            type uint16;
            description
              "The identifier, or token used to represent
               the Confidential Path Segment (CPS) within
               the context of the PCE";
          }
          container cps {
            description
              "The Confidential Path Segment (CPS)";
            list explicit-route-objects {
              key "index";
              description
                "List of explicit route objects";
              leaf index {
                type uint32;
                description
                  "ERO subobject index";
              }
              uses te-types:explicit-route-hop;
            }
          }
          leaf pcc-original {
            type leafref {
              path "/pcep/entity/peers/peer/addr";
            }
            description
              "Reference to PCC peer address of
               the original request";
          }
          leaf req-id {
            type uint32;
            description
              "The request ID of the original PCReq.";
          }
          leaf retrieved {
            type boolean;
            description
              "If path-key has been retrieved yet";
          }
          leaf pcc-retrieved {
            type leafref {
              path "/pcep/entity/peers/peer/addr";
            }
            must '(../retrieved = true())' {
              error-message "The Path-key should be retreived";
            }
            description
              "Reference to PCC peer address which
               retreived the path-key";
          }
          leaf creation-time {
            type yang:timestamp;
            description
              "The timestamp value at the time this Path-Key
               was created.";
          }
          leaf discard-time {
            type uint32;
            units "minutes";
            description
              "A time after which this path-keys will be
               discarded";
          }
          leaf reuse-time {
            type uint32;
            units "minutes";
            description
              "A time after which this path-keys could be
               reused";
          }
        }
      }
      container peers {
        description
          "The list of configured peers for the
           entity (remote PCE)";
        list peer {
          key "addr";
          description
            "The peer configured for the entity.
             (remote PCE)";
          leaf addr {
            type inet:ip-address;
            description
              "The local Internet address of this
               PCEP peer.";
          }
          leaf role {
            type pcep-role;
            mandatory true;
            description
              "The role of the PCEP Peer.
               Takes one of the following values.
               - unknown(0): this PCEP peer role is not
               known.
               - pcc(1): this PCEP peer is a PCC.
               - pce(2): this PCEP peer is a PCE.
               - pcc-and-pce(3): this PCEP peer
               is both a PCC and a PCE.";
          }
          leaf description {
            type string;
            description
              "Description of the PCEP peer
               configured by the user";
          }
          uses info {
            description
              "PCE Peer information";
          }
          container pce-info {
            uses pce-info {
              description
                "PCE Peer information";
            }
            description
              "The PCE Peer information";
          }
          leaf delegation-pref {
            if-feature "stateful";
            type uint8 {
              range "0..7";
            }
            description
              "The PCE peer delegation preference.";
          }
          container auth {
            description
              "The Authentication options";
            choice auth-type-selection {
              description
                "Options for expressing authentication
                 setting.";
              case auth-key-chain {
                leaf key-chain {
                  type key-chain:key-chain-ref;
                  description
                    "key-chain name.";
                }
              }
              case auth-key {
                leaf crypto-algorithm {
                  type identityref {
                    base key-chain:crypto-algorithm;
                  }
                  mandatory true;
                  description
                    "Cryptographic algorithm associated
                     with key.";
                }
                choice key-string-style {
                  description
                    "Key string styles";
                  case keystring {
                    leaf keystring {
                      nacm:default-deny-all;
                      type string;
                      description
                        "Key string in ASCII format.";
                    }
                  }
                  case hexadecimal {
                    if-feature "key-chain:hex-key-string";
                    leaf hexadecimal-string {
                      nacm:default-deny-all;
                      type yang:hex-string;
                      description
                        "Key in hexadecimal string format. When
                         compared to ASCII, specification in
                         hexadecimal affords greater key entropy
                         with the same number of internal
                         key-string octets.  Additionally, it
                         discourages usage of well-known words or
                         numbers.";
                    }
                  }
                }
              }
              case auth-tls {
                if-feature "tls";
                choice role {
                  description
                    "The role of the local entity";
                  case server {
                    container tls-server {
                      uses tlss:tls-server-grouping {
                        description
                          "Server TLS information.";
                      }
                      description
                        "TLS related information";
                    }
                  }
                  case client {
                    container tls-client {
                      uses tlsc:tls-client-grouping {
                        description
                          "Client TLS information.";
                      }
                      description
                        "TLS related information";
                    }
                  }
                }
              }
            }
          }
          leaf discontinuity-time {
            type yang:timestamp;
            config false;
            description
              "The timestamp of the time when the information and
               statistics were last reset.";
          }
          leaf initiate-session {
            type boolean;
            config false;
            description
              "Indicates whether the local PCEP entity initiates
               sessions to this peer, or waits for the peer to
               initiate a session.";
          }
          leaf session-exists {
            type boolean;
            config false;
            description
              "Indicates whether a session with
               this peer currently exists.";
          }
          leaf session-up-time {
            type yang:timestamp;
            config false;
            description
              "The timestamp value of the last time a
               session with this peer was successfully
               established.";
          }
          leaf session-fail-time {
            type yang:timestamp;
            config false;
            description
              "The timestamp value of the last time a
               session with this peer failed to be
               established.";
          }
          leaf session-fail-up-time {
            type yang:timestamp;
            config false;
            description
              "The timestamp value of the last time a
               session with this peer failed from
               active.";
          }
          container sessions {
            config false;
            description
              "This entry represents a single PCEP
               session in which the local PCEP entity participates.
               This entry exists only if the corresponding PCEP
               session has been initialized by some event, such as
               manual user configuration, auto-discovery of a peer,
               or an incoming TCP connection.";
            list session {
              key "initiator";
              description
                "The list of sessions, note that for a time being
                 two sessions may exist for a peer";
              leaf initiator {
                type pcep-initiator;
                description
                  "The initiator of the session,that is, whether
                   the TCP connection was initiated by the local
                   PCEP entity or the peer.
                   There is a window during session
                   initialization where two sessions can exist
                   between a pair of PCEP speakers, each
                   initiated by one of the speakers. One of
                   these sessions is always discarded before it
                   leaves OpenWait state. However, before it is
                   discarded, two sessions to the given peer
                   appear transiently in this yang module. The
                   sessions are distinguished by who initiated
                   them, and so this field is the key.";
              }
              leaf role {
                type leafref {
                  path "/pcep/entity/role";
                }
                description
                  "The reference to peer role .";
              }
              leaf state-last-change {
                type yang:timestamp;
                description
                  "The timestamp value at the time this
                   session entered its current state as
                   denoted by the state leaf.";
              }
              leaf state {
                type pcep-sess-state;
                description
                  "The current state of the session.
                   The set of possible states excludes the
                   idle state since entries do not exist
                   in the idle state.";
              }
              leaf session-creation {
                type yang:timestamp;
                description
                  "The timestamp value at the time this
                   session was created.";
              }
              leaf connect-retry {
                type yang:counter32;
                description
                  "The number of times that the local PCEP
                   entity has attempted to establish a TCP
                   connection for this session without
                   success. The PCEP entity gives up when
                   this reaches connect-max-retry.";
              }
              leaf local-id {
                type uint8;
                description
                  "The value of the PCEP session ID used by
                   the local PCEP entity in the Open message
                   for this session. If state is tcp-pending
                   then this is the session ID that will be
                   used in the Open message. Otherwise, this
                   is the session ID that was sent in the
                   Open message.";
                reference
                  "RFC 5440: Path Computation Element (PCE)
                   Communication Protocol (PCEP)";
              }
              leaf remote-id {
                type uint8;
                must "((../state != 'tcp-pending'"
                   + "and "
                   + "../state != 'open-wait' )"
                   + "or "
                   + "((../state = 'tcp-pending'"
                   + " or "
                   + "../state = 'open-wait' )"
                   + "and (. = 0)))" {
                  error-message "Invalid remote-id";
                  description
                    "If state is tcp-pending or open-wait then
                     this leaf is not used and MUST be set to
                     zero.";
                }
                description
                  "The value of the PCEP session ID used by the
                   peer in its Open message for this session.";
                reference
                  "RFC 5440: Path Computation Element (PCE)
                   Communication Protocol (PCEP)";
              }
              leaf keepalive-timer {
                type uint8;
                units "seconds";
                must "(../state = 'session-up'"
                   + "or "
                   + "(../state != 'session-up'"
                   + "and (. = 0)))" {
                  error-message "Invalid keepalive timer";
                  description
                    "This field is used if and only if state is
                     session-up. Otherwise, it is not used and
                     MUST be set to zero.";
                }
                description
                  "The agreed maximum interval at which the local
                   PCEP entity transmits PCEP messages on this PCEP
                   session.  Zero means that the local PCEP entity
                   never sends Keepalives on this session.";
                reference
                  "RFC 5440: Path Computation Element (PCE)
                   Communication Protocol (PCEP)";
              }
              leaf peer-keepalive-timer {
                type uint8;
                units "seconds";
                must "(../state = 'session-up'"
                   + "or "
                   + "(../state != 'session-up'"
                   + "and "
                   + "(. = 0)))" {
                  error-message "Invalid Peer keepalive timer";
                  description
                    "This field is used if and only if state is
                     session-up. Otherwise, it is not used and MUST
                     be set to zero.";
                }
                description
                  "The agreed maximum interval at which the peer
                   transmits PCEP messages on this PCEP session.
                   Zero means that the peer never sends Keepalives
                   on this session.";
                reference
                  "RFC 5440: Path Computation Element (PCE)
                   Communication Protocol (PCEP)";
              }
              leaf dead-timer {
                type uint8;
                units "seconds";
                description
                  "The dead timer interval for this PCEP session.";
                reference
                  "RFC 5440: Path Computation Element (PCE)
                   Communication Protocol (PCEP)";
              }
              leaf peer-dead-timer {
                type uint8;
                units "seconds";
                must "((../state != 'tcp-pending'"
                   + "and "
                   + "../state != 'open-wait' )"
                   + "or "
                   + "((../state = 'tcp-pending'"
                   + " or "
                   + "../state = 'open-wait' )"
                   + "and "
                   + "(. = 0)))" {
                  error-message "Invalid Peer Dead timer";
                  description
                    "If state is tcp-pending or open-wait then this
                     leaf is not used and MUST be set to zero.";
                }
                description
                  "The peer's dead-timer interval
                   for this PCEP session.";
                reference
                  "RFC 5440: Path Computation Element (PCE)
                   Communication Protocol (PCEP)";
              }
              leaf ka-hold-time-rem {
                type uint8;
                units "seconds";
                must "((../state != 'tcp-pending'"
                   + "and "
                   + "../state != 'open-wait' ) "
                   + "or "
                   + "((../state = 'tcp-pending'"
                   + "or "
                   + "../state = 'open-wait' )"
                   + "and "
                   + "(. = 0)))" {
                  error-message
                    "Invalid Keepalive hold time remaining";
                  description
                    "If state is tcp-pending or open-wait then this
                     field is not used and MUST be set to zero.";
                }
                description
                  "The keep alive hold time remaining for this
                   session.";
              }
              leaf overloaded {
                type boolean;
                description
                  "If the local PCEP entity has informed the peer that
                   it is currently overloaded, then this is set to true.
                   Otherwise, it is set to false.";
                reference
                  "RFC 5440: Path Computation Element (PCE)
                   Communication Protocol (PCEP)";
              }
              leaf overload-time {
                type uint32;
                units "seconds";
                must '((../overloaded = true()) '
                   + 'or ((../overloaded != true()) '
                   + 'and (. = 0)))' {
                  error-message "Invalid overload-time";
                  description
                    "This field is only used if overloaded is set to
                     true. Otherwise, it is not used and MUST be set
                     to zero.";
                }
                description
                  "The interval of time that is remaining until the
                   local PCEP entity will cease to be overloaded on
                   this session.";
                reference
                  "RFC 5440: Path Computation Element (PCE)
                   Communication Protocol (PCEP)";
              }
              leaf peer-overloaded {
                type boolean;
                description
                  "If the peer has informed the local PCEP entity
                   that it is currently overloaded, then this is
                   set to true. Otherwise, it is set to false.";
                reference
                  "RFC 5440: Path Computation Element (PCE)
                   Communication Protocol (PCEP)";
              }
              leaf peer-overload-time {
                type uint32;
                units "seconds";
                must '((../peer-overloaded = '
                   + 'true()) or '
                   + '((../peer-overloaded !='
                   + 'true())'
                   + ' and '
                   + '(. = 0)))' {
                  error-message "Invalid peer overload time";
                  description
                    "This field is only used if peer-overloaded
                     is set to true. Otherwise, it is not used
                     and MUST be set to zero.";
                }
                description
                  "The interval of time that is remaining until
                   the peer will cease to be overloaded.  If it
                   is not known how long the peer will stay in
                   overloaded state, this leaf is set to zero.";
                reference
                  "RFC 5440: Path Computation Element (PCE)
                   Communication Protocol (PCEP)";
              }
              leaf lspdb-sync {
                if-feature "stateful";
                type sync-state;
                description
                  "The LSP-DB state synchronization status.";
                reference
                  "RFC 8231: Path Computation Element Communication
                   Protocol (PCEP) Extensions for Stateful PCE";
              }
              leaf recv-db-ver {
                when "../role = 'pcc'"
                   + "or "
                   + "../role = 'pcc-and-pce'" {
                  description
                    "This field is applicable when the role is
                     PCC";
                }
                if-feature "stateful";
                if-feature "sync-opt";
                type uint64;
                description
                  "The last received LSP State Database Version
                   Number";
                reference
                  "RFC 8231: Path Computation Element Communication
                   Protocol (PCEP) Extensions for Stateful PCE";
              }
              container of-list {
                when "../role = 'pce'"
                   + "or "
                   + "../role = 'pcc-and-pce'" {
                  description
                    "These fields are applicable when the role is
                     PCE";
                }
                if-feature "objective-function";
                uses of-list;
                description
                  "Indicate the list of supported OF on this
                   session";
                reference
                  "RFC 5541: Encoding of Objective Functions in
                   the Path  Computation Element Communication
                   Protocol (PCEP)";
              }
              container pst-list {
                when "../role = 'pce'"
                   + "or "
                   + "../role = 'pcc-and-pce'" {
                  description
                    "These fields are applicable when the role is
                     PCE";
                }
                description
                  "Indicate the list of supported
                   PST on this session";
                reference
                  "RFC 8408: Conveying Path Setup Type in PCE
                   Communication Protocol (PCEP) Messages";
                list path-setup-type {
                  key "pst";
                  description
                    "The list of authorized PST";
                  leaf pst {
                    type identityref {
                      base te-types:path-signaling-type;
                    }
                    description
                      "The PST authorized";
                  }
                }
              }
              container assoc-type-list {
                if-feature "association";
                description
                  "Indicate the list of supported association types
                   on this session";
                reference
                  "RFC 8697: Path Computation Element Communication
                   Protocol (PCEP) Extensions for Establishing
                   Relationships between Sets of Label Switched
                   Paths (LSPs)";
                list assoc-type {
                  key "at";
                  description
                    "The list of authorized association types";
                  leaf at {
                    type identityref {
                      base te-types:association-type;
                    }
                    description
                      "The association type authorized";
                  }
                }
              }
              leaf speaker-entity-id {
                if-feature "sync-opt";
                type string;
                description
                  "The Speaker Entity Identifier";
                reference
                  "RFC 8232: Optimizations of Label Switched
                   Path State  Synchronization Procedures for
                   a Stateful PCE";
              }
              leaf discontinuity-time {
                type yang:timestamp;
                description
                  "The timestamp value of the time when the
                   statistics were last reset.";
              }
            }
            // session
          }
          // sessions
        }
        //peer
      }
      //peers
    }
    //entity
  }

  //pcep
  /*
   * Notifications
   */

  notification pcep-session-up {
    description
      "This notification is sent when the value of
       '/pcep/peers/peer/sessions/session/state'
       enters the 'session-up' state.";
    uses notification-instance-hdr;
    uses notification-session-hdr;
    leaf state-last-change {
      type yang:timestamp;
      description
        "The timestamp value at the time this session
         entered its current state as denoted by the state
         leaf.";
    }
    leaf state {
      type pcep-sess-state;
      description
        "The current state of the session.
         The set of possible states excludes the idle state
         since entries do not exist in the idle state.";
    }
    reference
      "RFC 5440: Path Computation Element (PCE) Communication
       Protocol (PCEP)";
  }

  //notification

  notification pcep-session-down {
    description
      "This notification is sent when the value of
       '/pcep/peers/peer/sessions/session/state'
       leaves the 'session-up' state.";
    uses notification-instance-hdr;
    leaf session-initiator {
      type pcep-initiator;
      description
        "The initiator of the session.";
    }
    leaf state-last-change {
      type yang:timestamp;
      description
        "The timestamp value at the time this session
         entered its current state as denoted by the state
         leaf.";
    }
    leaf state {
      type pcep-sess-state;
      description
        "The current state of the session.
         The set of possible states excludes the idle state
         since entries do not exist in the idle state.";
    }
    reference
      "RFC 5440: Path Computation Element (PCE) Communication
       Protocol (PCEP)";
  }

  //notification

  notification pcep-session-local-overload {
    description
      "This notification is sent when the local PCEP entity
       enters overload state for a peer.";
    uses notification-instance-hdr;
    uses notification-session-hdr;
    leaf overloaded {
      type boolean;
      description
        "If the local PCEP entity has informed the peer
         that it is currently overloaded, then this is set
         to true. Otherwise, it is set to false.";
    }
    leaf overload-time {
      type uint32;
      units "seconds";
      description
        "The interval of time that is remaining until the
         local PCEP entity will cease to be overloaded on
         this session.";
    }
    reference
      "RFC 5440: Path Computation Element (PCE) Communication
       Protocol (PCEP)";
  }

  //notification

  notification pcep-session-local-overload-clear {
    description
      "This notification is sent when the local PCEP entity
       leaves overload state for a peer.";
    uses notification-instance-hdr;
    leaf overloaded {
      type boolean;
      description
        "If the local PCEP entity has informed the peer
         that it is currently overloaded, then this is set
         to true.  Otherwise, it is set to false.";
    }
    reference
      "RFC 5440: Path Computation Element (PCE) Communication
       Protocol (PCEP)";
  }

  //notification

  notification pcep-session-peer-overload {
    description
      "This notification is sent when a peer enters overload
       state.";
    uses notification-instance-hdr;
    uses notification-session-hdr;
    leaf peer-overloaded {
      type boolean;
      description
        "If the peer has informed the local PCEP entity that
         it is currently overloaded, then this is set to
         true. Otherwise, it is set to false.";
    }
    leaf peer-overload-time {
      type uint32;
      units "seconds";
      description
        "The interval of time that is remaining until the
         peer will cease to be overloaded.  If it is not
         known how long the peer will stay in overloaded
         state, this leaf is set to zero.";
    }
    reference
      "RFC 5440: Path Computation Element (PCE) Communication
       Protocol (PCEP)";
  }

  //notification

  notification pcep-session-peer-overload-clear {
    description
      "This notification is sent when a peer leaves overload
       state.";
    uses notification-instance-hdr;
    leaf peer-overloaded {
      type boolean;
      description
        "If the peer has informed the local PCEP entity that
         it is currently overloaded, then this is set to
         true. Otherwise, it is set to false.";
    }
    reference
      "RFC 5440: Path Computation Element (PCE) Communication
       Protocol (PCEP)";
  }

  //notification
  /*
   * RPC
   */
  rpc trigger-resync {
    if-feature "stateful";
    if-feature "sync-opt";
    description
      "Trigger the resyncrinization at the PCE";
    reference
      "RFC 8232: Optimizations of Label Switched Path State
       Synchronization Procedures for a Stateful PCE";
    input {
      leaf pcc {
        type leafref {
          path "/pcep/entity/peers/peer/addr";
        }
        description
          "The IP address to identify the PCC. The state
           syncronization is re-triggered for all LSPs from
           the PCC. The rpc on the PCC will be ignored.";
      }
    }
    //input
  }

  //rpc
}
