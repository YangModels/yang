module ietf-key-chain {
    namespace "urn:ietf:params:xml:ns:yang:ietf-key-chain";
    // replace with IANA namespace when assigned
    prefix "key-chain";
   import ietf-yang-types {
        prefix "yang";
    }

    import ietf-netconf-acm {
        prefix "nacm";
    }

    organization
        "IETF RTG (Routing) Working Group";
    contact
        "Acee Lindem - acee@cisco.com";

    description
        "This YANG module defines the generic configuration
     data for key-chain. It is intended that the module
     will be extended by vendors to define vendor-specific
     key-chain configuration parameters.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";

    revision 2017-01-20 {
        description
            "Add support of using NETCONF Access Control for
             key-string.";
        reference
            "RFC XXXX: A YANG Data Model for key-chain";
    }
    revision 2016-11-14 {
        description
            "Restore last-modified timestamp leaf.";
        reference
            "RFC XXXX: A YANG Data Model for key-chain";
    }
    revision 2016-10-27 {
        description
            "Restructure into separate config and state trees to
             match YANG structure.";
        reference
            "RFC XXXX: A YANG Data Model for key-chain";
    }
    revision 2016-08-17 {
        description
            "Add description and last-modified timestamp leaves.";
        reference
            "RFC XXXX: A YANG Data Model for key-chain";
    }
    revision 2016-07-01 {
        description
            "Rename module back to ietf-key-chain.
             Added replay-protection-only feature and algorithm.";
        reference
            "RFC XXXX: A YANG Data Model for key-chain";
    }
    revision 2016-03-15 {
        description
            "Rename module from ietf-key-chain to
       ietf-routing-key-chain.";
        reference
            "RFC XXXX: A YANG Data Model for Routing key-chain";
    }
    revision 2016-02-16 {
        description
            "Updated version. Added clear-text algorithm as a
       feature.";
        reference
            "RFC XXXX: A YANG Data Model for key-chain";
    }
    revision 2015-10-15 {
        description
            "Updated version, organization, and copyright.
             Added aes-cmac-prf-128 and aes-key-wrap features.";
        reference
            "RFC XXXX: A YANG Data Model for key-chain";
    }
    revision 2015-06-29 {
        description
            "Updated version. Added Operation State following
             draft-openconfig-netmod-opstate-00.";
        reference
            "RFC XXXX: A YANG Data Model for key-chain";
    }
    revision 2015-02-24 {
        description
            "Initial revision.";
        reference
            "RFC XXXX: A YANG Data Model for key-chain";
    }

    typedef key-chain-ref {
        type leafref {
            path "/key-chain:key-chain/key-chain:key-chain-list/"
                + "key-chain:name";
        }
        description
            "This type is used by data models that need to reference
             configured key-chains.";
    }

    /* feature list */
    feature hex-key-string {
        description
            "Support hexadecimal key string.";
    }

    feature accept-tolerance {
        description
            "To specify the tolerance or acceptance limit.";
    }

    feature independent-send-accept-lifetime {
        description
            "Support for independent send and accept key lifetimes.";
    }

    feature crypto-hmac-sha-1-12 {
        description
            "Support for TCP HMAC-SHA-1 12 byte digest hack.";
    }

    feature clear-text {
        description
            "Support for clear-text algorithm. Usage is
             NOT RECOMMENDED.";
    }

    feature aes-cmac-prf-128 {
        description
            "Support for AES Cipher based Message Authentication
             Code Pseudo Random Function.";
    }

    feature aes-key-wrap {
        description
            "Support for Advanced Encryption Standard (AES)
             Key Wrap.";
    }

    feature replay-protection-only {
        description
            "Provide replay-protection without any authentication
             as required by protocols such as Bidirectional
             Forwarding Detection (BFD).";
    }

    /* groupings */
    grouping lifetime {
        description
            "Key lifetime specification.";
        choice lifetime {
            default always;
            description
                "Options for specifying key accept or send
                 lifetimes";
            case always {
                leaf always {
                    type empty;
                    description
                        "Indicates key lifetime is always valid.";
                }
            }
            case start-end-time {
                leaf start-date-time {
                    type yang:date-and-time;
                    description "Start time.";
                }
                choice end-time {
                    default infinite;
                    description
                        "End-time setting.";
                    case infinite {
                        leaf no-end-time {
                            type empty;
                            description
                                "Indicates key lifetime end-time in
                                 infinite.";
                        }
                    }
                    case duration {
                        leaf duration {
                            type uint32 {
                                range "1..2147483646";
                            }
                            units seconds;
                            description "Key lifetime duration,
                           in seconds";
                        }
                    }
                    case end-date-time {
                        leaf end-date-time {
                            type yang:date-and-time;
                            description "End time.";
                        }
                    }
                }
            }
        }
    }

    grouping crypto-algorithm-types {
        description "Cryptographic algorithm types.";
        choice algorithm {
            description
                "Options for cryptographic algorithm specification.";
            case hmac-sha-1-12 {
                if-feature crypto-hmac-sha-1-12;
                leaf hmac-sha1-12 {
                    type empty;
                    description "The HMAC-SHA1-12 algorithm.";
                }
            }
            case aes-cmac-prf-128 {
                if-feature aes-cmac-prf-128;
                leaf aes-cmac-prf-128 {
                    type empty;
                    description "The AES-CMAC-PRF-128 algorithm -
                                 required by RFC 5926 for TCP-AO key
                                 derivation functions.";
                }
            }
            case md5 {
                leaf md5 {
                    type empty;
                    description "The MD5 algorithm.";
                }
            }
            case sha-1 {
                leaf sha-1 {
                    type empty;
                    description "The SHA-1 algorithm.";
                }
            }
            case hmac-sha-1 {
                leaf hmac-sha-1 {
                    type empty;
                    description
                        "HMAC-SHA-1 authentication algorithm.";
                }
            }
            case hmac-sha-256 {
                leaf hmac-sha-256 {
                    type empty;
                    description
                        "HMAC-SHA-256 authentication algorithm.";
                }
            }
            case hmac-sha-384 {
                leaf hmac-sha-384 {
                    type empty;
                    description
                        "HMAC-SHA-384 authentication algorithm.";
                }
            }
            case hmac-sha-512 {
                leaf hmac-sha-512 {
                    type empty;
                    description
                        "HMAC-SHA-512 authentication algorithm.";
                }
            }
            case clear-text {
                if-feature clear-text;
                leaf clear-text {
                    type empty;
                    description "Clear text.";
                }
            }
            case replay-protection-only {
                if-feature replay-protection-only;
                leaf replay-protection-only {
                    type empty;
                    description
                        "Provide replay-protection without any
                         authentication as required by protocols
                         such as Bidirectional Forwarding
                         Detection (BFD).";
                }
            }
        }
    }

    grouping key-chain-common-entry {
        description "Key-chain entry data nodes common to
                     configuration and state.";
        container lifetime {
            description "Specify a key's lifetime.";
            choice lifetime {
                description
                    "Options for specification of send and accept
                     lifetimes.";
                case send-and-accept-lifetime {
                    description
                        "Send and accept key have the same
                         lifetime.";
                    container send-accept-lifetime {
                        uses lifetime;
                        description
                            "Single lifetime specification for both
                             send and accept lifetimes.";
                    }
                }
                case independent-send-accept-lifetime {
                    if-feature independent-send-accept-lifetime;
                    description
                        "Independent send and accept key lifetimes.";
                    container send-lifetime {
                        uses lifetime;
                        description
                            "Separate lifetime specification for send
                             lifetime.";
                    }
                    container accept-lifetime {
                        uses lifetime;
                        description
                            "Separate lifetime specification for
                             accept lifetime.";
                    }
                }
            }
        }
        container crypto-algorithm {
            uses crypto-algorithm-types;
            description
                "Cryptographic algorithm associated with key.";
        }
        container key-string {
            description "The key string.";
            nacm:default-deny-all;
            choice key-string-style {
                description
                    "Key string styles";
                case keystring {
                    leaf keystring {
                        type string;
                        description
                            "Key string in ASCII format.";
                    }
                }
                case hexadecimal {
                    if-feature hex-key-string;
                    leaf hexadecimal-string {
                        type yang:hex-string;
                        description
                            "Key in hexadecimal string format.";
                    }
                }
            }
        }
    }

    grouping key-chain-config-entry {
        description "Key-chain configuration entry.";
        uses key-chain-common-entry;
    }
    grouping key-chain-state-entry {
        description "Key-chain state entry.";
        uses key-chain-common-entry;
        leaf send-lifetime-active {
            type boolean;
            config false;
            description
                "Indicates if the send lifetime of the
                 key-chain entry is currently active.";
        }
        leaf accept-lifetime-active {
            type boolean;
            config false;
            description
                "Indicates if the accept lifetime of the
                 key-chain entry is currently active.";
        }
    }

    grouping key-chain-common {
        description
            "key-chain common grouping.";
        leaf name {
            type string;
            description "Name of the key-chain.";
        }
        leaf description {
            type string;
            description "A description of the key-chain";
        }
        container accept-tolerance {
            if-feature accept-tolerance;
            description
                "Tolerance for key lifetime acceptance (seconds).";
            leaf duration {
                type uint32;
                units seconds;
                default "0";
                description
                    "Tolerance range, in seconds.";
            }
        }
    }

    grouping key-chain-config {
        description
            "key-chain configuration grouping.";
        uses key-chain-common;
        list key-chain-entries {
            key "key-id";
            description "One key.";
            leaf key-id {
                type uint64;
                description "Key ID.";
            }
            uses key-chain-config-entry;
        }
    }
    grouping key-chain-state {
        description
            "key-chain state grouping.";
        uses key-chain-common;
        leaf last-modified-timestamp {
            type yang:date-and-time;
            description "Timestamp of the most recent update
                         to the key-chain";
        }
        list key-chain-entries {
            key "key-id";
            description "One key.";
            leaf key-id {
                type uint64;
                description "Key ID.";
            }
            uses key-chain-state-entry;
        }
    }

    container key-chain {
        list key-chain-list {
            key "name";
            description
                "List of key-chains.";
            uses key-chain-config;
        }

        container aes-key-wrap {
            if-feature aes-key-wrap;
            description
                "AES Key Wrap password encryption.";
            leaf enable {
                type boolean;
                default false;
                description
                    "Enable AES Key Wrap encryption.";
            }
        }
        description "All configured key-chains
                     on the device.";
    }

    container key-chain-state {
        config false;
        list key-chain-list {
            key "name";
            description
                "List of key-chains and operational state.";
            uses key-chain-state;
        }
        container aes-key-wrap {
            if-feature aes-key-wrap;
            description
                "AES Key Wrap password encryption.";
            leaf enable {
                type boolean;
                description
                    "Indicates whether AES Key Wrap encryption
                     is enabled.";
            }
        }
        description "State for all configured key-chains
                     on the device.";
    }
}
