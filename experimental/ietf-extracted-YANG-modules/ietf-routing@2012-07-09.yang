module ietf-routing {

  namespace "urn:ietf:params:xml:ns:yang:ietf-routing";

  prefix "rt";

  import ietf-inet-types {
    prefix "inet";
  }

  import ietf-interfaces {
    prefix "if";
  }

  import iana-afn-safi {
    prefix "ianaaf";
  }

  organization
    "IETF NETMOD (NETCONF Data Modeling Language) Working Group";

  contact
    "WG Web: <http://tools.ietf.org/wg/netmod/>
     WG List: <mailto:netmod@ietf.org>

     WG Chair: David Kessens
     <mailto:david.kessens@nsn.com>

     WG Chair: Juergen Schoenwaelder
     <mailto:j.schoenwaelder@jacobs-university.de>

     Editor: Ladislav Lhotka
     <mailto:lhotka@nic.cz>
    ";

  description
    "This YANG module defines essential components that may be used
     for configuring a routing subsystem.

     Copyright (c) 2012 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.
    ";

  revision 2012-07-09 {
    description
      "Initial revision.";
    reference
      "RFC XXXX: A YANG Data Model for Routing Configuration";
  }

  /* Identities */

  identity routing-protocol {
    description
      "Base identity from which routing protocol identities are
       derived.";
  }

  identity direct {
    base routing-protocol;
    description
      "Routing pseudo-protocol which provides routes to directly
       connected networks.";
  }

  identity static {
    base routing-protocol;
    description
      "Static routing pseudo-protocol.";
  }

  identity route-filter {
    description
      "Base identity from which all route filters are derived.";
  }

  identity deny-all-route-filter {
    base route-filter;
    description
      "Route filter that blocks all routes.";
  }

  identity allow-all-route-filter {
    base route-filter;
    description
      "Route filter that permits all routes.
      ";
  }

  /* Type Definitions */

  typedef router-ref {
    type leafref {
      path "/rt:routing/rt:router/rt:name";
    }
    description
      "This type is used for leafs that reference a router
       instance.";
  }

  /* Groupings */

  grouping afn-safi {
    leaf address-family {
      type ianaaf:address-family;
      default "ipv4";
      description
        "Address family of routes in the routing table.";
    }
    leaf safi {
      type ianaaf:subsequent-address-family;
      default "nlri-unicast";
      description
        "Subsequent address family identifier of routes in the
         routing table.";
    }
    description
      "This grouping provides two parameters specifying address
       family and subsequent address family.";
  }

  grouping route-content {
    description
      "Generic parameters of routes.

       A module for an address family should define a specific
       version of this grouping containing 'uses rt:route-content'.
      ";
    leaf outgoing-interface {
      type if:interface-ref;
      description
        "Outgoing interface.";
    }
  }

  /* RPC Methods */

  rpc active-route {
    description
      "Return the active route (or multiple routes, in the case of
       multi-path routing) to a destination address.

       Parameters

       1. 'router-name',

       2. 'destination-address'.

       If the logical router with 'router-name' doesn't exist, then
       this operation will fail with error-tag 'missing-element' and
       error-app-tag 'router-not-found'.

       If there is no active route for 'destination-address', then
       this operation will fail with error-tag 'data-missing' and
       error-app-tag 'no-route'.
      ";
    input {
      leaf router-name {
        type router-ref;
        mandatory "true";
        description
          "Name of the router instance whose forwarding information
           base is being queried.";
      }
      container destination-address {
        uses afn-safi;
        description
          "Network layer destination address.

           AFN/SAFI-specific modules must augment this container with
           a leaf named 'address'.
          ";
      }
    }
    output {
      list route {
        min-elements "1";
        uses afn-safi;
        uses route-content;
        description
          "Route contents specific for each address family should be
           defined through augmenting.";
      }
    }
  }

  rpc route-count {
    description
      "Return the current number of routes in a routing table.

       Parameters:

       1. 'router-name',

       2. 'routing-table-name'.

       If the logical router with 'router-name' doesn't exist, then
       this operation will fail with error-tag 'missing-element' and
       error-app-tag 'router-not-found'.

       If the routing table with 'routing-table-name' doesn't exist,
       then this operation will fail with error-tag 'missing-element'
       and error-app-tag 'routing-table-not-found'.
      ";
    input {
      leaf router-name {
        type router-ref;
        mandatory "true";
        description
          "Name of the router instance containing the routing
           table.";
      }
      leaf routing-table {
        type leafref {
          path "/routing/router/routing-tables/routing-table/name";
        }
        mandatory "true";
        description
          "Name of the routing table.";
      }
    }
    output {
      leaf number-of-routes {
        type uint32;
        mandatory "true";
        description
          "Number of routes in the routing table.";
      }
    }
  }

  /* Data Nodes */

  container routing {
    description
      "Routing parameters.";
    list router {
      key "name";
      unique "router-id";
      description
        'Each list entry is a container for configuration and
         operational state data of a single (logical) router.

         Network layer interfaces assigned to the router must have
         their entries in the "interfaces" list.
        ';
      leaf name {
        type string;
        description
          "The unique router name.";
      }
      leaf router-id {
        type inet:ipv4-address;
        description
          "Global router ID in the form of an IPv4 address.

           An implementation may select a value if this parameter is
           not configured.

           Routing protocols may override this global parameter
           inside their configuration.
          ";
      }
      leaf description {
        type string;
        description
          "Textual description of the router.";
      }
      leaf enabled {
        type boolean;
        default "true";
        description
          "Enable the router. The default value is 'true'.

           If this parameter is false, the parent router instance is
           disabled, despite any other configuration that might be
           present.
          ";
      }
      container interfaces {
        description
          "Router interface parameters.";
        list interface {
          key "name";
          description
            "List of network layer interfaces assigned to the router
             instance.";
          leaf name {
            type if:interface-ref;
            description
              "A reference to the name of a configured network layer
               interface.";
          }
        }
      }
      container routing-protocols {
        description
          "Container for the list of configured routing protocol
           instances.";
        list routing-protocol {
          key "name";
          description
            "An instance of a routing protocol.";
          leaf name {
            type string;
            description
              "The name of the routing protocol instance.";
          }
          leaf description {
            type string;
            description
              "Textual description of the routing protocol
               instance.";
          }
          leaf type {
            type identityref {
              base routing-protocol;
            }
            mandatory "true";
            description
              "Type of the routing protocol - an identity derived
               from the 'routing-protocol' base identity.";
          }
          container connected-routing-tables {
            description
              "Container for connected routing tables.";
            list routing-table {
              must "not(../../../../routing-tables/"
                 + "routing-table[rt:name=current()/"
                 + "preceding-sibling::routing-table/name]/"
                 + "address-family=../../../../routing-tables/"
                 + "routing-table[rt:name=current()/name]/"
                 + "address-family and ../../../../routing-tables/"
                 + "routing-table[rt:name=current()/"
                 + "preceding-sibling::routing-table/name]/safi=../"
                 + "../../../routing-tables/"
                 + "routing-table[rt:name=current()/name]/safi)" {
                error-message "Each routing protocol may have no "
                            + "more than one connected routing "
                            + "table for each AFN and SAFI.";
                description
                  "For each AFN/SAFI pair there may be at most one
                   connected routing table.";
              }
              key "name";
              description
                "List of routing tables to which the routing protocol
                 instance is connected.

                 If no connected routing table is defined for an
                 address family, the routing protocol should be
                 connected by default to the main routing table for
                 that address family.
                ";
              leaf name {
                type leafref {
                  path "../../../../../routing-tables/routing-table/"
                     + "name";
                }
                description
                  "Reference to an existing routing table.";
              }
              leaf import-filter {
                type leafref {
                  path "/routing/route-filters/route-filter/name";
                }
                description
                  "Reference to a route filter that is used for
                   filtering routes passed from this routing protocol
                   instance to the routing table specified by the
                   'name' sibling node. If this leaf is not present,
                   the behavior is protocol-specific, but typically
                   it means that all routes are accepted.";
              }
              leaf export-filter {
                type leafref {
                  path "/routing/route-filters/route-filter/name";
                }
                description
                  "Reference to a route filter that is used for
                   filtering routes passed from the routing table
                   specified by the 'name' sibling node to this
                   routing protocol instance. If this leaf is not
                   present, the behavior is protocol-specific -
                   typically it means that all routes are accepted,
                   except for the 'direct' and 'static'
                   pseudo-protocols which accept no routes from any
                   routing table.";
              }
            }
          }
          container static-routes {
            must "../type='rt:static'" {
              error-message "Static routes may be configured only "
                          + "for 'static' routing protocol.";
              description
                "This container is only valid for the 'static'
                 routing protocol.";
            }
            description
              "Configuration of 'static' pseudo-protocol.";
          }
        }
      }
      container routing-tables {
        description
          "Container for configured routing tables.";
        list routing-table {
          key "name";
          description
            "Each entry represents a routing table identified by the
             'name' key. All routes in a routing table must have the
             same AFN and SAFI.";
          leaf name {
            type string;
            description
              "The name of the routing table.";
          }
          uses afn-safi;
          leaf description {
            type string;
            description
              "Textual description of the routing table.";
          }
          container routes {
            config "false";
            description
              "Current contents of the routing table (operational
               state data).";
            list route {
              description
                "A routing table entry. This data node must augmented
                 with information specific for routes of each address
                 family.";
              uses route-content;
              leaf source-protocol {
                type leafref {
                  path "/routing/router/routing-protocols/"
                     + "routing-protocol/name";
                }
                mandatory "true";
                description
                  "The name of the routing protocol instance from
                   which the route comes. This routing protocol must
                   be configured (automatically or manually) in the
                   device.";
              }
              leaf age {
                type uint32;
                units "seconds";
                mandatory "true";
                description
                  "The number of seconds since the parent route was
                   created or last updated.";
              }
            }
          }
          container recipient-routing-tables {
            description
              "Container for recipient routing tables.";
            list recipient-routing-table {
              key "name";
              description
                "A list of routing tables that receive routes from
                 this routing table.";
              leaf name {
                type leafref {
                  path "/routing/router/routing-tables/"
                     + "routing-table/name";
                }
                description
                  "The name of the recipient routing table.";
              }
              leaf filter {
                type leafref {
                  path "/routing/route-filters/route-filter/name";
                }
                description
                  "A route filter which is applied to the routes
                   passed on to the recipient routing table.";
              }
            }
          }
        }
      }
    }
    container route-filters {
      description
        "Container for configured route filters.";
      list route-filter {
        key "name";
        description
          "Route filters are used for filtering and/or manipulating
           routes that are passed between a routing protocol and a
           routing table or vice versa, or between two routing
           tables. It is expected that other modules augment this
           list with contents specific for a particular route filter
           type.";
        leaf name {
          type string;
          description
            "The name of the route filter.";
        }
        leaf description {
          type string;
          description
            "Textual description of the route filter.";
        }
        leaf type {
          type identityref {
            base route-filter;
          }
          default "rt:deny-all-route-filter";
          description
            "Type of the route-filter - an identity derived from the
             'route-filter' base identity. The default value
             represents an all-blocking filter.";
        }
      }
    }
  }
}
