submodule snmp-target {

  belongs-to snmp {
    prefix snmp;
  }

  import ietf-inet-types {
    prefix inet;
  }

  include snmp-common;
  include snmp-usm;

  reference
    "RFC3413: Simple Network Management Protocol (SNMP) Applications
     SNMP-TARGET-MIB";

  revision 2010-10-17 {
    description
      "Initial revision.";
  }

  augment /snmp:snmp {

    list target {
      key name;

      description "List of targets.";
      reference "SNMP-TARGET-MIB.snmpTargetAddrTable";

      leaf name {
        type snmp:identifier;
        description
          "Identifies the target.";
        reference "SNMP-TARGET-MIB.snmpTargetAddrName";
      }

      // make a choice here so we can add other transports, or
      // they can augment.

      leaf ip {
        type inet:ip-address;
        mandatory true;
        description "Transport IP address of the target";
        reference "SNMP-TARGET-MIB.snmpTargetAddrTDomain
                   SNMP-TARGET-MIB.snmpTargetAddrTAddress";
      }
      leaf udp-port {
        type inet:port-number;
        default 162;
        description "UDP port number";
        reference "SNMP-TARGET-MIB.snmpTargetAddrTDomain
                   SNMP-TARGET-MIB.snmpTargetAddrTAddress";
      }
      leaf-list tag {
        type snmp:identifier;
        description
          "List of tag values used to select target address.";
        reference "SNMP-TARGET-MIB.snmpTargetAddrTagList";
      }

      leaf timeout {
        type uint32;
        units "0.01 seconds";
        default 1500;
        description
          "Needed only if this target can receive v3 informs.";
        reference "SNMP-TARGET-MIB.snmpTargetAddrTimeout";
      }
      leaf retries {
        type uint8;
        default 3;
        description
          "Needed only if this target can receive v3 informs.";
        reference "SNMP-TARGET-MIB.snmpTargetAddrRetryCount";
      }
      leaf engine-id {
        type leafref {
          path "/snmp/usm/remote/engine-id";
        }
        must '../usm/user-name' {
          error-message
            "When engine-id is set, usm/user-name must also be set.";
        }
        must '/snmp/usm/remote[engine-id=current()]/'
           + 'user[name=current()/../usm/user-name]' {
          error-message
            "When engine-id is set, the usm/user-name must exist in the
            /snmp/usm/remote list for this engine-id.";
        }
        description
          "Needed only if this target can receive v3 informs.
          This object is not present in the SNMP MIBs.  In
          RFC 3412, it is a implementation specific matter how this
          engine-id is handled.";
        reference "RFC 3412 7.1.9a";
      }
    }

  }
}
