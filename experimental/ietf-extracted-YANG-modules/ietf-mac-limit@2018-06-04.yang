module ietf-mac-limit {
namespace "urn:ietf:params:xml:ns:yang:ietf-mac-limit";
prefix mac-limit;
organization
  "IETF SACM Working Group";
contact
  "Liang Xia: Frank.xialiang@huawei.com;
  Guangying Zheng: Zhengguangying@huawei.com";
description
  "MAC address limit.";

revision 2018-06-04 {
  description
    "Init revision";
  reference "xxx.";
}

/*
 * Typedefs
 */
typedef mac-limit-forward {
  type enumeration {
    enum "forward" {
      description
        "Forward.";
    }
    enum "discard" {
      description
        "Discard.";
    }
  }
  description
    "MAC Limit Forward";
}
typedef mac-enable-status {
  type enumeration {
    enum "enable" {
      description
        "Enable.";
    }
    enum "disable" {
      description
        "Disable.";
    }
  }
  description
    "MAC Enable Status";
}
typedef mac-vlan-id {
  type uint16 {
    range "1..4094";
  }
  description
    "MAC Vlan Id";
}
typedef mac-type {
  type enumeration {
    enum "static" {
      description
        "Static MAC address entry.";
    }
    enum "dynamic" {
      description
        "Dynamic MAC address entry.";
    }
    enum "black-hole" {
      description
        "Blackhole MAC address entry";
    }
    enum "sticky" {
      description
        "sticky MAC address entry";
    }
    enum "security" {
      description
        "security MAC address entry";
    }
    enum "evn" {
      description
        "EVN MAC address entry.";
    }
    enum "mux" {
      description
        "MUX MAC address entry.";
    }
    enum "snooping" {
      description
        "SNOOPING MAC address entry.";
    }
    enum "tunnel" {
      description
        "TUNNEL MAC address entry.";
    }
    enum "authen" {
      description
        "AUTHEN MAC address entry.";
    }
  }
  description
    "MAC Type";
}
typedef suppress-type {
  type enumeration {
    enum "broadcast" {
      description
        "Broadcast.";
    }
    enum "multicast" {
      description
        "Multicast.";
    }
    enum "unknown-unicast" {
      description
        "Unknown unicast.";
    }
    enum "unicast" {
      description
        "Unicast.";
    }
  }
  description
    "Suppress Type";
}
typedef limit-type {
  type enumeration {
    enum "-mac-limit" {
      description
        "Interface MAC rule limit.";
    }
    enum "mac-apply" {
      description
        "Interface MAC rule application.";
    }
  }
  description
    "Limit Type";
}

typedef mac-pw-encap-type {
  type enumeration {
    enum "ethernet" {
      description
        "Ethernet.";
    }
    enum "vlan" {
      description
        "VLAN.";
    }
  }
  description
    "MAC PW Encapsulation Type";
}

typedef suppress-style {
  type enumeration {
    enum "percent" {
      description
        "Percent.";
    }
    enum "absolute-value" {
      description
        "Absolute value.";
    }
  }
  description
    "Suppress Style";
}

typedef direction-type {
  type enumeration {
    enum "inbound" {
      description
        "Inbound.";
    }
    enum "outbound" {
      description
        "Outbound.";
    }
  }
  description
    "Direction Type";
}

typedef storm-ctrl-action-type {
  type enumeration {
    enum "normal" {
      description
        "Normal.";
    }
    enum "error-down" {
      description
        "Error down.";
    }
    enum "block" {
      description
        "Block.";
    }
    enum "suppress" {
      description
        "Suppress";
    }
  }
  description
    "Storm Ctrl Action Type";
}

typedef enable-type {
  type enumeration {
    enum "disable" {
      description
        "Disable.";
    }
    enum "enable" {
      description
        "Enable.";
    }
  }
  description
    "Enable Type";
}

typedef storm-ctrl-type {
  type enumeration {
    enum "broadcast" {
      description
        "Broadcast.";
    }
    enum "multicast" {
      description
        "Multicast.";
    }
    enum "unicast" {
      description
        "Unicast.";
    }
    enum "unknown-unicast" {
      description
        "Unknown unicast.";
    }
  }
  description
    "Storm Ctrl Type";
}

typedef storm-ctrl-rate-type {
  type enumeration {
    enum "pps" {
      description
        "Packets per second.";
    }
    enum "percent" {
      description
        "Percent.";
    }
    enum "kbps" {
      description
        "Kilo bits per second.";
    }
  }
  description
    "Storm Ctrl Rate Type";
}

container mac {
  description
    "MAC address forwarding. ";
  container mac-limit-rules {
    description
      "Global MAC address learning limit rule.";
    list mac-limit-rule {
      key "rule-name";
      description
        "Global MAC address learning limit.";
      leaf rule-name {
        type string {
          length "1..31";
        }
        description
          "Global MAC address learning limit rule name.";
      }
      leaf maximum {
        type uint32 {
          range "0..131072";
        }
        mandatory true;
        description
          "Maximum number of MAC addresses that can be learned.";
      }
      leaf rate {
        type uint16 {
          range "0..1000";
        }
        default "0";
        description
          "Interval at which MAC addresses are learned.";
      }
      leaf action {
        type mac-limit-forward;
        default "discard";
        description
          "Discard or forward after the number of learned MAC addresses reaches the maximum number.";
      }
      leaf alarm {
        type mac-enable-status;
        default "enable";
        description
          "Whether an alarm is generated after the number of learned MAC addresses reaches the maximum number.";
      }
    }
  }
  container vlan-mac-limits {
    description
      "VLAN MAC address limit list.";
    list vlan-mac-limit {
      key "vlan-id";
      description
        "VLAN MAC address limit.";
      leaf vlan-id {
        type mac-vlan-id;
        description
          "VLAN ID.";
      }
      leaf maximum {
        type uint32 {
          range "0..130048";
        }
        mandatory true;
        description
          "Maximum number of MAC addresses that can be learned in a VLAN.";
      }
      leaf rate {
        type uint16 {
          range "0..1000";
        }
        default "0";
        description
          "Interval at which MAC addresses are learned in a VLAN.";
      }
      leaf action {
        type mac-limit-forward;
        default "discard";
        description
          "Discard or forward after the number of learned MAC addresses reaches the maximum number in a VLAN.";
      }
      leaf alarm {
        type mac-enable-status;
        default "enable";
        description
          "Whether an alarm is generated after the number of learned MAC addresses reaches the maximum number in a VLAN.";
      }
    }
  }
  container vsi-mac-limits {
    description
      "VSI MAC address limit list.";
    list vsi-mac-limit {
      key "vsi-name";
      description
        "VSI MAC address limit.";
      leaf vsi-name {
        type string {
          length "1..31";
        }
        description
          "VSI name.";
      }
      leaf maximum {
        type uint32 {
          range "0..524288";
        }
        mandatory true;
        description
          "Maximum number of MAC addresses that can be learned in a VSI.";
      }
      leaf rate {
        type uint16 {
          range "0..1000";
        }
        default "0";
        description
          "Interval at which MAC addresses are learned in a VSI.";
      }
      leaf action {
        type mac-limit-forward;
        default "discard";
        description
          "Discard or forward after the number of learned MAC addresses reaches the maximum number in a VSI.";
      }
      leaf alarm {
        type mac-enable-status;
        default "disable";
        description
          "Whether an alarm is generated after the number of learned MAC addresses reaches the maximum number in a VSI.";
      }
      leaf up-threshold {
        type uint8 {
          range "80..100";
        }
        mandatory true;
        description
          "Upper limit for the number of MAC addresses.";
      }
      leaf down-threshold {
        type uint8 {
          range "60..100";
        }
        mandatory true;
        description
          "Upper limit for the number of MAC addresses.";
      }
    }
  }
  container bd-mac-limits {
    description
      "BD MAC address limit list.";
    list bd-mac-limit {
      key "bd-id";
      description
        "BD MAC address limit.";
      leaf bd-id {
        type uint32 {
          range "1..16777215";
        }
        description
          "Specifies the ID of a bridge domain.";
      }
      leaf maximum {
        type uint32 {
          range "0..130048";
        }
        mandatory true;
        description
          "Maximum number of MAC addresses that can be learned in a BD.";
      }
      leaf rate {
        type uint16 {
          range "0..1000";
        }
        default "0";
        description
          "Interval at which MAC addresses are learned in a BD.";
      }
      leaf action {
        type mac-limit-forward;
        default "discard";

        description
          "Forward or discard the packet.";
      }
      leaf alarm {
        type mac-enable-status;
        default "enable";
        description
          "Whether an alarm is generated after the number of learned MAC addresses reaches the maximum number.";
      }
    }
  }
  container pw-mac-limits {
    description
      "PW MAC address limit list.";
    list pw-mac-limit {
      key "vsi-name pw-name";
      description
        "PW MAC address limit.";
      leaf vsi-name {
        type string {
          length "1..31";
        }
        description
          "VSI name.";
      }
      leaf pw-name {
        type string {
          length "1..15";
        }
        description
          "PW name.";
      }
      leaf maximum {
        type uint32 {
          range "0..130048";
        }
        mandatory true;
        description
          "Maximum number of MAC addresses that can be learned in a PW.";
      }
      leaf rate {
        type uint16 {
          range "0..1000";
        }
        default "0";
        description
          "Interval at which MAC addresses are learned in a PW.";
      }
      leaf action {
        type mac-limit-forward;
        default "discard";
        description
          "Discard or forward after the number of learned MAC addresses reaches the maximum number in a PW.";
      }
      leaf alarm {
        type mac-enable-status;
        default "enable";
        description
          "Whether an alarm is generated after the number of learned MAC addresses reaches the maximum number in a PW.";
      }
    }
  }
  container if-mac-limits {
    description
      "Interface MAC address limit list.";
    list if-mac-limit {
      key "if-name limit-type";
      description
        "Interface MAC address limit.";
      leaf if-name {
        type string;
        description
          "Interface name.";
      }
      leaf limit-type {
        type limit-type;
        description
          "Interface MAC limit type.";
      }
      leaf rule-name {
        type leafref {
          path "/mac/mac-limit-rules/mac-limit-rule/rule-name";
        }
        description
          "Rule name.";
      }
      leaf maximum {
        type uint32 {
          range "0..131072";
        }
        mandatory true;
        description
          "Maximum number of MAC addresses that can be learned on an interface.";
      }
      leaf rate {
        type uint16 {
          range "0..1000";
        }
        default "0";
        description
          "Interval (ms) at which MAC addresses are learned on an interface.";
      }
      leaf action {
        type mac-limit-forward;
        default "discard";
        description
          "Discard or forward after the number of learned MAC addresses reaches the maximum number on an interface";
      }
      leaf alarm {
        type mac-enable-status;
        default "enable";
        description
          "Whether an alarm is generated after the number of learned MAC addresses reaches the maximum number on an interface.";
      }
    }
  }
  container if-vlan-mac-limits {
    description
      "Interface + VLAN MAC address limit list.";
    list if-vlan-mac-limit {
      key "if-name vlan-begin limit-type";
      config false;
      description
        "Interface + VLAN MAC address limit.";
      leaf if-name {
        type string;
        description
          "-name of an interface. ";
      }
      leaf vlan-begin {
        type mac-vlan-id;
        description
          "Start VLAN ID.";
      }
      leaf vlan-end {
        type mac-vlan-id;
        description
          "End VLAN ID.";
      }
      leaf limit-type {
        type limit-type;
        description
          "Interface MAC limit type.";
      }
      leaf rule-name {
        type leafref {
          path "/mac/mac-limit-rules/mac-limit-rule/rule-name";
        }
        description
          "Rule name.";
      }
      leaf maximum {
        type uint32 {
          range "0..131072";
        }
        mandatory true;
        description
          "Maximum number of MAC addresses that can be learned on an interface.";
      }
      leaf rate {
        type uint16 {
          range "0..1000";
        }
        mandatory true;
        description
          "Interval (ms) at which MAC addresses are learned on an interface.";
      }
      leaf action {
        type mac-limit-forward;
        default "discard";
        description
          "Discard or forward the packet.";
      }
      leaf alarm {
        type mac-enable-status;
        default "enable";
        description
          "Whether an alarm is generated after the number of learned MAC addresses reaches the maximum number.";
      }
    }
  }
  container subif-mac-limits {
    description
      "Sub-interface MAC address limit list.";
    list subif-mac-limit {
      key "if-name limit-type";
      description
        "Sub-interface MAC address limit.";
      leaf if-name {
        type string;
        description
          "-name of a sub-interface. ";
      }
      leaf limit-type {
        type limit-type;
        description
          "Sub-interface MAC limit type.";
      }
      leaf vsi-name {
        type string {
          length "1..36";
        }
        config false;
        mandatory true;
        description
          "VSI name , EVPN name or bridge domain ID.";
      }
      leaf rule-name {
        type string {
          length "1..31";
        }
        mandatory true;
        description
          "Rule name.";
      }
      leaf maximum {
        type uint32 {
          range "0..131072";
        }
        mandatory true;
        description
          "Maximum number of MAC addresses that can be learned on a sub-interface.";
      }
      leaf rate {
        type uint16 {
          range "0..1000";
        }
        default "0";
        description
          "Interval (ms) at which MAC addresses are learned on a sub-interface.";
      }
      leaf action {
        type mac-limit-forward;
        default "discard";
        description
          "Discard or forward after the number of learned MAC addresses reaches the maximum number on a sub-interface.";
      }
      leaf alarm {
        type mac-enable-status;
        default "enable";
        description
          "Whether an alarm is generated after the number of learned MAC addresses reaches the maximum number on a sub-interface.";
      }
    }
  }
  container vsi-storm-supps {
    description
      "VSI Suppression List.";
    list vsi-storm-supp {
      key "vsi-name suppress-type";
      description
        "VSI Suppression.";
      leaf vsi-name {
        type string {
          length "1..31";
        }
        description
          "VSI name.";
      }
      leaf suppress-type {
        type suppress-type;
        description
          "Traffic suppression type.";
      }
      leaf cir {
        type uint64 {
          range "0..4294967295";
        }
        default "0";
        description
          "CIR value.";
      }
      leaf cbs {
        type uint64 {
          range "0..4294967295";
        }
        description
          "CBS value.";
      }
    }
  }
  container vlan-storm-supps {
    description
      "VLAN Suppression List.";
    list vlan-storm-supp {
      key "vlan-id suppress-type";
      description
        "VLAN Suppression.";
      leaf vlan-id {
        type mac-vlan-id;
        description
          "VLAN ID.";
      }
      leaf suppress-type {
        type suppress-type;
        description
          "Traffic suppression type.";
      }
      leaf cir {
        type uint64 {
          range "64..4294967295";
        }
        default "64";
        description
          "CIR value.";
      }
      leaf cbs {
        type uint64 {
          range "10000..4294967295";
        }
        description
          "CBS value.";
      }
    }
  }
  container sub-if-suppresss {
    description
      "Sub-interface traffic suppression list.";
    list sub-if-suppress {
      key "if-name suppress-type direction";
      description
        "Sub-Interface traffic suppression.";
      leaf if-name {
        type string;
        description
          "Sub-interface name.";
      }
      leaf suppress-type {
        type suppress-type;
        description
          "Suppression type.";
      }
      leaf direction {
        type direction-type;
        description
          "Suppression direction.";
      }
      leaf cir {
        type uint64 {
          range "0..4294967295";
        }
        default "0";
        description
          "CIR value.";
      }
      leaf cbs {
        type uint64 {
          range "0..4294967295";
        }
        description
          "CBS value.";
      }
    }
  }
  container pw-suppresss {
    description
      "PW traffic suppress list.";
    list pw-suppress {
      key "vsi-name pw-name suppress-type";
      description
        "PW traffic suppression.";
      leaf vsi-name {
        type string {
          length "1..31";
        }
        description
          "VSI name.";
      }
      leaf pw-name {
        type string {
          length "1..15";
        }
        description
          "PW name.";
      }
      leaf suppress-type {
        type suppress-type;
        description
          "Traffic suppression type.";
      }
      leaf cir {
        type uint64 {
          range "100..4294967295";
        }
        default "100";
        description
          "CIR value.";
      }
      leaf cbs {
        type uint64 {
          range "100..4294967295";
        }
        description
          "CBS value.";
      }
    }
  }

  container vsi-in-suppressions {
    description
      "VSI inbound traffic suppression list.";
    list vsi-in-suppression {
      key "vsi-name";
      description
        "VSI inbound traffic suppression.";
      leaf vsi-name {
        type string {
          length "1..31";
        }
        description
          "VSI name.";
      }
      leaf inbound-supp {
        type mac-enable-status;
        default "enable";
        description
          "Inbound suppression.";
      }
    }
  }
  container vsi-out-suppressions {
    description
      "VSI outbound traffic suppression list.";
    list vsi-out-suppression {
      key "vsi-name";
      description
        "VSI outbound traffic suppression.";
      leaf vsi-name {
        type string {
          length "1..31";
        }
        description
          "VSI name.";
      }
      leaf out-bound-supp {
        type mac-enable-status;
        default "enable";
        description
          "Outbound suppression.";
      }
    }
  }
  container vsi-suppresss {
    description
      "VSI traffic suppression list.";
    list vsi-suppress {
      key "sub-if-name";
      description
        "VSI traffic suppression.";
      leaf vsi-name {
        type string {
          length "1..31";
        }
        mandatory true;
        description
          "VSI name.";
      }

      leaf sub-if-name {
        type string;
        description
          "Sub-interface name.";
      }
      leaf is-enable {
        type boolean;
        default "true";
        description
          "Enable status.";
      }
      leaf suppress-type {
        type suppress-style;
        default "percent";
        description
          "Traffic suppression type.";
      }
      leaf broadcast {
        type uint32 {
          range "0..200000000";
        }
        default "64";
        description
          "Broadcast suppression (kbit/s)";
      }
      leaf broadcast-percent {
        type uint32 {
          range "0..100";
        }
        default "1";
        description
          "Broadcast suppression.";
      }
      leaf unicast {
        type uint32 {
          range "0..200000000";
        }
        default "64";
        description
          "Unknown unicast suppression (kbit/s).";
      }
      leaf unicast-percent {
        type uint32 {
          range "0..100";
        }
        default "1";
        description
          "Unknown unicast suppression.";

      }
      leaf multicast {
        type uint32 {
          range "0..200000000";
        }
        default "64";
        description
          "Multicast suppression (kbit/s).";
      }
      leaf multicast-percent {
        type uint32 {
          range "0..100";
        }
        default "1";
        description
          "Multicast suppression.";
      }
    }
  }
  container vsi-total-numbers {
    description
      "List of MAC address total numbers in a VSI.";
    list vsi-total-number {
      key "vsi-name slot-id mac-type";
      config false;
      description
        "Total number of MAC addresses in a VSI.";
      leaf vsi-name {
        type string {
          length "1..31";
        }
        description
          "VSI name.";
      }
      leaf slot-id {
        type string {
          length "1..24";
        }
        description
          "Slot ID.";
      }
      leaf mac-type {
        type mac-type;
        description
          "MAC address type.";
      }
      leaf number {
        type uint32;
        mandatory true;
        description
          "Number of MAC addresses.";
      }
    }
  }
  container if-storm-supps {
    description
      "Interface traffic suppression list.";
    list if-storm-supp {
      key "if-name suppress-type";
      description
        "Interface traffic suppression.";
      leaf if-name {
        type string;
        description
          "-name of an interface. ";
      }
      leaf suppress-type {
        type suppress-type;
        description
          "Suppression type.";
      }
      leaf percent {
        type uint64 {
          range "0..99";
        }
        description
          "Percent.";
      }
      leaf packets {
        type uint64 {
          range "0..148810000";
        }
        description
          "Packets per second.";
      }
      leaf cir {
        type uint64 {
          range "0..100000000";
        }
        description
          "CIR(Kbit/s).";
      }
      leaf cbs {
        type uint64 {
          range "10000..4294967295";
        }
        description
          "CBS(Bytes).";
      }
    }
  }
  container if-storm-blocks {
    description
      "Interface traffic block list.";
    list if-storm-block {
      key "if-name block-type direction";
      description
        "Interface traffic suppression.";
      leaf if-name {
        type string;
        description
          "-name of an interface. ";
      }
      leaf block-type {
        type suppress-type;
        description
          "Block type.";
      }
      leaf direction {
        type direction-type;
        description
          "Direction.";
      }
    }
  }
  container if-storm-contrls {
    description
      "Interface storm control list.";
    list if-storm-contrl {
      key "if-name";
      description
        "Interface storm control.";
      leaf if-name {
        type string;
        description
          "-name of an interface. ";
      }
      leaf action {
        type storm-ctrl-action-type;
        default "normal";
        description
          "Action type.";
      }
      leaf trap-enable {

        type enable-type;
        default "disable";
        description
          "Trap state.";
      }
      leaf log-enable {
        type enable-type;
        default "disable";
        description
          "Log state.";
      }
      leaf interval {
        type uint64 {
          range "1..180";
        }
        default "5";
        description
          "Detect interval.";
      }
      container if-packet-contrl-attributes {
        description
          "Storm control rate list.";
        list if-packet-contrl-attribute {
          key "packet-type";
          description
            "Storm control rate.";
          leaf packet-type {
            type storm-ctrl-type;
            description
              "Packet type.";
          }
          leaf rate-type {
            type storm-ctrl-rate-type;
            default "pps";
            description
              "Storm control rate type.";
          }
          leaf min-rate {
            type uint32 {
              range "1..148810000";
            }
            mandatory true;
            description
              "Storm control min rate.";
          }
          leaf max-rate {
            type uint64 {
              range "1..148810000";
            }
            mandatory true;
            description
              "Storm control max rate.";
          }
        }
      }
      container ifstorm-contrl-infos {
        description
          "Storm control info list.";
        list ifstorm-contrl-info {
          key "packet-type";
          config false;
          description
            "Storm control info";
          leaf packet-type {
            type storm-ctrl-type;
            description
              "Packet type.";
          }
          leaf punish-status {
            type storm-ctrl-action-type;
            description
              "Storm control status.";
          }
          leaf last-punish-time {
            type string {
              length "1..50";
            }
            description
              "Last punish time.";
          }
        }
      }
    }
  }
}
}
