module ietf-location {
  namespace "urn:ietf:params:xml:ns:yang:ietf-location";
  prefix loc;

  include iana-civic-address-type {
     revision-date 2014-05-08;
  }
  include iana-geo-uri-type {
    revision-date 2014-05-08;
  }

  organization
    "IETF NETMOD (NETCONF Data Modeling Language) Working Group";

  contact
    "WG Web:   <http://tools.ietf.org/wg/netmod/>
     WG List:  <mailto:netmod@ietf.org>

     Author:   Yi Yang
               <mailto:yiya@cisco.com>

     Author:   Wojciech Dec
               <mailto:wdec@cisco.com>";

  description
    "This YANG module defines a reusable group for location
     information"; 

  revision 2014-05-08 {
    description
      "Initial revision.";
  } 

  typedef country {
    type string {
      pattern '[A-Z]{2}';
    }
    description 
      "ISO 3166 country code";
  }

  grouping location {
    container location {
      leaf geo-uri {
        type geo-uri;
        description
          "Uniform Resource Identifier for Geographic Locations
           ('geo' URI) as defined by RFC 5870.";
      }

      leaf country {
        type country;
        description 
          "ISO 3166 country code";
      }
      leaf CA0 {
        type CA0;
        description
          "Language.";
      }

      leaf A1 {
        type A1;
        description
          "National subdivisions:
           state, canton, region, province, prefecture";
       }

      leaf A2 {
        type A2;
        description
          "county, parish, gun (JP), district (IN)";
      }

      leaf A3 {
        type A3;
        description
          "city, township, shi (JP)";
      }

      leaf A4 {
        type A4;
        description
          "city division, borough, city district, ward, chou (JP)";
      }

      leaf A5 {
        type A5;
        description
          "neighborhood, block";
      }

      leaf A6 {
        type A6;
        description
          "group of streets below the neighborhood level";
      }

      leaf PRD {
        type PRD;
        description
          "leading street direction";
      }
      leaf POD {
        type POD;
        description
          "trailing street suffix";
      }

      leaf STS {
        type STS;
        description
          "street suffix or type";
      }

      leaf HNO {
        type HNO;
        description
          "house number";
      }

      leaf HNS {
        type HNS;
        description
          "house number suffix";
      }

      leaf LMK {
        type LMK;
        description
          "landmark or vanity address";
      }

      leaf LOC {
        type LOC;
        description
          "additional location information";
      }

      leaf NAM {
        type NAM;
        description
          "name (residence and office occupant)";
      }

      leaf PC {
        type PC;
        description
          "postal/zip code";
      }

      leaf BLD {
        type BLD;
        description
          "building (structure)";
      }

      leaf UNIT {
        type UNIT;
        description
          "unit (apartment, suite)";
      }

      leaf FLR {
        type FLR;
        description
          "floor";
      }

      leaf ROOM {
        type ROOM;
        description
          "room number";
      }

      leaf PLC {
        type PLC;
        description
          "type of place";
      }

      leaf PCN {
        type PCN;
        description
          "postal community name";
      }

      leaf POBOX {
        type POBOX;
        description
          "post office box (P.O. Box)";
      }

      leaf ADDCODE {
        type ADDCODE;
        description
          "additional code";
      }

      leaf SEAT {
        type SEAT;
        description
          "seat (desk, cubicle, workstation)";
      }

      leaf RD {
        type RD;
        description
          "Primary road or street";
      }

      leaf RDSEC {
        type RDSEC;
        description
          "Road section";
      }

      leaf RDBR {
        type RDBR;
        description
          "Road branch";
      }

      leaf RDSUBBR {
        type RDSUBBR;
        description
          "Road sub-branch";
      }

      leaf PRM {
        type PRM;
        description
          "Street name pre-modifier";
      }

      leaf POM {
        type POM;
        description
          "Street name post-modifier";
      }

      leaf PN {
        type PN;
        description
          "Post number that is attributed to a lamp post or utility 
           pole.";
      }
      leaf MP {
        type MP;
        description
          "Milepost: a marker indicating distance to or from a place 
           (often a town).";
      }

      leaf STP {
        type STP;
        description
          "Street Type Prefix.";
      }

      leaf HNP {
        type HNP;
        description
          "House Number Prefix.";
      }

      leaf STPS {
        type STPS;
        description
          "Separator between the existing Street Type Prefix (STP)
           and the Road Name (RD) elements.";
      }

      leaf LMKP {
        type LMKP;
        description
          "Component part of a Complete Landmark Name.";
      }

      leaf CA128 {
        type CA128;
        description
          "script";
      }
    }
  }
}
