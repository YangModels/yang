module ietf-isis-flex-algo {
  yang-version 1.1;
  namespace "urn:ietf:params:xml:ns:yang:ietf-isis-flex-algo";
  prefix isis-flex-algo;

  import ietf-routing {
    prefix rt;
    reference
      "RFC 8349: A YANG Data Model for Routing
                 Management (NMDA Version)";
  }
  import ietf-te-types {
    prefix te-types;
    reference
      "RFC 8776: Common YANG Data Types for Traffic Engineering.";
  }
  import ietf-isis {
    prefix isis;
    reference
      "RFC 9130: YANG Data Model for the IS-IS Protocol";
  }
  import iana-igp-algo-types {
    prefix iana-algo-types;
    reference
      "IANA IGP Algorithm Types registry,
       <https://www.iana.org/assignments/igp-parameters>.";
  }
  import iana-igp-metric-types {
    prefix iana-metric-types;
    reference
      "IANA IGP Metric-Type registry,
       <https://www.iana.org/assignments/igp-parameters>.";
  }

  organization
    "IETF LSR - Link State Routing Working Group";
  contact
    "WG Web:   <https://datatracker.ietf.org/wg/lsr>
     WG List:  <mailto:lsr@ietf.org>

     Author:    Yingzhen Qu
                <mailto:yingzhen.ietf@gmail.com>
     Author:    Acee Lindem
                <mailto:acee.ietf@gmail.com>
     Author:    Madhavi Joshi
                <mailto:madhavi@arrcus.com>
    ";
  description
    "The YANG module defines the configuration and operational
     state for IS-IS Flexible Algorithm as defined in RFC 9350.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-07-11 {
    description
      "Initial Version";
    reference
      "RFC XXXX: A YANG Data Model for IS-IS Application-Specific
                 Link Attributes and Flexible Algorithm";
  }

  /* Identities */

  identity fad-flags {
    description
      "Base identity for IS-IS FAD flags.";
  }

  identity m-flag {
    base fad-flags;
    description
      "M-flag in the Flex-Algorithm Definition (FAD) flags sub-TLV.
       When this flag is present in the fad-flags leaf-list, the
       Flex-Algorithm-specific prefix metric is used for inter-area
       and external prefix calculation.  Note that this flag is not
       applicable to prefixes advertised as SRv6 locators.";
    reference
      "RFC 9350: IGP Flexible Algorithm, Section 6.4";
  }

  /* Groupings */

  grouping fa-ex-ag-sub-tlv {
    container fa-ex-ag-sub-tlv {
      leaf extended-admin-group {
        type te-types:extended-admin-group;
        description
          "Extended administrative group value.";
        reference
          "RFC 7308: Extended Administrative Groups in MPLS-TE";
      }
      description
        "The flex-algo exclude admin group sub-tlv. Note that the
         presence of more than one Exclude Extended Admin Group
         sub-TLV will result in an invalid FAD TLV.";
    }
    description
      "The flex-algo exclude admin group sub-tlv.";
  }

  grouping fa-in-any-ag-sub-tlv {
    container fa-in-any-ag-sub-tlv {
      leaf extended-admin-group {
        type te-types:extended-admin-group;
        description
          "Extended administrative group value.";
        reference
          "RFC 7308: Extended Administrative Groups in MPLS-TE";
      }
      description
        "The flex-algo include-any admin group sub-tlv. Note that
         the presence of more than one Include-Any Extended Admin
         Group sub-TLV will result in an invalid FAD TLV.";
    }
    description
      "The flex-algo include-any admin group sub-tlv.";
  }

  grouping fa-in-all-ag-sub-tlv {
    container fa-in-all-ag-sub-tlv {
      leaf extended-admin-group {
        type te-types:extended-admin-group;
        description
          "Extended administrative group value.";
        reference
          "RFC 7308: Extended Administrative Groups in MPLS-TE";
      }
      description
        "The flex-algo include-all admin group sub-tlv. Note that
         the presence of more than one Include-All Extended Admin
         Group sub-TLV will result in an invalid FAD TLV.";
    }
    description
      "The flex-algo include-all admin group sub-tlv.";
  }

  grouping fad-flags-sub-tlv {
    container fad-flags-sub-tlv {
      leaf-list fad-flag {
        type identityref {
          base fad-flags;
        }
        description
          "Flex-algo definition flags list.";
      }
      description
        "IS-IS flex-algo definition flags.";
    }
    description
      "The flex-algo definition flags sub-tlv.";
  }

  grouping fa-ex-srlg-sub-tlv {
    container fa-ex-srlg-sub-tlv {
      leaf-list srlg {
        type te-types:srlg;
        description
          "SRLG value as defined in RFC 5307.";
      }
      description
        "The flex-algo exclude SRLG sub-tlv.";
      reference
        "RFC 5307: IS-IS Extensions in Support of
         Generalized Multi-Protocol Label Switching (GMPLS)";
    }
    description
      "The flex-algo exclude SRLG sub-tlv.";
  }

  grouping fad-tlvs {
    container fad-tlvs {
      list fad-tlv {
        leaf algo-number {
          type uint8;
          description
            "Flex-algo number - A value not in the inclusive range
             of 128-255 is an invalid FAD TLV specification.  Valid
             Flex-Algorithm numbers are in the inclusive range
             128-255 as specified in RFC 9350. There should only be
             a single FAD TLV per algorithm number.";
        }
        leaf metric-type {
          type iana-metric-types:metric-type;
          description
            "Type of metric to be used during the calculation.";
        }
        leaf calc-type {
          type iana-algo-types:algo-type;
          description
            "IGP algorithm types, value from 0 to 127 as
             defined under 'Interior Gateway Protocol (IGP)
             Parameter' by IANA.";
        }
        leaf priority {
          type uint8;
          description
            "Priority of the advertisement.";
        }
        uses fa-ex-ag-sub-tlv;
        uses fa-in-any-ag-sub-tlv;
        uses fa-in-all-ag-sub-tlv;
        uses fad-flags-sub-tlv;
        uses fa-ex-srlg-sub-tlv;
        uses isis:unknown-tlvs;
        description
          "List of flex-algo definition TLVs.";
      }
      description
        "IS-IS Flexible Algorithm Definition TLV.";
      reference
        "RFC 9350: IGP Flexible Algorithm, Section 5";
    }
    description
      "IS-IS Flexible Algorithm Definition (FAD) TLV.";
  }

  grouping fapm-sub-tlvs {
    container fapm-sub-tlvs {
      list fapm-sub-tlv {
        leaf algo-number {
          type uint8;
          description
            "Flex-algo number - A value not in the inclusive range
             of 128-255 is an invalid FAPM sub-TLV specification.";
        }
        leaf metric {
          type uint32;
          description
            "Prefix metric.";
        }
        description
          "List of flex-algo prefix sub-tlvs.";
      }
      description
        "Flex-algo prefix metric sub-tlvs.";
    }
    description
      "Flexible Algorithm Prefix Metric (FAPM) sub TLVs.";
  }

  /* Management */

  augment "/rt:routing/"
        + "rt:control-plane-protocols/rt:control-plane-protocol"
        + "/isis:isis" {
    when "derived-from-or-self(/rt:routing"
       + "/rt:control-plane-protocols/"
       + "rt:control-plane-protocol/rt:type, 'isis:isis')" {
      description
        "This augments the IS-IS routing protocol when used";
    }
    description
      "This augments the IS-IS protocol management
       with flexible algorithm.";
    container isis-flex-algo {
      list flex-algo {
        key "algo-number";
        leaf algo-number {
          type uint8 {
            range "128..255";
          }
          description
            "Flex-algo number - must be in the inclusive range
             of 128-255.";
        }
        leaf advertise-definition {
          type boolean;
          default "true";
          description
            "When set to true, enables advertisement of the
             Flexible Algorithm Definition (FAD) TLV for this
             flex-algo instance.";
        }
        container admin-groups {
          if-feature "te-types:extended-admin-groups";
          leaf exclude-admin-group {
            type te-types:extended-admin-group;
            description
              "Exclude rule used during the flex-algo
               path computation.";
          }
          leaf include-any-admin-group {
            type te-types:extended-admin-group;
            description
              "Include-any rule used during the flex-algo
               path computation.";
          }
          leaf include-all-admin-group {
            type te-types:extended-admin-group;
            description
              "Include-all rule used during the flex-algo
               path computation.";
          }
          description
            "Specify administrative groups for the flex-algo
             path computation.";
        }
        leaf-list exclude-srlg {
          type te-types:srlg;
          description
            "Shared Risk Link Groups (SRLGs) to be excluded during
             the flex-algo path computation.";
        }
        leaf metric-type {
          type iana-metric-types:metric-type;
          description
            "Type of metric to be used during the calculation.";
        }
        leaf calc-type {
          type iana-algo-types:algo-type;
          description
            "Calculation-type. Value from 0-127 inclusive from the
             IANA 'IGP Algorithm Types' registry defined under the
             'Interior Gateway Protocol (IGP) Parameters' registry.";
        }
        container prefix-metric {
          presence "Use flex-algo specific prefix metric.";
          description
            "Use flex-algo prefix metric.";
        }
        leaf priority {
          type uint8;
          description
            "Priority of the advertisement.";
        }
        description
          "List of flex-algo configurations.";
        reference
          "RFC 9350: IGP Flexible Algorithm, Section 5";
      }
      description
        "Flexible Algorithm configuration.";
    }
  }

  /* Database */

  augment "/rt:routing/"
        + "rt:control-plane-protocols/rt:control-plane-protocol"
        + "/isis:isis/isis:database/isis:levels/isis:lsp"
        + "/isis:router-capabilities/isis:router-capability" {
    when "derived-from-or-self(/rt:routing"
       + "/rt:control-plane-protocols"
       + "/rt:control-plane-protocol/rt:type, 'isis:isis')" {
      description
        "This augments the IS-IS routing protocol when used";
    }
    description
      "This augments the IS-IS protocol LSDB router capability.";
    uses fad-tlvs;
  }

  augment "/rt:routing/"
        + "rt:control-plane-protocols/rt:control-plane-protocol"
        + "/isis:isis/isis:database/isis:levels/isis:lsp"
        + "/isis:extended-ipv4-reachability/"
        + "isis:prefixes" {
    when "derived-from-or-self(/rt:routing"
       + "/rt:control-plane-protocols"
       + "/rt:control-plane-protocol/rt:type, 'isis:isis')" {
      description
        "This augments the IS-IS routing protocol when used";
    }
    description
      "This augments the IS-IS protocol LSDB prefix.";
    uses fapm-sub-tlvs;
  }

  augment "/rt:routing/"
        + "rt:control-plane-protocols/rt:control-plane-protocol"
        + "/isis:isis/isis:database/isis:levels/isis:lsp"
        + "/isis:mt-extended-ipv4-reachability/isis:prefixes" {
    when "derived-from-or-self(/rt:routing"
       + "/rt:control-plane-protocols"
       + "/rt:control-plane-protocol/rt:type, 'isis:isis')" {
      description
        "This augments the IS-IS routing protocol when used";
    }
    description
      "This augments the IS-IS protocol LSDB prefix.";
    uses fapm-sub-tlvs;
  }

  augment "/rt:routing/"
        + "rt:control-plane-protocols/rt:control-plane-protocol"
        + "/isis:isis/isis:database/isis:levels/isis:lsp"
        + "/isis:ipv6-reachability/isis:prefixes" {
    when "derived-from-or-self(/rt:routing"
       + "/rt:control-plane-protocols"
       + "/rt:control-plane-protocol/rt:type, 'isis:isis')" {
      description
        "This augments the IS-IS routing protocol when used";
    }
    description
      "This augments the IS-IS protocol LSDB prefix.";
    uses fapm-sub-tlvs;
  }

  augment "/rt:routing/"
        + "rt:control-plane-protocols/rt:control-plane-protocol"
        + "/isis:isis/isis:database/isis:levels/isis:lsp"
        + "/isis:mt-ipv6-reachability/isis:prefixes" {
    when "derived-from-or-self(/rt:routing"
       + "/rt:control-plane-protocols"
       + "/rt:control-plane-protocol/rt:type, 'isis:isis')" {
      description
        "This augments the IS-IS routing protocol when used";
    }
    description
      "This augments the IS-IS protocol LSDB prefix.";
    uses fapm-sub-tlvs;
  }

  /* Notification */

  notification flex-algo-not-supported {
    uses isis:notification-instance-hdr;
    leaf algo-number {
      type uint8;
      description
        "Flex-algo identifier which is not supported by the IS-IS
         instance.  Valid Flex-Algorithm numbers are in the
         inclusive range 128-255 as specified in RFC 9350.
         A value outside this range in a received FAD TLV
         is invalid.";
      reference
        "RFC 9350: IGP Flexible Algorithm, Section 5";
    }
    description
      "This notification is sent when an IS-IS instance does not
       support this flex-algo.";
  }
}
