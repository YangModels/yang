module ietf-netconf-exi {
    namespace "urn:ietf:params:xml:ns:netconf:exi:1.0";

    prefix exi;

    organization
        "IETF NETCONF (Network Configuration) Working Group";

    contact
        "Robert Varga <robert.varga@pantheon.sk>";

    description
        "NETCONF Protocol Operations for Efficient XML Interchange.";

    revision 2013-10-21 {
        description
            "Initial revision";
        reference
            "I-D.varga-netconf-exi-capability-01";
    }

    typedef exi-alignment {
        type enumeration {
            enum bit-packed {
                description
                    "Use bit-packed EXI alignment";
            }
            enum byte-aligned {
                description
                    "Use byte-aligned EXI alignment";
            }
            enum pre-compression {
                description
                    "Use pre-compression EXI alignment";
            }
            enum compressed {
                description
                    "Do not set EXI alignment, use EXI compression
                    instead";
            }
        }

        description "EXI alignment specification.";
    }

    typedef exi-fidelity {
        type enumeration {
            enum comments {
                description
                    "Preserve.comments EXI Fidelity option";
            }
            enum dtd {
                description
                    "Preserve.dtd EXI Fidelity option";
            }
            enum lexical-values {
                description
                    "Preserve.lexicalValues EXI Fidelity option";
            }
            enum pis {
                description
                    "Preserve.pis EXI Fidelity option";
            }
            enum prefixes {
                description
                    "Preserve.prefixes EXI Fidelity option";
            }
        }

        description "EXI fidelity options.";
    }

    rpc start-exi {
        description
            "Start encoding protocol messages in Efficient XML
            Interchange format.";

        reference "I-D.varga-netconf-exi-capability";

        input {
            leaf alignment {
                type exi-alignment;
                default "bit-packed";
                description "EXI alignment to use.";
            }

            leaf-list fidelity {
                type exi-fidelity;
                description "EXI fidelity options to use.";
            }
        }
    }

    rpc stop-exi {
        description
            "Stop encoding protocol messages in Efficient XML
            Interchange format. Revert back to using the usual text
            XML encoding.";
    }
}
