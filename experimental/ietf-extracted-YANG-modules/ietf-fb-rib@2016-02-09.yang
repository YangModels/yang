module ietf-fb-rib {
  yang-version "1";

  // namespace
  namespace "urn:ietf:params:xml:ns:yang:ietf-fb-rib";
  // replace with iana namespace when assigned
    prefix "fb-rib";

  // import some basic inet types
  import ietf-yang-types {prefix "yang";}
  import ietf-fb-rib-types { prefix "fb-rib-t";}

  // meta
  organization
    "IETF";

  contact
     "email: sriganesh.kini@ericsson.com
          email: cengiz@packetdesign.com
      email: anoop@ieee.duke.edu
      email: ivandean@gmail.org
      email: shares@ndzh.com;
      email: linda.dunbar@huawei.com;
      email: russ@riw.com;
         ";

  description
    "This Top level module describes a YANG model for the I2RS
        Filter-based RIB which is an global protocol independent FB RIB module.";

     revision "2016-02-09" {
       description "initial revision";
       reference "draft-hares-i2rs-fb-rib-data-model-01";
     }

        feature config-filter-based-RIB {
    description
      "This feature means that a node support
       config filter-based rib.";
    }
        feature I2RS-filter-based-RIB {
    description
      "This feature means that a node support
       I2RS filter-based rib.";
    }
        feature BGP-FS-filter-based-RIB {
    description
      "This feature means that a node support
      BGP FS filter-based rib.";
    }

         container ietf-fb-rib {
           presence "top-level structure for
            configuration";
       leaf default-instance-name {
             type string;
                 mandatory true;
        description
          "A routing instance is identified by its name,
           INSTANCE_name.  This MUST be unique across all routing
           instances in a given network device.";
         }
             leaf default-router-id {
                    type yang:dotted-quad;
                    description "Default router id";
                }
                container config-fb-rib {
                 if-feature config-filter-based-RIB;
                  uses fb-rib-t:fb-ribs;
                 description "config filter-based RIB";
                }

                container i2rs-fb-rib {
                  if-feature I2RS-filter-based-RIB;
                  uses fb-rib-t:fb-ribs;
                 description "bgp-fs filter-based RIB";
                }
                container bgp-fs-fb-rib {
                  if-feature BGP-FS-filter-based-RIB;
                  uses fb-rib-t:fb-ribs;
                 description "bgp fs filter-based RIB";
                }
           description "fb-rib augments routing instance";
         }

        container ietf-fb-rib-opstate {
           presence "top-level structure for
            op-state";
           config "false";
       leaf default-instance-name {
             type string;
                 mandatory true;
        description
          "A routing instance is identified by its name,
           INSTANCE_name.  This MUST be unique across all routing
           instances in a given network device.";
         }
             leaf default-router-id {
                    type yang:dotted-quad;
                    description "Default router id";
                }
                container config-fb-rib-opstate {
                  if-feature config-filter-based-RIB;
                  uses fb-rib-t:fb-ribs-oper-status;
                 description "config filter-based RIB";
                }
                container i2rs-fb-rib-opstate {
                  if-feature I2RS-filter-based-RIB;
                  uses fb-rib-t:fb-ribs-oper-status;
                 description "bgp-fs filter-based RIB";
                }
                container bgp-fs-fb-rib-opstate {
                  if-feature BGP-FS-filter-based-RIB;
                  uses fb-rib-t:fb-ribs-oper-status;
                 description "bgp fs filter-based RIB";
                }
           description "fb-rib augments routing instance";
         }
}
