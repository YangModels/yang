module ietf-on-path-telemetry {
  yang-version 1.1;
  namespace "urn:ietf:params:xml:ns:yang:ietf-on-path-telemetry";
  prefix "on-path-telemetry";

  import ietf-interfaces {
    prefix if;
    reference
      "RFC 8343: A YANG Data Model for Interface Management";
  }

  import ietf-yang-types {
    prefix yang;
    reference
      "Section 3 of RFC 9911";
  }

  import ietf-ioam {
    prefix ioam;
    reference
      "RFC 9617";
  }

  import ietf-altmark {
    prefix altmark;
    reference
      "draft-ietf-ippm-alt-mark-yang";
  }
  import ietf-lime-time-types {
    prefix lime;
    reference
      "RFC 8532: Generic YANG Data Model for the Management of
       Operations, Administration, and Maintenance (OAM) Protocols
       That Use Connectionless Communications";
  }

  organization
    "IETF IPPM (IP Performance Metrics) Working Group";

  contact
    "WG Web: <https://datatracker.ietf.org/wg/ippm>
     WG List: <ippm@ietf.org>
     Author: giuseppe.fioccola@huawei.com
     Author: zhoutianran@huawei.com
     Author: zhuyq8@chinatelecom.cn
     Author: zhangwq@chinatelecom.cn
     Author: zhukeyi@huawei.com";

  description
    "This YANG module specifies a vendor-independent data
     model for On-Path Telemetry.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-08-26 {
    description "First revision.";
    reference "RFC XXXX: A YANG Data Model for On-path Telemetry";
  }
 /*
  * FEATURES
  */

  feature pathdelay {
    description
      "This feature indicates that the Path Delay is
       supported.";
    reference
      "RFC 9951: Export of Delay Performance Metrics in IPFIX";
  }

 /*
  * IDENTITIES
  */

  identity trace-data {
    description
      "IOAM trace data as defined in RFC 9197.";
  }

  identity pot-data {
    description
      "IOAM pot data as defined in RFC 9197.";
  }

  identity e2e-data {
    description
      "IOAM edge-to-edge data as defined in RFC 9197.";
  }

 /*
  * TYPE DEFINITIONS
  */

  typedef ioam-trace-data {
    type identityref {
      base trace-data;
    }
    description
      "It specifies the trace data.";
  }

  typedef ioam-pot-data {
    type identityref {
      base pot-data;
    }
    description
      "It specifies the pot data.";
  }

  typedef ioam-e2e-data {
    type identityref {
      base e2e-data;
    }
    description
      "It specifies the edge-to-edge data.";
  }

 /*
  * GROUP DEFINITIONS
  */

  grouping loss-counters {
    description
      "The set of counters for RFC 9341 and RFC 9342 loss
       calculation.";

    leaf loss-flag {
      type boolean;
      config false;
      description
        "The loss-flag value is defined in RFC 9343 and RFC 9714.
         Note that it corresponds to the altmarkLossFlag parameter
         defined in draft-ietf-opsawg-ipfix-alt-mark.";
    }

    leaf in-traffic-pkts {
      type yang:counter64;
      config false;
      description
        "Total inbound packets of the period according to RFC 9341
         and RFC 9342";
    }

    leaf out-traffic-pkts {
      type yang:counter64;
      config false;
      description
        "Total outbound packets of the period according to RFC 9341
         and RFC 9342";
    }

    leaf in-traffic-bytes {
      type uint64;
      units "bytes";
      config false;
      description
        "Total inbound bytes of the period according to RFC 9341
         and RFC 9342";
    }

    leaf out-traffic-bytes {
      type uint64;
      units "bytes";
      config false;
      description
        "Total outbound bytes of the period according to RFC 9341
         and RFC 9342";
    }
  }

  grouping delay-timestamps {
    description
      "It indicates the set of timestamps for RFC 9341 and RFC 9342
       delay calculation.";

    leaf delay-flag {
      type boolean;
      config false;
      description
        "The delay-flag value is defined in RFC 9343 and RFC 9714.
         Note that it corresponds to the altmarkDelayFlag parameter
         defined in draft-ietf-opsawg-ipfix-alt-mark.";
    }

    container in-pkts-timestamps {
      config false;
      description
        "The list of timestamps of the period according to RFC 9341
         and RFC 9342";

      leaf in-pkt-timestamp {
        type yang:date-and-time;
        description
          "To specify the timestamp of the delay packet for delay
           measurements";
      }

      leaf in-pkt-seq-num {
        type uint32;
        description
          "To specify the sequence number of the delay packet for
           delay measurements";
      }
    }

    container out-pkts-timestamps {
      config false;
      description
        "The list of timestamps of the period according to RFC 9341
         and RFC 9342";

      leaf out-pkt-timestamp {
        type yang:date-and-time;
        description
          "To specify the timestamp of the delay packet for delay
           measurements";
      }

      leaf out-pkt-seq-num {
        type uint32;
        description
          "To specify the sequence number of the delay packet for
           delay measurements";
      }
    }
  }

  grouping path-delay-metrics {
    description
      "It indicates the path delay measurements.";

    leaf path-delay-mean {
      type uint32;
      units "microseconds";
      config false;
      description
        "mean path delay as per RFC 9951";
    }
    leaf path-delay-min {
      type uint32;
      units "microseconds";
      config false;
      description
        "min path delay as per RFC 9951";
    }

    leaf path-delay-max {
      type uint32;
      units "microseconds";
      config false;
      description
        "max path delay as per RFC 9951";
    }

    leaf path-delay-sum {
      type uint64;
      units "microseconds";
      config false;
      description
        "sum of the path delay as per RFC 9951";
    }
  }

  grouping ioam-incremental-tracing-data-list {
    description
      "A grouping for incremental tracing data.";

    leaf-list incremental-tracing {
      type ioam-trace-data;
      config false;
      description
        "This object indicates the incremental tracing data.";
    }
  }

  grouping ioam-preallocated-tracing-data-list {
    description
      "A grouping for the list of pre-allocated tracing data.";

    leaf-list preallocated-tracing {
      type ioam-trace-data;
      config false;
      description
        "This object indicates the preallocated tracing data.";
    }
  }

  grouping ioam-direct-export-tracing-data-list {
    description
      "A grouping for the list of direct export data.";

    leaf-list direct-export {
      type ioam-trace-data;
      config false;
      description
        "This object indicates the direct export data.";
    }
  }
  grouping ioam-proof-of-transit-data-list {
    description
      "A grouping for the list of proof of transit data.";

    leaf-list proof-of-transit {
      type ioam-pot-data;
      config false;
      description
        "This object indicates the proof of transit data.";
    }
  }

  grouping ioam-edge-to-edge-data-list {
    description
      "A grouping for the list of edge-to-edge data.";

    leaf-list edge-to-edge {
      type ioam-e2e-data;
      config false;
      description
        "This object indicates the edge to edge data.";
    }
  }

 /*
  * DATA NODES
  */

  augment "/altmark:altmark" {
    description "Augments the AltMark with timestamp information";

    container altmark-info {
      config false;
      description
        "Describes information such as units or timestamp format
        that assists monitoring systems in the interpretation of the
        on-path-telemetry data.";

      leaf timestamp-type {
        type identityref {
          base lime:timestamp-type;
        }
        description
          "Type of timestamp, such as Truncated PTP or NTP.";
      }
    }
  }

  augment "/altmark:altmark/altmark:available-interfaces/"
        + "altmark:available-interface/altmark:altmark-profiles/"
        + "altmark:altmark-profile" {
    description "Augments the AltMark with the On-path Telemetry data";

    leaf measurement-period-number {
      type uint32;
      config false;
      description
        "It specifies the On-path Telemetry period number.";
    }

    container altmark-loss-measurement {
      if-feature altmark:altmark;
      presence
        "Present when AltMark loss measurement is enabled.";
      description
        "It reports the loss measurement data.";

      uses loss-counters;
    }

    container altmark-delay-measurement {
      if-feature altmark:altmark;
      presence
        "Present when AltMark delay measurement is enabled.";
      description
        "It reports the delay measurement data.";

      uses delay-timestamps;
    }

    container path-delay-measurement {
      if-feature pathdelay;
      description
        "It reports the path delay measurement data.";

      uses path-delay-metrics;
    }
  }

  augment "/ioam:ioam/ioam:profiles/ioam:profile" {
    description "Augments the AltMark with the On-path Telemetry data";

    list available-interface {
      key "if-name";
      description
        "It contains the list of the interfaces activated for
         Telemetry";
      leaf if-name {
        type if:interface-ref;
        description "This is a reference to the Interface name.";
      }

      container ioam-incremental-tracing {
        if-feature ioam:incremental-trace;
        presence
          "Present when incremental tracing option is available.";
        description
          "It reports the incremental tracing option data.";

        uses ioam-incremental-tracing-data-list;
      }

      container ioam-preallocated-tracing {
        if-feature ioam:preallocated-trace;
        presence
          "Present when preallocated tracing option is available.";
        description
          "It reports the preallocated tracing option data.";

        uses ioam-preallocated-tracing-data-list;
      }

      container ioam-direct-export {
        if-feature ioam:direct-export;
        presence
          "Present when direct-export option is available.";
        description
          "It reports the direct-export option data";

        uses ioam-direct-export-tracing-data-list;
      }

      container ioam-proof-of-transit {
        if-feature ioam:proof-of-transit;
        presence
          "Present when proof of transit option is available.";
        description
          "It reports the PoT option data.";

        uses ioam-proof-of-transit-data-list;
      }

      container ioam-edge-to-edge {
        if-feature ioam:edge-to-edge;
        presence
          "Present when edge-to-edge option is available.";
        description
          "It reports the edge-to-edge option data.";

        uses ioam-edge-to-edge-data-list;
      }

      container path-delay-measurement {
        if-feature pathdelay;
        description
          "It reports the path delay measurement data.";

        uses path-delay-metrics;
      }
    }
  }
}
