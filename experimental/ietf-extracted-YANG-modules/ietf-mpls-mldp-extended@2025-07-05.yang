module ietf-mpls-mldp-extended {
  yang-version 1.1;

  namespace "urn:ietf:params:xml:ns:yang:ietf-mpls-mldp-extended";
  prefix "mldp-ext";

  import ietf-inet-types {
    prefix "inet";
    reference "RFC 6991: Common YANG Data Types";
  }

  import ietf-interfaces {
    prefix "if";
    reference "RFC 8343: A YANG Data Model for Interface Management";
  }

  import ietf-routing {
    prefix "rt";
    reference
      "RFC 8349: A YANG Data Model for Routing Management (NMDA
       version)";
  }

  import ietf-routing-types {
    prefix "rt-types";
    reference
      "RFC 8294: Common YANG Data Types for the Routing Area";
  }

  import ietf-mpls-ldp {
    prefix "ldp";
    reference "RFC 9070: YANG Data Model for MPLS LDP";
  }

  import ietf-mpls-ldp-extended {
    prefix "ldp-ext";
    reference "RFC 9070: YANG Data Model for MPLS LDP";
  }
  import ietf-mpls-mldp {
    prefix "mldp";
   reference "RFC XXXX: Base YANG Data Model for MPLS mLDP";
// RFC Editor: replace the XXXX with actual mLDP YANG RFC number at
// time of publication and remove this note.
  }

  organization
    "IETF MPLS Working Group";
  contact
    "WG Web:   <http://tools.ietf.org/wg/mpls/>
     WG List:  <mailto:mpls@ietf.org>

     Editor:   Kamran Raza
               <mailto:skraza@cisco.com>

     Editor:   Xufeng Liu
               <mailto:xufeng.liu.ietf@gmail.com>

     Editor:   Santosh Esale
               <mailto:santosh_easale@berkeley.edu>

     Editor:   Loa Andersson
               <mailto:loa@pi.nu>

     Editor:   Jeff Tantsura
               <mailto:jefftant.ietf@gmail.com>";

  description
    "This YANG module defines the extended components for the
     management of Multiprotocol Label Switching (MPLS) Multipoint
     LDP (mLDP).

     The types and groupings defined in this module are intended exclusively
     for use within this module itself or any other module that augments this
     module.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

     // RFC Editor: replace XXXX with actual RFC number and remove
     // this note

  revision 2025-07-05 {
    // RFC Editor: replace the above date with the date of
    // publication and remove this note.
    description
      "Addressing RtgDir review comments";
    reference
      "RFC XXXX: Base YANG Data Model for MPLS mLDP";
     // RFC Editor: replace XXXX with actual RFC number and remove
     // this note
  }

  revision 2024-12-01 {
    // RFC Editor: replace the above date 2024-12-01 with the date of
    // publication and remove this note.
    description
      "Addressing YANG doctors review comments";
    reference
      "RFC XXXX: Base YANG Data Model for MPLS mLDP";
     // RFC Editor: replace XXXX with actual RFC number and remove
     // this note
  }

  revision 2021-11-11 {
    description
      "Initial revision.";
    reference
      "RFC XXXX: Extended YANG Data Model for MPLS mLDP";
     // RFC Editor: replace XXXX with actual RFC number and remove
     // this note
  }

  /*
   * Features
   */
  feature capability-mldp-hsmp {
    description
      "This feature indicates that the system allows to configure
       mLDP hub-and-spoke-multipoint capability.";
     reference
       "RFC7140: LDP Extensions for Hub and Spoke Multipoint
        Label Switched Path";
  }

  feature capability-mldp-node-protection {
    description
      "This feature indicates that the system allows to configure
       mLDP node-protection capability.";
    reference
        "RFC7715: Multipoint LDP (mLDP) Node Protection";
  }

  feature mldp-mofrr {
    description
      "This feature indicates that the system supports mLDP
       Multicast only FRR (MoFRR).";
     reference
       "RFC7431: Multicast-Only Fast Reroute";
  }

  feature per-peer-capability {
    description
      "This feature indicates that the system allows to configure
       mLDP capabilities at the per peer level.";
  }

  /*
   * Typedefs
   */
  typedef lsp-mofrr-role {
    type enumeration {
      enum none {
        description "MoFRR is not enabled.";
      }
      enum primary {
        description "This LSP is primary.";
      }
      enum backup {
        description "This LSP is backup.";
      }
    }
    description
      "This type represents the MoFRR (Multicast-only FRR)
       role of an LSP.";
  }

  /*
   * Groupings
   */
  grouping  mldp-ext-binding-label-peer-state {
    description
      "mLDP label binding peer state.";

    list peer {
      key "direction peer advertisement-type";
      description
        "List of peers with bindings exchnaged (sent and/or received)";
      leaf peer {
        type leafref {
          path
            "../../../../../../../../../../../ldp:peers/ldp:peer/"
          + "ldp:lsr-id";
        }
        description
          "[m]LDP peer from which this binding is received, or
           to which this binding is advertised.";
      }
      uses mldp:mldp-binding-label-peer-state-attributes;

      leaf mofrr-status {
        when "../direction = 'upstream'" {
          description
           "This leaf is used for MoFRR upstream direction only.";
        }
        type lsp-mofrr-role;
        description
          "The MoFRR status of this LSP";
      }
    } // peer
  } // mldp-ext-binding-label-peer-state

  grouping mldp-ext-capabilities {
    description
      "mLDP extended capabilities";
    container hub-and-spoke {
      if-feature capability-mldp-hsmp;
      description
        "Configure hub-and-spoke-multipoint capability";
      reference
        "RFC7140: LDP Extensions for Hub and Spoke Multipoint
         Label Switched Path";
      leaf enabled {
        type boolean;
        description
          "Enable hub-and-spoke-multipoint";
      }
    }
    container node-protection {
      if-feature capability-mldp-node-protection;
      description
        "Configure node-protection capability.";
      reference
        "RFC7715: mLDP Node Protection.";
      leaf plr {
        type boolean;
        description
          "Point of Local Repair (PLR) capable for Multipoint LSP
           node protection";
      }
      container merge-point {
        description
          "Merge Point capable for Multipoint LSP node protection";
        leaf enabled {
          type boolean;
          description
            "Enable merge point capability";
        }
        leaf targeted-session-teardown-delay {
          type uint16;
          units seconds;
          description
            "Targeted session teardown delay";
        }
      } // merge-point
    } // node-protection
  } // mldp-ext-capabilities

  grouping mldp-ext-per-af-config-attributes {
    description
      "mLDP per address family configuration attributes";
    container multicast-only-frr {
      if-feature mldp-mofrr;
      description
        "Multicast-only FRR (MoFRR) policy";
      reference
        "RFC7431: Multicast-Only Fast Reroute";
      leaf prefix-list {
        type ldp-ext:prefix-list-ref;
        description
          "Enables Multicast-only FRR (MoFRR) for the specified prefix-list";
      }
    } // multicast-only-frr

    container recursive-fec {
      description
        "Recursive FEC policy";
      leaf prefix-list {
        type ldp-ext:prefix-list-ref;
        description
          "Enables recursive FEC for the specified prefix-list";
      }
    } // recursive-fec
  } // mldp-ext-per-af-config-attributes

  grouping recursive-fec-base-attributes {
    description
      "mLDP recursive FEC base attributes.";
      reference
        "RFC6512: Using Multipoint LDP When the
         Backbone Has No Route to the Root";
    leaf recur-root-address {
      type inet:ip-address;
      description
        "Recursive root address";
    }
  } // recursive-fec-base-attributes

 grouping recursive-fec-attributes {
    description
      "mLDP recursive FEC attributes.";
      reference
        "RFC6512: Using Multipoint LDP When the
         Backbone Has No Route to the Root";

    uses recursive-fec-base-attributes;

    leaf recur-rd {
      type rt-types:route-distinguisher;
      description
        "Route Distinguisher in the VPN-Recursive
         Opaque Value";
    }
 } // recursive-fec-attributes

  /*
   * Configuration data and operational state data nodes
   */
  // Global capability
  augment "/rt:routing/rt:control-plane-protocols/"
    + "rt:control-plane-protocol/ldp:mpls-ldp/ldp:global/"
    + "ldp:capability/mldp:mldp" {
    description "Augmentation for mLDP global capabilities.";

    uses mldp-ext-capabilities;
  }

  /* TODO: FIXME
  // Peer capability
  augment "/rt:routing/rt:control-plane-protocols/"
    + "rt:control-plane-protocol/ldp:mpls-ldp/ldp:peers/ldp:peer/"
    + "ldp:capability" {
    description "Augmentation for mLDP peer capability.";
    container mldp {
      if-feature per-peer-capability;
      description
        "mLDP capabilities";
      uses mldp:mldp-capabilities;
    }
  } */

  // IPv4 config
  augment "/rt:routing/rt:control-plane-protocols/"
    + "rt:control-plane-protocol/ldp:mpls-ldp/ldp:global/mldp:mldp/"
    + "mldp:address-families/mldp:ipv4" {
    description "Augmentation for mLDP IPv4 configuration";
    uses mldp-ext-per-af-config-attributes;
  }

  // IPv4 static-lsps-leaf config
  augment "/rt:routing/rt:control-plane-protocols/"
    + "rt:control-plane-protocol/ldp:mpls-ldp/ldp:global/mldp:mldp/"
    + "mldp:address-families/mldp:ipv4/mldp:static-lsps-leaf/"
    + "mldp:opaque-element-lspid/mldp:fec-label" {
    description
      "Augmentation for mLDP IPv4 static-lsps-leaf
       configuration for opaque-element-lspid with recursive-fec";
    list recursive-fec {
      key
        "recur-root-address";
      description
        "List of recursive-fec opaque values";
      uses recursive-fec-base-attributes;
    } // recursive-fec
  }

  augment "/rt:routing/rt:control-plane-protocols/"
    + "rt:control-plane-protocol/ldp:mpls-ldp/ldp:global/mldp:mldp/"
    + "mldp:address-families/mldp:ipv4/mldp:static-lsps-leaf" {
    description
      "Augmentation for mLDP IPv4 static-lsps-leaf
       configuration for other opaque types";

    container opaque-element-transit-source {
      description
        "Transit IPv4/VPNv4 Source opaque type";
      reference
        "RFC6826: Multipoint LDP In-Band Signaling for
         Point-to-Multipoint and
         Multipoint-to-Multipoint Label Switched Paths.";
      list fec-label {
        key
          "root-address source-address group-address " +
          "rd recur-root-address recur-rd";
        description
          "List of FEC-label bindings";
        leaf root-address {
          type inet:ipv4-address;
          description
            "Root address";
        }
        leaf source-address {
          type inet:ipv4-address;
          description
            "Source address (0.0.0.0 refers to wildcard *)";
        }
        leaf group-address {
          type inet:ipv4-address;
          description
            "Group address (0.0.0.0 refers to wildcard *)";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
      } // fec-label
    } // opaque-element-transit-source

    container opaque-element-transit-bidir {
      description
        "Transit IPv4/VPNv4 Bidir opaque type";
      reference
        "RFC6826: Multipoint LDP In-Band Signaling for
         Point-to-Multipoint and
         Multipoint-to-Multipoint Label Switched
         Paths.";
      list fec-label {
        key
          "root-address masklen rp group-address rd recur-root-address "
        + "recur-rd";
        description
          "List of FEC-label bindings";
        leaf root-address {
          type inet:ipv4-address;
          description
            "Root address";
        }
        leaf masklen {
          type uint8;
          description "Mask length for the subnet";
        }
        leaf rp {
          type inet:ipv4-address;
          description
            "Rendezvous-Point (RP) address";
        }
        leaf group-address {
          type inet:ipv4-address;
          description
            "Group address";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
      } // fec-label
    } // opaque-element-transit-bidir
  }

  // IPv6 config
  augment "/rt:routing/rt:control-plane-protocols/"
    + "rt:control-plane-protocol/ldp:mpls-ldp/ldp:global/mldp:mldp/"
    + "mldp:address-families/ipv6" {
    description "Augmentation for mLDP IPv6 configuration";
    uses mldp-ext-per-af-config-attributes;
  }

  // Global forwarding-nexthop
  augment "/rt:routing/rt:control-plane-protocols/"
    + "rt:control-plane-protocol/ldp:mpls-ldp/ldp:global/"
    + "ldp-ext:forwarding-nexthop/ldp-ext:interfaces/"
    + "ldp-ext:interface/ldp-ext:address-family" {
    description
      "Augmentation for mLDP nexthop forwarding interface";
    leaf mldp-disable {
      type boolean;
      description
        "Disable mLDP forwarding on this interface";
    }
  }

  /*
   * Operational state data nodes
   */
  // IPv4 state for per peer bindings
  augment "/rt:routing/rt:control-plane-protocols/"
    + "rt:control-plane-protocol/ldp:mpls-ldp/ldp:global/mldp:mldp/"
    + "mldp:address-families/mldp:ipv4/mldp:roots/mldp:root/"
    + "mldp:bindings/mldp:opaque-element-lspid/mldp:fec-label/"
    + "mldp:peer" {
    description "Augmentation for mLDP IPv4 state";

    leaf mofrr-status {
      when "../mldp:direction = 'upstream'" {
        description
          "This leaf is used for upstream direction only.";
      }
      type lsp-mofrr-role;
      description
        "The MoFRR status of this LSP";
    }
  }

  // Peer capability state
  augment "/rt:routing/rt:control-plane-protocols/"
    + "rt:control-plane-protocol/ldp:mpls-ldp/ldp:peers/ldp:peer/"
    + "ldp:received-peer-state/ldp:capability/mldp:mldp" {
    description
      "Augmentation for mLDP received peer state capability.";
    container hub-and-spoke {
      description
        "Operatiobal state information for the peer's hub-and-spoke-multipoint
        capability.";
      reference
        "RFC7140: LDP Extensions for Hub and Spoke Multipoint
         Label Switched Path";
      leaf is-capable {
        type boolean;
        description
          "'true' when hub-and-spoke-multipoint capability is received from
          peer";
      }
    }
    container node-protection {
      description
        "Operatiobal state information for the peer's node-protection
        capability";
      reference
        "RFC7715: mLDP Node Protection.";
      leaf is-plr-capable {
        type boolean;
        description
          "'true' when Point of Local Repair (PLR) node-protection capability
          is received from peer";
      }
      leaf is-merge-point-capable {
        type boolean;
        description
          "'true' when Merge-point node-protection capability is received from
          peer";
      } // merge-point
    } // node-protection
  }

  // IPv4 bindings state
  augment "/rt:routing/rt:control-plane-protocols/"
    + "rt:control-plane-protocol/ldp:mpls-ldp/ldp:global/mldp:mldp/"
    + "mldp:address-families/mldp:ipv4/mldp:roots/mldp:root/"
    + "mldp:bindings" {
    description "Augmentation for mLDP IPv4 bindings extended type.";

    container opaque-element-transit-source {
      description
        "Transit IPv4/VPNv4 Source opaque type";
      reference
        "RFC6826: Multipoint LDP In-Band Signaling for
         Point-to-Multipoint and
         Multipoint-to-Multipoint Label Switched Paths.";
      list fec-label {
        key
          "source-address group-address "
        + "rd recur-root-address recur-rd";
        description
          "List of FEC-label bindings";
        leaf source-address {
          type inet:ipv4-address;
          description
            "Source address (0.0.0.0 refers to wildcard *)";
        }
        leaf group-address {
          type inet:ipv4-address;
          description
            "Group address (0.0.0.0 refers to wildcard *)";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
        uses mldp-ext-binding-label-peer-state;
      } // fec-label
    } // opaque-element-transit-source

    container opaque-element-transit-bidir {
      description
        "Transit IPv4/VPNv4 Bidir opaque type";
      reference
        "RFC6826: Multipoint LDP In-Band Signaling for
         Point-to-Multipoint and
         Multipoint-to-Multipoint Label Switched
         Paths.";
      list fec-label {
        key
          "masklen rp group-address rd recur-root-address recur-rd";
        description
          "List of FEC-label bindings";
        leaf masklen {
          type uint8;
          description "Mask length for the subnet";
        }
        leaf rp {
          type inet:ipv4-address;
          description
            "Rendezvous Point (RP) address";
        }
        leaf group-address {
          type inet:ipv4-address;
          description
            "Group address";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
        uses mldp-ext-binding-label-peer-state;
      } // fec-label
    } // opaque-element-transit-bidir
  }

  // IPv6 bindings state
  augment "/rt:routing/rt:control-plane-protocols/"
    + "rt:control-plane-protocol/ldp:mpls-ldp/ldp:global/mldp:mldp/"
    + "mldp:address-families/ipv6/roots/root/bindings" {
    description "Augmentation for mLDP IPv6 bindings.";
    container opaque-element-transit-source {
      config false;
      description
        "Transit IPv6/VPNv6 Source opaque type";
      reference
        "RFC6826: Multipoint LDP In-Band Signaling for
         Point-to-Multipoint and
         Multipoint-to-Multipoint Label Switched
         Paths.";
      list fec-label {
        key
          "source-address group-address "
        + "rd recur-root-address recur-rd";
        description
          "List of FEC-label bindings";
        leaf source-address {
          type inet:ipv6-address;
          description
            "Source address (::0 refers to wildcard *)";
        }
        leaf group-address {
          type inet:ipv6-address;
          description
            "Group address (::0 refers to wildcard *)";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
        uses mldp-ext-binding-label-peer-state;
      } // fec-label
    } // opaque-element-transit-source

    container opaque-element-transit-bidir {
      config false;
      description
        "Transit IPv6/VPNv6 Bidir opaque type";
      reference
        "RFC6826: Multipoint LDP In-Band Signaling for
         Point-to-Multipoint and
         Multipoint-to-Multipoint Label Switched
         Paths.";
      list fec-label {
        key
          "masklen rp group-address rd recur-root-address recur-rd";
        description
          "List of FEC-label bindings";
        leaf masklen {
          type uint8;
          description "Mask length for the subnet";
        }
        leaf rp {
          type inet:ipv6-address;
          description
            "Rendezvous Point (RP) address";
        }
        leaf group-address {
          type inet:ipv6-address;
          description
            "Group address";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
        uses mldp-ext-binding-label-peer-state;
      } // fec-label
    } // opaque-element-transit-bidir
  }

  // IPv4 bindings opaque-element-lspid state
  augment "/rt:routing/rt:control-plane-protocols/"
    + "rt:control-plane-protocol/ldp:mpls-ldp/ldp:global/mldp:mldp/"
    + "mldp:address-families/mldp:ipv4/mldp:roots/mldp:root/"
    + "mldp:bindings/mldp:opaque-element-lspid/mldp:fec-label" {
    description
      "Augmentation for mLDP IPv4 bindings opaque type LSP ID.";
    list recursive-fec {
      key
        "recur-root-address";
      description
        "List of recursive opaque values";
      uses recursive-fec-base-attributes;
    } // recursive-fec
  }

  // IPv6 bindings opaque-element-lspid state
  augment "/rt:routing/rt:control-plane-protocols/"
    + "rt:control-plane-protocol/ldp:mpls-ldp/ldp:global/mldp:mldp/"
    + "mldp:address-families/ipv6/roots/root/bindings/"
    + "opaque-element-lspid/fec-label" {
    description
      "Augmentation for mLDP IPv6 bindings with opaque type LSP ID.";
    list recursive-fec {
      key "recur-root-address";
      config false;
      description
        "List of recursive opaque values";
      uses recursive-fec-base-attributes;
    } // recursive-fec
  }

  /*
   * Per AF augmentation
   */
  // IPv6 augmentation
  augment "/rt:routing/rt:control-plane-protocols/"
    + "rt:control-plane-protocol/ldp:mpls-ldp/ldp:global/mldp:mldp/"
    + "mldp:address-families" {
    description "Augmentation for mLDP IPv6 address family.";
    container ipv6 {
      presence "Enables IPv6 mLDP support unless the
                'enabled' leaf is set to 'false'.";
      description
             "Containing data related to the IPv6 address family.";
      leaf enabled {
        type boolean;
        default "true"; // TBD
        description
             "'false' to disable the IPv6 address family.";
       }

      container roots {
        config false;
        description
          "IPv6 multicast LSP roots";
        list root {
          key "root-address";
          description
            "List of roots for configured multicast LSPs";

          leaf root-address {
            type inet:ipv6-address;
            description
              "Root address";
          }

          leaf is-self {
            type boolean;
            description
                  "The node itself is the root node.";
          }

          list reachability {
            key "address interface";
            description
                  "Root reachability information in form of a next-hop";
            leaf address {
              type inet:ipv6-address;
              description
                "The next-hop address to reach root";
            }
            leaf interface {
              type if:interface-ref;
              description
                "The next-hop interface to reach root";
            }
            leaf peer {
              type leafref {
                path
                  "../../../../../../../../ldp:peers/"
                  + "ldp:peer/ldp:lsr-id";
              }
              description
                "LDP peer associated with the nexthop (address, interface)";
            }
          }

          container bindings {
            description
              "mLDP FEC-label bindings";
            container opaque-element-lspid {
              description
                "Generic LSP identifier opaque element FEC-label bindings container";
              reference
                "RFC6388: Label Distribution Protocol
                 Extensions for Point-to-Multipoint and
                 Multipoint-to-Multipoint Label Switched
                 Paths.";
              list fec-label {
                key
                  "lsp-id";
                description
                  "List of FEC-label bindings";
                leaf lsp-id {
                  type uint32;
                  description "LSP identifier";
                }
                leaf multipoint-type {
                  type mldp:multipoint-type;
                  description
                    "The type of multipoint: p2mp or mp2mp";
                }

                uses mldp-ext-binding-label-peer-state;
              } // fec-label
            } // opaque-element-lspid
          } // bindings
        } // list root
      } // roots

      container static-lsps-leaf {
        description
          "Statically Configured multicast LSPs at leaf node.";

        container opaque-element-lspid {
          description
            "Generic LSP identifier opaque element FEC-label bindings container";
          reference
            "RFC6388: Label Distribution Protocol
             Extensions for Point-to-Multipoint and
             Multipoint-to-Multipoint Label Switched
             Paths.";
          list fec-label {
            key
              "root-address lsp-id";
            description
              "List of FEC-label bindings";
            leaf root-address {
              type inet:ipv6-address;
              description
                "Root address";
            }
            leaf lsp-id {
              type uint32;
              description "LSP identifier";
            }
            leaf multipoint-type {
              type mldp:multipoint-type;
              description
                "The type of multipoint: p2mp or mp2mp";
            }
            list recursive-fec {
              key
                "recur-root-address";
              description
                "List of recursive opaque values";
              uses recursive-fec-base-attributes;
            } // recursive-fec
          } // fec-label
        } // opaque-element-lspid

        container opaque-element-transit-source {
          description
            "Transit IPv6/VPNv6 Source opaque type";
          reference
            "RFC6826: Multipoint LDP In-Band Signaling for
             Point-to-Multipoint and
             Multipoint-to-Multipoint Label Switched Paths.";
          list fec-label {
            key
              "root-address source-address group-address "
              + "rd recur-root-address recur-rd";
            description
              "List of FEC-label bindings";
            leaf root-address {
              type inet:ipv6-address;
              description
                "Root address";
            }
            leaf source-address {
              type inet:ipv6-address;
              description
                "Source address (::0 refers to wildcard *)";
            }
            leaf group-address {
              type inet:ipv6-address;
              description
                "Group address (::0 refers to wildcard *)";
            }
            leaf rd {
              type rt-types:route-distinguisher;
              description
                "Route Distinguisher";
              reference
                "RFC7246: Multipoint Label Distribution
                 Protocol In-Band Signaling in a Virtual
                 Routing and Forwarding (VRF) Table
                 Context.";
            }
            uses recursive-fec-attributes;
          } // fec-label
        } // opaque-element-transit-source

        container opaque-element-transit-bidir {
          description
            "Transit IPv6/VPNv6 Bidir opaque type";
          reference
            "RFC6826: Multipoint LDP In-Band Signaling for
             Point-to-Multipoint and
             Multipoint-to-Multipoint Label Switched
             Paths.";
          list fec-label {
            key
              "root-address masklen rp group-address rd recur-root-address "
            + "recur-rd";
            description
              "List of FEC-label bindings.";
            leaf root-address {
              type inet:ipv6-address;
              description
                "Root address";
            }
            leaf masklen {
               type uint8;
               description "Mask length for the subnet";
            }
            leaf rp {
              type inet:ipv6-address;
              description
                "Rendezvous Point (RP) address";
            }
            leaf group-address {
              type inet:ipv6-address;
              description
                "Group address";
            }
            leaf rd {
              type rt-types:route-distinguisher;
              description
                "Route Distinguisher";
              reference
                "RFC7246: Multipoint Label Distribution
                 Protocol In-Band Signaling in a Virtual
                 Routing and Forwarding (VRF) Table
                 Context.";
            }
            uses recursive-fec-attributes;
          } // fec-label
        } // opaque-element-transit-bidir
      } // static-lsps-leaf
    } // ipv6
  }

  /*
   * Global augmentation
   */
  /*
   * Notifications
   */
  augment "/mldp:mpls-mldp-fec-event/mldp:opaque-element/"
    + "mldp:opaque-element-lspid/mldp:opaque-element-lspid" {
    description
      "Augmentation for mLDP notification for opaque-element-lspid.";
    container recursive-fec {
      description
        "Container of recursive opaque values";
      uses recursive-fec-base-attributes;
    } // recursive-fec
  }

  augment "/mldp:mpls-mldp-fec-event/mldp:opaque-element" {
    description
      "Augmentation for mLDP notification for opaque types other than lspid.";
    case opaque-element-transit-source {
      container opaque-element-transit-source {
        description
          "Transit IP/VPN Source opaque type";
        reference
          "RFC6826: Multipoint LDP In-Band Signaling for
           Point-to-Multipoint and
           Multipoint-to-Multipoint Label Switched Paths.";
        leaf root-address {
          type inet:ip-address;
          description
            "Root address";
        }
        leaf source-address {
          type inet:ip-address;
          description
            "Source address";
        }
        leaf group-address {
          type inet:ip-address;
          description
            "Group address";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
      } // opaque-element-transit-source container
    } // opaque-element-transit-source case

    case opaque-element-transit-bidir {
      container opaque-element-transit-bidir {
        description
          "Transit IP/VPN Bidir opaque type";
        reference
          "RFC6826: Multipoint LDP In-Band Signaling for
           Point-to-Multipoint and
           Multipoint-to-Multipoint Label Switched
           Paths.";
        leaf root-address {
          type inet:ip-address;
          description
            "Root address";
        }
        leaf masklen {
          type uint8;
          description "Mask length for the subnet";
        }
        leaf rp {
          type inet:ip-address;
          description
            "Rendezvous Point (RP) address";
        }
        leaf group-address {
          type inet:ip-address;
          description
            "Group address";
        }
        leaf rd {
          type rt-types:route-distinguisher;
          description
            "Route Distinguisher";
          reference
            "RFC7246: Multipoint Label Distribution
             Protocol In-Band Signaling in a Virtual
             Routing and Forwarding (VRF) Table
             Context.";
        }
        uses recursive-fec-attributes;
      } // opaque-element-transit-bidir container
    } // opaque-element-transit-bidir case
  } // augment
} // module
