module ietf-te-topology-sf-state {
  yang-version 1;
  namespace "urn:ietf:params:xml:ns:yang:ietf-te-topology-sf-state";

  prefix "tet-sf-s";

  import ietf-te-topology-sf {
    prefix "tet-sf";
  }

  import ietf-network-state {
    prefix "nd-s";
  }

  import ietf-network-topology-state {
    prefix "lnk-s";
  }

  import ietf-te-topology-state {
    prefix "tet-s";
  }

  organization
    "Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editors:  Igor Bryskin
               <mailto:Igor.Bryskin@huawei.com>

               Xufeng Liu
               <mailto:Xufeng_Liu@jabil.com>";

  description "SF aware TE topology model";

  revision 2017-10-22 {
    description "Initial revision";
    reference "TBD";
  }

  /*
   * Augmentations
   */
  /* Augmentations to network-types/te-topology */
  augment "/nd-s:networks/nd-s:network/nd-s:network-types/"
    + "tet-s:te-topology" {
    description
      "Defines the SF aware TE topology type.";
    uses tet-sf:sf-topology-type;
  }

  /* Augmentations to connectivity-matrix */
  augment "/nd-s:networks/nd-s:network/nd-s:node/tet-s:te/"
    + "tet-s:te-node-attributes" {
    description
      "Parameters for SF aware TE topology.";
    uses tet-sf:service-function-node-augmentation;
  }

  augment "/nd-s:networks/nd-s:network/nd-s:node/tet-s:te/"
        + "tet-s:information-source-entry" {
    description
      "Parameters for SF aware TE topology.";
    uses tet-sf:service-function-node-augmentation;
  }

  /* Augmentations to tunnel-termination-point */
  augment "/nd-s:networks/nd-s:network/nd-s:node/tet-s:te/"
    + "tet-s:tunnel-termination-point" {
    description
      "Parameters for SF aware TE topology.";
    uses tet-sf:service-function-ttp-augmentation;
  }

  /* Augmentations to connectivity-matrix */
  augment "/nd-s:networks/nd-s:network/nd-s:node/tet-s:te/"
    + "tet-s:te-node-attributes/tet-sf-s:service-function/"
    + "tet-sf-s:link-terminations/tet-sf-s:link-termination/"
    + "tet-sf-s:from" {
    description
      "Add reference to the link termination point.
       This portion cannot be shared with the state module.";
    leaf tp-ref {
      type leafref {
        path "../../../../../../../lnk-s:termination-point/"
          + "lnk-s:tp-id";
      }
      description
        "Reference to the link termination point.";
    }
  }
}
