module sd-onos-common-types { 
  namespace "urn:onos:types"; 
  prefix types ; 

  import ietf-inet-types{ 
    prefix inet;  
  } 
  import ietf-yang-types { 
    prefix yang-types; 
  } 

  organization "";  
  contact ""; 
  revision "2015-10-14" {description "revised revision.";} 

  typedef admin-status { 
    type enumeration { 
      enum admin-up { 
        value 0 ; 
            description "admin up, the operate-status is depend on 
            the real running status ." ; 
      } 
      enum admin-down { 
        value 1 ; 
            description "admin down,the operate-status is forced 
            to down no matter what the real status is" ; 
      } 
      enum config-up { 
        value 2 ; 
            description "the operate-status is forced to up no 
            matter what the real status is." ; 
      } 
    } 
    default admin-up; 
  } 

  typedef notification-status { 
    type enumeration { 
      enum up { 
        value 0 ; 
        description "up." ; 
      } 
      enum down { 
        value 1 ; 
        description "down." ; 
      } 
    } 
    default up; 
  } 

  typedef notification-type { 
    type enumeration { 
      enum ne{ 
        value 0 ; 
        description "ncd change." ; 
      } 
      enum link{ 
        value 1 ; 
        description "link change." ; 
      } 
      enum ltp{ 
        value 2 ; 
        description "ltp change." ; 
      } 
    } 
    default ltp; 
  } 

  typedef operate-status { 
    type enumeration { 
      enum operate-up { 
        value 0 ; 
        description "operate up." ; 
      } 
      enum operate-down { 
        value 1 ; 
        description "operate down." ; 
      } 
    } 
    default operate-up; 
  } 

   grouping command-result { 
     container command-result { 
       leaf result { 
        description "1 : success, 2 : failed, 3 : partly 
failed" ; 
        type int8; 
      } 
      container success-resources { 
        list success-resource-list { 
          leaf resource-id { 
            type string; 
          } 
        } 
      } 
      container failed-resources { 
        list failed-resource-list { 
          leaf resource-id { 
            type string; 
          } 
          leaf error-code { 
            type string; 
          } 
        } 
      } 
    } 
  } 
}
