module ietf-bandwidth-availability-topology {
   yang-version "1.1";
   namespace
  "urn:ietf:params:xml:ns:yang:ietf-bandwidth-availability-topology";
   prefix "bwatopo";

   import ietf-yang-types {
     prefix yang;
     reference
       "RFC 6991";
   }

   import ietf-network {
     prefix "nw";
     reference "RFC 8345: A YANG Data Model for Network Topologies";
   }

   import ietf-network-topology {
     prefix "nt";
     reference "RFC 8345: A YANG Data Model for Network Topologies";
   }

   import ietf-te-topology {
     prefix "tet";
     reference "RFC 8795: YANG Data Model for Traffic Engineering
                (TE) Topologies";
   }

   organization
     "Internet Engineering Task Force (IETF) CCAMP WG";
   contact
     "WG List: <mailto:ccamp@ietf.org>

//[JonasA] Who would like to be on the list of editors/contributors?
      Editor: Jonas Ahlberg
              <mailto:jonas.ahlberg@ericsson.com>
      Editor: Scott Mansfield
              <mailto:scott.mansfield@ericsson.com>
      Editor: Min Ye
              <mailto:amy.yemin@huawei.com>
      Editor: Italo Busi
              <mailto:Italo.Busi@huawei.com>
      Editor: Xi Li
              <mailto:Xi.Li@neclab.eu>
      Editor: Daniela Spreafico
              <mailto:daniela.spreafico@nokia.com>
     ";

   // Note to RFC Editor: replace XXXX with actual RFC number and
   // remove this note.
   description
     "This is a module for defining bandwidth availability matrix,
      for links in a topology. It is intended to be used in
      conjunction with an instance of ietf-network-topology and its

      augmentations.
      Example use cases include:
      - Defining bandwidth availability matrix for a microwave link
      - Defining bandwidth availability matrix for a LAG link
        comprising of two or more member links

      Copyright (c) 2020 IETF Trust and the persons identified as
      authors of the code.  All rights reserved.
      Redistribution and use in source and binary forms, with or
      without modification, is permitted pursuant to, and subject to
      the license terms contained in, the Simplified BSD License set
      forth in Section 4.c of the IETF Trust's Legal Provisions
      Relating to IETF Documents
      (http://trustee.ietf.org/license-info).
      This version of this YANG module is part of RFC XXXX
      (https://tools.ietf.org/html/rfcXXXX); see the RFC itself for
      full legal notices.";

   revision 2021-10-20 {
     description
     "First rough draft.";
     reference "";
   }

   /*
    * Groupings
    */
   grouping link-bw-availability-table {

     description "Grouping used for bandwidth availability.";

     list link-availability{
       key "availability";
       description
         "Table describing the bandwidths available at corresponding
          availability level for a link.";

       leaf availability {
         type decimal64 {
           fraction-digits 4;
           range "0..99.9999";
         }
         description "Availability level";
       }

       leaf link-bandwidth {
         type uint64;
         units "Kbps";

         description
           "The link bandwidth corresponding to the availability
            level";
       }
     }
     leaf actual-bandwidth{
       type yang:gauge64;
       units "bits/second";
       config false;
       description
         "An estimate of the link's current bandwidth in bits per
          second. Related to the data node speed in RFC 8343.";
       reference
         "RFC 8343: A YANG Data Model for Interface Management";
     }
   }

   /*
    * Data nodes
    */

   augment "/nw:networks/nw:network/nt:link/tet:te/"
           + "tet:te-link-attributes" {
     description
       "Augmenting link with link bandwidth availability matrix.";
     uses link-bw-availability-table;
   }
 }
