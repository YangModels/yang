module   ietf-optical-impairment-topology {
  yang-version 1.1;

  namespace "urn:ietf:params:xml:ns:yang:ietf-optical-impairment-topology";

  prefix "optical-imp-topo";
  import ietf-network {
    prefix "nw";
  }

  import ietf-network-topology {
    prefix "nt";
  }

  import ietf-te-topology {
    prefix "tet";
  }

  import ietf-layer0-types {
    prefix "layer0-types";
  }

  organization
    "IETF CCAMP Working Group";

  contact
    "Editor:   Young Lee  <leeyoung@huawei.com>
     Editor:   Haomian Zheng <zhenghaomian@huawei.com>
     Editor:   Nicola Sambo <nicosambo@gmail.com>
     Editor:   Victor Lopez <victor.lopezalvarez@telefonica.com>
     Editor:   Gabriele Galimberti <ggalimbe@cisco.com>
     Editor:   Auge Jean-Luc <jeanluc.auge@orange.com>
     Editor:   Le Rouzic Esther <esther.lerouzic@orange.com>
     Editor:   Julien Meuric <julien.meuric@orange.com>
     Editor:   Italo Busi <Italo.Busi@huawei.com>";

  description
    "This module contains a collection of YANG definitions for
     impairment-aware optical networks.

     Copyright (c) 2019 IETF Trust and the persons identified as
     authors of the code.  All rights reserved.

     Redistribution and use in source and binary forms, with or
     without modification, is permitted pursuant to, and subject
     to the license terms contained in, the Simplified BSD
     License set forth in Section 4.c of the IETF Trust's Legal
     Provisions Relating to IETF Documents
     (http://trustee.ietf.org/license-info).";

  revision 2019-02-27 {
    description
      "Initial Version";
    reference
      "RFC XXXX: A Yang Data Model for Impairment-aware
       Optical Networks";
  }

  identity modulation {
    description "base identity for modulation type";
  }

  identity QPSK {
    base modulation;
    description
      "QPSK (Quadrature Phase Shift Keying) modulation";
  }

  identity DP_QPSK {
    base modulation;
    description
      "DP-QPSK (Dual Polarization Quadrature
       Phase Shift Keying) modulation";
  }
  identity QAM8 {
    base modulation;
    description
      "8QAM (8-State Quadrature Amplitude Modulation) modulation";
  }
  identity QAM16 {
    base modulation;
    description
      "QAM16 (Quadrature Amplitude Modulation)";
  }
  identity DP_QAM8 {
    base modulation;
    description
      "DP-QAM8 (Dual Polarization Quadrature Amplitude Modulation)";
  }
  identity DC_DP_QAM8 {
    base modulation;
    description
      "DC DP-QAM8 (Dual Polarization Quadrature Amplitude Modulation)";
  }
  identity DP_QAM16 {
    base modulation;
    description
      "DP-QAM16 (Dual Polarization Quadrature Amplitude Modulation)";
  }
  identity DC_DP_QAM16 {
    base modulation;
    description
      "DC DP-QAM16 (Dual Polarization Quadrature Amplitude Modulation)";
  }

  identity FEC {
    description
      "Enumeration that defines the type of
       Forward Error Correction";
  }
  identity reed-solomon {
    base FEC;
      description
   "Reed-Solomon error correction";
  }
  identity hamming-code {
    base FEC;
      description
   "Hamming Code error correction";
  }
  identity golay {
    base FEC;
      description "Golay error correction";
  }

  typedef fiber-type {
    type enumeration {
      enum G.652 {
       description "G.652 Standard Singlemode Fiber";
      }
      enum G.654 {
        description "G.654 Cutoff Shifted Fiber";
      }
      enum G.653 {
        description "G.653 Dispersion Shifted Fiber";
      }
      enum G.655 {
        description "G.655 Non-Zero Dispersion Shifted Fiber";
      }
      enum G.656 {
        description "G.656 Non-Zero Dispersion for Wideband
                Optical Transport";
      }
      enum G.657 {
        description "G.657 Bend-Insensitive Fiber";
      }
    }
    description
      "ITU-T based fiber-types";
  }

  grouping transponder-attributes {
    description "Configuration of an optical transponder";

    leaf-list available-modulation {
      type identityref {
       base modulation;
      }
      config false;
     description
       "List determining all the available modulations";
    }

    leaf modulation-type {
      type identityref {
       base modulation;
      }
     config false;
      description
       "Modulation configured for the transponder";
    }

    leaf-list available-baud-rates {
      type uint32;
      units Bd;
      config false;
      description
        "list of available baud-rates. Baud-rate is the unit for
         symbol rate or modulation rate in symbols per second or
         pulses per second. It is the number of distinct symbol
         changes (signaling events) made to the transmission medium
         per second in a digitally modulated signal or a line code";
    }

    leaf configured-baud-rate {
      type uint32;
      units Bd;
     config false;
      description "configured baud-rate";
    }

    leaf-list available-FEC {
      type identityref {
       base FEC;
      }
      config false;
      description "List determining all the available FEC";
    }

    leaf FEC-type {
      type identityref {
       base FEC;
      }
      config false;
     description
       "FEC type configured for the transponder";
    }

    leaf FEC-code-rate {
      type decimal64 {
       fraction-digits 8;
       range "0..max";
      }
      config false;
      description "FEC-code-rate";
    }

    leaf FEC-threshold {
      type decimal64 {
       fraction-digits 8;
       range "0..max";
      }
      config false;
     description
        "Threshold on the BER, for which FEC is able to correct errors";
    }

  }

  grouping sliceable-transponder-attributes {
    description
      "Configuration of a sliceable transponder.";
    list transponder-list {
      key "carrier-id";
      config false;
      description "List of carriers";
      leaf carrier-id {
        type uint32;
        config false;
        description "Identifier of the carrier";
      }
    }
  }

  grouping optical-fiber-data {
    description
     "optical link (fiber) attributes with impairment data";
    leaf fiber-type {
      type fiber-type;
      config false;
      description "fiber-type";
    }

    leaf span-length {
      type decimal64 {
        fraction-digits 2;
      }
      units "km";
      config false;
      description "the lenght of the fiber span in km";
    }

    leaf input-power {
      type decimal64 {
        fraction-digits 2;
      }
      units "dBm";
      config false;
      description
       "Average input power level estimated at the receiver
         of the link";
    }

    leaf output-power {
      type decimal64 {
        fraction-digits 2;
      }
      units "dBm";
      description
       "Mean launched power at the transmitter of the link";
    }

    leaf pmd {
      type decimal64 {
        fraction-digits 8;
        range "0..max";
      }
      units "ps/(km)^0.5";
      config false;
      description
       "Polarization Mode Dispersion";
    }

    leaf cd {
      type decimal64 {
        fraction-digits 5;
      }
      units "ps/nm/km";
      config false;
      description
       "Cromatic Dispersion";
    }

    leaf osnr {
      type decimal64 {
        fraction-digits 5;
      }
      units "dB";
      config false;
      description
       "Optical Signal-to-Noise Ratio (OSNR) estimated
         at the receiver";
    }

    leaf sigma {
      type decimal64 {
        fraction-digits 5;
      }
      units "dB";
      config false;
      description
       "sigma in the Gausian Noise Model";
    }
  }

  grouping optical-channel-data {
   description
     "optical impairment data per channel/wavelength";
   leaf bit-rate {
     type decimal64 {
       fraction-digits 8;
        range "0..max";
     }
     units "Gbit/s";
     config false;
     description
       "Gross bit rate";
   }

    leaf BER {
     type decimal64 {
       fraction-digits 18;
            range "0..max";
     }
     config false;
      description
       "BER (Bit Error Rate)";
   }

    leaf ch-input-power {
          type decimal64 {
           fraction-digits 2;
        }
        units "dBm";
        config false;
        description
     "Per channel average input power level
          estimated at the receiver of the link";
        }

   leaf ch-pmd {
     type decimal64 {
       fraction-digits 8;
       range "0..max";
     }
     units "ps/(km)^0.5";
     config false;
     description
       "per channel Polarization Mode Dispersion";
   }

   leaf ch-cd {
     type decimal64 {
            fraction-digits 5;
     }
     units "ps/nm/km";
     config false;
          description
       "per channel Cromatic Dispersion";
   }

   leaf ch-osnr {
     type decimal64 {
       fraction-digits 5;
     }
      units "dB";
     config false;
     description
       "per channel Optical Signal-to-Noise Ratio
            (OSNR) estimated at the receiver";
        }

    leaf q-factor {
     type decimal64 {
       fraction-digits 5;
     }
     units "dB";
     config false;
      description
       "q-factor estimated at the receiver";
   }
  }

  grouping standard_mode {
    description
      "ITU-T G.698.2 standard mode that guarantees interoperability.
       It must be an string with the following format:
       B-DScW-ytz(v) where all these attributes are conformant
       to the ITU-T recomendation";

    leaf standard_mode {
      type layer0-types:standard-mode;
      config false;
      description
        "G.698.2 standard mode";
    }
  }

  grouping organizational_mode {
    description
      "Transponder operational mode supported by organizations or
       vendor";

    leaf operational-mode {
      type layer0-types:operational-mode;
      config false;
      description
        "configured organization- or vendor-specific
         application identifiers (AI) supported by the transponder";
    }

    leaf organization-identifier {
      type layer0-types:vendor-identifier;
      config false;
      description
       "organization identifier that uses organizational
         mode";

    }
  }

    /*
   * Identities
   */
  identity type-element {
    description
      "Base identity for element type";
  }

  identity Fiber {
    base type-element;
    description
      "Fiber element";
  }

  identity Roadm {
    base type-element;
    description
      "Roadm element";
  }

  identity Edfa {
    base type-element;
    description
      "Edfa element";
  }

  identity Concentratedloss {
    base type-element;
    description
      "Concentratedloss element";
  }

  identity type-power-mode {
    description
      "power equalization mode used within the OMS and its elements";
  }

  identity power-spectral-density {
    base type-power-mode;
    description
      "all elements must use power spectral density (W/Hz)";
  }

  identity channel-power {
    base type-power-mode;
    description
      "all elements must use power (dBm)";
  }

  /*
   * Groupings
   */
  grouping amplifier-params {
    description "describes parameters for an amplifier";
    container amplifier{
     description "amplifier type, operatonal parameters are described";
      leaf type_variety {
        type string ;
        mandatory true ;
        description
          "String identifier of amplifier type referencing
          a specification in a separate equipment catalog";
      }
      container operational {
        description "amplifier operationnal parameters";
        leaf actual-gain {
          type decimal64 {
            fraction-digits 2;
          }
          units dB ;
        mandatory true ;
          description "..";
        }
        leaf tilt-target {
          type decimal64 {
            fraction-digits 2;
          }
          mandatory true ;
          description "..";
        }
        leaf out-voa {
          type decimal64 {
            fraction-digits 2;
          }
          units dB;
        mandatory true;
          description "..";
        }
        leaf in-voa {
          type decimal64 {
            fraction-digits 2;
          }
          units dB;
        mandatory true;
          description "..";
        }
        uses power-param;
      }
    }
  }

  grouping fiber-params {
    description "String identifier of fiber type referencing a specification in a
separate equipment catalog";
    container fiber {
     description "fiber characteristics";
      leaf type_variety {
        type string ;
      mandatory true ;
        description "fiber type";
      }
      leaf length {
        type decimal64 {
          fraction-digits 2;
        }
        units km;
      mandatory true ;
      description "length of fiber";
      }
      leaf loss_coef {
        type decimal64 {
          fraction-digits 2;
        }
        units dB/km;
      mandatory true ;
      description "loss coefficient of the fiber";
      }
      leaf total_loss {
        type decimal64 {
          fraction-digits 2;
        }
        units dB;
      mandatory true ;
        description
          "includes all losses: fiber loss and conn_in and conn_out losses";
      }
      leaf pmd{
        type decimal64 {
          fraction-digits 2;
        }
        units sqrt(ps);
      description "pmd of the fiber";
      }
      leaf conn_in{
        type decimal64 {
          fraction-digits 2;
        }
        units dB;
      description "connector-in";
      }
      leaf conn_out{
        type decimal64 {
          fraction-digits 2;
        }
        units dB;
      description "connector-out";
      }
    }
  }

  grouping roadm-params{
    description "roadm parameters description";
    container roadm{
     description "roadm parameters";
      leaf type_variety {
        type string ;
        mandatory true ;
        description "String identifier of roadm type referencing a specification in a
separate equipment catalog";
      }
      leaf loss {
        type decimal64 {
          fraction-digits 2;
        }
        units dB ;
        description "..";
      }
    }
  }

  grouping concentratedloss-params{
    description "concentrated loss";
    container concentratedloss{
     description "concentrated loss";
      leaf loss {
        type decimal64 {
          fraction-digits 2;
        }
        units dB ;
        description "..";
      }
    }
  }

  grouping power-param{
    description
      "optical power or PSD after the ROADM or after the out-voa";
    choice power-param {
      description
        "select the mode: channel power or power spectral density";
      case channel-power {
  /*      when "../../equalization-mode='channel-power'"; */
        leaf nominal-channel-power{
          type decimal64 {
              fraction-digits 1;
          }
          units dBm ;
          description
            " Reference channel power after the ROADM or after the out-voa. ";
        }
      }
      case power-spectral-density{
  /*      when "../../equalization-mode='power-spectral-density'"; */
        leaf nominal-power-spectral-density{
          type decimal64 {
              fraction-digits 16;
          }
          units W/Hz ;
          description
            " Reference power spectral density after the ROADM or after the out-voa.
              Typical value : 3.9 E-14, resolution 0.1nW/MHz";
        }
      }
    }
  }

  grouping oms-general-optical-params {
    description "OMS link optical parameters";
    leaf generalized-snr {
      type decimal64 {
        fraction-digits 5;
      }
      units "dB@0.1nm";
      description "generalized snr";
    }
    leaf equalization-mode{
      type identityref {
        base type-power-mode;
      }
      mandatory true;
      description "equalization mode";
    }
    uses power-param;
  }

  grouping network-media-channel-group {
    description "network media channel group";
    list network-media-channel-group {
     key "i";
      description
        "list of network media channel group's member";
      leaf i {
        type int16;
      description "index of network media channel group member";
      }

      list current-channels {
        key "flex-n";
        description
          "list of media channels in the OMS";

        uses layer0-types:flex-grid-channel;
     }

     list OTSiG-container {
        key "carrier-id";
       description
         "list of OTSi under OTSi-G";
      leaf carrier-id {
        type int16;
        description "carrier-id under OTSi-G";
      }
      leaf OTSi-carrier-frequency {
        type decimal64 {
          fraction-digits 3;
        }
        units GHz;
        config false;
        description
          "OTSi carrier frequency";
      }
      leaf OTSi-signal-width {
        type decimal64 {
          fraction-digits 3;
        }
        units GHz;
        config false;
        description
          "OTSi signal width";
      }
        leaf channel-delta-power {
          type decimal64 {
            fraction-digits 2;
          }
          units dB;
        config false;
          description
            "optional ; delta power to ref channel input-power applied to this
channel";
        }
      }
    }
  }

  grouping oms-element {
    description "OMS description";
    list OMS-elements {
        key "elt-index";
        description
          "defines the spans and the amplifier blocks of the amplified lines";
        leaf elt-index {
          type uint16;
          description
            "ordered list of Index of OMS element (whether it's a Fiber, an EDFA or a
Concentratedloss)";
        }
        leaf uid {
          type string;
          description
            "unique id of the element if it exists";
        }
        leaf type {
          type identityref {
             base type-element;
          }
        mandatory true;
        description "element type";
        }

        container element {
          description "element of the list of elements of the OMS";
          choice element {
          description "OMS element type";
            case amplifier {
     /*         when "../../type = 'Edfa'"; */
              uses amplifier-params ;
            }
            case fiber {
     /*        when "../../type = 'Fiber'"; */
              uses fiber-params ;
            }
            case concentratedloss {
     /*        when "../../type = 'Concentratedloss'"; */
              uses concentratedloss-params ;
            }
          }
        }
    }
  }

/* Data nodes */

  augment "/nw:networks/nw:network/nw:network-types"
    + "/tet:te-topology" {
    description "optical-impairment topology augmented";
    container optical-impairment-topology {
      presence "indicates an impairment-aware topology of optical networks";
      description
       "Container to identify impairment-aware topology type";
    }
  }

  augment "/nw:networks/nw:network/nt:link/tet:te"
    + "/tet:te-link-attributes"   {
    when "/nw:networks/nw:network/nw:network-types"
      +"/tet:te-topology/optical-imp-topo:optical-impairment-topology" {
      description
        "This augment is only valid for Optical Impairment.";
    }
    description "Optical Link augmentation for impairment data.";
    container OMS-attributes {
       config false;
       description "OMS attributes";
       uses oms-general-optical-params;
      uses network-media-channel-group;
       uses oms-element;
     }
  }

  augment "/nw:networks/nw:network/nw:node/tet:te"
    + "/tet:tunnel-termination-point" {
    when "/nw:networks/nw:network/nw:network-types"
      +"/tet:te-topology/optical-imp-topo:optical-impairment-topology" {
      description
        "This augment is only valid for Impairment with non-sliceable
         transponder model";
    }
    description
      "Tunnel termination point augmentation for non-sliceable
       transponder model.";
     list transponders-list {
         key "transponder-id";
       config false;
         description "list of transponders";
         leaf transponder-id {
         type uint32;
         description "transponder identifier";
         }

         choice mode {
             description "standard mode, organizational mode or explicit mode";

             case G.692.2 {
               uses standard_mode;
             }

             case organizational_mode {
               uses organizational_mode;
             }

             case explicit_mode {
               uses transponder-attributes;
             }
         }

         leaf power {
           type int32;
           units "dBm";
           config false;
           description "per channel power";
         }

         leaf power-min {
           type int32;
           units "dBm";
           config false;
           description "minimum power of the transponder";
         }

         leaf power-max {
           type int32;
           units "dBm";
           config false;
           description "maximum power of the transponder";
         }
    }
  }

  augment "/nw:networks/nw:network/nw:node/tet:te"
    + "/tet:tunnel-termination-point" {
    when "/nw:networks/nw:network/nw:network-types"
      +"/tet:te-topology/optical-imp-topo:optical-impairment-topology" {
      description
        "This augment is only valid for optical impairment with sliceable
        transponder model";
    }
    description
      "Tunnel termination point augmentation for sliceable transponder model.";
    uses sliceable-transponder-attributes;
  }
}
