module ietf-l3vpn {
  namespace "urn:ietf:params:xml:ns:yang:ietf-l3vpn";
  // replace with IANA namespace when assigned
  prefix "l3vpn";

  import ietf-routing {
    prefix "rt";
    //draft-ietf-netmod-routing-cfg-19
  }

  organization  "IETF BGP Enabled Services WG";
  contact       "draft-li-bess-l3vpn-yang@tools.ietf.org";
  description
    "This YANG module defines the generic configuration data
     for L3VPN service.

     Terms and Acronyms

     BGP (bgp): Border Gateway Protocol
     IPv4 (ipv4):Internet Protocol Version 4
     IPv6 (ipv6): Internet Protocol Version 6

    ";

  revision 2015-10-09 {
    description
      "Initial revision.";
      reference "RFC4271, RFC4364, RFC4365, RFC4760.";
  }

  /* typedefs */

  typedef bgp-rt-type {
    type enumeration {
      enum import {
        description "For import";
      }
      enum export {
        description "For export";
      }
      enum both {
        description "For both import and export";
      }
    }
    description "BGP route-target type. Import from BGP YANG.";
  }

  typedef apply-label-mode-def {
    type enumeration {
      enum "per-route" {
        value 0;
        description
          "By default, the VPN instance IPv4 address family
           assigns a unique label to each route to be sent
           to the peer PE.";
      }
      enum "per-instance" {
        value 1;
        description
          "The apply-label per-instance command enables the
           one-label-per-VPN-instance mode.";
      }
    }
    description "...";
  }

  typedef routing-instance-type-ref {
    type leafref {
      path "/rt:routing/rt:routing-instance/rt:type";
    }
    description
      "This type is used for leafs that reference a routing
       instance configuration.";
  }

  grouping bgp-parameters-grp {
    description
      "BGP parameters grouping.";
    container bgp-parameters {
      description
        "Parameters for BGP.";
      container common {
        description
          "Common BGP parameters.";
        leaf route-distinguisher {
          type string;
          description "BGP RD.";
        }
        list vpn-targets {
          key rt-value;
          description
            "Route Targets.";
          leaf rt-value {
            type string;
            description
              "Route-Target value.";
          }
          leaf rt-type {
            type bgp-rt-type;
            mandatory true;
            description
              "Type of RT.";
          }
        }
      }
    }
  }

  grouping vpn-af-config {
    description
      "A set of configuration parameters that is applicable to both
       IPv4 and IPv6 address family for a VPN instance .";

    leaf apply-label-mode {
      type apply-label-mode-def;
      default "per-route";
      description ".";
    }

    leaf import-route-policy {
      type string {
        length "1..40";
      }
      description
        "The import route-policy command associates a VPN instance
         enabled with the IPv4 or IPv6 address family with an
         import routing policy.
         Only one import routing policy can be associated with a
         VPN instance enabled with the IPv4 or IPv6 address family.
         If the import route-policy command is run more than once,
         the latest configuration overrides the previous ones.";
    }

    leaf export-route-policy {
      type string {
        length "1..40";
      }
      description
        "The export route-policy command associates a VPN instance
         enabled with the IPv4 or IPv6 address family with an
         export routing policy.
         Only one export routing policy can be associated with a
         VPN instance enabled with the IPv4 or IPv6 address family.
         If the export route-policy command is run more than once,
         the latest configuration overrides the previous ones.";
    }

    leaf tunnel-policy {
       type string;
       description
         "Tunnel policy name.";
    }

    container prefix-limit {
      description
        "The prefix limit command sets a limit on the maximum
         number of prefixes supported in the existing VPN
         instance, preventing the PE from importing excessive
         VPN route prefixes.";

      leaf prefix-limit-number {
        type uint32 {
          range "1..4294967295";
        }
        description
          "Specifies the maximum number of prefixes supported in the
           VPN instance IPv4 or IPv6 address family.";
      }

      choice prefix-limit-action {
        description ".";
        case enable-alert-percent {
          leaf alert-percent-value {
            type uint8 {
              range "1..100";
            }
            description
              "Specifies the proportion of the alarm threshold to the
               maximum number of prefixes.";
          }
          leaf route-unchanged {
            type boolean;
            default "false";
            description
              "Indicates that the routing table remains unchanged.
               By default, route-unchanged is not configured. When
               the number of prefixes in the routing table is
               greater than the value of the parameter number,
               routes are processed as follows:
               (1)If route-unchanged is configured, routes in the
                  routing table remain unchanged.
               (2)If route-unchanged is not configured, all routes
                  in the routing table are deleted and then
                  re-added.";
          }
        }
        case enable-simple-alert {
          leaf simple-alert {
            type boolean;
            default "false";
            description
              "Indicates that when the number of VPN route prefixes
               exceeds number, prefixes can still join the VPN
               routing table and alarms are displayed.";
          }
        }
      }
    }

    container routing-table-limit {
      description
        "The routing-table limit command sets a limit on the maximum
         number of routes that the IPv4 or IPv6 address family of a
         VPN instance can support.
         By default, there is no limit on the maximum number of
         routes that the IPv4 or IPv6 address family of a VPN
         instance can support, but the total number of private
         network and public network routes on a device cannot
         exceed the allowed maximum number of unicast routes.";

      leaf routing-table-limit-number {
        type uint32 {
          range "1..4294967295";
        }
        description
          "Specifies the maximum number of routes supported by a
           VPN instance. ";
      }

      choice routing-table-limit-action {
        description ".";
        case enable-alert-percent {
          leaf alert-percent-value {
            type uint8 {
              range "1..100";
            }
            description
              "Specifies the percentage of the maximum number of
               routes. When the maximum number of routes that join
               the VPN instance is up to the value
               (number*alert-percent)/100, the system prompts
               alarms. The VPN routes can be still added to the
               routing table, but after the number of routes
               reaches number, the subsequent routes are
               dropped.";
          }
        }
        case enable-simple-alert {
          leaf simple-alert {
            type boolean;
            description
              "Indicates that when VPN routes exceed number, routes
               can still be added into the routing table, but the
               system prompts alarms.
               However, after the total number of VPN routes and
               network public routes reaches the unicast route limit
               specified in the License, the subsequent VPN routes
               are dropped.";
          }
        }
      }
    }

    container import-global-rib {
      description
        "Route Leaking from a Global Routing Table into a VRF.";

      leaf protocol {
        type enumeration {
          enum ALL {
            value "0";
            description "ALL:";
          }
          enum Direct {
            value "1";
            description "Direct:";
          }
          enum OSPF {
            value "2";
            description "OSPF:";
          }
          enum ISIS {
            value "3";
            description "ISIS:";
          }
          enum Static {
            value "4";
            description "Static:";
          }
          enum RIP {
            value "5";
            description "RIP:";
          }
          enum BGP {
            value "6";
            description "BGP:";
          }
          enum OSPFV3 {
            value "7";
            description "OSPFV3:";
          }
          enum RIPNG {
            value "8";
            description "RIPNG:";
          }
          enum INVALID {
            value "9";
            description "INVALID:";
          }
        }
        description
          "Specifies the protocol from which routes are imported.
           At present, In the IPv4 unicast address family view,
           the protocol can be IS-IS,static, direct and BGP.";
      }

      leaf processId {
        type uint32 {
          range "0..4294967295";
        }
        default "0";
        description
          "Specifies the process ID if the protocol from routes
           are imported is IS-IS.";
      }

      leaf bgp-valid-route {
        type boolean;
        description ".";
      }

      leaf route-policy-name {
        type string;
        description
          "Policy Id for import routes";
      }

    }
  }

  augment "/rt:routing/rt:routing-instance" {
    description ".";
    container l3vpn {
      when "routing-instance-type-ref = 'vrf-routing-instance'" {
        description ".";
      }
      description ".";
      container ipv4-family {
        description
          "The IPv4 address family is enabled for the VPN
           instance.";

        uses bgp-parameters-grp;
        uses vpn-af-config;
      }

      container ipv6-family {
        description
          "The IPv6 address family is enabled for the VPN
           instance.";

        uses bgp-parameters-grp;
        uses vpn-af-config;
      }
    } //End of case type

  } //End of augment "/rt:routing/rt:routing-instance"

}
