module ietf-snmp-security {
  yang-version 1.1;
  namespace "urn:ietf:params:xml:ns:yang:ietf-snmp-security";
  prefix snmpsec;

  import ietf-snmp {
    prefix snmp;
        reference
      "RFC 7407.";
  }

  organization
    "IETF SACM (Security Automation and Continuous Monitoring) Working Group";

  contact
    "WG Web: http://tools.ietf.org/wg/sacm/
    WG List: sacm@ietf.org

    Editor: Qiushi Lin
            linqiushi@huawei.com;
    Editor: Liang Xia
            frank.xialiang@huawei.com
        Editor: Henk Birkholz
            henk.birkholz@sit.fraunhofer.de";

  description
    "This YANG module defines ietf-snmp-security YANG module.";

  revision 2018-10-16 {
    description "Initial version.";
        reference
      "draft-lin-sacm-nid-mp-security-baseline-04: The Data Model of Network Infrastructure Device Management Plane Security Baseline";
  }

  feature tsm {
    description
      "Whether the network device supports Transport Security Model for SNMP.";
  }

  /*
  * typedef
  */
  typedef snmp-transport-type {
    type enumeration {
      enum "udp" {
        description
          "SNMP over UDP.";
      }
      enum "ssh" {
        description
          "SNMP over SSH.";
      }
      enum "tls" {
        description
           "SNMP over TLS.";
      }
      enum "dtls" {
        description
          "SNMP over DTLS.";
      }
    }
    description
      "The transport channels on which the SNMP engine listens.";
   }

  typedef snmp-version-type {
    type enumeration {
      enum "v1" {
        description
          "SNMPv1";
      }
      enum "v2c" {
        description
          "SNMPv2c";
      }
      enum "v3" {
        description
           "SNMPv3";
      }
    }
    description
      "The version of SNMP protocol";
  }

  typedef auth-pro-type {
    type enumeration {
      enum "none" {
        description
          "Do not enable the authentication of messages sent on behalf of the user.";
      }
      enum "md5" {
        description
          "HMAC-MD5-96 authentication protocol";
      }
      enum "sha" {
        description
          "HMAC-SHA-96 authentication protocol";
      }
    }
    description
      "An indication of whether messages sent on behalf of this user can be authenticated, and if so, the type of authentication protocol which is used: MD5, SHA.";
    reference
      "RFC 3414";
  }

  typedef priv-pro-type {
    type enumeration {
      enum "none" {
        description
          "Do not enable the encryption of messages sent on behalf of the user.";
      }
      enum "des" {
        description
          "DES is used to encrypt messages sent on behalf of the user.";
      }
      enum "aes" {
        description
          "AES is used to encrypt messages sent on behalf of the user.";
      }
    }
    description
      "An indication of whether messages sent on behalf of this user can be protected from disclosure, and if so, the type of privacy protocol which is used: EDS, AES.";
    reference
      "RFC 3414 & RFC 3826";
  }

  /*
  * grouping
  */
  grouping user-auth-priv {
    list user {
        key "name";
        leaf name {
          type snmp:identifier;
          description
            "The identifier that represents a user.";
        }
                leaf auth-protocol {
          type auth-pro-type;
          description
            "The type of authentication protocol: none, md5, sha.";
        }
                leaf priv-protocol {
          type priv-pro-type;
          description
            "The type of encryption protocol: none, des, aes.";
        }
        description
          "A list of users and their corresponding authProtocol, privProtocol.";
      }
      description
        "A grouping that represents a list of users and their corresponding authProtocol, privProtocol.";
      reference
        "RFC 3414";
  }

  leaf snmp-enable {
    type boolean;
    description
      "whether SNMP is used.";
  }

  /*
  * containers
  */
  container engine {
    leaf enabled {
      type boolean;
      description
        "The status of the SNMP engine: enabled, disabled.";
    }
    list listen {
      key "name";
      leaf name {
        type snmp:identifier;
        description
          "The name of a transport channel on which the SNMP engine listens.";
      }
      leaf transport {
        type snmp-transport-type;
        description
          "The transport protocol that SNMP uses.";
      }
      description
        "A list of transport channels on which the SNMP engine listens.";
    }
    leaf version {
      type snmp-version-type;
      description
        "SNMP version used by the SNMP engine.";
    }
    leaf enable-authen-traps {
      type boolean;
      description
        "Whether the SNMP entity is permitted to generate authenticationFailure traps.";
      reference
        "RFC 3418: Management Information Base (MIB) for the Simple Network Management Protocol (SNMP) SNMPv2-MIB.snmpEnableAuthenTraps";
    }
    description
      "The security configurations for SNMP engine.";
  }

  list target {
    key name;
    leaf name {
      type snmp:identifier;
      description
        "The name identifies the target.";
    }
    leaf transport {
      type snmp-transport-type;
      description
        "The transport protocol used.";
    }
    leaf target-parmas {
      type snmp:identifier;
      description
        "Parameters for the target.";
    }
    description
      "The list of targets.";
    reference
      "RFC 3413 & RFC 7407";
  }

  list target-params {
    key name;
    leaf name {
      type snmp:identifier;
      description
        "The name identifies the target params.";
    }
    choice params {
      case usm {
        uses snmp:usm-target-params;
        description
          "Reuse the grouping defined in ietf-snmp-usm";
      }
      case tsm {
        if-feature snmp:tsm;
        uses snmp:tsm-target-params;
        description
          "Reuse the grouping defined in ietf-snmp-tsm";
      }
      description
        "The parameters specific to each security model.";
    }
    description
      "List of target parameters.";
  }

  container vacm {
    leaf vacm-enable {
      type boolean;
      config false;
      description
        "Whether VACM based security configurations are used.";
    }
    list group {
      key name;
      leaf name {
        type snmp:group-name;
        description
          "The name of this VACM group.";
      }
      list member {
        key "security-name";
        leaf security-name {
          type snmp:security-name;
          description
            "The securityName of a group member.";
        }
        leaf-list security-model {
          type snmp:security-model;
          min-elements 1;
          description
            "The security models under which this security-name is a member of this group.";
        }
        description
          "A member of this VACM group.";
      }
      list access {
        key "context security-model security-level";
        leaf context {
          type snmp:context-name;
          description
            "The context under which the access rights apply.";
        }
        leaf context-match {
          type enumeration {
            enum exact {
              value 1;
              description
                "The context match type: exact.";
            }
            enum prefix {
              value 2;
              description
                "The context match type: prefix";
            }
          }
          description
            "The match type of the context.";
        }
        leaf security-model {
          type snmp:security-model-or-any;
          description
            "The security model under which the access rights apply.";
        }
        leaf security-level {
          type snmp:security-level;
          description
            "The minimum security level under which the access rights apply.";
        }
        leaf read-view {
          type snmp:view-name;
          description
            "The name of the MIB view of the SNMP context authorizing read access. If this leaf does not exist in a configuration, it maps to a zero-length vacmAccessReadViewName.";
        }
        leaf wirte-view {
          type snmp:view-name;
          description
            "The name of the MIB view of the SNMP context authorizing write access. If this leaf does not exist in a configuration, it maps to a zero-length vacmAccessWriteViewName.";
        }
        leaf notify-view {
          type snmp:view-name;
          description
            "The name of the MIB view of the SNMP context authorizing notify access. If this leaf does not exist in a configuration, it maps to a zero-length vacmAccessNotifyViewName.";
        }
        description
          "Definition of access right for groups.";
      }
      description
        "VACM groups";
      reference
        "RFC 3415: View-based Access Control Model (VACM) for the Simple Network Management Protocol (SNMP)";
    }
    list view {
      key name;
      leaf name {
        type snmp:view-name;
        description
          "The name of this MIB view.";
      }
      leaf-list include {
        type snmp:wildcard-object-identifier;
        description
          "A family of subtrees included in this MIB view.";
      }
      leaf-list exclude {
        type snmp:wildcard-object-identifier;
        description
          "A family of subtrees excluded in this MIB view.";
      }
      description
        "Definition of MIB views.";
    }
    description
      "The security configurations for View-based Access Control Model (VACM).";
  }

  container usm {
    leaf usm-enable {
      type boolean;
      config false;
      description
        "Whether USM based security configurations are used.";
    }
    container local {
      uses user-auth-priv;
      description
        "A list of local users and their corresponding authentication and privacy protocols.";
    }
    container remote {
      uses user-auth-priv;
      description
        "A list of remote users and their corresponding authentication and privacy protocols.";
    }
    description
      "Configuration of the User-based Security Model.";
  }

  container tsm {
    if-feature tsm;
    leaf tsm-enable {
      type boolean;
      config false;
      description
        "Whether TSM based security configurations are used.";
    }
    description
      "Configuration of Transport Security Model.";
  }
}
