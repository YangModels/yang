module ietf-declarative-policy { 
  namespace "urn:ietf:params:xml:ns:yang:ietf-declarative-policy"; 
  // replace with IANA namespace when assigned 
  prefix policy; 

  import ietf-yang-types { 
    prefix yang; 
  } 
  organization "IETF"; 
  contact 
    "Editor: Yiyong Zha"; 

  description 
    "This YANG module defines a component that describing 
     the declarative policy data model to describe the states and  
     constraints. 

     Terms and Acronyms 
     "; 
    revision 2015-10-10 { 
    reference "ietf-declarative-policy@2015-10-10"; 
  } 
  revision 2015-09-10 { 
    reference "ietf-declarative-policy@2015-9-10"; 
  } 
  container policy{ 
    description 
      "This defines a policy data model with declarative policy  
      constraint"; 
    leaf policy-name {   
      type string; 
      description  
        "The name of the policy"; 
    } 
    leaf policy-priority { 
      type uint8; 
      description 
        "The priority of the defined policy"; 
    } 
    container policy-validity-period { 
      description 
        "The valid time of the policy. E.g., the policy  
        will be valid 9am-9am daily"; 
       leaf start { 
        type yang:date-and-time; 
        description 
          "When the policy will be start to work."; 
      }  
      leaf end { 
        type yang:date-and-time; 
        description 
          "When the policy will be terminated."; 
      } 
      leaf duration { 
        type uint32; 
        description 
          "How long the policy will be valid."; 
      } 
      leaf periodicity { 
        type enumeration { 
          enum daily {   
            value 0; 
            description 
              "The policy will be repeated daily."; 
          } 
          enum monthly { 
            value 1; 
            description 
              "The policy will be repeated monthly.";                                                                         
          } 
        } 
        description 
          "How the policy will be repeated."; 
      } 
    } 
    container policy-target { 
      description  
        "SUPAPolicyTarget is an abstract class that  
        defines a set of managed objects that may be  
        affected by the actions of a SUPAPolicyStatement."; 
      leaf profileType { 
        type string; 
        description 
          "Which profile the policy will be worked on."; 
      } 
      leaf domain-name { 
        type string; 
        description 
          "Which domain the policy will be worked on."; 
      } 
      leaf admin-subnet { 
        type string; 
        description 
          "Which subnet the policy will be worked on."; 
      } 
      leaf business-type-name { 
        type string; 
        description 
          "Which business the policy will be worked on."; 
      }   
      container instance  { 
        description 
          "Which instance the policy will be worked on? E.g., 
          a VPN, a flow or a link"; 
        }   
    } 
    container policy-atomic { 
      description 
        "Define an atomic declarative policy."; 
      container declarative-policy { 
        description  
          "supa declarative policy only describes the desired  
          state and constraints of the policy and what is  
          wanted without  
          telling how to do."; 
        leaf policy-rule-deploy-status { 
          type enumeration { 
            enum undefined{ 
              value 0; 
              description "undefined";        
            } 
            enum enabled{ 
              value 1; 
              description "deployed and enabled";        
            } 
            enum in-test{ 
              value 2; 
              description "deployed and in test";        
            } 
            enum not-enabled{ 
              value 3; 
              description "deployed but not enabled";        
            } 
            enum ready{ 
              value 4; 
              description "ready to be deployed";        
            } 
            enum not-deployed{ 
              value 5; 
              description "not deployed";        
            } 
          } 
          description 
            "Describes the deploy status of the policy."; 
        } 
        leaf policy-rule-exec-status { 
          type enumeration { 
            enum undefined{ 
              value 0; 
              description "undefined";        
            } 
            enum OPmode-executed-succeeded{ 
              value 1; 
              description  
                "executed and SUCEEDED (operational mode)";        
            } 
            enum OPmode-executed-failed{ 
              value 2; 
              description  
                "executed and FAILED (operational mode)";        
            } 
            enum OPmode-executing{ 
              value 3; 
              description  
                "currently executing (operational mode)";        
            } 
            enum TEmode-executed-succeeded{ 
              value 4; 
              description  
                "executed and SUCEEDED (test mode)";        
            } 
            enum TEmode-executed-failed{ 
              value 5; 
              description  
                "executed and FAILED (test mode)";        
            } 
            enum TEmode-executing{ 
              value 6; 
              description  
                "currently executing (test mode)";        
            } 
          } 
          description 
            "Describes the execution status of the policy."; 
        } 

        container declarative-policy-rule { 
          description 
            "The declarative policy rule is defined as  
            constraints on states and actions."; 
          grouping FOL-statement { 
            description 
              "SUPA declarative policy is based on constraint.  
              The constraint is defined as first order logic 
              statement which consists of quantified variables 
              and predicate expression."; 
            container quantified-variable {  
              description 
                "The quantified-variable defines existence  
                of the element that is being described. It is 
                the major difference of FOL from propositional 
                logic."; 
              leaf quantifier { 
                type enumeration { 
                  enum none { 
                    value 0; 
                    description 
                      "None: no one in the set meets  
                      certain requirement."; 
                  } 
                  enum all{ 
                    value 1; 
                    description 
                      "All: all elements in the set meets  
                      certain requirement."; 
                  } 
                  enum some{ 
                    value 2; 
                    description 
                      "At least one: there is at least one  
                      element in the set meets certain  
                      requirement."; 
                  } 
                  enum lone{ 
                    value 3; 
                    description 
                      "Also called At most one: there is at  
                      most one element in the set meets  
                      certain requirement."; 
                  } 
                  enum singleton{ 
                    value 4; 
                    description 
                      "Singleton: there is only one element  
                      in the set meets certain requirement."; 
                  } 
                } 
                description 
                  "Quantifier defines the quantity of  
                  specimens in the domain of discourse that  
                  satisfy an predicate expression."; 
              } 
              leaf element { 
                type string; 
                description 
                  "The objects of constraints, which is the  
                  elements of the predicate"; 
              } 
              leaf set { 
                type string; 
                description 
                  "The set of which the element belongs to. It 
                  is usually pre-defined as policy target or  
                  certain problem domain such as a subnet. "; 
              } 
            } 
            container predicate { 
              description 
                "Predicate expression is no constraint that  
                holds for all the predefined quantified  
                variables. "; 
              leaf object { 
                type string; 
                description 
                  "The object of constraints, which is the  
                  subject of the predicate. It can be but  
                  not must be the same of element in quantified  
                  variables."; 
              } 
              leaf logic-operator { 
                type enumeration{ 
                  enum unknown { 
                    value 0; 
                    description "Unknown"; 
                  } 
                  enum match { 
                    value 1; 
                    description "Match"; 
                  } 
                  enum greater-than { 
                    value 2; 
                    description "Greater than"; 
                  } 
                  enum greater-than-or-equal-to { 
                    value 3; 
                    description "Greater than or equal to"; 
                  } 
                  enum less-than { 
                    value 4; 
                    description "Less than"; 
                  } 
                  enum less-than-or-equal-to { 
                    value 5; 
                    description "Less than or equal to"; 
                  } 
                  enum equal-to { 
                    value 6; 
                    description "Equal to"; 
                  } 
                  enum not-equal-to { 
                    value 7; 
                    description "Not equal to"; 
                  } 
                  enum in { 
                    value 8; 
                    description "IN"; 
                  } 
                  enum not-in { 
                    value 9; 
                    description "NOT IN"; 
                  } 
                } 
                description 
                  "A predicate is commonly understood to be a  
                  Boolean-valued expression."; 
              } 
              leaf value { 
                type string; 
                  description  
                    "The value in the predicate expression to  
                    describe the relationship of the objects."; 
              } 
            } 
          }           
          container desired-state { 
            description 
              "Describes the final state based on user's  
              goal. Just defines one of multiple states  
              without telling how"; 
            container constraint-on-state { 
              uses FOL-statement; 
              description 
                "Use first order logic to describe the  
                constraint. FOL statement includes  
                quantifier and predicate to describe the  
                state."; 
            } 
          leaf constraint-priority { 
              type uint8; 
              description 
                "0-7 denotes the priority of this state  
                constraint"; 
            } 
          } 
        } 
      } 
    }   
  } 
}
