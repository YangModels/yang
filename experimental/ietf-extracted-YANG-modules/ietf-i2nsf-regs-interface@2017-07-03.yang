module ietf-i2nsf-regs-interface {
    namespace
     "urn:ietf:params:xml:ns:yang:ietf-i2nsf-regs-interface";
    prefix
      regs-interface;
    import ietf-inet-types{
      prefix inet;
    }

    organization
      "IETF I2NSF (Interface to Network Security Functions)
      Working Group";

    contact
      "WG Web: <http://tools.ietf.org/wg/i2nsf>
      WG List: <mailto:i2nsf@ietf.org>

      WG Chair: Adrian Farrel
      <mailto:Adrain@olddog.co.uk>

      WG Chair: Linda Dunbar
      <mailto:Linda.duhbar@huawei.com>

      Editor: Sangwon Hyun
      <mailto:swhyun77@skku.edu>

      Editor: Taekyun Roh
      <mailto:tkroh@imtl.skku.ac.kr>

      Editor: Sarang Wi
      <mailto:sarang@imtl.skku.ac.kr>

      Editor: Jaehoon Paul Jeong
      <mailto:pauljeong@skku.edu>

      Editor: Jung-Soo Park
      <mailto:pjs@etri.re.kr>";

    description
      "It defines a YANG data module for Registration Interface.";

    revision "2017-07-03"{
      description "Initial revision";
      reference
        "draft-hares-i2nsf-capability-data-model-01.txt
        draft-hyun-i2nsf-registration-interface-im-01.txt";
    }

  grouping i2nsf-nsf-performance-caps {
      description
        "NSF performance capailities";

      container vcpus{
        description
          "vcpus info";
          container cpu-topology{
            description
              "cpu-topology";
              leaf cores{
                type uint16;
                description
                    "cpu-cores";
              }

              leaf cpu-socket{
                type uint16;
                description
                  "cpu-socket";
            }

              leaf cpu-threads{
                type uint16;
                description
                    "cpu-threads";
              }
          }

          choice cpu-limitation{
            description
              "cpu-limitation";
                leaf cpu-limit{
                  type uint16;
                  description
                    "cpu-limit";
                }
          }

          choice cpu-reservation{
            description
              "cpu-reservation";
                leaf cpu-reserve{
                  type uint16;
                  description
                  "cpu-reserve";
                }
            }

          leaf cpu-num{
            type uint16;
            description
              "cpu-num";
          }
      }

      container disk{
        description
          "disk info";
          leaf disk-size{
            type uint16;
            description
              "disk-size";
        }

      choice disk-limitation{
        description
          "disk-limitation";
          leaf disk-limit{
          type uint16;
          description
          "disk-limit";
          }
      }

      choice disk-reservation{
        description
          "disk-reservation";
          leaf disk-reserve{
            type uint16;
            description
            "disk-reserve";
            }
        }
      }

      container memory{
        description
          "memory info";
          leaf memory-size{
            type uint16;
            description
            "memory-size";
        }
        choice memory-limitation{
          description
          "memory-limitation";
          leaf memory-limit{
            type uint16;
            description
            "memory-limit";
          }
        }
        choice memory-reservation{
          description
          "memory-reservation";
          leaf memory-reserve{
            type uint16;
            description
            "memory-reserve";
          }
        }
      }
      container bandwidth{
        description
        "bandwidth info";
          container inbound{
          description
          "inbound";
          leaf inbound-average{
            type uint16;
            description
            "inbound-average";
          }
          leaf inbound-peak{
            type uint16;
            description
            "inbound-peak";
          }
          }
          container outbound{
          description
          "outbound";
          leaf outbound-average{
            type uint16;
            description
            "outbound-average";
          }
          leaf outbound-peak{
            type uint16;
            description
            "outbound-peak";
          }
          }
      container i2nsf-nsf-profile {
          description
          "Detail information of an NSF";
          container performance-capability {
          description
            "performance-capability";
        }
      }

        container i2nsf-capability {
          description
            "It refers draft-hares-i2nsf-capability-data-model-01";
        }
    }

      grouping i2nsf-nsf-access-info {
        description
        "NSF access information";
          leaf nsf-address {
          type inet:ipv4-address;
          mandatory true;
          description
          "nsf-address";
        }
        leaf nsf-port-address {
          type inet:port-number;
          description
          "nsf-port-address";
        }
    }

      container i2nsf-regs-req {
       description
       "The capability information of newly created NSF to notify its
       capability to Security Controller";
       container nsf-profile {
          description
          "i2nsf-nsf-profile";
        }
        container nsf-access-info {
          description
          "nsf-access-info";
          uses i2nsf-nsf-access-info;
        }
      }

      container i2nsf-life-cycle-mgnt-req {
        description
        "Rquired information for req-creation-type and
        req-elimination-type";
        leaf req-level {
          type uint16;
          description
          "req-level";
        }
        leaf req-id {
          type uint64;
          mandatory true;
          description
          "req-id";
        }
        choice req-type {
          description
          "req-type";
          case req-creation-type {
          description
          "req-creation-type";
          }
          case req-elimination-type{
            description
            "req-elimination-type";
            container nsf-access-info {
            description
            "nsf-access-info";
            uses i2nsf-nsf-access-info;
            }
          }
        }
        container nsf-profile {
          description
          "i2nsf-nsf-profile";
        }
      }
    }
}
