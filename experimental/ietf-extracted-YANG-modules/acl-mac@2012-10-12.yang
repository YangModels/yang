module acl-mac {
    namespace "urn:cisco:params:xml:ns:yang:acl-mac";
    // replace with IANA namespace when assigned
    prefix acl-mac;

    import acl { prefix acl;  }

    import common-types {
        prefix "c-types";
    }

    import ietf-inet-types {
        prefix "inet";
    }

    import ietf-yang-types {
        prefix "yang";
    }

    organization
       "IETF NETMOD (NETCONF Data Modeling Language) Working Group";

    contact
         "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com
        Editor: Alexander Clemm
        alex@cisco.com

        Editor: Andy Bierman
        andy@yumaworks.com";

     description
        "This YANG module augments the 'acl' module with
        configuration and operational data for MAC access control list

        An ACL is an ordered set of rules and actions used to
        filter traffic.
        Each set of rules and actions is represented as an Access
        Control Entries (ACE). Each ACE is evaluated sequentially.
        When the rule matches then action for that rule is applied
        to the packet.

        MAC ACLs - MAC ACLs are used to filter traffic using the
            information in the Layer 2 header of each packet.
            MAC ACLs are by default only applied to non-IP
            traffic; however, Layer 2 interfaces can be configured to
            apply MAC ACLs to all traffic.

        Terms and Acronyms
         ACE (ace): Access Control Entry

         ACL (acl): Access Control List

         AFI (afi): Authority and Format Identifier (Address Field
             Identifier)

         CoS (cos): Class of Service

         MAC: Media Access Control

         TTL (ttl): Time to Live

         VLAN (vlan): Virtual Local Area Network

         VRF(vrf) : Virtual Routing and Forwarding
       ";
    reference
        "Access List Commands on Cisco IOS XR Software,
        Cisco Nexus 7000 Series NX-OS Security Configuration Guide,
        Catalyst 6500 Release 12.2SX Software Configuration Guide";

    revision 2012-10-12 {
        description "Initial revision. ";
    }

    /* Features */

    feature ethertype-mask {
        description
            "The ability to fiter packets based on ether-type mask
            in hex 0x0-0xFFFF.";
    }

    /* Identities */

    identity mac-acl {
        base acl:acl-type;
        description "layer 2 ACL type";
    }

    /* Groupings */

    grouping MAC-SOURCE-NETWORK {
        description "MAC address and mask pair for source.";

        grouping MAC-SOURCE-HOST {
            description
              "Choice within a case not allowed so need
               this grouping.";
            choice src-address-or-name {
                mandatory true;
                leaf source-host-address {
                    type inet:ip-address;
                    description
                       "Use the host address combination as an
                        abbreviation for an address and wildcard
                        of address 0.0.0.0";
                }
                leaf source-host-name {
                   if-feature acl:host-by-name;
                   type inet:domain-name;
                }
            }
        }

        choice source-network {
            mandatory true;
            case source-mac {
                description
                  "Used with address and mask couple to
                   express network.";
                leaf source-address {
                    type yang:mac-address;
                    mandatory true;
                    description "A source MAC address.";
                }
                leaf source-address-mask {
                    type yang:mac-address;
                    mandatory true;
                    description "A source MAC address mask.";
                }
            }
            leaf source-any {
                type empty;
                description "To express Any network or address";
            }
            case source-host {
                description
                  "Use the host address combination as an
                   abbreviation for an address and wildcard
                   of address 0.0.0.0";
                uses MAC-SOURCE-HOST;
            }
        }
    }

    grouping MAC-DESTINATION-NETWORK {
        description
          "MAC address and mask pair for destination.";

        grouping MAC-DESTINATION-HOST {
            description
              "Choice within a case not allowed so need
               this grouping.";
            choice dest-address-or-name {
                mandatory true;
                leaf dest-host-address {
                    type inet:ip-address;
                    description
                       "Use the host address combination as an
                        abbreviation for an address and wildcard
                        of address 0.0.0.0";
                }
                leaf dest-host-name {
                   if-feature acl:host-by-name;
                   type inet:domain-name;
                }
            }
        }
        choice dest-network {
            mandatory true;
            case dest-mac {
                description
                  "Used with address and mask couple to
                   express network.";
                leaf dest-address {
                    type yang:mac-address;
                    mandatory true;
                    description "A source MAC address.";
                }
                leaf dest-address-mask {
                    type yang:mac-address;
                    mandatory true;
                    description "A source MAC address mask.";
                }
            }
            leaf dest-any {
                type empty;
                description "To express Any network or address";
            }
            case dest-host {
                description
                  "Use the host address combination as an
                   abbreviation for an address and wildcard
                   of address 0.0.0.0";
                uses MAC-DESTINATION-HOST;
            }
        }
    }

    /* Layer 2 ACL */

    augment "/acl:acls/acl:acl" {
        when "acl:acl-type = 'mac-acl'";
        description
            "Layer 2 Access Control Entry (ACE). The mac-aces
            container contains a list of mac-ace. Each mac-ace is
            comprised of a name, an optional remark
            and a rule.
            A rule is referred to as 'packet-filter', although it
            contains both a filter and an action.
            The packet-filter requires a mandatory action (permit/deny)
            and one or more options such as source-address with mask,
            ethertype, vlan etc.";
        container mac-aces {
            list mac-ace {
              key name;
              ordered-by user;

              leaf name {
                type acl:acl-name-string;
                description "Unique ACE identifier";
              }

              choice remark-or-mac-ace {
                leaf remark {
                    type acl:acl-remark;
                    // mandatory true;
                }
                case mac-ace {
                  container filters {
                    uses MAC-SOURCE-NETWORK;
                    uses MAC-DESTINATION-NETWORK;

                    leaf ethertype {
                      type c-types:ether-type;
                      description "ether-type (also known as
                         protocol) in hex 0x0-0xffff";
                    }

                    leaf ethertype-mask {
                      if-feature ethertype-mask;
                      when "boolean(../ethertype)";
                      type c-types:ether-type;
                      default "0x0000";
                      description
                        "Ether-type mask in hex 0x0-0xFFFF.
                         0x0 is exactly match of the Ethertype..";
                    }

                    leaf cos {
                      type c-types:cos;
                       description "CoS value <0-7>";
                    }

                    leaf time-range {
                      type acl:time-range-ref;
                      description
                        "Enable packet capture on this
                         filter for a specify  time range
                         by name.";
                      }

                      leaf vlan {
                         type c-types:vlan-identifier;
                         description "VLAN number";
                      }

                      uses acl:FILTER-COMMON;

                }  // container filters

                uses acl:ACE-COMMON;

              } // case mac-ace
            } // choice remark-or-ace
          }  // list mac-ace
        }  // container mac-aces
    }  // augment

}
