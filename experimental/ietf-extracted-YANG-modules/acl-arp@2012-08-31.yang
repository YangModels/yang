module acl-arp {
    namespace "urn:cisco:params:xml:ns:yang:acl-arp";
    // replace with IANA namespace when assigned
    prefix acl-arp;
    import acl {
        prefix acl;
    }

    organization
       "IETF NETMOD (NETCONF Data Modeling Language) Working Group";

    contact
    "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com

        Editor: Alexander Clemm
        alex@cisco.com";

    description
        "This YANG module augments the 'acl' module with
        configuration and operational data for ARP access control list

        An ACL is an ordered set of rules and actions used to filter
        traffic.
        Each set of rules and actions is represented as an Access
        Control Entries (ACE). Each ACE is evaluated sequentially.
        When the rule matches then action for that rule is applied
        to the packet.

        ARP ACLs - The device applies ARP ACLs to IP traffic.

        Terms and Acronyms
         ACE (ace): Access Control Entry

         ACL (acl): Access Control List

         ARP (arp): Address Resolution Protocol

         IP (ip): Internet Protocol

         MAC: Media Access Control

         VLAN (vlan): Virtual Local Area Network
       ";

    revision 2012-08-31 {
        description "Initial revision. ";
    }
    grouping ARP-ACE-GROUP {
        description "ARP Access Control Entry (ACE).";
        container arp-aces {
            list arp-ace {
                key "sequence-num";
                leaf sequence-num {
                    type acl:Sequence-Number;
                    mandatory true;
                    description
                        "This number determines the order in which the
                        statements within the access list will be
                        evaluated.";
                }
                choice remark-or-ace-filter {
                    case remark {
                        leaf remark {
                            mandatory true;
                            type acl:Remark;
                            description
                                "A remark is a comment that can be
                                inserted into an ACL in order to make
                                the access list easier for the network
                                administrator to understand.
                                It is retained to facilitate
                                co-existence with CLI.";
                        }
                    }
                    case filter {
                        container filters {
                            leaf direction {
                                default "bi-direction";
                                type enumeration {
                                    enum bi-direction;
                                    enum request;
                                    enum response;
                                }
                                description "ARP request/response.";
                            }

                            uses acl:IP-SOURCE-NETWORK;
                            uses acl:IP-DESTINATION-NETWORK {
                                when "../direction = 'response'";
                            }

                            uses acl:MAC-SOURCE-NETWORK;
                            uses acl:MAC-DESTINATION-NETWORK {
                                when "../direction = 'response'";
                            }
                            leaf enable-capture {
                                type boolean ;
                                description
                                    "Enable packet capture on this
                                    filter for this session.";
                            }
                            leaf capture-session-id {
                                type uint32 {
                                    range "1..48";
                                }
                                description
                                    "Enable packet capture on this
                                    filter for this session.
                                    Session ID range is 1 to 48";
                            }

                        }
                        container actions {
                            leaf action {
                                type acl:ACL-Action;
                                mandatory true;
                                description "Permit/deny on match";
                            }
                            leaf log {
                                type boolean;
                                default false;
                                description "Log on match";
                            }

                        }
                        leaf match {
                            config false;
                            type uint64;
                            description
                                "The total packet that have matched for
                                the particular ACE";
                        }
                    }
                }
            }
        }
    }

    augment "/acl:acls/acl:acl" {
        when "acl:acl-type = 'arp-acl'";
         uses ARP-ACE-GROUP;
    }
}
