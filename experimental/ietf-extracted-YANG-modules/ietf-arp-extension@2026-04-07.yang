module ietf-arp-extension {
  yang-version 1.1;
  namespace "urn:ietf:params:xml:ns:yang:ietf-arp-extension";
  prefix arp-ext;

  import ietf-yang-types {
    prefix yang;
    reference
      "RFC 9911: Common YANG Data Types";
  }
  import ietf-interfaces {
    prefix if;
    reference
      "RFC 8343: A Yang Data Model for Interface Management";
  }
  import ietf-ip {
    prefix ip;
    reference
      "RFC 8344: A Yang Data Model for IP Management";
  }

  organization
    "IETF Internet Area Working Group (intarea)";
  contact
    "WG Web:  <https://datatracker.ietf.org/wg/intarea/>
     WG List: <mailto:int-area@ietf.org>

     Author:  Feng Zheng
              <habby.zheng@huawei.com>
     Editor:  Bo Wu
              <lana.wubo@huawei.com>
     Editor:  Robert Wilton
              <rwilton@cisco.com>
     Editor:  Fan Zhang
              <zhangf52@chinatelecom.cn>
     Author:  Yongqing Zhu
              <zhuyq8@chinatelecom.cn>
     Author:  Xiaojian Ding
              <wjswsl@163.com>";
  description
    "This YANG module extends Address Resolution Protocol (ARP)
     configuration and management defined in the ietf-ip, which 
     includes dynamic ARP learning, proxy ARP, gratuitous ARP, 
     and packet statistics collection.

     Copyright (c) 2026 IETF Trust and the persons identified as
     authors of the code.  All rights reserved.

     Redistribution and use in source and binary forms, with or
     without modification, is permitted pursuant to, and subject
     to the license terms contained in, the Revised BSD License set
     forth in Section 4.c of the IETF Trust's Legal Provisions
     Relating to IETF Documents
     (https://trustee.ietf.org/license-info).

     This version of this YANG module is part of RFC XXXX; see the
     RFC itself for full legal notices.";

  revision 2026-04-07 {
    description
      "Initial version.";
    reference
      "RFC XXXX: A YANG Data Model for ARP Extensions";
  }

  /* Data nodes */

  augment "/if:interfaces/if:interface/ip:ipv4" {
    description
      "Augment interfaces with ARP configuration and state.";
    container arp {
      description
        "Address Resolution Protocol (ARP) related configuration
         and state";
      leaf expiry-time {
        type uint32 {
          range "30..86400";
        }
        units "seconds";
        description
          "Aging time of a received dynamic ARP entry before it is
           removed from the cache.";
      }
      leaf dynamic-learning {
        type boolean;
        default "true";
        description
          "Controls whether dynamic ARP learning is enabled on the
           interface.

             true -  dynamic learning is enabled
             false - dynamic learning is disabled";
      }
      container proxy-arp {
        description
          "Configuration parameters for proxy ARP";
        leaf mode {
          type enumeration {
            enum disabled {
              description
                "The system only responds to ARP requests that
                 specify a target address configured on the local
                 interface.";
            }
            enum remote-only {
              description
                "The system only responds to ARP requests when the
                 sender and target IP addresses are in different
                 subnets.";
            }
            enum all {
              description
                "The system responds to ARP requests where the sender
                 and target IP addresses are in different subnets, as
                 well as those where they are in the same subnet.";
            }
          }
          default "disabled";
          description
            "When set to a value other than 'disabled', the local
             system should respond to ARP requests that are for
             target addresses other than those that are configured on
             the local subinterface using its own MAC address as the
             target hardware address.  If the 'remote-only' value is
             specified, replies are only sent when the target address
             falls outside the locally configured subnets on the
             interface, whereas with the 'all' value, all requests,
             regardless of their target address are replied to.";
          reference
            "RFC1027: Using ARP to Implement Transparent Subnet
             Gateways";
        }
      }
      container gratuitous-arp {
        description
          "Configure gratuitous ARP.";
        reference
          "RFC5227: IPv4 Address Conflict Detection";
        leaf enabled {
          type boolean;
          description
            "Enable or disable sending gratuitous ARP packet on the
             interface.

             The default behaviour is device specific, and a
             deviation could be used to specify a device specific
             default.";
        }
        leaf interval {
          type uint32 {
            range "1..86400";
          }
          units "seconds";
          description
            "The interval, in seconds, between sending gratuitous ARP
             packets on the interface.

             The default behaviour is device specific, and a
             deviation could be used to specify a device specific
             default.";
        }
      }
      container statistics {
        config false;
        description
          "ARP per-interface packet statistics

           For all ARP interface counters, discontinuities in the
           value can occur at re-initialization of the management
           system and at other times as indicated by the value of
           '../../statistics/discontinuity-time' in the
           ietf-interfaces YANG module.";
        leaf in-requests-pkts {
          type yang:counter64;
          description
            "The number of ARP request packets received on this
             interface.";
        }
        leaf in-replies-pkts {
          type yang:counter64;
          description
            "The number of ARP reply packets received on this
             interface.";
        }
        leaf in-gratuitous-pkts {
          type yang:counter64;
          description
            "The number of gratuitous ARP packets received on this
             interface.";
        }
        leaf out-requests-pkts {
          type yang:counter64;
          description
            "The number of ARP request packets sent on this
             interface.";
        }
        leaf out-replies-pkts {
          type yang:counter64;
          description
            "The number of ARP reply packets sent on this
             interface.";
        }
        leaf out-gratuitous-pkts {
          type yang:counter64;
          description
            "The number of gratuitous ARP packets sent on this
             interface.";
        }
      }
    }
  }

  augment "/if:interfaces/if:interface/ip:ipv4/ip:neighbor" {
    description
      "Augment IPv4 neighbor list with ARP expiry time.";
    leaf remaining-expiry-time {
      type uint32;
      units "seconds";
      config false;
      description
        "The number of seconds until the dynamic ARP entry expires
         and is removed from the ARP cache.";
    }
  }
}
