module evn {
  namespace "urn:huawei:params:xml:ns:yang:evn";
  // replace with IANA namespace when assigned
  prefix "evn";

  import ietf-interfaces {
    prefix if;
    //rfc7223-YANG Interface Management
  }

  import ietf-inet-types {
    prefix inet;
    //RFC6991
  }

  description
    "This YANG module defines the generic configuration data for
     EVN service.

     Terms and Acronyms

     EVN: Ethernet Virtual Network
     EVPN: Ethernet VPN
     ESI: Ethernet Segment Identifier

    ";

  revision 2014-08-17 {
    description
      "Initial revision.";
  }

  /*
   * ethernet segment ID config.
   */
  container interfaces {
    list interface {
      key "name";
      leaf name {
        type leafref {
          path "/if:interfaces/if:interface/if:name";
        }
      }
      leaf esi {
        description
          "Specify the ethernet segment ID.";

        config "true";
        type string {
          length "24";
          pattern "(^00([0-9a-fA-F]){2}\.(([0-9a-fA-F]){4}\.){3}
          (([0-9a-fA-F]){4})$)";
        }
      }
    }
  }

  /*
   * Enable Ethernet Virtual Network.
   */
  container evnGlobal {

    leaf evnEnable {
      config "true";
      type "boolean";
      default "false";
    }

    leaf arp-cache-disable {
      config "true";
      type boolean;
      default "false";
    }

    leaf arp-cache-timeout {
      config "true";
      type uint32 {
        range "0..100000";
      }
      default "240";
    }

  }
  /*
   * Configuring BFD for EVN BGP.
   */
  container evn-bgp {

    container bfd {
      leaf isBfdEnable {
        description "Enable BFD";

        config "true";
        type boolean;
        default "false";
      }

      leaf txInterval {
        description "Specify the minimum transmit interval";

        config "true";
        type uint32 {
          range "0..4294967295";
        }
      }
      leaf rxInterval {
        description "Specify the minimum receive interval";

        config "true";
        type uint32 {
          range "0..4294967295";
        }
      }
      leaf multiplier {
        description "Specify the detect multiplier";
        config "true";
        default "3";
        type uint8 {
          range "3..50";
        }
      }

    }

    container mac-limit-per-peer {

      leaf mac-limit-value {
        description
          "Specify Mac route limit value.";

        config "true";
        type uint32 {
          range "1..4294967295";
        }
      }
      leaf mac-limit-alert-percent {
        description
          "Specify maximum percentage value. Start to generate
           warning messages if it reaches maximum percentage
           value";

        config "true";
        type uint8 {
          range "1..100";
        }
        default "75";
      }

      choice mac-limit-type {

        case enable-alert-only {
          leaf alert-only {
            description
              "Allows the router to generate log message without
               terminating session when the maximum is exceeded.";

            config "true";
            type boolean;
            default "false";
          }
        }
        case enable-idle-forever {
          leaf idle-forever {
            description
              "Do not auto-connect-retry until reset bgp when the
               maximum is exceeded and then terminating session.";

            config "true";
            type boolean;
            default "false";
          }
        }
        case enable-idle-timeout {
          leaf idle-timeout {
            description
              "Specify Value of idle-timeout timer(minutes).
               Auto-connect-retry after timeout when the maximum is
               exceeded and then terminating session.";

            config "true";
            type uint16 {
              range "1..1200";
            }
          }
        }
      }
    }
    leaf source-address {
      config "true";
      type inet:ip-address;
    }

    /*
     * Configuring an Authentication Mode for EVN BGP.
     */
    container authentication {
      description
        "To improve network security, you can configure MD5 or
         Keychain authentication for EVN BGP peers when they
         set up a TCP connection.
        ";

      leaf cipherPassword {
        config "true";
        type "string";
      }
      leaf keychainName {
        config "true";
        type "string";
      }
    }

    container bgpPeers {
      list bgpPeer {
      key "peerAddr";
      max-elements "unbounded";
      min-elements "0";
        description
          "BGP Peer configure class.";

        leaf peerAddr {
          description
            "The nerighbor address.";
            config "true";
            type inet:ip-address;
            mandatory true;
        }

      }
    }

    container set-route-reflect-function {
      description
        "Configure an EVN BGP RR to reduce the number of EVN BGP
         peer connections, saving network resources.";

      choice set-type {
        description
          "An EVN BGP RR can be manually specified or dynamically
           configured.

           Static RR:
           After a static RR is configured, you need to manually
           establish peer relationships between the RR and other
           PE devices and specify the PE devices as the RR clients.

           Dynamic RR:
           Only a non-PE device can be configured as a dynamic RR.
           After a device is configured as a dynamic RR, it can
           automatically set up peer relationships with devices
           specified by the peer ip-address command (ip-address is
           the source address of the dynamic RR).
           ";

        case static {
          container bgp-clients {
            list bgp-client {
              key "clientAddr";
              max-elements "unbounded";
              min-elements "0";
              description
                "Configure some peers as route reflector clients.";

              leaf clientAddr {
                description
                  "The client address. A static RR is configured. Only
                   the specified peers can become the RR clients.";

                config "true";
                type inet:ip-address;
              }
            }
          }
        }

        case dynamic {
          leaf server-enable {
            description
              "Enable Server function for dynamic peer. A dynamic RR is
               configured. After a dynamic RR is configured, all PE
               devices that have established peer relationships with the
               RR can become the RR clients.";
            type boolean;
            default "false";
          }
        }

      }

      leaf redundancy-mode {
        description
          "Specify redundancy-mode.";

        config "true";
        type enumeration {
          enum "single-active";
          enum "all-active";
        }
        default "single-active";
      }

      leaf df-delay-timer{
        description
          "Specify designated forwarder election delay-timer
           value(seconds).";

        config "true";
        type uint32 {
          range "1..1200";
        }
        default "60";
      }

      container timer {
        leaf keepaliveTime {
          description "Specifies the Keepalive interval";
          config "true";
          default "60";
          type uint16 {
            range "0..21845";
          }
        }
        leaf holdTime {
          description "Specifies the Holdtime interval";
          config "true";
          default "180";
          type uint16 {
            range "0..65535";
          }
        }
      }

    }

  }

  container evnInstances {
    description
      "EVN instance configuration parameters.";

    list evnInstance {
      max-elements "unbounded";
      min-elements "0";
      key "evnName";

      leaf evnName {
        description
          "EVN Instance Name";

        config "true";
        type string {
          length "1..31";
        }
      }

      leaf evnId {
        description
          "Specify the EVN instance id. Each EVN instance has a unique
           ID.";

        config "true";
        type uint32 {
          range "1..65535";
        }
      }

      container vlanList {
        description
          "Specify a vlan list.";

        list vlan-id {
          key "vlan-id-number";

          leaf vlan-id-number {
            type uint16 {
              range "1..4094";
            }
          }
        }
      }

      container exportAclNameOrId {
        description
          "Filter outgoing routing updates. To accurately control EVN
           routes, configure an export routing policy. The export
           routing policy filters routes before they are advertised to
           other PE devices.";

        choice aclNumOrName {
          case Specify-aclNum {
            leaf aclNum {
              config "true";
              type uint16 {
                range "2000..2999";
              }
            }
          }
          case Specify-aclName {
            leaf aclName {
              config "true";
              type string;
            }
          }
        }
      }

      container importAclNameOrId {
        description
          "Set route filtering policy. To accurately control EVN routes,
           configure an import routing policy. The import routing policy
           filters routes received from other PE devices.";

        choice aclNumOrName {
          case Specify-aclNum {
            leaf aclNum {
              config "true";
              type uint16 {
                range "2000..2999";
              }
            }
          }
          case Specify-aclName {
            leaf aclName {
              config "true";
              type string;
            }
          }
        }
      }

      container evnInstanceInfo {
        description
          "Display the information of the evn instance.
           It is intended that this container may be augmented by
           vendors to reflect the vendor-specific operational state
           parameters.";

        leaf exportRT {
          config "false";
          type "string";
        }
        leaf importRT {
          config "false";
          type "string";
        }
        leaf evnRd {
          config "false";
          type "string";
        }
      }

    }

  }

}
