module ietf-dtnma-agent {
  namespace "ari:/ietf-dtnma-agent";
  prefix da;
  amm:enum "0";

  import ietf-amm {
    prefix amm;
  }

  organization
    "IETF Delay Tolerant Networking (DTN) Working Group";
  contact
    "WG Web: <http://tools.ietf.org/wg/dtn/>
     WG List: <mailto:dtn@ietf.org>

     Editor: Brian Sipos
             <mailto:brian.sipos+ietf@gmail.com>";
  description
    "This module implements the DTN Management Architecture (DTNMA)
     Agent core functionality.";
  reference
    "draft-birrane-dtn-adm";

  revision 2023-06-08 {
    description
      "Updated for latest AMM contents.";
    reference
      "draft-birrane-dtn-adm";
  }

  feature rules {
    description
      "Conforming to this feature enables time-based and
       state-based autonomy rules.";
  }

  amm:edd amp_version {
    amm:type TEXTSTR;
    description
      "The version of AMP which this agent supports.";
  }
  amm:edd capability {
    amm:tblt {
      amm:key "adm_name";
      amm:column adm_name {
        amm:type amm:LABEL;
        description
          "The module name of the ADM";
      }
      amm:column revision {
        amm:type amm:TEXTSTR;
        description
          "The specific revision the agent supports.";
      }
      amm:column features {
        amm:ulist {
          amm:type amm:LABEL;
        }
        description
          "The features of the ADM which the agent supports.";
      }
    }
    description
      "A table to indicate the ADM capability of the sending agent.";
  }
  amm:const hello {
    amm:type amm:RPTT;
    amm:init-value "(../EDD/amp_version,../EDD/capability)";
    description
      "A report template to indicate the presence of an agent
       on a network.";
  }

  // MAC helper controls
  amm:ctrl if_then_else {
    amm:parameter condition {
      amm:type amm:EXPR;
      description
        "The condition to evaluate.";
    }
    amm:parameter on_truthy {
      amm:type amm:EXEC-REF;
      description
        "The object to execute when the condition is truthy.";
    }
    amm:parameter on_falsy {
      amm:union {
        amm:type amm:NULL;
        amm:type amm:EXEC-REF;
      }
      amm:default "null";
      description
        "An optional execution when the condition is falsey.";
    }
    description
      "Evaluate an expression and follow one of two branches of
       further evaluation.";
  }
  amm:ctrl catch {
    amm:parameter try {
      amm:type amm:EXEC-REF;
      description
        "The object to execute.";
    }
    amm:parameter on_failure {
      amm:union {
        amm:type amm:NULL;
        amm:type amm:EXEC-REF;
      }
      amm:default "null";
      description
        "An optional execution after failure.";
    }
    description
      "Attempt to execute an object, and if there is some failure catch it
       and execute an alternative object.";
  }
  amm:ctrl inspect {
    amm:parameter ref {
      amm:type amm:VALUE-REF;
      description
        "An object to produce a value from.";
    }
    amm:result val {
      amm:type amm:ANY;
      description
        "The produced value.";
    }
    description
      "Produce a result value to inspect the agent state.
       This does not perform any EXPR evaluation or RPTT handling.";
  }
  amm:ctrl report_on {
    amm:parameter rptt {
      amm:type amm:RPTT;
    }
    description
      "Generate a report on an object without needing to define an object.
       The parameter is a single RPTT list that would be produced by an object.
       If used for more than one-shot diagnostics, defining a RPTT
       (e.g. in a VAR) is more efficient because the RPTT item would not
       be present in the report.";
  }

  grouping obj-list-params {
    amm:parameter include_adm {
      amm:type amm:BOOL;
      amm:default "false";
      description
        "If true, listings will include objects from ADMs";
    }
    description
      "Common parameters for object listing";
  }

  amm:edd typedef_list {
    uses obj-list-params;
    amm:tblt {
      amm:key "obj";
      amm:column obj {
        amm:type amm:TYPEDEF-REF;
      }
    }
    description
      "A table of TYPEDEF within the agent.";
  }

  // Objects related to VAR handling
  amm:edd var_list {
    uses obj-list-params;
    amm:tblt {
      amm:key "obj";
      amm:column obj {
        amm:type amm:VAR-REF;
      }
      amm:column type {
        amm:type amm:TYPE-REF;
      }
    }
    description
      "A table of VAR within the agent.";
  }
  amm:ctrl var_present {
    amm:parameter obj {
      amm:type amm:VAR-REF;
      description
        "A reference to a VAR within an ODM only.";
    }
    amm:parameter type {
      amm:type amm:TYPE-REF;
      description
        "The type for the VAR object.";
    }
    amm:parameter init {
      amm:union {
        amm:type amm:NULL;
        amm:type amm:EXPR;
      }
      amm:default "null";
      description
        "An optional initializer expression.";
    }
    description
      "Ensure a specific VAR is present.";
  }
  amm:ctrl var_absent {
    amm:parameter obj {
      amm:type amm:VAR-REF;
      description
        "A reference to a VAR within an ODM only.";
    }
    description
      "Ensure a specific VAR is not present.";
  }

  // Objects related to SBR handling
  amm:edd sbr_list {
    if-feature "rules";
    amm:tblt {
      amm:key "obj";
      amm:column obj {
        amm:type amm:SBR-REF;
      }
      amm:column action {
        amm:type amm:MAC;
        description
          "The execution when this rule triggers.";
      }
      amm:column start_time {
        amm:type amm:TIME;
      }
      amm:column condition {
        amm:type amm:EXPR;
      }
      amm:column min_interval {
        amm:type TD;
      }
      amm:column max_count {
        amm:type UVAST;
      }
    }
  }
  amm:edd tbr_list {
    if-feature "rules";
    amm:tblt {
      amm:key "obj";
      amm:column obj {
        amm:type amm:OBJ-REF;
      }
      amm:column action {
        amm:type amm:MAC;
        description
          "The execution when this rule triggers.";
      }
      amm:column start_time {
        amm:type amm:TIME;
      }
      amm:column period {
        amm:type TD;
      }
      amm:column max_count {
        amm:type UVAST;
      }
    }
  }

  grouping numeric-unary-operands {
    amm:operand val {
      amm:type amm:NUMERIC;
      description
        "The single value.";
    }
  }

  grouping numeric-binary-operands {
    amm:operand left {
      amm:type amm:NUMERIC;
      description
        "The left-side operand.";
    }
    amm:operand right {
      amm:type amm:NUMERIC;
      description
        "The left-side operand.";
    }
  }

  grouping numeric-unary-result {
    amm:result val {
      amm:type amm:NUMERIC;
      description
        "The single value.";
    }
  }

  amm:oper negate {
    uses numeric-unary-operands;
    uses numeric-unary-result;
    description
      "Negate a value.
       This is equivalent to multiplying by -1 but a shorter
       expression.";
  }
  amm:oper add {
    uses numeric-binary-operands;
    uses numeric-unary-result;
    description
      "Add two numeric values.
       The operands are cast to the least compatible numeric type
       before the arithmetic.";
  }

  // amm:oper sub
  // amm:oper multiply
  // amm:oper divide
  // amm:oper add
  // amm:oper bit_not
  // amm:oper bit_and
  // amm:oper bit_or
  // amm:oper bit_xor
  // amm:oper bool_not
  // amm:oper bool_and
  // amm:oper bool_or
  // amm:oper bool_xor
  // amm:oper compare_eq
  // amm:oper compare_ne
  // amm:oper compare_gt
  // amm:oper compare_ge
  amm:oper compare_lt {
    uses numeric-binary-operands;
    uses numeric-unary-result;
    description
      "Compare two operands by value.
       The result is true if the left value is less than the right.
       The operands are cast to the least compatible numeric type
       before the comparison.";
  }
  amm:oper compare_le {
    uses numeric-binary-operands;
    uses numeric-unary-result;
    description
      "Compare two operands by value.
       The result is true if the left value is less than or
       equal to the right.
       The operands are cast to the least compatible numeric type
       before the comparison.";
  }
}
