module ietf-uses-geo-location {
  namespace
    "urn:ietf:params:xml:ns:yang:ietf-uses-geo-location";
  prefix ugeo;
  import geo-location { prefix geo; }
  organization "Empty Org";
  contact "Example Author <eauthor@example.com>";
  description "Example use of geo-location";
  revision 2019-02-02 { reference "None"; }
  container locatable-items {
    description "container of locatable items";
    list locatable-item {
      key name;
      description "A of locatable item";
      leaf name {
        type string;
        description "name of locatable item";
      }
      uses geo:geo-location;
    }
  }
}
