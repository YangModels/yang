module ietf-service-assurance-is-is {
  yang-version 1.1;
  namespace "urn:ietf:params:xml:ns:yang:ietf-service-assurance-is-is";
  prefix service-assurance-is-is;

  import ietf-service-assurance {
    prefix service-assurance;
  }

  organization
    "IETF NETCONF (Network Configuration) Working Group";
  contact
    "WG Web:   <https://datatracker.ietf.org/wg/netconf/>
     WG List:  <mailto:netconf@ietf.org>
     Author:   Benoit Claise  <mailto:benoit.claise@huawei.com>
     Author:   Jean Quilbeuf  <mailto:jean.quilbeuf@huawei.com>";
  description
    "This module extends the ietf-service-assurance module to add
     support for the subservice IS-ISHealthy.

     Checks whether an IS-IS instance is healthy.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see the
     RFC itself for full legal notices.  ";

  revision 2021-06-28 {
    description
      "Initial revision.";
    reference
      "RFC xxxx: Title to be completed";
  }

  identity is-is-idty {
    base service-assurance:subservice-idty;
    description
      "Health of IS-IS routing protocol.";
  }

  augment "/service-assurance:subservices/service-assurance:subservice/service-assurance:parameter" {
    description
      "Specify the required parameters for a new subservice type";
    container parameters {
      when "derived-from-or-self(../service-assurance:type, 'is-is-idty')";
      description
        "Specify the required parameters for the IS-IS subservice type";
      leaf instance-name {
        type string;
        mandatory true;
        description
          "The instance to monitor.";
      }
    }
  }
}
