module ietf-l2vpn-ntw {
  yang-version 1.1;
  namespace "urn:ietf:params:xml:ns:yang:ietf-l2vpn-ntw";
  prefix l2vpn-ntw;

  import ietf-inet-types {
    prefix inet;
    reference
      "RFC 6991: Common YANG Data Types, Section 4";
  }
  import ietf-yang-types {
    prefix yang;
    reference
      "RFC 6991: Common YANG Data Types, Section 3";
  }
  import ietf-vpn-common {
    prefix vpn-common;
    reference
      "RFC CCCC: A Layer 2/3 VPN Common YANG Model";
  }
  import iana-bgp-l2-encaps {
    prefix iana-bgp-l2-encaps;
  }
  import iana-pseudowire-types {
    prefix iana-pw-types;
  }
  import ietf-routing-types {
    prefix rt-types;
    reference
      "RFC 8294: Common YANG Data Types for the Routing Area";
  }

  organization
    "IETF OPSA (Operations and Management Area) Working Group";
  contact
    "WG Web:   <http://tools.ietf.org/wg/opsawg/>
     WG List:  <mailto:opsawg@ietf.org>

     Editor:    Mohamed Boucadair
               <mailto:mohamed.boucadair@orange.com>
     Editor:    Samier Barguil
               <mailto:samier.barguilgiraldo.ext@telefonica.com>
     Author:    Oscar Gonzalez de Dios
               <mailto:oscar.gonzalezdedios@telefonica.com>";
  description
    "This YANG module defines a network model for layer 2 VPN
     services.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2021-07-08 {
    description
      "Initial version.";
    reference
      "RFC XXXX: A Layer 2 VPN Network YANG Model.";
  }

  /* Features */

  feature oam-3ah {
    description
      "Indicates the support of OAM 802.3ah.";
    reference
      "IEEE Std 802.3ah: Media Access Control Parameters, Physical
                         Layers, and  Management Parameters for
                         Subscriber Access Networks";
  }

  /* Identities */

  identity esi-type {
    description
      "T-(Ethernet Segment Identifier (ESI) Type) is a 1-octet field
       (most significant octet) that specifies the format of the
       remaining 9 octets (ESI Value).";
    reference
      "RFC 7432: BGP MPLS-Based Ethernet VPN, Section 5";
  }

  identity esi-type-0 {
    base esi-type;
    description
      "This type indicates an arbitrary 9-octet ESI value,
       which is managed and configured by the operator.";
  }

  identity esi-type-1 {
    base esi-type;
    description
      "When IEEE 802.1AX Link Aggregation Control Protocol (LACP)
       is used between the Provider Edge (PE) and Customer Edge (CE)
       devices, this ESI type indicates an auto-generated ESI value
       determined from LACP.";
  }

  identity esi-type-2 {
    base esi-type;
    description
      "The ESI value is auto-generated and determined based
       on the Layer 2 bridge protocol.";
  }

  identity esi-type-3 {
    base esi-type;
    description
      "This type indicates a MAC-based ESI value that can be
       auto-generated or configured by the operator.";
  }

  identity esi-type-4 {
    base esi-type;
    description
      "This type indicates a Router-ID ESI value that can be
       auto-generated or configured by the operator.";
  }

  identity esi-type-5 {
    base esi-type;
    description
      "This type indicates an Autonomous System (AS)-based ESI value
       that can be auto-generated or configured by the operator.";
  }

  identity df-election-methods {
    description
      "Base Identity Designated Forwarder (DF) election method.";
  }

  identity default-7432 {
    base df-election-methods;
    description
      "The default DF election method.

       The default procedure for DF election at the granularity of <ES,
       VLAN> for VLAN-based service or <ES, VLAN bundle> for VLAN-
       (aware) bundle service is referred to as 'service carving'.";
    reference
      "RFC 7432: BGP MPLS-Based Ethernet VPN, Section 8.5";
  }

  identity highest-random-weight {
    base df-election-methods;
    description
      "The highest random weight (HRW) method.";
    reference
      "RFC 8584: Framework for Ethernet VPN Designated
                 Forwarder Election Extensibility, Section 3";
  }

  identity preference {
    base df-election-methods;
    description
      "The preference based method. PEs are assigned with
       preferences to become the DF in the Ethernet Segment (ES).
       The exact preference-based algorithm (e.g., lowest-preference
       algorithm, highest-preference algorithm) to use is
       signaled at the control plane.";
  }

  identity evpn-redundancy-mode {
    description
      "Base identity for Ethernet VPN (EVPN) redundancy modes.";
  }

  identity single-active {
    base evpn-redundancy-mode;
    description
      "Indicates Single-Active redundancy mode for a given ES.";
    reference
      "RFC 7432: BGP MPLS-Based Ethernet VPN, Section 14.1.1";
  }

  identity all-active {
    base evpn-redundancy-mode;
    description
      "Indicates All-Active redundancy mode for a given ES.";
    reference
      "RFC 7432: BGP MPLS-Based Ethernet VPN, Section 14.1.2";
  }

  identity evpn-service-type {
    description
      "Base identity for EVPN service type.";
  }
  identity vlan-based-service-interface {
    base evpn-redundancy-mode;
    description
      "VLAN-Based Service Interface.";
    reference
      "RFC 7432: BGP MPLS-Based Ethernet VPN, Section 6.1";
  }

  identity vlan-bundle-service-interface {
    base evpn-redundancy-mode;
    description
      "VLAN Bundle Service Interface.";
    reference
      "RFC 7432: BGP MPLS-Based Ethernet VPN, Section 6.2";
  }

  identity vlan-aware-bundle-service-interface {
    base evpn-redundancy-mode;
    description
      "VLAN-Aware Bundle Service Interface.";
    reference
      "RFC 7432: BGP MPLS-Based Ethernet VPN, Section 6.3";
  }

  identity mapping-type {
    base vpn-common:multicast-gp-address-mapping;
    description
      "Identity for multicast group mapping type.";
  }

  identity loop-prevention-type {
    description
      "Identity of loop prevention.";
  }

  identity shut {
    base loop-prevention-type;
    description
      "Identity of shut protection.";
  }

  identity trap {
    base loop-prevention-type;
    description
      "Identity of trap protection.";
  }

  identity color-type {
    description
      "Identity of color types.";
  }

  identity green {
    base color-type;
    description
      "Identity of the 'green' color type.";
  }

  identity yellow {
    base color-type;
    description
      "Identity of the 'yellow' color type.";
  }

  identity red {
    base color-type;
    description
      "Identity of the 'red' color type.";
  }

  identity t-ldp-pw-type {
    description
      "Identity for t-ldp-pw-type.";
  }

  identity vpws-type {
    base t-ldp-pw-type;
    description
      "Identity for VPWS.";
  }

  identity vpls-type {
    base t-ldp-pw-type;
    description
      "Identity for VPLS.";
  }

  identity hvpls {
    base t-ldp-pw-type;
    description
      "Identity for H-VPLS.";
  }

  identity evpn-type {
    description
      "Ethernet VPN types.";
  }

  identity evpn-vpws {
    base evpn-type;
    description
      "VPWS support in EVPN.";
  }

  identity evpn-pbb {
    base evpn-type;
    description
      "Provider Backbone Bridging Support in EVPN.";
  }

  identity pm-type {
    description
      "Identity for performance monitoring type.";
  }

  identity loss {
    base pm-type;
    description
      "Loss measurement.";
  }

  identity delay {
    base pm-type;
    description
      "Delay measurement.";
  }

  identity mac-learning-mode {
    description
      "Media Access Control (MAC) learning mode.";
  }

  identity data-plane {
    base mac-learning-mode;
    description
      "User MAC addresses are learned through ARP broadcast.";
  }

  identity control-plane {
    base mac-learning-mode;
    description
      "User MAC addresses are advertised through EVPN-BGP.";
  }

  identity mac-action {
    description
      "Base identity for a MAC action.";
  }

  identity drop {
    base mac-action;
    description
      "Identity for dropping a packet.";
  }

  identity flood {
    base mac-action;
    description
      "Identity for packet flooding.";
  }

  identity warning {
    base mac-action;
    description
      "Identity for sending a warning log message.";
  }

  identity precedence-type {
    description
      "Redundancy type. The service can be created
       with active and bakcup signalization.";
  }

  identity primary {
    base precedence-type;
    description
      "Identifies the main VPN network access.";
  }

  identity backup {
    base precedence-type;
    description
      "Identifies the backup VPN network access.";
  }

  identity pw-type {
    description
      "Identity for allowed LDP-based PW type.";
    reference
      "RFC 4762: Virtual Private LAN Service (VPLS) Using
                 Label Distribution Protocol (LDP)
                 Signaling, Section 6.1.1";
  }

  identity ethernet {
    base pw-type;
    description
      "Identity for PW Ethernet type.";
  }

  identity ethernet-tagged {
    base pw-type;
    description
      "Identity for PW Ethernet tagged mode type.";
  }

  /* Typedefs */

  typedef ccm-priority-type {
    type uint8 {
      range "0..7";
    }
    description
      "A 3-bit priority value to be used in the VLAN tag,
       if present in the transmitted frame.";
  }

  /* Groupings */

  grouping cfm-802-grouping {
    description
      "Grouping for 802.1ag CFM attributes.";
    reference
      "IEEE Std 802-1ag: Virtual Bridged Local Area Networks
                         Amendment 5: Connectivity Fault Management";
    leaf maid {
      type string;
      description
        "MA ID";
    }
    leaf mep-id {
      type uint32;
      description
        "Local Maintenance End Point (MEP) ID.";
    }
    leaf mep-level {
      type uint32;
      description
        "MEP level.";
    }
    leaf mep-up-down {
      type enumeration {
        enum up {
          description
            "MEP is up.";
        }
        enum down {
          description
            "MEP is down.";
        }
      }
      description
        "MEP up/down";
    }
    leaf remote-mep-id {
      type uint32;
      description
        "Remote MEP ID.";
    }
    leaf cos-for-cfm-pdus {
      type uint32;
      description
        "COS for CFM PDUs.";
    }
    leaf ccm-interval {
      type uint32;
      description
        "CCM interval.";
    }
    leaf ccm-holdtime {
      type uint32;
      description
        "CCM hold time.";
    }
    leaf ccm-p-bits-pri {
      type ccm-priority-type;
      description
        "The priority parameter for Continuity Check Messages (CCMs)
         transmitted by the MEP.";
    }
  }

  grouping y-1731 {
    description
      "Grouping for y.1731";
    reference
      "ITU-T Y-1731:  Operations, administration and maintenance
                      (OAM) functions and mechanisms for
                      Ethernet-based networks";
    list y-1731 {
      key "maid";
      description
        "List for y-1731.";
      leaf maid {
        type string;
        description
          "MA ID.";
      }
      leaf mep-id {
        type uint32;
        description
          "Local MEP ID.";
      }
      leaf type {
        type identityref {
          base pm-type;
        }
        description
          "Performance monitor types.";
      }
      leaf remote-mep-id {
        type uint32;
        description
          "Remote MEP ID.";
      }
      leaf message-period {
        type uint32;
        description
          "Defines the interval between OAM messages. The message
           period is expressed in milliseconds.";
      }
      leaf measurement-interval {
        type uint32;
        description
          "Specifies the measurement interval for statistics. The
           measurement interval is expressed in seconds.";
      }
      leaf cos {
        type uint32;
        description
          "Identifies the Class of Service.";
      }
      leaf loss-measurement {
        type boolean;
        description
          "Controls whether loss measurement is enabled/disabled.";
      }
      leaf synthethic-loss-measurement {
        type boolean;
        description
          "Indicates whether enable synthetic loss measurement.";
      }
      container delay-measurement {
        description
          "Container for delay measurement";
        leaf enable-dm {
          type boolean;
          description
            "Whether to enable delay measurement.";
        }
        leaf two-way {
          type boolean;
          description
            "Whether delay measurement is two-way (true) of one-
             way (false).";
        }
      }
      leaf frame-size {
        type uint32;
        description
          "Frame size";
      }
      leaf session-type {
        type enumeration {
          enum proactive {
            description
              "Proactive mode.";
          }
          enum on-demand {
            description
              "On-demand mode.";
          }
        }
        description
          "Session type.";
      }
    }
  }

  grouping global-parameters-profile {
    description
      "Container for per-service parameters.";
    leaf local-autonomous-system {
      type inet:as-number;
      description
        "Indicates a local AS Number (ASN).";
    }
    leaf svc-mtu {
      type uint32;
      description
        "Service MTU, it is also known as the maximum transmission unit
         or maximum frame size. When a frame is larger than the MTU,
         it is fragmented to accommodate the MTU of the network.";
    }
    leaf ce-vlan-preservation {
      type boolean;
      description
        "Preserve the CE-VLAN ID from ingress to egress,i.e.,
         CE-VLAN tag of the egress frame are identical to
         those of the ingress frame that yielded this egress
         service frame. If All-to-One bundling within a site
         is Enabled, then preservation applies to all Ingress
         service frames. If All-to-One bundling is disabled,
         then preservation applies to tagged Ingress service
         frames having CE-VLAN ID 1 through 4094.";
    }
    leaf ce-vlan-cos-perservation {
      type boolean;
      description
        "CE vlan CoS preservation. PCP bits in the CE-VLAN tag
         of the egress frame are identical to those of the ingress
         frame that yielded this egress service frame.";
    }
    leaf control-word-negotiation {
      type boolean;
      description
        "Controls whether Control-word negotiation is enabled
         (if set to true) or not (if set to false).";
      reference
        "Section 7 of RFC 8077";
    }
    container mac-policies {
      description
        "Container of MAC policies.";
      container mac-addr-limit {
        description
          "Container of MAC-Addr limit configuration.";
        leaf mac-num-limit {
          type uint16;
          description
            "Maximum number of MAC addresses learned from
             the customer for a single service instance.";
        }
        leaf time-interval {
          type uint32;
          units "milliseconds";
          description
            "The aging time of the mac address.";
        }
        leaf action {
          type identityref {
            base mac-action;
          }
          description
            "Specifies the action when the upper limit is
             exceeded: drop the packet, flood the
             packet, or simply send a warning log message.";
        }
      }
      container mac-loop-prevention {
        description
          "Container for MAC loop prevention.";
        leaf window {
          type uint32;
          units "seconds";
          default "180";
          description
            "The timer when a MAC mobility event is detected.";
        }
        leaf frequency {
          type uint32;
          default "5";
          description
            "The number of times to detect MAC duplication, where
             a 'duplicate MAC address' situation has occurred and
             the duplicate MAC address has been added to a list of
             duplicate MAC addresses.";
        }
        leaf retry-timer {
          type uint32;
          units "seconds";
          description
            "The retry timer. When the retry timer expires,
             the duplicate MAC address will be flushed from
             the MAC-VRF.";
        }
        leaf protection-type {
          type identityref {
            base loop-prevention-type;
          }
          description
            "Protection type.";
        }
      }
    }
    container multicast-like {
      if-feature "vpn-common:multicast";
      description
        "Multicast-like container.";
      leaf enabled {
        type boolean;
        default "false";
        description
          "Enables multicast.";
      }
      container customer-tree-flavors {
        description
          "Type of trees used by customer.";
        leaf-list tree-flavor {
          type identityref {
            base vpn-common:multicast-tree-type;
          }
          description
            "Type of multicast tree to be used.";
        }
      }
    }
  }

  /* Main L2NM Container */

  container l2vpn-ntw {
    description
      "Container for the L2NM.";
    container vpn-profiles {
      description
        "Container for VPN profiles.";
      uses vpn-common:vpn-profile-cfg;
    }
    container vpn-services {
      description
        "Container for L2VPN services.";
      list vpn-service {
        key "vpn-id";
        description
          "Container of a VPN service.";
        uses vpn-common:vpn-description;
        leaf parent-service-id {
          type vpn-common:vpn-id;
          description
            "Pointer to the parent service that
             triggered the L2NM.";
        }
        leaf vpn-type {
          type identityref {
            base vpn-common:service-type;
          }
          must "not(derived-from-or-self(current(), "
             + "'vpn-common:l3vpn'))" {
            error-message "L3VPN is only applicable in L3NM.";
          }
          description
            "Service type.";
        }
        leaf vpn-service-topology {
          type identityref {
            base vpn-common:vpn-topology;
          }
          description
            "Defining service topology, such as
             any-to-any, hub-spoke, etc.";
        }
        leaf bgp-ad-enabled {
          type boolean;
          description
            "Indicates whether BGP auto-discovey is enabled
             or disabled.";
        }
        leaf signaling-type {
          type identityref {
            base vpn-common:vpn-signaling-type;
          }
          description
            "VPN signaling type.";
        }
        container global-parameters-profiles {
          description
            "Container for a list of global parameters profiles.";
          list global-parameters-profile {
            key "profile-id";
            description
              "List of global parameters profiles.";
            leaf profile-id {
              type string;
              description
                "The identifier of the global parameters profile.";
            }
            uses vpn-common:route-distinguisher;
            uses vpn-common:vpn-route-targets;
            uses global-parameters-profile;
          }
        }
        container ethernet-segments {
          description
            "Top container for the Ethernet Segment Identifier (ESI).";
          list ethernet-segment {
            key "name";
            description
              "Top list for ESIs.";
            leaf name {
              type string;
              description
                "Includes the name of the Ethernet Segment (ES).";
            }
            leaf esi-type {
              type identityref {
                base esi-type;
              }
              default "esi-type-0";
              description
                "T-(ESI Type) is a 1-octet field (most significant
                 octet) that specifies the format of the remaining
                 9 octets (ESI Value).";
              reference
                "RFC 7432: BGP MPLS-Based Ethernet VPN, Section 5";
            }
            choice esi-choice {
              description
                "Ethernet segment choice between several types.
                 For ESI Type 0: The esi is directly configured by the
                                 operator.
                 For ESI Type 1: The auto-mode must be used.
                 For ESI Type 2: The auto-mode must be used.
                 For ESI Type 3: The directly-assigned or auto-mode must
                                 be used.
                 For ESI Type 4: The directly-assigned or auto-mode must
                                 be used.
                 For ESI Type 5: The directly-assigned or auto-mode must
                                 be used.";
              case directly-assigned {
                description
                  "Explicitly assign an ESI value.";
                leaf ethernet-segment-identifier {
                  type yang:hex-string {
                    length "29";
                  }
                  description
                    "10-octet ESI.";
                }
              }
              case auto-assigned {
                description
                  "The ESI is auto-assigned.";
                container esi-auto {
                  description
                    "The ESI is auto-assigned.";
                  choice auto-mode {
                    description
                      "Indicates the auto-assignment mode. ESI can be
                       automatically assigned either with or without
                       indicating a pool from which the ESI should be
                       taken.

                       For both cases, the server will auto-assign an
                       ESI value 'auto-assigned-ESI' and use that value
                       operationally.";
                    case from-pool {
                      leaf esi-pool-name {
                        type string;
                        description
                          "The auto-assignment will be made from the
                           pool identified by the ESI-pool-name.";
                      }
                    }
                    case full-auto {
                      leaf auto {
                        type empty;
                        description
                          "Indicates an ESI is fully auto-assigned.";
                      }
                    }
                  }
                  leaf auto-ethernet-segment-identifier {
                    type yang:hex-string {
                      length "29";
                    }
                    config false;
                    description
                      "The value of the auto-assigned ESI.";
                  }
                }
              }
            }
            leaf esi-redundancy-mode {
              type identityref {
                base evpn-redundancy-mode;
              }
              description
                "Indicates the EVPN redundancy mode for a multihomed
                 CE.";
              reference
                "RFC 7432: BGP MPLS-Based Ethernet VPN, Section 14.1";
            }
            container df-election {
              description
                "Top container for the DF election method properties.";
              leaf df-election-method {
                type identityref {
                  base df-election-methods;
                }
                default "default-7432";
                description
                  "Specifies the DF election method.";
                reference
                  "RFC 8584: Framework for Ethernet VPN Designated
                             Forwarder Election Extensibility";
              }
              leaf preference {
                when "derived-from-or-self(../df-election-method, "
                   + "'preference')" {
                  description
                    "The preference value is only applicable
                     to the preference based method.";
                }
                type uint16;
                description
                  "Defines a 2-octet value that indicates the PE
                   preference to become the DF in the ES.";
                reference
                  "RFC 8584: Framework for Ethernet VPN Designated
                             Forwarder Election Extensibility";
              }
              leaf revertive {
                when "derived-from-or-self(../df-election-method, "
                   + "'preference')" {
                  description
                    "The revertive value is only applicable
                     to the preference method.";
                }
                type boolean;
                default "true";
                description
                  "The 'preempt' or 'revertive' behavior. This
                   option allows a non-revertive behavior in the
                   DF election.";
                reference
                  "RFC 8584: Framework for Ethernet VPN Designated
                             Forwarder Election Extensibility";
              }
              leaf election-wait-time {
                type uint32;
                description
                  "Election wait timer.";
                reference
                  "RFC 8584: Framework for Ethernet VPN Designated
                             Forwarder Election Extensibility";
              }
            }
            leaf split-horizon-filtering {
              type boolean;
              description
                "Controls split-horizon filtering.

                 In order to achieve split-horizon filtering, every
                 Broadcast, unknown unicast, or multicast (BUM)
                 packet originating from a non-DF PE is encapsulated
                 with an MPLS label that identifies the origin ES.";
              reference
                "RFC 7432: BGP MPLS-Based Ethernet VPN, Section 5";
            }
            container pbb {
              description
                "Provider Backbone Bridging parameters .";
              reference
                "IEEE 802.1ah: Provider Backbone Bridge";
              leaf backbone-src-mac {
                type yang:mac-address;
                description
                  "The PEs connected to the same CE must share the
                   same Provider Backbone (B-MAC) address in
                   All-Active mode.";
                reference
                  "RFC 7623: Provider Backbone Bridging Combined with
                             Ethernet VPN (PBB-EVPN), Section 6.2.1.1";
              }
            }
          }
        }
        container underlay-transport {
          description
            "Container for the underlay transport.";
          uses vpn-common:underlay-transport;
        }
        uses vpn-common:service-status;
        container vpn-nodes {
          description
            "Set of VPN nodes that are involved in the L2NM.";
          list vpn-node {
            key "vpn-node-id";
            description
              "Container of the VPN nodes.";
            leaf vpn-node-id {
              type vpn-common:vpn-id;
              description
                "Sets the indentifier of the VPN node.";
            }
            leaf description {
              type string;
              description
                "Textual description of a VPN node.";
            }
            leaf ne-id {
              type string;
              description
                "Indicates the node's IP address.";
            }
            leaf role {
              type identityref {
                base vpn-common:role;
              }
              default "vpn-common:any-to-any-role";
              description
                "Role of the VPN node in the VPN.";
            }
            leaf router-id {
              type rt-types:router-id;
              description
                "A 32-bit number in the dotted-quad format that is
                 used to uniquely identify a node within an
                 autonomous system (AS). ";
            }
            container active-global-parameters-profiles {
              description
                "Container for a list of global parameters profiles.";
              list global-parameters-profile {
                key "profile-id";
                description
                  "List of active global parameters profiles.";
                leaf profile-id {
                  type leafref {
                    path "/l2vpn-ntw/vpn-services/vpn-service"
                       + "/global-parameters-profiles"
                       + "/global-parameters-profile/profile-id";
                  }
                  description
                    "Points to a global profile defined at the
                     service level.";
                }
                uses global-parameters-profile;
              }
            }
            uses vpn-common:service-status;
            container bgp-auto-discovery {
              when "/l2vpn-ntw/vpn-services/vpn-service"
                 + "/bgp-ad-enabled = 'true'" {
                description
                  "Only applies when BGP auto-discovery is enabled.";
              }
              description
                "BGP is used for auto-discovery.";
              choice bgp-type {
                description
                  "Choice for the BGP type.";
                case l2vpn-bgp {
                  description
                    "Container for BGP L2VPN.";
                  leaf vpn-id {
                    type vpn-common:vpn-id;
                    description
                      "VPN Identifier. This identifier serves to unify
                       components of a given VPN for the sake of
                       auto-discovery.";
                    reference
                      "RFC 6624: Layer 2 Virtual Private Networks Using
                                 BGP for Auto-Discovery and Signaling";
                  }
                }
                case evpn-bgp {
                  when "derived-from-or-self(/l2vpn-ntw/vpn-services"
                     + "/vpn-service/vpn-type, 'vpn-common:vpws-evpn') "
                     + "or derived-from-or-self(/l2vpn-ntw/vpn-services"
                     + "/vpn-service/vpn-type, 'vpn-common:pbb-evpn') "
                     + "or derived-from-or-self(/l2vpn-ntw/vpn-services"
                     + "/vpn-service/vpn-type, 'vpn-common:mpls-evpn') "
                     + "or derived-from-or-self(/l2vpn-ntw/vpn-services"
                     + "/vpn-service/vpn-type, "
                     + "'vpn-common:vxlan-evpn')" {
                    description
                      "Can only be used when EVPN is used.";
                  }
                  description
                    "Container for MP-BGP L2VPN.";
                  leaf evpn-type {
                    type identityref {
                      base evpn-type;
                    }
                    description
                      "EVPN type.";
                  }
                  leaf auto-rt-enable {
                    type boolean;
                    default "false";
                    description
                      "Enables/disabled RT auto-derivation based on
                       the ASN and Ethernet Tag ID.";
                    reference
                      "RFC 7432: BGP MPLS-Based Ethernet VPN,
                                 Section 7.10.1";
                  }
                  leaf auto-route-target {
                    when "../auto-rt-enable = 'true'" {
                      description
                        "Can only be used when auto-RD is enabled.";
                    }
                    type rt-types:route-target;
                    config false;
                    description
                      "The value of the auto-assigned RT.";
                  }
                }
              }
              uses vpn-common:route-distinguisher;
              uses vpn-common:vpn-route-targets;
            }
            container signaling-option {
              description
                "Container for the L2VPN signaling.";
              leaf mtu-pw {
                type uint16;
                description
                  "Sets the PW MTU.";
              }
              leaf mtu-allow-mismatch {
                type boolean;
                description
                  "When set to true, it allows MTU mismatch.";
                reference
                  "RFC 4667: Layer 2 Virtual Private Network (L2VPN)
                             Extensions for Layer 2 Tunneling
                             Protocol (L2TP), Section 4.3";
              }
              leaf type {
                type leafref {
                  path "/l2vpn-ntw/vpn-services/vpn-service"
                     + "/signaling-type";
                }
                description
                  "VPN signaling type.";
              }
              choice signaling-option {
                description
                  "Choice for the signaling-option.";
                case bgp {
                  when "derived-from-or-self(./type, "
                     + "'vpn-common:bgp-signaling')" {
                    description
                      "Only applies when VPN signaling type is BGP.";
                  }
                  description
                    "BGP is used as the signaling protocol.";
                  choice bgp-type {
                    description
                      "Choice for the BGP type.";
                    case l2vpn-bgp {
                      description
                        "Container for BGP L2VPN.";
                      leaf ce-id {
                        type uint16;
                        description
                          "The PE must know the set of virtual circuits
                           connecting it to the CE and a CE ID
                           identifying the CE within the VPN.";
                        reference
                          "RFC 6624: Layer 2 Virtual Private Networks
                                     Using BGP for Auto-Discovery and
                                     Signaling";
                      }
                      leaf ce-range {
                        type uint16;
                        description
                          "Determines the number of remote CEs with
                           which a given CE can communicate in the
                            contex of a VPN.";
                        reference
                          "RFC 6624: Layer 2 Virtual Private Networks
                                     Using BGP for Auto-Discovery and
                                     Signaling";
                      }
                      leaf pw-encapsulation-type {
                        type identityref {
                          base iana-bgp-l2-encaps:bgp-l2-encaps-type;
                        }
                        description
                          "PW encapsulation type.";
                      }
                      container vpls-instance {
                        when "derived-from-or-self(/l2vpn-ntw"
                           + "/vpn-services/vpn-service/vpn-type, "
                           + "'vpn-common:vpls')" {
                          description
                            "Only applies for VPLS.";
                        }
                        description
                          "VPLS instance.";
                        leaf vpls-edge-id {
                          type uint16;
                          description
                            "VPLS Edge Identifier (VE ID). VE ID";
                          reference
                            "RFC 4761: Virtual Private LAN Service
                                       (VPLS) Using BGP for Auto-
                                       Discovery and Signaling";
                        }
                        leaf vpls-edge-id-range {
                          type uint16;
                          description
                            "Specifies the size of the range of VE ID in
                             a VPLS service. The range controls the size
                             of the label block advertised in the
                             context of a VPLS instance.";
                          reference
                            "RFC 4761: Virtual Private LAN Service
                                       (VPLS) Using BGP for Auto-
                                       Discovery and Signaling";
                        }
                      }
                    }
                    case evpn-bgp {
                      description
                        "Container for MP BGP L2VPN.";
                      leaf evpn-type {
                        type leafref {
                          path "/l2vpn-ntw/vpn-services/vpn-service"
                             + "/vpn-nodes/vpn-node/bgp-auto-discovery"
                             + "/evpn-type";
                        }
                        description
                          "EVPN type.";
                      }
                      leaf service-interface-type {
                        type identityref {
                          base evpn-service-type;
                        }
                        description
                          "EVPN service interface type.";
                      }
                      container evpn-policies {
                        description
                          "Includes a set of EVPN policies such as those
                           related to handling MAC addresses.";
                        leaf mac-learning-mode {
                          type identityref {
                            base mac-learning-mode;
                          }
                          description
                            "Indicates through which plane MAC addresses
                             are advertised.";
                        }
                        leaf ingress-replication {
                          type boolean;
                          description
                            "Controles whether ingress replication is
                             enabled/disabled.";
                          reference
                            "RFC 7432: BGP MPLS-Based Ethernet VPN,
                                       Section 8.3.1.1";
                        }
                        leaf p2mp-replication {
                          type boolean;
                          description
                            "Controles whether P2MP replication is
                             enabled/disabled.";
                          reference
                            "RFC 7432: BGP MPLS-Based Ethernet VPN,
                                       Section 8.3.1.2";
                        }
                        container arp-proxy {
                          if-feature "vpn-common:ipv4";
                          description
                            "Top container for the ARP Proxy";
                          leaf enable {
                            type boolean;
                            default "false";
                            description
                              "Enables (when set to 'true') or disables
                                (when set to 'false') ARP proxy.";
                          }
                          leaf arp-suppression {
                            type boolean;
                            default "false";
                            description
                              "Enables (when set to 'true') or disables
                               (when set to 'false') ARP suppression.";
                            reference
                              "RFC 7432: BGP MPLS-Based Ethernet VPN";
                          }
                          leaf ip-mobility-threshold {
                            type uint16;
                            description
                              "Enable (TRUE) or disable (FALSE). It is
                               possible for a given host or end-station
                               (as defined by its IP address) to move
                               from one Ethernet segment to another. The
                               number of IP mobility events that
                               are detected for a given IP address
                               within the detection-threshold before it
                               is identified as a duplicate IP address.
                               Once the detection threshold is reached,
                               updates for the IP address are
                               suppressed.";
                          }
                          leaf duplicate-ip-detection-interval {
                            type uint16;
                            description
                              "The time interval used in detecting a
                               duplicate IP address. Duplicate IP
                               address detection number of host moves
                               allowed within interval period";
                          }
                        }
                        container nd-proxy {
                          if-feature "vpn-common:ipv6";
                          description
                            "Top container for the ND Proxy";
                          leaf enable {
                            type boolean;
                            default "false";
                            description
                              "Enables (when set to 'true') or disables
                               (when set to 'false') ND proxy. If true
                               the NDP queries for an IP address that
                               is not on that network are suppressed.
                               NDP suppression is a technique that is
                               used to reduce the amount of NDP packets
                               flooding within individual segments,
                               that is between hosts connected to the
                               same logical switch.";
                          }
                          leaf nd-suppression {
                            type boolean;
                            default "false";
                            description
                              "Enables (when set to 'true') or disables
                               (when set to 'false') ND suppression.";
                          }
                          leaf ip-mobility-threshold {
                            type uint16;
                            description
                              "Enable (TRUE) or disable (FALSE). It is
                               possible for a given host or end-station
                               (as defined by its IP address) to move
                               from one ES to another. The number of IP
                               address mobility events that are detected
                               for a  given IP address within the
                               detection-threshold before it is
                               identified as a duplicate IP address.
                               Once the detection threshold is reached,
                               updates for the IP address are
                               suppressed.";
                          }
                          leaf duplicate-ip-detection-interval {
                            type uint16;
                            description
                              "The time interval used in detecting a
                               duplicate IP address. Duplicate IP
                               address detection number of host
                               moves allowed within interval period";
                          }
                        }
                        leaf underlay-multicast {
                          type boolean;
                          default "false";
                          description
                            "Enables (when set to 'true') or disables
                             (when set to 'false') underlay multicast.";
                        }
                        leaf flood-unknown-unicast-supression {
                          type boolean;
                          default "false";
                          description
                            "Enables (when set to 'true') or disables
                             (when set to 'false') unknown flood unicast
                             suppression.";
                        }
                        leaf vpws-vlan-aware {
                          type boolean;
                          default "false";
                          description
                            "Enables (when set to 'true') or disables
                             (when set to 'false') VPWS VLAN-aware.";
                        }
                        container bum-management {
                          description
                            "broadcast-unknown-unicast-multicast
                             management";
                          leaf discard-broadcast {
                            type boolean;
                            description
                              "Discards broadcast, when enabled.";
                          }
                          leaf discard-unknown-multicast {
                            type boolean;
                            description
                              "Discards unknown multicast, when
                               enabled.";
                          }
                          leaf discard-unknown-unicast {
                            type boolean;
                            description
                              "Discards unknown unicast, when enabled.";
                          }
                        }
                        container pbb {
                          when "derived-from-or-self(../../evpn-type,"
                             + " 'evpn-pbb')" {
                            description
                              "Only applies for PBB EVPN.";
                          }
                          description
                            "PBB parameters container.";
                          reference
                            "IEEE 802.1ah: Provider Backbone Bridge";
                          leaf backbone-src-mac {
                            type yang:mac-address;
                            description
                              "Includes provider backbone MAC (B-MAC)
                               address.";
                            reference
                              "RFC 7623: Provider Backbone Bridging
                                         Combined with Ethernet VPN
                                         (PBB-EVPN), Section 8.1";
                          }
                        }
                      }
                    }
                  }
                }
                container ldp-or-l2tp {
                  description
                    "Container of LDP or L2TP-signaled PWs";
                  leaf agi {
                    type rt-types:route-distinguisher;
                    description
                      "Attachment Group Identifier. Also, called
                       VPLS-Id.";
                    reference
                      "RFC 4667: Layer 2 Virtual Private Network (L2VPN)
                                 Extensions for Layer 2 Tunneling
                                 Protocol (L2TP), Section 4.3
                       RFC 4762: Virtual Private LAN Service (VPLS)
                                 Using Label Distribution Protocol (LDP)
                                 Signaling, Section 6.1.1";
                  }
                  leaf saii {
                    type uint32;
                    description
                      "Source Attachment Individual Identifier.";
                    reference
                      "RFC 4667: Layer 2 Virtual Private Network (L2VPN)
                                 Extensions for Layer 2 Tunneling
                                 Protocol (L2TP), Section 3";
                  }
                  list remote-targets {
                    key "taii";
                    description
                      "List of allowed target AII and peers.";
                    reference
                      "RFC 4667: Layer 2 Virtual Private Network (L2VPN)
                                 Extensions for Layer 2 Tunneling
                                 Protocol (L2TP), Section 5";
                    leaf taii {
                      type uint32;
                      description
                        "Target Attachment Individual Identifier.";
                      reference
                        "RFC 4667: Layer 2 Virtual Private Network
                                   (L2VPN) Extensions for Layer 2
                                   Tunneling  Protocol (L2TP),
                                   Section 3";
                    }
                    leaf peer-addr {
                      type inet:ip-address;
                      description
                        "Indicates the peer forwarder's IP address.";
                    }
                  }
                  choice ldp-or-l2tp {
                    description
                      "Choice of LDP or L2TP-signaled PWs";
                    case ldp {
                      when "derived-from-or-self(../type, "
                         + "'vpn-common:ldp-signaling')" {
                        description
                          "Only applies when VPN signaling type is Target
                           LDP.";
                      }
                      description
                        "Container of T-LDP PW configurations";
                      leaf t-ldp-pw-type {
                        type identityref {
                          base t-ldp-pw-type;
                        }
                        description
                          "T-LDP PW type.";
                      }
                      leaf pw-type {
                        type identityref {
                          base pw-type;
                        }
                        description
                          "PW encapsulation type.";
                        reference
                          "RFC 4762: Virtual Private LAN Service (VPLS)
                                     Using Label Distribution Protocol (LDP)
                                     Signaling, Section 6.1.1";
                      }
                      leaf pw-description {
                        type string;
                        description
                          "Includes an interface description used to send
                           a human-readable administrative string describing
                           the interface to the remote.";
                        reference
                          "RFC 4762: Virtual Private LAN Service (VPLS)
                                     Using Label Distribution Protocol (LDP)
                                     Signaling, Section 6.1.1";
                      }
                      leaf mac-addr-withdraw {
                        type boolean;
                        description
                          "If set to 'true', then MAC address withdrawal
                           is enabled.  If 'false', then MAC address
                           withdrawal is disabled.";
                        reference
                          "RFC 4762: Virtual Private LAN Service (VPLS)
                                     Using Label Distribution Protocol (LDP)
                                     Signaling, Section 6.2";
                      }
                      list ac-pw-list {
                        key "peer-addr vc-id";
                        description
                          "List of AC and PW bindings.";
                        leaf peer-addr {
                          type inet:ip-address;
                          description
                            "Indicates the peer's IP address.";
                        }
                        leaf vc-id {
                          type vpn-common:vpn-id;
                          description
                            "VC label used to identify a PW.";
                        }
                        leaf pw-priority {
                          type uint32;
                          description
                            "Defines the priority for the PW.
                             The higher the pw-priority value,
                             the higher the preference of the PW will be.";
                        }
                      }
                      container qinq {
                        when "derived-from-or-self(../t-ldp-pw-type, "
                           + "'hvpls')" {
                          description
                            "Only applies when t-ldp pw type is h-vpls.";
                        }
                        description
                          "Container for QinQ.";
                        leaf s-tag {
                          type uint32;
                          description
                            "S-TAG.";
                        }
                        leaf c-tag {
                          type uint32;
                          description
                            "C-TAG.";
                        }
                      }
                    }
                    case l2tp {
                      when "derived-from-or-self(../type, "
                         + "'vpn-common:l2tp-signaling')" {
                        description
                          "Applies when VPN signaling type is L2TP.";
                      }
                      description
                        "Container for L2TP PWs.";
                      leaf router-id {
                        type rt-types:router-id;
                        description
                          "A 32-bit number in the dotted-quad format that is
                           used to uniquely identify a node within an
                           autonomous system.";
                        reference
                          "RFC 4667: Layer 2 Virtual Private Network (L2VPN)
                                     Extensions for Layer 2 Tunneling
                                     Protocol (L2TP), Section 4.2";
                      }
                      leaf pseudowire-type {
                        type identityref {
                          base iana-pw-types:iana-pw-types;
                        }
                        description
                          "Encapsulation type.";
                        reference
                          "RFC 4667: Layer 2 Virtual Private Network (L2VPN)
                                     Extensions for Layer 2 Tunneling
                                     Protocol (L2TP), Section 4.2";
                      }
                    }
                  }
                }
              }
            }
            container vpn-network-accesses {
              description
                "List of VPN Nodes.";
              list vpn-network-access {
                key "id";
                description
                  "List of VPN Network Accesses.";
                leaf id {
                  type vpn-common:vpn-id;
                  description
                    "Identifier of network access";
                }
                leaf description {
                  type string;
                  description
                    "String to describe the element.";
                }
                leaf port-id {
                  type vpn-common:vpn-id;
                  description
                    "NE Port-id";
                }
                leaf global-parameters-profile {
                  type leafref {
                    path "/l2vpn-ntw/vpn-services/vpn-service/vpn-nodes"
                       + "/vpn-node/active-global-parameters-profiles"
                       + "/global-parameters-profile/profile-id";
                  }
                  description
                    "An identifier of an active VPN instance profile.";
                }
                uses vpn-common:service-status;
                container connection {
                  description
                    "Container for bearer and AC.";
                  leaf l2-termination-point {
                    type vpn-common:vpn-id;
                    description
                      "Specifies a reference to a local layer 2
                       termination point such as a layer 2
                       sub-interface.";
                  }
                  leaf local-bridge-reference {
                    type vpn-common:vpn-id;
                    description
                      "Specifies a local bridge reference to
                       accommodate, for example, implementations
                       that require internal bridging.
                       A reference may be a local bridge domain.";
                  }
                  leaf bearer-reference {
                    if-feature "vpn-common:bearer-reference";
                    type string;
                    description
                      "This is an internal reference for the service
                       provider to identify the bearer associated
                       with this VPN.";
                  }
                  container encapsulation {
                    description
                      "Container for layer 2 encapsulation.";
                    leaf type {
                      type identityref {
                        base vpn-common:encapsulation-type;
                      }
                      default "vpn-common:priority-tagged";
                      description
                        "Tagged interface type. By default, the type of
                         the tagged interface is 'priority-tagged'.";
                    }
                    container dot1q {
                      when "derived-from-or-self(../type, "
                         + "'vpn-common:dot1q')" {
                        description
                          "Only applies when the type of the
                           tagged interface is 'dot1q'.";
                      }
                      if-feature "vpn-common:dot1q";
                      description
                        "Tagged interface.";
                      leaf tag-type {
                        type identityref {
                          base vpn-common:tag-type;
                        }
                        default "vpn-common:c-vlan";
                        description
                          "Tag type. By default, the tag type is
                           'c-vlan'.";
                      }
                      leaf cvlan-id {
                        type uint16;
                        description
                          "VLAN identifier.";
                      }
                      container rewrite {
                        description
                          "Sets the tag rewriting policy for this
                           'vpn-network-accesses'. Enables the
                           manipulation of the layer-2 frame header for
                           data frames as they are processed on the
                           'vpn-network-access'.";
                        choice tag-choice {
                          description
                            "Selects the tag rewriting policy for a VPN
                             network access. It defines a set of
                             standard tag manipulations that allow for
                             the insertion, removal, or rewriting of one
                             or two 802.1Q VLAN tags.";
                          leaf pop {
                            type enumeration {
                              enum 1 {
                                description
                                  "Allows one (1) tag removal.";
                              }
                              enum 2 {
                                description
                                  "Allows two (2) tags removal.";
                              }
                            }
                            description
                              "Standard tag removal.
                               The number of 802.1Q VLAN tags to pop.";
                          }
                          leaf push {
                            type empty;
                            description
                              "Standard tag Push.
                               The number of 802.1Q tags to push on the
                               front of the frame.";
                          }
                          leaf translate {
                            type enumeration {
                              enum 1-to-1 {
                                description
                                  "Allows one (1) to one (1) tag
                                   translation.";
                              }
                              enum 1-to-2 {
                                description
                                  "Allows one (1) to two (2) tags
                                   translation.";
                              }
                              enum 2-to-1 {
                                description
                                  "Allows two (2) to one (1) tag
                                   translation.";
                              }
                              enum 2-to-2 {
                                description
                                  "Allows two (2) to two (2) tags
                                   translation.";
                              }
                            }
                            description
                              "Replaces tags with other tags.
                               Translate operations are expressed as
                               as a combination of tag push and pop
                               operations. For example, translating the
                               outer tag is expressed as popping a
                               single tag.";
                          }
                        }
                        leaf cvlan-id {
                          when 'not(../pop)';
                          type uint16;
                          description
                            "Push/Translate vlan tags";
                        }
                        leaf direction {
                          type enumeration {
                            enum symmetric {
                              description
                                "TAGs operation is performed in a
                                 symetric way.

                                 The operation is performed on the
                                 outbound traffic on an interface, then
                                 the reverse operation is performed on
                                 the inbound traffic out of the
                                 same interface.";
                            }
                          }
                          description
                            "Indicates the direction.";
                        }
                      }
                    }
                    container priority-tagged {
                      when "derived-from-or-self(../type, "
                         + "'vpn-common:priority-tagged')" {
                        description
                          "Only applies when the type of the
                           tagged interface is 'priority-tagged'.";
                      }
                      description
                        "Priority tagged.";
                      leaf tag-type {
                        type identityref {
                          base vpn-common:tag-type;
                        }
                        default "vpn-common:c-vlan";
                        description
                          "Tag type. By default, the tag type is
                           'c-vlan'.";
                      }
                    }
                    container qinq {
                      when "derived-from-or-self(../type, "
                         + "'vpn-common:qinq')" {
                        description
                          "Only applies when the type of the tagged
                           interface is QinQ.";
                      }
                      if-feature "vpn-common:qinq";
                      description
                        "Includes QinQ parameters.";
                      leaf tag-type {
                        type identityref {
                          base vpn-common:tag-type;
                        }
                        default "vpn-common:c-s-vlan";
                        description
                          "Tag type. By default, the tag type is
                           'c-s-vlan'.";
                      }
                      leaf svlan-id {
                        type uint16;
                        mandatory true;
                        description
                          "SVLAN identifier.";
                      }
                      leaf cvlan-id {
                        type uint16;
                        mandatory true;
                        description
                          "CVLAN identifier.";
                      }
                    }
                  }
                  container lag-interface {
                    if-feature "vpn-common:lag-interface";
                    description
                      "Container of LAG interface attributes
                       configuration";
                    list lag-interface {
                      key "lag-interface-number";
                      description
                        "List of LAG interfaces";
                      leaf lag-interface-number {
                        type uint32;
                        description
                          "LAG interface number";
                      }
                      container lacp {
                        description
                          "LACP";
                        leaf lacp-state {
                          type boolean;
                          description
                            "LACP on/off";
                        }
                        leaf lacp-mode {
                          type boolean;
                          description
                            "LACP mode";
                        }
                        leaf lacp-speed {
                          type boolean;
                          description
                            "LACP speed";
                        }
                        leaf mini-link {
                          type uint32;
                          description
                            "The minimum aggregate bandwidth for a
                             LAG";
                        }
                        leaf system-id {
                          type yang:mac-address;
                          description
                            "Indicates the System ID used by LACP.";
                        }
                        leaf admin-key {
                          type uint16;
                          description
                            "Indicates the value of the key used for the
                             aggregate interface.";
                        }
                        leaf system-priority {
                          type uint16 {
                            range "0..65535";
                          }
                          default "32768";
                          description
                            "Indicates the LACP priority for the
                             system.";
                        }
                        container member-link-list {
                          description
                            "Container of Member link list";
                          list member-link {
                            key "name";
                            description
                              "Member link";
                            leaf name {
                              type string;
                              description
                                "Member link name";
                            }
                            leaf port-speed {
                              type uint32;
                              description
                                "Port speed";
                            }
                            leaf mode {
                              type identityref {
                                base vpn-common:neg-mode;
                              }
                              description
                                "Negotiation mode";
                            }
                            leaf link-mtu {
                              type uint32;
                              description
                                "Link MTU size.";
                            }
                            container oam-802.3ah-link {
                              if-feature "oam-3ah";
                              description
                                "Container for oam 802.3 ah link.";
                              leaf enable {
                                type boolean;
                                description
                                  "Indicate whether support OAM 802.3 ah
                                   link.";
                              }
                            }
                          }
                        }
                        leaf flow-control {
                          type string;
                          description
                            "Flow control";
                        }
                        leaf lldp {
                          type boolean;
                          description
                            "LLDP";
                        }
                      }
                    }
                    container split-horizon {
                      description
                        "Configuration with split horizon enabled";
                      leaf group-name {
                        type string;
                        description
                          "group-name of the Split Horizon";
                      }
                    }
                  }
                }
                container vpws-service-instance {
                  when "derived-from-or-self(/l2vpn-ntw/vpn-services"
                     + "/vpn-service/vpn-nodes/vpn-node"
                     + "/bgp-auto-discovery/evpn-type, "
                     + "'evpn-vpws')" {
                    description
                      "Only applies for EVPN-VPWS.";
                  }
                  description
                    "Local and remote VPWS Service Instance (VSI)";
                  reference
                    "RFC 8214: Virtual Private Wire Service Support
                               in Ethernet VPN";
                  choice local-vsi-choice {
                    description
                      "Choices for assigning local VSI.";
                    case directly-assigned {
                      description
                        "Explicitly assign a local VSI.";
                      leaf local-vpws-service-instance {
                        type uint32 {
                          range "1..16777215";
                        }
                        description
                          "Indicates the assigned local VSI.";
                      }
                    }
                    case auto-assigned {
                      description
                        "The local VSI is auto-assigned.";
                      container local-vsi-auto {
                        description
                          "The local VSI is auto-assigned.";
                        choice auto-mode {
                          description
                            "Indicates the auto-assignment mode of
                             local VSI. VSI can be automatically
                             assigned either with or without
                             indicating a pool from which the VSI
                             should be taken.

                             For both cases, the server will
                             auto-assign a local VSI value and use
                             that value.";
                          case from-pool {
                            leaf vsi-pool-name {
                              type string;
                              description
                                "The auto-assignment will be made
                                 from this pool.";
                            }
                          }
                          case full-auto {
                            leaf auto {
                              type empty;
                              description
                                "Indicates that a local VSI is
                                 fully auto-assigned.";
                            }
                          }
                        }
                        leaf auto-local-vsi {
                          type uint32 {
                            range "1..16777215";
                          }
                          config false;
                          description
                            "The value of the auto-assigned local
                             VSI.";
                        }
                      }
                    }
                  }
                  choice remote-vsi-choice {
                    description
                      "Choice for assigning the remote VSI.";
                    case directly-assigned {
                      description
                        "Explicitly assign a remote VSI.";
                      leaf remote-vpws-service-instance {
                        type uint32 {
                          range "1..16777215";
                        }
                        description
                          "Indicates the value of the remote
                           VSI.";
                      }
                    }
                    case auto-assigned {
                      description
                        "The remote VSI is auto-assigned.";
                      container remote-vsi-auto {
                        description
                          "The remote VSI is auto-assigned.";
                        choice auto-mode {
                          description
                            "Indicates the auto-assignment mode
                             of remote VSI. VSI can be
                             automatically assigned either withor
                             without indicating a pool from which
                             the VSI should be taken.

                             For both cases, the server will
                             auto-assign a remote VSI value and use
                             that value.";
                          case from-pool {
                            leaf vsi-pool-name {
                              type string;
                              description
                                "The auto-assignment will be made
                                 from this pool.";
                            }
                          }
                          case full-auto {
                            leaf auto {
                              type empty;
                              description
                                "Indicates that a remote VSI is fully
                                 auto-assigned.";
                            }
                          }
                        }
                        leaf auto-remote-vsi {
                          type uint32 {
                            range "1..16777215";
                          }
                          config false;
                          description
                            "The value of the auto-assigned remote
                             VSI.";
                        }
                      }
                    }
                  }
                }
                list group {
                  key "group-id";
                  description
                    "List of group-ids.";
                  leaf group-id {
                    type string;
                    description
                      "Indicates the group-id to which the network
                       access belongs to.";
                  }
                  leaf group-color {
                    type string;
                    description
                      "Group color associated with a particular VPN.";
                  }
                  leaf precedence {
                    type identityref {
                      base precedence-type;
                    }
                    description
                      "Defining service redundancy in transport
                       network.";
                  }
                  leaf ethernet-segment-identifier {
                    type leafref {
                      path "/l2vpn-ntw/vpn-services/vpn-service"
                         + "/ethernet-segments/ethernet-segment/name";
                    }
                    description
                      "Reference to the ESI associated to the VPN
                       network access.";
                  }
                }
                container ethernet-service-oam {
                  description
                    "Container for Ethernet service OAM.";
                  leaf md-name {
                    type string;
                    description
                      "Maintenance domain name.";
                  }
                  leaf md-level {
                    type uint8;
                    description
                      "Maintenance domain level.";
                  }
                  container cfm-802.1-ag {
                    description
                      "Container of 802.1ag CFM configurations.";
                    list n2-uni-c {
                      key "maid";
                      description
                        "List of UNI-N to UNI-C.";
                      uses cfm-802-grouping;
                    }
                    list n2-uni-n {
                      key "maid";
                      description
                        "List of UNI-N to UNI-N.";
                      uses cfm-802-grouping;
                    }
                  }
                  uses y-1731;
                }
                container service {
                  description
                    "Container for service";
                  leaf mtu {
                    type uint32;
                    description
                      "MTU, it is also known as the maximum
                       transmission unit or maximum frame size. When a
                       frame is larger than the MTU, it is broken down,
                       or fragmented, into smaller pieces by the
                       network protocol to accommodate the MTU of the
                       network";
                  }
                  container svc-input-bandwidth {
                    if-feature "vpn-common:input-bw";
                    description
                      "From the PE perspective, the service input
                       bandwidth of the connection.";
                    list input-bandwidth {
                      key "type";
                      description
                        "List for input bandwidth data nodes.";
                      leaf type {
                        type identityref {
                          base vpn-common:bw-type;
                        }
                        description
                          "Indicates the bandwidth type.";
                      }
                      leaf cos-id {
                        if-feature "vpn-common:qos";
                        type uint8;
                        description
                          "Identifier of the Class of Service (CoS),
                           indicated by DSCP or a CE-CLAN
                           CoS (802.1p) value in the service frame.";
                      }
                      leaf cir {
                        type uint64;
                        description
                          "Committed Information Rate. The maximum
                           number of bits that a port can receive or
                           send during one-second over an interface.";
                      }
                      leaf cbs {
                        type uint64;
                        description
                          "Committed Burst Size. CBS controls the bursty
                           nature of the traffic. Traffic that does not
                           use the configured CIR accumulates credits
                           until the credits reach the configured CBS.";
                      }
                      leaf eir {
                        type uint64;
                        description
                          "Excess Information Rate, i.e., excess frame
                           delivery allowed not subject to SLA. The
                           traffic rate can be limited by EIR.";
                      }
                      leaf ebs {
                        type uint64;
                        description
                          "Excess Burst Size. The bandwidth available
                           for burst traffic from the EBS is subject to
                           the amount of bandwidth that is accumulated
                           during periods when traffic allocated by the
                           EIR policy is not used.";
                      }
                      leaf pir {
                        type uint64;
                        description
                          "Peak Information Rate, i.e., maixmum frame
                           delivery allowed. It is equal to or less
                           than sum of CIR and EIR.";
                      }
                      leaf pbs {
                        type uint64;
                        units "bytes per second";
                        description
                          "Peak Burst Size.";
                      }
                    }
                  }
                  container svc-output-bandwidth {
                    if-feature "vpn-common:output-bw";
                    description
                      "From the PE perspective, the service output
                       bandwidth of the connection.";
                    list output-bandwidth {
                      key "type";
                      description
                        "List for output bandwidth";
                      leaf type {
                        type identityref {
                          base vpn-common:bw-type;
                        }
                        description
                          "Bandwidth Type";
                      }
                      leaf cos-id {
                        if-feature "vpn-common:qos";
                        type uint8;
                        description
                          "Identifier of the CoS, indicated by
                           DSCP or a CE-CLAN CoS (802.1p) value in
                           the service frame.";
                      }
                      leaf cir {
                        type uint64;
                        description
                          "Committed Information Rate. The maximum
                           number of bits that a port can receive or
                           send during one-second over an interface.";
                      }
                      leaf cbs {
                        type uint64;
                        description
                          "Committed Burst Size. CBS controls the bursty
                           nature of the traffic. Traffic that does not
                           use the configured CIR accumulates credits
                           until the credits reach the configured CBS.";
                      }
                      leaf eir {
                        type uint64;
                        description
                          "Excess Information Rate, i.e., excess frame
                           delivery allowed not subject to SLA. The
                           traffic rate can be limited by EIR.";
                      }
                      leaf ebs {
                        type uint64;
                        description
                          "Excess Burst Size. The bandwidth available
                           for burst traffic from the EBS is subject to
                           the amount of bandwidth that is accumulated
                           during periods when traffic allocated by the
                           EIR policy is not used.";
                      }
                      leaf pir {
                        type uint64;
                        description
                          "Peak Information Rate, i.e., maixmum frame
                           delivery allowed. It is equal to or less than
                           sum of CIR and EIR.";
                      }
                      leaf pbs {
                        type uint64;
                        units "bytes per second";
                        description
                          "Peak Burst Size.";
                      }
                    }
                  }
                  container qos {
                    if-feature "vpn-common:qos";
                    description
                      "QoS configuration.";
                    container qos-classification-policy {
                      description
                        "Configuration of the traffic classification
                         policy.";
                      list rule {
                        key "id";
                        ordered-by user;
                        description
                          "List of classification rules.";
                        leaf id {
                          type string;
                          description
                            "A description identifying the QoS
                             classification policy rule.";
                        }
                        choice match-type {
                          default "match-flow";
                          description
                            "Choice for classification.";
                          case match-flow {
                            container match-flow {
                              description
                                "Describes flow-matching criteria.";
                              leaf dscp {
                                type inet:dscp;
                                description
                                  "DSCP value.";
                              }
                              leaf dot1q {
                                type uint16;
                                description
                                  "802.1Q matching. It is a VLAN tag
                                   added into a frame.";
                              }
                              leaf pcp {
                                type uint8 {
                                  range "0..7";
                                }
                                description
                                  "PCP value.";
                              }
                              leaf src-mac-address {
                                type yang:mac-address;
                                description
                                  "Source MAC address.";
                              }
                              leaf dst-mac-address {
                                type yang:mac-address;
                                description
                                  "Destination MAC address.";
                              }
                              leaf color-type {
                                type identityref {
                                  base color-type;
                                }
                                description
                                  "Color type.";
                              }
                              leaf any {
                                type empty;
                                description
                                  "Allows all.";
                              }
                            }
                          }
                          case match-application {
                            leaf match-application {
                              type identityref {
                                base vpn-common:customer-application;
                              }
                              description
                                "Defines the application to match.";
                            }
                          }
                        }
                        leaf target-class-id {
                          type string;
                          description
                            "Identification of the CoS.
                             This identifier is internal to the
                             administration.";
                        }
                      }
                    }
                    container qos-profile {
                      description
                        "QoS profile configuration.";
                      list qos-profile {
                        key "profile";
                        description
                          "QoS profile.
                           Can be standard profile or customized
                           profile.";
                        leaf profile {
                          type leafref {
                            path "/l2vpn-ntw/vpn-profiles"
                               + "/valid-provider-identifiers"
                               + "/qos-profile-identifier/id";
                          }
                          description
                            "QoS profile to be used.";
                        }
                        leaf direction {
                          type identityref {
                            base vpn-common:qos-profile-direction;
                          }
                          default "vpn-common:both";
                          description
                            "The direction to which the QoS profile
                             is applied.";
                        }
                      }
                    }
                  }
                  container mac-policies {
                    description
                      "Container for MAC-related policies.";
                    list access-control-list {
                      key "name";
                      description
                        "Container for access control List.";
                      leaf name {
                        type string;
                        description
                          "Specifies the name of the ACL.";
                      }
                      leaf-list src-mac-address {
                        type yang:mac-address;
                        description
                          "Specifies the source MAC address.";
                      }
                      leaf-list src-mac-address-mask {
                        type yang:mac-address;
                        description
                          "Specifies the source MAC address mask.";
                      }
                      leaf-list dst-mac-address {
                        type yang:mac-address;
                        description
                          "Specifies the destination MAC address.";
                      }
                      leaf-list dst-mac-address-mask {
                        type yang:mac-address;
                        description
                          "Specifies the destination MAC address mask.";
                      }
                      leaf action {
                        type identityref {
                          base mac-action;
                        }
                        default "drop";
                        description
                          "Specifies the filtering action.";
                      }
                      leaf rate-limit {
                        when "derived-from-or-self(../action, 'flood')" {
                          description
                            "Rate-limit is valid only when the action is
                             to accept the matching frame.";
                        }
                        type decimal64 {
                          fraction-digits 2;
                        }
                        units "bytes per second";
                        description
                          "Specifies how to rate-limit the traffic.";
                      }
                    }
                    container mac-loop-prevention {
                      description
                        "Container of MAC loop prevention.";
                      leaf window {
                        type uint32;
                        units "seconds";
                        default "180";
                        description
                          "The timer when a MAC mobility event is
                           detected.";
                      }
                      leaf frequency {
                        type uint32;
                        default "5";
                        description
                          "The number of times to detect MAC
                           duplication, where a 'duplicate MAC address'
                           situation has occurred and the duplicate MAC
                           address has been added to a list of duplicate
                           MAC addresses.";
                      }
                      leaf retry-timer {
                        type uint32;
                        units "seconds";
                        description
                          "The retry timer. When the retry timer
                           expires, the duplicate MAC address will be
                           flushed from the MAC-VRF.";
                      }
                      leaf protection-type {
                        type identityref {
                          base loop-prevention-type;
                        }
                        description
                          "Protection type";
                      }
                    }
                    container mac-addr-limit {
                      description
                        "Container of MAC-Addr limit configurations";
                      leaf mac-num-limit {
                        type uint16;
                        description
                          "maximum number of MAC addresses learned from
                           the subscriber for a single service
                           instance.";
                      }
                      leaf time-interval {
                        type uint32;
                        units "milliseconds";
                        description
                          "The aging time of the mac address.";
                      }
                      leaf action {
                        type identityref {
                          base mac-action;
                        }
                        description
                          "specify the action when the upper limit is
                           exceeded: drop the packet, flood the
                           packet, or simply send a warning log
                           message.";
                      }
                    }
                  }
                  container broadcast-unknown-unicast-multicast {
                    description
                      "Container of broadcast, unknown unicast, and
                       multicast configurations";
                    leaf multicast-site-type {
                      type enumeration {
                        enum receiver-only {
                          description
                            "The site only has receivers.";
                        }
                        enum source-only {
                          description
                            "The site only has sources.";
                        }
                        enum source-receiver {
                          description
                            "The site has both sources and receivers.";
                        }
                      }
                      default "source-receiver";
                      description
                        "Type of multicast site.";
                    }
                    list multicast-gp-address-mapping {
                      key "id";
                      description
                        "List of Port to group mappings.";
                      leaf id {
                        type uint16;
                        description
                          "Unique identifier for the mapping.";
                      }
                      leaf vlan-id {
                        type uint32;
                        description
                          "The VLAN ID of the Multicast group.";
                      }
                      leaf mac-gp-address {
                        type yang:mac-address;
                        description
                          "The MAC address of the Multicast group.";
                      }
                      leaf port-lag-number {
                        type uint32;
                        description
                          "The ports/LAGs belonging to the Multicast
                           group.";
                      }
                    }
                    leaf bum-overall-rate {
                      type uint32;
                      description
                        "overall rate for BUM.";
                    }
                  }
                }
              }
            }
          }
        }
      }
    }
  }
}
