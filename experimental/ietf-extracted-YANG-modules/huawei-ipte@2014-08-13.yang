module huawei-ipte {

  prefix "nc";

  description "V8R7 schema";
  revision "2014-08-13";

  container ipteFlows {

    list ipteFlow {

      key ipteFlowName;
      max-elements unbounded;
      min-elements 0;
      description "IP flow intends to be adjusted.";

      leaf ipteFlowName {
        description "String name of the IP flow";
        config true;
        type string {
          length "0..64";
          pattern "([^?]*)";
        }
      }
      container pathPrefixs {

        list pathPrefix {

          key prefix;

          max-elements unbounded;
          min-elements 0;
          description "IP address prefix to specify the
destination IP address of the flow.";

          leaf prefix {
            description "prefix";
            config true;
            type string {
              length "0..64";
              pattern "([^?]*)";
            }
          }
          leaf maskLength {
            description "mask length";
            config true;
            type uint32 {
              range "0..128";
            }
          }
        }

      }

      leaf bandwidth {
        description "Minimum available bandwidth required in
kbps";
        config true;
        type uint32 {
          range "0..128";
        }
      }
      container paths {
        description "Constrained path of the flow";
        config true;
        list path {

          key pathName;
          max-elements unbounded;
          min-elements 0;
          description "constraint path";

          leaf pathName {
            description "String name of the constrained path";
            config true;
            type string {
              length "0..64";
              pattern "([^?]*)";
            }
          }
          leaf pathType {

            description "Constrained type of the path";
            config true;
            default "auto";
            type enumeration {
              enum strict {
                value 0;
                description "strict";
              }
              enum auto {
                value 1;
                description "auto";
              }
            }
          }

          container pathNodes {

            list pathNode {

              key nodeId;
              max-elements unbounded;
              min-elements 0;
              description ".";

              leaf nodeId {
                description "constraint path node";
                config true;
                type string {
                  length "0..64";
                  pattern "([^?]*)";
                }
              }
              leaf nodeRole {

                description "The role of the node";
                config true;

                type enumeration {
                  enum ingress {
                    value 0;
                    description "ingress node";
                  }
                  enum egress {
                    value 1;
                    description "egress node";
                  }
                  enum transit {
                    value 2;
                    description "transit node";
                  }
                }

              }

              leaf sequence {
                description "constraint path node sequence";
                config true;
                default 1;
                type uint32 {
                  range "0..128";
                }
              }
            }

          }

        }

      }

    }

  }

  container iptePathResults {
    list iptePathResult {

      config false;
      key pathName;
      max-elements unbounded;
      min-elements 0;

      description "Traffic engineered IP path as a result of IP
flow adjustment.";

      leaf iptePrefixName {
        description "prefix name";
        config false;
        type string {
          length "0..64";
          pattern "([^?]*)";
        }
      }
      leaf pathName {
        description "constraint path name";
        config false;
        type string {
          length "0..64";
          pattern "([^?]*)";
        }
      }
      container iptePathResultNodes {

        list iptePathResultNode {

          max-elements unbounded;
          min-elements 0;
          description ".";
          key nodeId;
          leaf nodeId {
            description "constraint path node ID";
            config false;
            type string {
              length "0..64";
              pattern "([^?]*)";
            }
          }
          leaf nodeRole {

            description "The role of the node";
            config false;
            type enumeration {
              enum ingress {
                value 0;
                description "ingress node";
              }
              enum egress {
                value 1;
                description "egress node";
              }
              enum transit {
                value 2;
                description "transit node";
              }
            }
          }

          leaf sequence {
            description "constraint path node sequence";
            config false;
            default 1;
            type uint32 {
              range "0..128";
            }
          }
        }

      }

    }

  }
}
