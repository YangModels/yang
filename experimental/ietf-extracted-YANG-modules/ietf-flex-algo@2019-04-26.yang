module ietf-flex-algo {
  yang-version 1.1;
  namespace "urn:ietf:params:xml:ns:yang:ietf-flex-algo";
  prefix flex-algo;

  import ietf-routing {
    prefix rt;
  }
  import ietf-yang-types {
    prefix yang;
  }
  import ietf-ospf {
    prefix ospf;
  }
  import ietf-isis {
    prefix isis;
  }
  import ietf-srv6-base {
    prefix srv6;
  }

  /* Import TE generic types */
  import ietf-te-types {
    prefix te-types;
  }

  organization
    "IETF LSR Working Group";
  contact
    "WG Web:   <http://tools.ietf.org/wg/lsr/>
     WG List:  <mailto:lsr@ietf.org>

     Editor:
     <mailto:mobash.rasool@gmail.com>
     <mailto:sreekanths@huawei.com>
     <mailto:mahendrasingh@huawei.com>
    ";
  description
    "This YANG module defines the essential types for the
     management of Flex-Algorithm for IGP. It also defines the
     module for configuration and management of IGP Flex-Algorithms.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).";
  reference "RFC XXXX";

  // RFC Editor: replace XXXX with actual RFC number and remove
  // this note

  revision 2019-04-26 {
    description
      "Initial revision.";
    reference "RFC XXXX";
  }

  /* Types definitions */

  identity flex-metric-type {
    description
      "Identity from which Metric type for Flex-algorithm are
       derived";
  }

  identity igp {
    base flex-metric-type;
    description
      "IGP metric to be used during the calculation.";
  }

  identity link-delay {
    base flex-metric-type;
    description
      "Min Unidirectional Link Delay as defined in [RFC7810] to
       be used during the calculation.";
  }

  identity te {
    base flex-metric-type;
    description
      "TE default metric as defined in [RFC5305] to be used during
       the calculation.";
  }

  typedef flex-algo-id {
    type uint8 {
      range "128 .. 255";
    }
    description
      "Flex-Algorithm value is a single octet value between
       128 and 255 both inclusive.";
  }

  typedef flex-algo-calc-type {
    type uint8 {
      range "0 .. 127";
    }
    default "0";
    description
      "Calculation type value ranges from 0 to 127 both inclusive
       from the IGP Algorithm Types registry defined under
       Interior Gateway Protocol (IGP)
       Parameters IANA registries.
       If the required calculation type is Shortest Path First,
       the value 0 SHOULD appear in this field.";
  }

  /* Groupings */

  grouping fad-definition {
    description
      "Flexible Algorithm Definition";
    leaf flex-algo-id {
      type flex-algo-id;
      mandatory true;
      description
        "Flex Algorithm Identifier";
    }
    leaf metric-type {
      type identityref {
        base flex-metric-type;
      }
      description
        "Indicates which is the corresponding metric type for
         this algorithm, default is IGP";
    }
    leaf calc-type {
      type flex-algo-calc-type;
      description
        "Indicates the calculation type";
    }
    leaf priority {
      type uint8;
      description
        "Indicates the priority for this algorithm";
    }
    container extended-admin-groups {
      description
        "Extended Admin group configuration for this
         flex algorithm";
      list extended-admin-group {
        key "eag-val";
        description
          "Configure an Extended admin group";
        leaf eag-val {
          type te-types:extended-admin-group;
          description
            "The Flexible-Algorithm definition can specify
             'colors' that are used by the operator to include
             or exclude links during the Flex-Algorithm
             path computation.";
        }
      }
    }
  }

  grouping fad-tlvs {
    description
      "Flexible Algorithm Definition TLV";
    container fad-tlvs {
      description
        "Flex Algorithms Definition TLV";
      list fad-tlv {
        key "flex-algo-id";
        description
          "List of FAD TLVs.";
        uses fad-definition;
      }
    }
  }

  /* Configuration and State Info */

  augment "/rt:routing" {
    description
      "This augments routing-instance configuration with
       Flexible Algorithm.";
    container flex-algos {
      description
        "Flex Algorithms";
      list flex-algo {
        key "flex-algo-id";
        description
          "Configure a Flex Algorithm";
        uses fad-definition;
        list routing-protocols {
          config false;
          description
            "Details of Routing Protocols using this Flexible
             algorithm";
          leaf routing-protocol {
            type leafref {
              path "/rt:routing/rt:control-plane-protocols"
              + "/rt:control-plane-protocol/rt:name";
            }
            config false;
            description
              "Indicates which routing protocol used this flex
               algorithm";
          }
        }
        container flex-algo-counters {
          config false;
          description
            "Flex Algorithm Counters";
          leaf igp-use-count {
            type yang:counter64;
            config false;
            description
              "This counter helps to find the number of IGP instances
               using this FAD";
          }
        }
      }
    }
  }

  /* Configuration and state information for ISIS */
    augment "/rt:routing/" +
        "rt:control-plane-protocols/rt:control-plane-protocol"+
        "/isis:isis/isis:database/isis:levels/isis:lsp"+
        "/isis:router-capabilities" {
    when "/rt:routing/rt:control-plane-protocols/"+
         "rt:control-plane-protocol/rt:type = 'isis:isis'" {
      description
        "This augment ISIS routing protocol when used";
    }
    description
      "This augments ISIS protocol LSDB router capability.";
    uses fad-tlvs;
  }

  augment "/rt:routing/" +
        "rt:control-plane-protocols/rt:control-plane-protocol"+
        "/isis:isis" {
    description
      "This augments isis configuration.";
    list fad-bindings {
      key "flex-algo-id";
      description
        "Flex Algorithm Counters";
      leaf flex-algo-id {
        type leafref {
          path "/rt:routing/flex-algos/flex-algo/flex-algo-id";
        }
        description
          "Flex Algorithm Identifier binded to ISIS";
      }
      leaf is-level {
        type isis:level;
        description
          "ISIS Level associted with this Flex Algorithm";
      }
    }
  }

  /*SRv6 Locator config and state */

  augment "/rt:routing/srv6:srv6/srv6:locators/srv6:locator" {
    description
      "This augments locator configuration in segment-routing
       SRv6.";
    leaf flex-algo-id {
      type leafref {
        path "/rt:routing/flex-algos/flex-algo/flex-algo-id";
      }
      description
        "Flex Algorithm Identifier that is used by this locator";
    }
  }

  /* OSPF configuration */

  augment "/rt:routing/rt:control-plane-protocols"
           + "/rt:control-plane-protocol/ospf:ospf" {
    description
      "Flex Algorithm is binded to OSPF. OSPF then
       advertises FAD TLVs in RI LSA in AS-scope";
    container fad-bindings {
      description
        "Flex Algorithm is binded to OSPF.";
      leaf-list flex-algo-id {
        type leafref {
          path "/rt:routing/flex-algos/flex-algo/flex-algo-id";
        }
        description
          "Flex Algorithm that the router will use and advertise.";
      }
    }
  }

  augment "/rt:routing/rt:control-plane-protocols"
           + "/rt:control-plane-protocol/ospf:ospf"
           + "/ospf:areas/ospf:area" {
    description
      "Flex Algorithm is binded to OSPF area. OSPF then
       advertises FAD TLVs in RI LSA in Area-scope";
    container fad-bindings {
      description
        "Flex Algorithm is binded to OSPF.";
      leaf-list flex-algo-id {
        type leafref {
          path "/rt:routing/flex-algos/flex-algo/flex-algo-id";
        }
        description
          "Flex Algorithm that the router will use and advertise.";
      }
    }
  }

  /* State information for OSPFv2*/
  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque" {
      when "../../../../../../../../"
        + "rt:type = 'ospf:ospfv2'" {
      description
        "This augmentation is only valid for OSPFv2.";
    }
    description
      "SR specific TLVs for OSPFv2 type 11 opaque LSA.";
    uses fad-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque" {
      when "../../../../../../../../../../"
         + "rt:type = 'ospf:ospfv2'" {
      description
        "This augmentation is only valid for OSPFv2.";
    }
    description
      "FAD TLVs for OSPFv2 type 10 opaque LSA.";
    uses fad-tlvs;
  }

  /* State information for OSPFv3 */
  augment "/rt:routing/"
        + "rt:control-plane-protocols/rt:control-plane-protocol/"
        + "ospf:ospf/ospf:database/ospf:as-scope-lsa-type/"
        + "ospf:as-scope-lsas/ospf:as-scope-lsa/"
        + "ospf:version/ospf:ospfv3/ospf:ospfv3/ospf:body/"
        + "ospf:router-information" {
     description "This is augmented only for OSPFv3";
    uses fad-tlvs;
  }

  augment "/rt:routing/"
      + "rt:control-plane-protocols/rt:control-plane-protocol/"
      + "ospf:ospf/ospf:areas/ospf:area/"
      + "ospf:database/"
      + "ospf:area-scope-lsa-type/ospf:area-scope-lsas/"
      + "ospf:area-scope-lsa/ospf:version/ospf:ospfv3/"
      + "ospf:ospfv3/ospf:body/ospf:router-information" {
     when "/rt:routing/rt:control-plane-protocols/"+
        "rt:control-plane-protocol/rt:type = 'ospf:ospfv3'" {
      description
        "This augment OSPFv3 routing protocol when used";
    }
    description
      "This displays FAD TLVs in router capability";
    uses fad-tlvs;
  }

  // RFC Editor: replace XXXX with actual RFC number and remove
  // this note
}
