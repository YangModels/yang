module ietf-eth-service-pm {
  /* TODO: FIXME */
  yang-version 1.1;

  namespace "urn:ietf:params:xml:ns:yang:ietf-eth-service-pm";
  prefix "ethsvc-pm";

  import ietf-eth-tran-service {
    prefix "ethtsvc";
  }

  import ietf-eth-tran-types {
    prefix "etht-types";
  }

  import ietf-yang-types {
    prefix "yang";
  }

  import ietf-te-types {
    prefix "te-types";
  }

  organization
    "Internet Engineering Task Force (IETF) CCAMP WG";
  contact
    "
      WG List: <mailto:ccamp@ietf.org>
      ID-draft editor:
        Haomian Zheng (zhenghaomian@huawei.com);
        Italo Busi (italo.busi@huawei.com);
        Yanlei Zheng (zhengyanlei@chinaunicom.cn);
    ";

  description
    "This module defines the performance monitoring for Ethernet
     services. The model fully conforms to the Network Management
     Datastore Architecture (NMDA).

     Copyright (c) 2020 IETF Trust and the persons
     identified as authors of the code.  All rights reserved.
     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  revision 2020-05-07 {
    description
      "Initial version";
    reference
      "ADD REFERENCE HERE";
  }

  typedef performance-parameter-value
    {
      type union {
        type uint32;
        type uint64;
        type decimal64 {
          fraction-digits 6;
        }
        type string;
      }
      description
        "A performance parameter value.";
    }

  identity performance-parameter-type {
    description
      "Base type of the performance parameter being monitored. ";
  }

  identity latency {
    base performance-parameter-type;
    description
      "Latency measurement for performance monitoring. ";
  }

  identity bit-error-rate {
    base performance-parameter-type;
    description
      "Bit Error Rate (BER) measurement for performance monitoring.";
  }

  identity packet-loss {
    base performance-parameter-type;
    description
      "Packet loss measurement for performance monitoring. ";
  }

  identity bandwidth {
    base performance-parameter-type;
    description
      "Bandwidth measurement for performance monitoring. ";
  }

  identity alarm-status {
    description "indicates whether there is alarm or not";
  }

  identity alarm {
    base alarm-status;
    description "There is one or multiple alarms from the monitor. ";
  }

  identity no-alarm {
    base alarm-status;
    description "There is no alarms from the monitor. ";
  }

  identity monitoring-state {
    description
      "The state of performance monitoring. ";
  }

  identity monitoring {
    base monitoring-state;
    description "The Ethernet client signal is under monitoring. ";
  }

  identity monitor-finished {
    base monitoring-state;
    description
      "The monitoring of Ethernet client signal is finished. ";
  }

  identity monitor-failed {
    base monitoring-state;
    description
      "The monitoring of Ethernet client signal is failed. ";
  }

  container performance-monitoring {
    description
      "This part is for performance monitoring. ";
    list service-pm {
      key "service-name";
      description
        "The list of service to be monitored.";
      leaf service-name {
        type leafref {
          path "/ethtsvc:etht-svc/ethtsvc:etht-svc-instances/ethtsvc:etht-svc-name";
        }
        description "The name of service.";
      }

      leaf pm-enable {
        type boolean;
        description
          "Indicate whether the performance monitoring
          is enable or not.";
      }

      leaf vlan-id {
        type etht-types:vlanid;
        description
          "The customer VLAN Identifier of the Ethernet Client to be monitored.";
      }

      container service-pm-state {
        config false;
        description
          "The state of service performance monitoring.";

        list performance-data{
          key parameter-name;
          description "The list of performance under monitor.";
          uses service-performance-monitor-set;
        }

        leaf monitor-state {
          type identityref {
            base ethsvc-pm:monitoring-state;
          }
          description "The status of performance monitoring. ";
        }

        leaf start-time {
          type yang:date-and-time;
          description
            "The time stamp when the service is started.";
        }

        leaf last-update-time {
          type yang:date-and-time;
          description
            "The time stamp when the service is last updated.";
        }

        leaf error-message {
          type string;
          description
            "The message of error.";
        }

        leaf service-oper-status {
          type identityref {
            base te-types:tunnel-state-type;
          }
          description
            "The operational status of the services.";
        }
        container alarm {
          description
            "To retrieve the Alarm during performance Monitoring.";
          leaf status {
            type identityref {
              base ethsvc-pm:alarm-status;
            }
            description "The status of the alarm. ";
          }
        }
      }
    }
  }

  grouping service-performance-monitor-set{
    description "the set of parameter name, value and description.";
    leaf parameter-name{
      type identityref {
        base performance-parameter-type;
      }
      description
        "The name of parameters to be monitored.
         For example, latency, Bit Error Rate, Bandwidth and so on.";
    }
    list parameter-value {
      key value-description;
      description
        "The table of values of the performance and
        their descriptions.";
      leaf value {
        type ethsvc-pm:performance-parameter-value;
        mandatory true;
        description
          "The value of the parameter. ";
      }
      leaf value-description{
        type string;
        description
          "The description of previous value. ";
      }
    }
  }
}
