module ietf-nvo-tp {
    namespace "urn:ietf:params:xml:ns:yang:ietf-nvo-tp";
    prefix TP;

    import ietf-yang-types {
        prefix yang;
    }

    import ietf-nvo-common-types {
        prefix  CommonTypes;
    }

    import ietf-nvo-vpn-routeprotocol {
        prefix  RouteProtocol;
    }

    import ietf-nvo-tp-types {
        prefix TPTypes;
    }

    organization  "";
    contact   "";
    description "This module contains a collection of YANG definitions
    for tp";
    revision 2016-10-24 {
        reference "draft-chen-opsawg-composite-vpn-dm-00";
    }

    container nvoTPMgr{
        description "nvo tp management";
        list tps {
            key "id";
            uses TP:Tp;
            description "tp retrieve functions";
        }
    }

    grouping Tp {
        description "model of TP";
        leaf id {
            type yang:uuid;
            description "yang:uuid-str for TP";
        }
        leaf name {
            type string {length "0..200";}
            description "Must abbey to name rule defined in system.
            Example FE0/0/1, GE1/2/1.1, Eth-Trunk1.1, etc";
        }
        leaf description {
            type string {length "0..200";}
            description "description for this tp.";
        }

        leaf neID {
            type yang:uuid;
            description "yang:uuid-str for NE ";
        }

        leaf containingMainTPID {
            type yang:uuid;
            description "uuid-str for main interface";
        }
        container tpBasicInfo {
            description "Tp non-instance basic info";
            uses TPTypes:TPBasicInfo;
        }
        container peerCeTp {
            description "CE TP Information";
            uses TPTypes:CeTp;
        }

        list routeProtocolSpec {
            key "type";
            description "route protocol spec";
            uses RouteProtocol:RouteProtocolSpec;
        }

        leaf operStatus {
            type CommonTypes:OperStatus;
            config false;
            description "Operational status." ;
        }
    }

    grouping TpInventory {
        description "inventory model of TP";
        leaf tpID {
            type yang:uuid;
            description "uuid of tp";
        }
        leaf detailType {
            type string {length "0..100";}
            description "tp detail type. reported by controller";
        }
        leaf maxBandWidth {
            type uint64;
            description "max bandwidth";
        }
        leaf-list potentialLayers {
            type CommonTypes:LayerRate;
            description "capability of tp to create VPN, reported by
            controller";
        }
    }
}
