module iana-tunnel-type {
  yang-version 1.1;
  namespace "urn:ietf:params:xml:ns:yang:iana-tunnel-type";
  prefix iana-tunnel-type;

  import iana-if-type  {
    prefix ift;
    reference
      "RFC 7224: IANA Interface Type YANG Module";
  }

  organization
    "IANA";
  contact
    "Internet Assigned Numbers Authority

  Postal: ICANN
          12025 Waterfront Drive, Suite 300
          Los Angeles, CA  90094-2536
          United States of America
  Tel:    +1 310 301 5800
  <mailto:iana@iana.org>";

  description
    "This module contains a collection of YANG data types defined
     by IANA and used for tunnel types.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2018-10-19 {
    description
      "Initial revision.";
    reference
      "RFC XXXX:  A Tunnel Extension to the Interface
                  Management YANG Module";
  }

  identity  other {
    base ift:tunnel;
    description
      "None of the following values.";
  }
  identity direct {
    base ift:tunnel;
    description
      "No intermediate header.";
   }
   identity gre {
     base ift:tunnel;
     description
       "GRE encapsulation.";
   }
   identity minimal {
     base ift:tunnel;
     description
       "Minimal encapsulation.";
   }
   identity l2tp {
     base ift:tunnel;
     description
       "L2TP encapsulation.";
   }
   identity pptp {
     base ift:tunnel;
     description
       "PPTP encapsulation.";
   }
   identity l2f {
     base ift:tunnel;
     description
       "L2F encapsulation.";
   }
   identity udp {
     base ift:tunnel;
     description
       "UDP encapsulation.";
   }
   identity atmp {
     base ift:tunnel;
     description
      "ATMP encapsulation.";
   }
   identity msdp {
     base ift:tunnel;
     description
       "MSDP encapsulation.";
   }
   identity sixtofour {
     base ift:tunnel;
     description
       "6to4 encapsulation.";
   }
   identity sixoverfour {
     base ift:tunnel;
     description
       "6over4 encapsulation.";
   }
   identity isatap {
     base ift:tunnel;
     description
       "ISATAP encapsulation.";
   }
   identity teredo {
     base ift:tunnel;
     description
       "Teredo encapsulation.";
   }
   identity iphttps {
     base ift:tunnel;
     description
       "IP over HTTPS.";
   }
   identity softwiremesh {
     base ift:tunnel;
     description
       "softwire mesh tunnel.";
   }
   identity dslite {
     base ift:tunnel;
     description
       "DS-Lite tunnel.";
  }
}
