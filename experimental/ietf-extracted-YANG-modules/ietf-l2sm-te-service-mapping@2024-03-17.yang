module ietf-l2sm-te-service-mapping {
  yang-version 1.1;
  namespace
    "urn:ietf:params:xml:ns:yang:ietf-l2sm-te-service-mapping";
  prefix l2-tsm;

  import ietf-te-service-mapping-types {
    prefix tsmt;
    reference
      "RFC XXXX:  Traffic Engineering and Service Mapping Yang Data
       Model";
  }
  import ietf-l2vpn-svc {
    prefix l2vpn-svc;
    reference
      "RFC 8466: A YANG Data Model for Layer 2 Virtual Private Network
       (L2VPN) Service Delivery";
  }

  organization
    "IETF Traffic Engineering Architecture and Signaling (TEAS)
     Working Group";
  contact
    "WG Web:   <https://datatracker.ietf.org/wg/teas/>
     WG List:  <mailto:teas@ietf.org>

     Editor:   Young Lee
               <mailto:younglee.tx@gmail.com>
     Editor:   Dhruv Dhody
               <mailto:dhruv.ietf@gmail.com>
     Editor:   Qin Wu
               <mailto:bill.wu@huawei.com>";
  description
    "This module contains a YANG module for the mapping of Layer 2
     Virtual Private Network (L2VPN) Service Delivery to the TE and
     Virtual Network (VN).

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2024-03-17 {
    description
      "Initial revision.";
    reference
      "RFC XXXX:  Traffic Engineering and Service Mapping Yang Data
       Model";
  }

  /*
   * Augmentation to L2SM
   */

  augment "/l2vpn-svc:l2vpn-svc/l2vpn-svc:vpn-services/"
        + "l2vpn-svc:vpn-service" {
    description
      "L2SM augmented to include TE parameters and mapping";
    container te-service-mapping {
      presence
        "indicates L2 service is relying on underlying TE";
      description
        "Container to augment L2SM to TE parameters and mapping
         If no other parameters exist, it indicates that the
         underlying TE resouces have not been mapped yet.";
      uses tsmt:te-mapping;
    }
  }

  augment "/l2vpn-svc:l2vpn-svc/l2vpn-svc:sites/l2vpn-svc:site"
        + "/l2vpn-svc:site-network-accesses"
        + "/l2vpn-svc:site-network-access" {
    description
      "This augment the L2SM network-access with a reference
       to TE endpoints when underlying TE is used";
    uses tsmt:te-endpoint-ref;
  }

  augment
    "/l2vpn-svc:l2vpn-svc/l2vpn-svc:sites/l2vpn-svc:site"
  + "/l2vpn-svc:service/l2vpn-svc:qos/l2vpn-svc:qos-profile"
  + "/l2vpn-svc:qos-profile/l2vpn-svc:custom"
  + "/l2vpn-svc:classes/l2vpn-svc:class" {
    when './l2vpn-svc:bandwidth/l2vpn-svc:end-to-end' {
      description
        "applicable only with end-to-end";
    }
    description
      "This augment is for per-class in site for custom QoS profile";
    uses tsmt:te-endpoint-ref;
  }

  augment
    "/l2vpn-svc:l2vpn-svc/l2vpn-svc:sites/l2vpn-svc:site"
  + "/l2vpn-svc:site-network-accesses"
  + "/l2vpn-svc:site-network-access"
  + "/l2vpn-svc:service/l2vpn-svc:qos/l2vpn-svc:qos-profile"
  + "/l2vpn-svc:qos-profile/l2vpn-svc:custom"
  + "/l2vpn-svc:classes/l2vpn-svc:class" {
    description
      "This augment is for per-class in site-network-access for custom
       QoS profile";
    uses tsmt:te-endpoint-ref;
  }
}
