module ietf-oam-test-sequence {
  yang-version 1.1;
  namespace "urn:ietf:params:xml:ns:yang:ietf-oam-test-sequence";
  prefix "oamts";

  import ietf-oam-unitary-test {
    prefix "oamut";
    // Update the reference with the correct RFC number or other reference when assigned
    //reference "RFCXXXX";
  }

  import ietf-schedule { prefix "schedule"; } // reference draft-ma-opsawg-ucl-acl

  organization
    "IETF OPSAWG (Operations and Management Area Working Group)";

  contact
    "WG Web:   <https://datatracker.ietf.org/wg/opsawg/>
     WG List:  <mailto:opsawg@ietf.org>
     Author: Luis Miguel Contreras Murillo
          <luismiguel.contrerasmurillo@telefonica.com>
     Author: Victor Lopez
          <victor.lopez@nokia.com>";
  description
    "This module defines the 'oam-unitary-test' YANG model for activation of network diagnosis procedures.

    Copyright (c) 2023 IETF Trust and the persons identified as
    authors of the code.  All rights reserved.

    Redistribution and use in source and binary forms, with or
    without modification, is permitted pursuant to, and subject
    to the license terms contained in, the Revised BSD License
    set forth in Section 4.c of the IETF Trust's Legal Provisions
    Relating to IETF Documents
      (https://trustee.ietf.org/license-info).

     This version of this YANG module is part of RFC XXXX
     (https://www.rfc-editor.org/info/rfcXXXX); see the RFC itself
     for full legal notices.";

  // RFC Ed.: update the date below with the date of RFC
  // publication and remove this note.
  // RFC Ed.: replace XXXX with actual RFC number and remove
  // this note.

  revision "2023-07-10" {
    description "Initial version";
    reference "RFCXXXX"; // Update with the correct RFC number when assigned
  }

  // Data model definition

  container oam-test-sequence {
    description "Container for executing a sequence of ietf-oam-unitary-tests N times.";

    list test-sequence {
      key "name";
      description "List of test sequences.";

      leaf name {
        type string;
        description "Unique name for the test sequence.";
      }

      list test-ref {
        key "name";
        description "References to the ietf-oam-unitary-tests.";

        uses "oamut:oam-unitary-test";

        leaf numexecutions {
          type uint32;
          default 1;
          description "Number of times the test sequence should be executed.";
        }
      }

      uses schedule:period;

      uses schedule:recurrence;

      leaf test-squence-status {
        type enumeration {
          enum "planned" {
            description "The test sequence is planned.";
          }
          enum "success" {
            description "All tests in the sequence were successful.";
          }
          enum "failure" {
            description "One or more tests in the sequence failed.";
          }
          enum "ongoing" {
            description "The test sequence status is ongoing.";
          }
          enum "unknown" {
            description "The test sequence status is unknown.";
          }
          enum "stop" {
            description "The test sequenceis stopped.";
          }
          enum "finish" {
            description "The test sequence is finished.";
          }
        }
        config false;
        description "Status of the test sequence execution.";
      }
    }
  }
}
