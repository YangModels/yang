module ietf-queue-policy {
  yang-version 1.1;
  namespace "urn:ietf:params:xml:ns:yang:ietf-queue-policy";
  prefix queue-policy;

  import ietf-traffic-policy {
    prefix traffic-policy;
  }
  import ietf-qos-action {
    prefix qos-action;
  }
  import ietf-diffserv {
    prefix diffserv;
  }
  import ietf-qos-types {
    prefix qos-types;
    reference
      "RFC XXXX: YANG Models for Quality of Service (QoS).";
  }

  organization
    "IETF Routing Area Working Group.";
  contact
    "WG Web:   <https://datatracker.ietf.org/wg/rtgwg/>
     WG List:  <mailto:rtgwg@ietf.org>

     Editor:   Aseem Choudhary
               <mailto:achoudhary@aviatrix.com>
     Editor:   Mahesh Jethanandani
               <mailto:mjethanandani@gmail.com>";

  description
    "This module contains a collection of YANG definitions for
     QoS Queue policies.

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2026-09-26 {
    description
      "Initial version.";
    reference
      "RFC XXXX: YANG Models for Quality of Service (QoS).";
  }

  augment "/traffic-policy:policies/traffic-policy:policy" +
          "/traffic-policy:classifier/traffic-policy:inline" +
          "/traffic-policy:filter" {
    when "derived-from-or-self(../../../traffic-policy:type, " +
         "'qos-types:queue-policy-type')" {
      description
        "If policy type is Queue Policy, this filter can be used.";
    }

    choice filter-params {
      description
        "Choice of Action types.";
      case traffic-group {
        uses diffserv:traffic-group;
        description
          "Traffic group name.";
      }
      case filter-match-all {
        uses diffserv:filter-match-all;
        description
          "When the filter type is set to match all packets.";
      }
    }
    description
      "Augments Queue Policy to add filter types.";
  }

  augment "/traffic-policy:policies/traffic-policy:policy" +
          "/traffic-policy:classifier/traffic-policy:action" {
    when "derived-from-or-self(../../traffic-policy:type,"  +
         "'qos-types:queue-policy-type')" {
      description
        "Queue Policy actions.";
    }

    choice action-params {
      description
        "Choice of different action parameters that can be taken.";

      case queue-template-name {
        uses qos-action:queue-reference;
      }

      case queue-inline {
        uses qos-action:queue;
      }
    }
    description
      "Augments Queue Policy action to add Queue template reference
       or Queue inline.";
  }
}
