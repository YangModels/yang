module ietf-te-topology-pwrgrp {
  yang-version 1.1;
  namespace "urn:ietf:params:xml:ns:yang:ietf-te-topology-pwrgrp";
  prefix tet-pg;

  import ietf-network {
    prefix nw;
    reference
      "RFC 8345: A YANG Data Model for Network Topologies";
  }
  import ietf-network-topology {
    prefix nt;
    reference
      "RFC 8345: A YANG Data Model for Network Topologies";
  }
  import ietf-te-topology {
    prefix tet;
    reference
      "RFC 8795: YANG Data Model for Traffic Engineering (TE)
       Topologies";
  }
  import ietf-te-types {
    prefix te-types;
    reference
      "RFC 8776: Common YANG Data Types for Traffic Engineering";
  }

  organization
    "IETF Traffic Engineering Architecture and Signaling (TEAS)
     Working Group.";
  contact
    "WG Web:   <http://tools.ietf.org/wg/teas/>
     WG List:  <mailto:teas@ietf.org>

     Editor:   Colby Barth
               <mailto:jonathan.barth@hpe.com>

     Editor:   Vishnu Pavan Beeram
               <mailto:vishnupavan.ietf@gmail.com>";
  description
    "YANG data model for representing Power-Group aware TE
     topology.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-03-02 {
    description
      "Initial revision.";
    reference
      "RFC XXXX: YANG Data Model for Power-Group aware TE Topology";
  }

  /*
   * Typedefs
   */

  typedef pg-ref {
    type leafref {
      path "/nw:networks/nw:network/nw:node/tet:te/"
         + "tet:te-node-attributes/tet-pg:power-groups/"
         + "tet-pg:power-group/tet-pg:name";
    }
    description
      "This type is used to reference a Power-Group on a given node";
  }

  /*
   * Groupings
   */

  grouping pg-topology-type {
    description
      "Identifies the Power-Group aware TE topology type.";
    container pg {
      presence "Indicates that the TE topology is Power-Group
                aware.";
      description
        "Its presence identifies that the TE topology is Power-Group
         aware.";
    }
  } // pg-topology-type

  grouping pg-node-attributes {
    description
      "Grouping for carrying Power-Group specific node attributes";
    container power-groups {
      description
        "Container for Power-Groups.";
      list power-group {
        key "name";
        unique "value";
        description
          "List of Power-Groups.";
        leaf name {
          type string;
          description
            "A string that uniquely identifies the Power-Group on a
             given node.";
        }
        leaf value {
          type uint32;
          description
            "An integer that uniquely identifies the Power-Group on
             a given node.";
        }
        leaf cost {
          type decimal64 {
            fraction-digits 2;
          }
          description
            "Rating/Cost of the Power-Group.";
        }
      }
    }
  } // pg-node-attributes

  grouping pg-link-attributes {
    description
      "Grouping for carrying Power-Group specific link attributes";
    leaf-list power-groups {
      type pg-ref;
      description
        "List of associated Power-Groups";
    }
    leaf power-save-capable {
      type boolean;
      description
        "Can the link be placed in power-save mode?";
    }
    container power-save-bandwidth {
      uses te-types:te-bandwidth;
      description
        "Amount of bandwidth that is currently unavailable on this
         link as a result of the link being in power-save mode. If
         the link is not in power-save mode, power-save-bandwidth
         is zero. Units are in bytes per second.";
    }
  } //pg-leaf-attributes
  /*
   * Augmentations
   */

  augment "/nw:networks/nw:network/nw:network-types/"
        + "tet:te-topology" {
    description
      "Defines the Power-Group aware TE topology type.";
    uses pg-topology-type;
  }

  augment "/nw:networks/nw:network/nw:node/tet:te/"
        + "tet:te-node-attributes" {
    description
      "Augmentation for Power-Group specific node attributes.";
    uses pg-node-attributes;
  }

  augment "/nw:networks/nw:network/nt:link/tet:te/"
        + "tet:te-link-attributes" {
    description
      "Augmentation for Power-Group specific link attributes.";
    uses pg-link-attributes;
  }
}
