module ietf-lime-common-types {
    yang-version 1.1;
    namespace "urn:ietf:params:xml:ns:yang:ietf-lime-common-types";
    prefix "lime";

    organization
      "IETF Layer Independent OAM Management(LIME)
       Working Group";

    contact
      "WG Web:   <https://datatracker.ietf.org/wg/lime>
       WG List:  <mailto:lmap@ietf.org>

       Editor:   Qin Wu
                 <bill.wu@huawei.com>";

    description
      "This module provides common definitions used by the data
       models written for Layer Independent OAM Management(LIME).
       This module defines identities but no schema tree elements.";

    revision "2017-09-06" {
      description
        "Initial version";
      reference
        "RFC xxxx: A YANG Data Model for OAM Protocols that use Connectionless
          Communications";
    }

 /*** Collection of common types related to time ***/
   /*** Time unit identity ***/
 identity time-unit-type {
   description
     "Time unit type";
 }
 identity hours {
   base time-unit-type;
   description
     "Time unit in Hours";
 }
 identity minutes {
   base time-unit-type;
   description
     "Time unit in Minutes";
 }
 identity seconds {
   base time-unit-type;
   description
     "Time unit in Seconds";
 }
 identity milliseconds {
   base time-unit-type;
   description
     "Time unit in Milliseconds";
 }
 identity microseconds {
   base time-unit-type;
   description
     "Time unit in Microseconds";
 }
 identity nanoseconds {
   base time-unit-type;
   description
     "Time unit in Nanoseconds";
 }
  /*** Timestamp format Identity ***/
identity timestamp-type {
 description
  "Base identity for Timestamp Type.";
}
identity truncated-ptp {
 base timestamp-type;
 description
  "Identity for 64bit short format PTP timestamp.";
}
identity truncated-ntp {
 base timestamp-type;
 description
  "Identity for 32bit short format NTP timestamp.";
}
identity ntp64 {
 base timestamp-type;
 description
  "Identity for 64bit NTP timestamp.";
}
identity icmp {
 base timestamp-type;
 description
  "Identity for 32bit ICMP timestamp.";
}
}
