module ietf-dtnma-agent-acl {
  yang-version 1.1;
  namespace "ari://ietf-dtnma-agent-acl";
  prefix acl;

  import ietf-amm {
    prefix amm;
  }
  import ietf-dtnma-agent {
    prefix da;
  }

  organization
    "IETF Delay Tolerant Networking (DTN) Working Group";
  contact
    "WG Web: <http://tools.ietf.org/wg/dtn/>
     WG List: <mailto:dtn@ietf.org>

     Editor: Brian Sipos
             <mailto:brian.sipos+ietf@gmail.com>";
  description
    "This module implements the DTN Management Architecture (DTNMA)
     Agent Access Control List (ACL) functionality.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2024-07-03 {
    description
      "Updated for latest ADM document.";
    reference
      "draft-ietf-dtn-adm-yang";
  }
  revision 2023-12-12 {
    description
      "Initial version for latest AMM document";
    reference
      "draft-birrane-dtn-adm";
  }
  amm:enum 2;
  amm:typedef tag {
    amm:enum 0;
    description
      "Datatype for access control list tags";
    amm:type "./TYPEDEF/permissions";
  }
  amm:typedef permissions {
    amm:enum 1;
    amm:type "/ARITYPE/BYTE" {
      amm:int-labels {
        bit tag-read {
          position 0;
          description
            "Permission bit for Read";
        }
        bit tag-write {
          position 1;
          description
            "Permission bit for Write";
        }
        bit tag-execute {
          position 2;
          description
            "Permission bit for Execute/Evaluate";
        }
      }
    }
  }
  amm:typedef entry-id {
    amm:enum 2;
    description
      "The identifier for an entry in any access control table.";
    amm:type "/ARITYPE/UVAST";
  }
  amm:typedef optional-entry-id {
    amm:enum 3;
    description
      "An optional entry identifier (or a null value).";
    amm:union {
      amm:type "./TYPEDEF/entry-id";
      amm:type "/ARITYPE/null";
    }
  }
  amm:typedef result {
    amm:enum 4;
    amm:type "/ARITYPE/INT" {
      amm:int-labels {
        enum success {
          value 0;
          description
            "Execution was successful";
        }
        enum error-generic {
          value 1;
          description
            "Generic execution failure";
        }
        enum error-permission-denied {
          value 2;
          description
            "Manager does not have permission";
        }
      }
    }
  }

  // Default access permission
  amm:var default-access {
    amm:enum 1;
    description
      "The default permission for any object if no specific access are
       present in the ./EDD/access-list table.";
    amm:type "./TYPEDEF/tag";
  }

  // Access control table and modifier controls
  amm:edd access-list {
    amm:enum 2;
    description
      "List the current group--object access.";
    amm:tblt {
      amm:key "id";
      amm:column id {
        amm:type "./TYPEDEF/entry-id";
      }
      amm:column group {
        description
          "A cross-reference to the group getting access, or null to match all groups.";
        amm:type "./TYPEDEF/optional-entry-id";
      }
      amm:column object-pattern {
        description
          "A pattern for objects being accessed, which may match all objects.";
        amm:type "/ARITYPE/TEXTSTR";
      }
      amm:column tag {
        description
          "A pattern for objects being accessed, which may match all objects.";
        amm:type "./TYPEDEF/tag";
      }
    }
  }
  amm:ctrl ensure-access {
    amm:enum 3;
    description
      "Ensures that an access control permission is set for the given group and ARI pattern.";
    amm:parameter group {
      description
        "Identify the group being assigned the permission";
      amm:type "./TYPEDEF/optional-entry-id";
    }
    amm:parameter object-pattern {
      description
        "ARI pattern to determine which objects shall be assigned the permission";
      amm:type "/ARITYPE/TEXTSTR";
    }
    amm:parameter tag {
      description
        "Permission tag value to set";
      amm:default "0";
      amm:type "./TYPEDEF/tag";
    }
    amm:result error-code {
      description
        "If non-zero, an indicator of an error.";
      amm:type "./TYPEDEF/result";
    }
  }
  amm:ctrl discard-access {
    amm:enum 4;
    description
      "Discard any permissions for the given group and ARI pattern.";
    amm:parameter group {
      description
        "Identify the group";
      amm:type "./TYPEDEF/optional-entry-id";
    }
    amm:parameter object-pattern {
      description
        "ARI pattern";
      amm:type "/ARITYPE/TEXTSTR";
    }
    amm:result error-code {
      description
        "If non-zero, an indicator of an error.";
      amm:type "./TYPEDEF/result";
    }
  }

  //
  // Group management
  //
  amm:typedef transport-endpoint-pattern {
    amm:enum 5;
    amm:type "/ARITYPE/IDENT" {
      amm:base "//ietf-dtnma-agent/IDENT/transport-endpoint-pattern";
    }
  }
  amm:edd current-group-id {
    amm:enum 3;
    description
      "Get the group ID for the current execution context, which may be
       the implicit Agent group ID zero.";
    amm:type "./TYPEDEF/entry-id";
  }
  amm:edd group-list {
    amm:enum 4;
    description
      "Get the defined access control groups.";
    amm:tblt {
      amm:key "id";
      amm:column id {
        description
          "The unique identifier for a group.
           The agent itself has implicit group ID zero.";
        amm:type "./TYPEDEF/entry-id";
      }
      amm:column name {
        description
          "The human-friendly name of the group.";
        amm:type "/ARITYPE/TEXTSTR";
      }
      amm:column members {
        description
          "The list of members of the group, identified by matching transport endpoint.";
        amm:ulist {
          amm:type "./TYPEDEF/transport-endpoint-pattern";
        }
      }
    }
  }
  amm:ctrl ensure-group {
    amm:enum 5;
    description
      "Ensure that after the control completes a group exists with the given information";
    amm:parameter id {
      description
        "Uniquely identify the group";
      amm:type "./TYPEDEF/entry-id";
    }
    amm:parameter name {
      description
        "Name of the group";
      amm:type "/ARITYPE/TEXTSTR";
    }
    amm:result error-code {
      description
        "If non-zero, an indicator of an error.";
      amm:type "./TYPEDEF/result";
    }
  }
  amm:ctrl ensure-group-members {
    amm:enum 7;
    description
      "Ensure that the membership of a group has a specific set of endpoint patterns.";
    amm:parameter id {
      description
        "Uniquely identify the group";
      amm:type "./TYPEDEF/entry-id";
    }
    amm:parameter members {
      amm:ulist {
        amm:type "./TYPEDEF/transport-endpoint-pattern";
      }
    }
    amm:result error-code {
      description
        "If non-zero, an indicator of an error.";
      amm:type "./TYPEDEF/result";
    }
  }
  amm:ctrl discard-group {
    amm:enum 6;
    description
      "Discard any group with the given ID.";
    amm:parameter group {
      description
        "Uniquely identify the group";
      amm:type "./TYPEDEF/entry-id";
    }
    amm:result error-code {
      description
        "If non-zero, an indicator of an error.";
      amm:type "./TYPEDEF/result";
    }
  }
}
