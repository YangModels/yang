module ietf-ikev2 {
  namespace "urn:ietf:params:xml:ns:yang:ietf-ikev2";
  prefix "ikev2";

  import "ietf-ikev2-crypto" {
    prefix "ikev2-crypto";
  }

  import ietf-inet-types {
    prefix inet;
  }

  organization "Ericsson AB.
                Huawei Technologies India Pvt Ltd.";

  contact "Web:   <http://www.ericsson.com>";

  description
    "This YANG module defines the configuration and operational
     state data for Internet Key Exchange version 2 (IKEv2) on
     IETF draft.
     Copyright (c) 2016 Ericsson AB.
     All rights reserved.";

  revision 2016-03-10 {
    description
      "First revision.";
    reference
      "YANG Data model for Internet Protocol Security - IPSec.
       draft-tran-ipecme-yang-ipsec-00.
       draft-wang-ipsecme-ike-yang-00.
       draft-wang-ipsecme-ipsec-yang-00.";
  }

  /*--------------------*/
  /* Feature            */
  /*--------------------*/

  feature ikev2 {
    description
      "Feature IKEv2";
  }
  feature ikev2-transport {
    description
      "Common IKEv2 Transport attributes";
  }
  feature ikev2-transport-anti-replay-mechanism {
    description
      "Optional: Enable INVALID_MESSAGE_ID defines whether an"+
      " optional INVALID_MESSAGE_ID  Notify Payload is sent when"+
      " the IKEv2 message received is outside the Operational"+
      " Window Size";
  }
  feature ikev2-transport-enable-notify-invalid-msg-id {
    description
      "Feature IKEv2 Transport enable notify of invalid message id";

  }
  feature ikev2-transport-retransmission {
    description
      "Feature IKEv2 Transport retransmission";

  }
  feature ikev2-transport-cookie-mechanism {
    description
      "Feature IKEv2 Transport Cookie mechanism";

  }
  feature ikev2-init {
    description
      "Feature IKEv2 INIT";

  }
  feature ikev2-init-authorized-dh {
    description
      "Feature IKEv2 INIT authorized Diffie-Hellman (DH)";

  }
  feature ikev2-init-authorized-certification-auth {
    description
      "Feature IKEv2 INIT authorized certification author";

  }
  feature ikev2-init-nat-detection-src-ip {
    description
      "Feature IKEv2 INIT NAT Detection Source IP Address";

  }
  feature ikev2-init-nat-detection-destination-ip {
    description
      "Feature IKEv2 INIT Detection Destination IP Address";

  }
  feature ikev2-init-redirect-supported {
    description
      "Feature IKEv2 INIT Redirect Supported";

  }
  feature ikev2-init-fragmentation-supported {
    description
      "Feature IKEv2 INIT Fragmentation Supported";

  }
  feature ikev2-init-responder-certreq {
    description
      "Feature IKEv2 INIT Responder CERTREQ";
  }
  feature ikev2-init-optional {
    description
      "Feature IKEv2 INIT Optional Attributes";
  }
  feature ikev2-auth-mobike-supported {
    description
      "Feature IKEv2 AUTH Mobike Supported";

  }
  feature ikev2-auth-rohc-supported {
    description
      "Feature IKEv2 AUTH RObust Header Compression ROHC Supported";

  }
  feature ikev2-auth-childless-supported {
    description
      "Feature IKEv2 AUTH Childless Supported";

  }
  feature ikev2-auth-message-id-supported {
    description
      "Feature IKEv2 AUTH Message ID supported";

  }
  feature ikev2-auth-ipsec-replay-counter-sync-supported {
    description
      "Feature IKEv2 AUTH IPSec Replay Counter Sync Supported";

  }
  feature ikev2-auth-erx-supported {
    description
      "Feature IKEv2 AUTH ERX Supported";
  }
  feature ikev2-auth-clone-ike-sa-supported {
    description
      "Feature IKEv2 AUTH Clone IKE-SA Supported";

  }

  feature ikev2-sa {
    description
      "Feature IKEv2 Security Association (SA)";
  }

  feature ikev2-auth {
    description
      "Feature IKEv2 AUTH";
  }

  feature ikev2-peer {
    description
      "Feature IKEv2 Peer";
  }

  feature ikev2-state {
    description
      "IKEv2 Operational State";
  }

  feature ikev2-proposal-state {
    description
      "IKEv2 Proposal Operational State";
  }

  feature ikev2-transport-state {
    description
      "IKEv2 Transport State";
  }

  /*--------------------*/
  /* Typedefs           */
  /*--------------------*/
  typedef ipsec-spi {
    type uint64 {
      range "1..max";
    }
    description
      "Security Parameter Index SPI";
  }
  typedef transport-protocol-name-t {
    type enumeration {
      enum tcp {
        value 1;
        description
          "Transmission Control Protocol (TCP) Transport Protocol.";
      }
      enum udp {
        value 2;
        description
          "User Datagram Protocol (UDP) Transport Protocol";
      }
      enum sctp {
        value 3;
        description
          "Stream Control Transmission Protocol (SCTP) Transport "+
          "Protocol";
      }
      enum icmp {
        value 4;
        description
          "Internet Control Message Protocol (ICMP) Transport "+
          "Protocol";
      }
    }
    description
      "Enumeration of well known transport protocols.";
  }

  typedef role-t {
    type enumeration {
      enum any {
        value 0;
        description
          "Role: Any";
      }
      enum initiator {
        value 1;
        description
          "Role: Initiator";
      }
      enum responder {
        value 2;
        description
          "Role: Responder";
      }
    }
    description
      "Role Type";
  }

  typedef cryptographic-material-t {
    type enumeration {
      enum sk-d {
        value 0;
        description
          "SK_d";
      }
      enum sk-ai {
        value 1;
        description
          "SK_ai";
      }
      enum sk-ar {
        value 2;
        description
          "SK_ar";
      }
      enum sk-ei {
        value 3;
        description
          "SK_ei";
      }
      enum sk-er {
        value 4;
        description
          "SK_er";
      }
      enum sk-pi {
        value 5;
        description
          "SK_pi";
      }
      enum sk-pr {
        value 6;
        description
          "SK_pr";
      }
      enum skeyseed {
        value 7;
        description
          "SKEYSEED";
      }
      enum nonces {
        value 8;
        description
          "Nonces";
      }
    }
    description
      "Cryptographic Material Type";
  }

  typedef ikev2-proposal-number-ref {
    type leafref {
      path "/ikev2/init/proposal/number";
    }
    description
      "reference to IKEv2 proposal number";
  }

  typedef ikev2-transport-base-mjver-ref {
    type leafref {
      path "/ikev2/transport/base-info/major-version";
    }
    description
      "reference to IKEv2 Transport Base Information
      Major Version";
  }

  typedef ikev2-transport-base-mnver-ref {
    type leafref {
      path "/ikev2/transport/base-info/minor-version";
    }
    description
      "reference to IKEv2 Transport Base Information
      Minor Version";
  }

  typedef ikev2-transport-base-spi-gen-policy-ref {
    type leafref {
      path "/ikev2/transport/base-info/spi-generation-policy";
    }
    description
      "reference to IKEv2 Transport Base Information
      SPI Generation Policy";
  }

  typedef ikev2-transport-anti-replay-mechanism-window-size-ref {
    type leafref {
      path "/ikev2/transport/anti-replay-mechanism/window-size";
    }
    description
      "reference to IKEv2 Transport Anti Replay Mechanism
      Window Size";
  }
  typedef ikev2-transport-anti-replay-mechanism-enable-notify-ref {
    type leafref {
      path "/ikev2/transport/anti-replay-mechanism/"+
            "enable-notify-invalid-msg-id";
    }
    description
      "reference to IKEv2 Transport Anti Replay Mechanism
      Enable Notify Invalid Message ID";
  }

  /*--------------------*/
  /*   grouping         */
  /*--------------------*/

   /* The following groupings are used in both configuration data
     and operational state data */
  grouping name-grouping {
    description
      "This grouping provides a leaf identifying the name.";
    leaf name {
      type string;
      description
        "Name of a identifying.";
    }
    leaf description {
      type string;
      description
        "Specify the description.";
    }
  }

  grouping ip-address-grouping {
    description
      "IP Address grouping";

    choice ip-address {
      description
        "Choice of IPv4 or IPv6.";
      leaf ipv4-address {
        type inet:ipv4-address;
        description
          "Specifies the identity as a single four (4)
           octet IPv4 address.
           An example is, 10.10.10.10. ";
      }
      leaf ipv6-address {
        type inet:ipv6-address;
        description
          "Specifies the identity as a single sixteen (16) "+
          "octet IPv6 address. "+
          "An example is, "+
          "FF01::101, 2001:DB8:0:0:8:800:200C:417A .";
      }
    }
  }

  grouping certificate-auth-grouping {
    description
      "Certificate Authority";
    leaf cert-encoding {
      type ikev2-crypto:ikev2-cert-encoding-t;
      description
        "Certificate Authority Encoding";
    }
    leaf cert-value {
      type uint32;
      description
        "Certificate Authority value";
    }
  }

  grouping sequence-number-grouping {
    description
      "This grouping provides a leaf identifying
       a sequence number.";
    leaf sequence-number {
      type uint32 {
        range "1..4294967295";
      }
      description
        "Specify the sequence number.";
    }
  }

  grouping description-grouping {
    description
      "description for free use.";
    leaf description {
      type string;
      description
        "description for free use.";
    }
  }

  grouping transform-encr-algorithm-grouping {
    description
      "Transform Type 1, Encryption Algorithm";
    list transform-encr-algorithm {
      key "encr-algorithm key-length";
      leaf encr-algorithm {
        type ikev2-crypto:ikev2-encryption-algorithm-t;
        description
          "IKEv2 Transform Type 1, Encryption Algorithm";
      }
      leaf key-length {
        type uint32;
        description
          "IKEv2 Transform Type 1, key length for Encryption"+
          " Algorithm";
      }
      description
        "IKEv2 Transform Type 1, Encryption Algorithm";
    }
  }

  grouping transform-prf-algorithm-grouping {
    description
      "IKEv2 Transform Type 2, Pseudo-Random Function PRF";
    list transform-prf-algorithm {
      key "prf-algorithm key-length";
      leaf prf-algorithm {
        type ikev2-crypto:ikev2-pseudo-random-function-t;
        description
          "IKEv2 Transform Type 2, Pseudo-Random Function"+
          " (PRF) Algorithm";
      }
      leaf key-length {
        type uint32;
        description
          "IKEv2 Transform Type 2, key length for PRF";
      }
      description
        "IKEv2 Transform Type 2, Pseudo-Random Function PRF";
    }
  }

  grouping transform-integrity-algorithm-grouping {
    description
      "IKEv2 Transform Type 3, Integrity Algorithm";
    list transform-integrity-algorithm {
      key "integrity-algorithm key-length";
      leaf integrity-algorithm {
        type ikev2-crypto:ikev2-integrity-algorithm-t;
        description
          "IKEv2 Transform Type 3, Integrity Algorithm";
      }
      leaf key-length {
        type uint32;
        description
          "IKEv2 Transform Type 3, key length for Integrity"+
          " Algorithm";
      }
      description
        "IKEv2 Transform Type 3, Integrity Algorithm";
    }
  }

  grouping transform-dh-grouping {
    description
      "IKEv2 Transform Type 4, Diffie-Hellman Group (DH)";
    list transform-dh {
      key "dh key-length";
      leaf dh {
        type ikev2-crypto:ikev2-diffie-hellman-group-t;
        description
          "IKEv2 Transform Type 4, Diffie-Hellman Group (DH)";
      }
      leaf key-length {
        type uint32;
        description
          "IKEv2 Transform Type 4, key length for Diffie-Hellman"+
          " Group (DH)";
      }
      description
        "IKEv2 Transform Type 4, Diffie-Hellman Group (DH)";
    }
  }

  grouping ikev2-proposal-grouping {
    description
      "IKEv2 Proposal";
    list proposal {
      key "number";
      description
        "Configure IKEv2 proposal";
      uses name-grouping;
      uses transform-encr-algorithm-grouping;
      uses transform-prf-algorithm-grouping;
      uses transform-integrity-algorithm-grouping;
      uses transform-dh-grouping;
      leaf number {
        type uint32;
        description
          "specify the order the proposals are sent";
      }
      leaf protocol {
        type ikev2-crypto:ikev2-protocol-identifiers-t;
        description
          "IKEv2 Proposal Protocol Identifier";
      }
    }
  }

  grouping ikev2-retransmission-grouping {
    description
      "IKEv2 retransmission policy configuration";
    container retransmision {
      if-feature ikev2-transport-retransmission;
      leaf max-retries {
        type uint32;
        description
          "maximum retry when retransmission failed";
      }
      leaf initial-retransmission-timeout {
        type uint32;
        description
          "initial retransmission timeout value";
      }
      leaf retransmission-timeout-policy {
        type string;
        description
          "defines of the Retransmission Timeout should be"+
          " computed";
      }
      leaf max-response-buffer-timeout {
        type uint32;
        description
          "This timer set when the response buffer can be clean"+
          " when the message ID is not being updated. It value"+
          " is expected to be in the order of several minutes";
      }
      leaf keepalive-timeout {
        type uint32;
        description
          "Keep-alive timeout";
      }
      leaf nat-keepalive-timeout {
        type uint32;
        description
          "Network Address Translation (NAT) Keep-alive timeout";
      }
      description
        "IKEv2 retransmission policy configuration";
    }
  }

  grouping ikev2-cookie-mechanism-grouping {
    description
      "IKEv2 Cookie Mechanism";
    container cookie-mechanism {
      if-feature ikev2-transport-cookie-mechanism;
      leaf cookie-lifetime {
        type uint32;
        description
          "Cookie Lifetime";
      }
      leaf half-open-ike-sa-threshold {
        type uint32;
        description
          "Half-open IKE-SA Threshold";
      }
      description
        "IKEv2 Cookie Mechanism";
    }
  }

  grouping ikev2-auth-avail-signing-capabilities-grouping {
    description
      "IKEv2 AUTH Available Signing Capabilities";
    list avail-signing-capabilities {
      key "auth-method-name";
      description
        "availiable signing capabilities";
      leaf auth-method-name {
        type string;
        description
          "Authentication method name";
      }
      leaf auth-method {
        type ikev2-crypto:ikev2-authentication-method-t;
        description
          "type of authentication method";
      }
      leaf auth-material-data {
        type string;
        description
          "authentication material data";
      }
    }
  }

  grouping ikev2-cert-auth-grouping {
    description
      "IKEv2 AUTH Certificate Authentication";
    container cert-auth {
      description
        "Certificate authentication";
      leaf cert-auth-encoding {
        type ikev2-crypto:ikev2-cert-encoding-t;
        description
          "certificate authentication encoding";
      }
      leaf cert-auth-value {
        type uint32;
        description
          "certificate authentication value";
      }
    }
  }

  grouping ikev2-cert-authentication-material-grouping {
    description
      "IKEv2 CERT Authentication Material";
    leaf cert-authentication-type {
      type string;
      default "cert";
      description
        "CERT Authentication Type";
    }
    uses ikev2-cert-auth-grouping;
  }

  grouping ikev2-auth-avail-hash-capabilities-grouping {
    description
      "IKEv2 AUTH Available Hash Capabilities";
    list avail-hash {
      key "hash-method";
      description
        "available hash";
      leaf hash-method {
        type string;
        description
          "hash method";
      }
      leaf auth-hash-lifetime {
        type uint32;
        description
          "Authentication Hash lifetime";
      }
    }
  }
  grouping ikev2-auth-avail-signature-verification-grouping {
    description
      "IKEv2 AUTH Available Signature Verification";
    list avail-signature-verify {
      key "signature-id";
      description
        "available signature verification";
      leaf signature-id {
        type string;
        description
          "signature ID";
      }
      leaf signature-lifetime {
        type uint32;
        description
          "signature lifetime";
      }
    }
  }

  grouping local-id-grouping {
    description
      "IKEv2 AUTH Local ID";
    list local-id {
      key "host-id";
      description
        "list of Local ID";
      leaf host-id {
        type string;
        description
          "Local Host ID";
      }
      leaf preference {
        type string;
        description
          "Local Preference";
      }
      leaf id-type {
        type string;
        description
          "Local ID type";
      }
      leaf id-value {
        type string;
        description
          "ID value";
      }
    }
  }

  grouping ikev2-vendor-id-grouping {
    description
      "IKEv2 Vendor ID";
    leaf vendor-id {
      type uint64;
      description
        "IKEv2 Vendor ID";
    }
  }

  grouping ikev2-base-info-grouping {
    description
      "IKEv2 Base Information";
    container base-info {
      description
        "IKEv2 basic information";
      leaf major-version {
        type uint8;
        default 2;
        description
          "IKEv2 Major Version";
      }
      leaf minor-version {
        type uint8;
        default 0;
        description
          "IKEv2 Minor Version";
      }
      leaf spi-generation-policy {
        type string;
        description
          "SPI genration policy";
      }
    }
  }

  grouping ikev2-anti-replay-mechanism-grouping {
    description
      "IKEv2 Anti Replay Mechanism";
    container anti-replay-mechanism {
      leaf window-size {
        type uint32;
        default 1;
        description
          "Window Size defines how much parallel exchange can"+
          " be performed between the peers. By default this"+
          " value is set to 1. When greater than 1, as defined"+
          " in [RFC7296] section 2.3, a SET_WINDOW_SIZE Notify"+
          " Payloads will be sent by the peer to agree withe the"+
          " other peer on the Window Size. After this exchange"+
          " succeeds, the operational attribute that defines"+
          " the Window Size used by the IKE_SA, will be updated"+
          " with the value agreed by the peers.";
      }
      leaf enable-notify-invalid-msg-id {
        if-feature ikev2-transport-enable-notify-invalid-msg-id;
        type empty;
        description
          "Optional Enable INVALID_MESSAGE_ID defines whether an"+
          " optional INVALID_MESSAGE_ID  Notify Payload is sent"+
          " when the IKEv2 message received is outside the"+
          " Operational Window Size.";
      }
      description
        "Anti Replay Mechanism describes when message should be"+
        " rejected or considered by the IKEv2 daemon. The anti"+
        " reply mechanism is defined for each session.";
    }
  }

  grouping ikev2-init-optional-grouping {
    description
      "IKEv2 INIT Optional";
    container optional {
      if-feature ikev2-init-optional;
      container nat-detection-source-ip {
        if-feature ikev2-init-nat-detection-src-ip;
        description
          "Optional support: for Network Address Translation (NAT)"+
          " Destination Source IP Address, sent during the"+
          " IKE_INIT";
        uses ip-address-grouping;
        leaf nat-keepalive-interval {
          type uint16 {
            range "5..300";
          }
          units "Seconds";
          default 20;
          description "NAT detected and keepalive interval";
        }
      }

      container nat-detection-destination-ip {
        if-feature ikev2-init-nat-detection-destination-ip;
        description
          "Optional support: for Network Address Translation (NAT)"+
          " Detecttion Destination IP Address, sent during the"+
          " IKE_INIT";
        uses ip-address-grouping;
        leaf nat-keepalive-interval {
          type uint16 {
            range "5..300";
          }
          units "Seconds";
          default 20;
          description "NAT detected and keepalive interval";
        }
      }

      leaf redirect-supported {
        if-feature ikev2-init-redirect-supported;
        type boolean;
        default true;
        description
          "Optional support: for redirect supported, sent"+
          " during the IKE_INIT";
      }
      leaf fragmentation-supported {
        if-feature ikev2-init-fragmentation-supported;
        type boolean;
        default true;
        description
          "Optional support: for fragmentation supported"+
          " sent during the IKE_INIT";
      }
      leaf mobike-supported {
        if-feature ikev2-auth-mobike-supported;
        type boolean;
        default true;
        description
          "Optional support: for mobike supported, sent during"+
          " IKE-AUTH";
      }
      leaf rohc-supported {
        if-feature ikev2-auth-rohc-supported;
        type boolean;
        default true;
        description
          "Optional support: for RObust Header Compression (ROHC)"+
          " supported, sent during IKE-AUTH";
      }
      leaf childless-ikev2-supported {
        if-feature ikev2-auth-childless-supported;
        type boolean;
        default true;
        description
          "Optional support: for CHILDLESS_IKEV2_SUPPORTED,"+
          " sent during IKE-AUTH";
      }
      leaf message-id-sync-supported {
        if-feature ikev2-auth-message-id-supported;
        type boolean;
        default true;
        description
          "Optional support: for IKEV2_MESSAGE_ID_SYNC_SUPPORTED,"+
          " sent during IKE-AUTH";
      }
      leaf ipsec-replay-counter-sync-supported {
        if-feature ikev2-auth-ipsec-replay-counter-sync-supported;
        type boolean;
        default true;
        description
          "Optional support: for"+
          " IPSEC_REPLAY_COUNTER_SYNC_SUPPORTED,"+
          " sent during IKE-AUTH";
      }
      leaf erx-supported {
        if-feature ikev2-auth-erx-supported;
        type boolean;
        default true;
        description
          "Optional support: for ERX_SUPPORTED,"+
          " sent during IKE-AUTH";
      }
      leaf clone-ike-sa-supported {
        if-feature ikev2-auth-clone-ike-sa-supported;
        type boolean;
        default true;
        description
          "Optional support: for CLONE_IKE_SA_SUPPORTED,"+
          " sent during IKE-AUTH";
      }
      description
        "IKEv2 INIT Optional Attributes";
    }
  }

  grouping ikev2-initiator-id-grouping {
    container initiator-id {
      leaf initiator-id-type {
        type ikev2-crypto:pad-type-t;
        description
          "Initiator ID Type";
      }
      leaf initiator-id {
        type string;
        description
          "Initiator ID";
      }
      description
        "Initiator ID";
    }
    description
      "Initiator ID";
  }

  grouping ikev2-responder-id-grouping {
    container responder-id {
      leaf responder-id-type {
        type ikev2-crypto:pad-type-t;
        description
          "Responder ID Type";
      }
      leaf responder-id {
        type string;
        description
          "Responder ID";
      }
      description
        "Responder ID";
    }
    description
      "Responder ID";
  }

  grouping ikev2-transport-grouping {
    description
      "IKEv2 Transport Attributes";
    container transport {
      if-feature ikev2-transport;
      description
        "Common IKEv2 transport attributes";

      uses ikev2-base-info-grouping;
      uses ikev2-anti-replay-mechanism-grouping;
      uses ikev2-retransmission-grouping;
      uses ikev2-cookie-mechanism-grouping;
      uses ikev2-vendor-id-grouping;
    } //  End of container transport
  }

  grouping ikev2-config-request-grouping {
    description
      "Optional Configuration Request";
    container config-request {
      uses ip-address-grouping;
      description
        "Optional Configuration Requester";
    }
  }

  grouping ikev2-config-responder-grouping {
    description
      "Optional Configuration Responder";
    container config-responder {
      uses ip-address-grouping;
      description
        "Optional Configuration Responder";
    }
  }

  grouping ikev2-init-grouping {
    description
      "IKEv2 INIT Attributes";
    container init {
      if-feature ikev2-init;
      description
        "configuration attributes for the IKE_INIT exchange";

      list authorized-dh {
        if-feature ikev2-init-authorized-dh;
        key "dhg key-length";
        leaf dhg {
          type ikev2-crypto:ikev2-diffie-hellman-group-t;
          description
            "IKEv2 Transform Type 4, Diffie-Hellman Group (DH)";
        }
        leaf key-length {
          type uint32;
          description
            "IKEv2 Transform Type 4, key length for Diffie-Hellman"+
            " Group (DH)";
        }
        description
          "IKEv2 INIT Authorized Diffie-Hellman";
      }

      uses ikev2-proposal-grouping;
      uses ikev2-init-optional-grouping;

      leaf auth-method {
        type ikev2-crypto:ikev2-authentication-method-t;
        default auth-preshared;
        description
          "The authentication method of IKEv2 peer";
      }

      container responder-certreq {
        if-feature ikev2-init-responder-certreq;
        uses certificate-auth-grouping;
        description
          "IKEv2 INIT Responder CERTREQ";
      }

      uses ikev2-config-request-grouping;
      uses ikev2-config-responder-grouping;

      list authorized-cert-auth {
        if-feature ikev2-init-authorized-certification-auth;
        key "cert-encoding";
        uses certificate-auth-grouping;
        description
          "IKev2 Initiator authorized certification authorities";
      }
    } // end of container init
  }

  grouping ikev2-auth-grouping {
    description
      "IKEv2 AUTH Attributes";
    container auth {
      if-feature ikev2-auth;
      description
        "IKEv2 AUTH Exchange";
      uses ikev2-auth-avail-signing-capabilities-grouping;
      uses ikev2-cert-auth-grouping;
      uses ikev2-auth-avail-hash-capabilities-grouping;
      uses ikev2-auth-avail-signature-verification-grouping;
      uses local-id-grouping;
      container authorized-certificate-authority {
        uses certificate-auth-grouping;
        description
          "IKEv2 AUTH Authorized Certificate Authority";
      }
    } // End of container auth
  }
  grouping ikev2-proposal-state-components {
    description
      "IKEv2 Operational state";
    list proposal {
      if-feature ikev2-proposal-state;
      key "name";
      description
        "IKEv2 proposal operational data";
      uses name-grouping;

      leaf encryption-algorithm {
        type ikev2-crypto:ikev2-encryption-algorithm-t;
        description
          "Transform Type 1 - IKEv2 Encryption Algorithm";
      }
      leaf prf-algorithm {
        type ikev2-crypto:ikev2-pseudo-random-function-t;
        description
          "Transform Type 2 - IKEv2 Pseudo-Random Function (PRF)";
      }
      leaf integrity-algorithm {
        type ikev2-crypto:ikev2-integrity-algorithm-t;
        description
          "Transform Type 3 - IKEv2 Integrity Algorithms";
      }
      leaf dh-group {
        type ikev2-crypto:ikev2-diffie-hellman-group-t;
        mandatory true;
        description
          "Transform Type 4 - IKEv2 Diffie-Hellman group.";
      }
      leaf esn {
        type ikev2-crypto:ikev2-extended-sequence-number-t;
        description
          "Transform Type 5 - IKEv2 Extended Sequence Number (ESN)";
      }
    }
    leaf connection-type {
      type ikev2-crypto:ikev2-connection-type-t;
      description
        "define whether the corresponding IKEv2 SA is being used"+
        " as an initiator or as a responder or both";
    }
  }

  /*---------------------------------------------------------*/
  /*************       Configuration Data        *************/
  /*---------------------------------------------------------*/

  /* ------------------- */
  /* IKEv2 configuration */
  /* ------------------- */
  container ikev2 {
    if-feature ikev2;
    description
      "Configuration IPSec IKEv2";

    uses ikev2-transport-grouping;
    uses ikev2-init-grouping;

    container sa {
      if-feature ikev2-sa;
      description
        "IKEv2 Security Association";
      leaf role {
        type role-t;
        description
          "IKEv2 SA Role [any | initiator | responder]";
      }
      container local-ip-address {
        description
          "IKEv2 SA Local IP Address";
        uses ip-address-grouping;
      }
      container remote-ip-address {
        description
          "IKEv2 SA Remote IP Address";
        uses ip-address-grouping;
      }
      leaf cryptgraphic {
        type cryptographic-material-t;
        description
          "Cryptographic Material Type";
      }
      leaf lifetime {
        type uint32;
        description
          "lifetime for IKEv2 SAs
           0: for no timeout.
           300 .. 99999999:  IKEv2 SA lifetime in seconds.";
      }
      leaf proposal {
        type ikev2-proposal-number-ref;
        description
          "IKE proposal number referenced by IKE peer";
      }
      uses ikev2-base-info-grouping;
      uses ikev2-anti-replay-mechanism-grouping;

      list retransmistion-ctx {
        key "window-id";
        leaf window-id {
          type uint32;
          description
            "Window ID";
        }
        uses ikev2-retransmission-grouping;
        description
          "IKEv2 Security Association Retransmission CTX
          that contains the element to enable retransmission
          for all ongoing exchange";
      }
      uses ikev2-initiator-id-grouping;
      uses ikev2-responder-id-grouping;
      uses ikev2-cert-authentication-material-grouping;
      uses ikev2-vendor-id-grouping;
      list optional-ctx {
        key "window-id";
        description
          "Optional Security Association CTX";
        leaf window-id {
          type uint32;
          description
            "Window ID";
        }
        uses ikev2-init-optional-grouping;
      }
    } // end of container sa

    list peer {
      if-feature ikev2-peer;
      key "peer-address";
      description "IKEv2 peer information";
      leaf peer-address {
        type string;
        description
          "Peer address";
      }
      leaf role {
        type role-t;
        default any;
        description
          "Peer Role [any | initiator | responder]";
      }

      list peer-id-entries {
        key "peer-id peer-id-type";
        description "IKE peer information";
        leaf peer-id-type {
          type ikev2-crypto:pad-type-t;
          description
            "Peer ID Type";
        }
        leaf peer-id {
          type string;
          description
            "Peer ID";
        }
      } // End of peer-entries

      list session {
        key "session-label";
        description
          "List of session";
        leaf session-label {
          type string;
          description
            "Session Label";
        }
        uses ikev2-initiator-id-grouping;
        uses ikev2-responder-id-grouping;
        uses ikev2-transport-grouping;
        uses ikev2-init-grouping;
        uses ikev2-auth-grouping;
        uses ikev2-config-request-grouping;
        uses ikev2-config-responder-grouping;
      }

      leaf preshared-key {
        type string;
        description "Preshare key";
      }
      leaf nat-traversal {
        type boolean;
        default false;
        description
          "Enable/Disable Network Address Translation"+
          " (NAT) traversal";
      }
    } //End of peer

  } // End of ikev2

  /*---------------------------------------------------------*/
  /*************         Operational State       *************/
  /*---------------------------------------------------------*/
  /*--------------------------*/
  /* IKEv2 Operational State  */
  /*--------------------------*/
  container ikev2-state {
    if-feature ikev2-state;
    config "false";

    container transport-state {
      if-feature ikev2-transport-state;
      description
        "Common IKEv2 operational transport state";
      leaf major-version {
        type uint8;
        default 2;
        description
          "IKEv2 Major Version";
      }
      leaf minor-version {
        type uint8;
        default 0;
        description
          "IKEv2 Minor Version";
      }
      leaf spi-generation-policy {
        type string;
        description
          "SPI genration policy";
      }
      leaf exchange-type {
        type ikev2-crypto:ikev2-exchange-type-t;
        description
          "IKEv2 Exchange Type";
      }
      leaf flags {
        type uint8;
        description
          "indicate specific options that are set for message";
      }
    }

    list sa-state {
      key "initiator-spi responder-spi";
      description
        "IKEv2 Security Association (SA) Operational State";

      leaf initiator-spi {
        type ipsec-spi;
        description
          "initiator Security Parameter Index (SPI)";
      }
      leaf responder-spi {
        type ipsec-spi;
        description
          "initiator Security Parameter Index (SPI)";
      }
      list retransmistion-ctx {
        key "window-id";
        leaf window-id {
          type uint32;
          description
            "Window ID";
        }
        uses ikev2-retransmission-grouping;
        description
          "IKEv2 Security Association Retransmission CTX
          that contains the element to enable retransmission
          for all ongoing exchange";
      }
      container anti-replay-mechanism {
        leaf window-size {
          type uint32;
          description
            "window size";
        }
        leaf peer-request-msg-id {
          type uint32;
          description
            "Peer Request Message ID";
        }
        leaf peer-response-msg-id {
          type uint32;
          description
            "Peer Response Message ID";
        }
        leaf local-request-msg-id {
          type uint32;
          description
            "Local Request Message ID";
        }
        leaf local-response-msg-id {
          type uint32;
          description
            "Local Response Message ID";
        }
        description
          "IKEv2 Anti Replay Mechanism Operational State";
      }
      uses ikev2-vendor-id-grouping;
      uses ikev2-initiator-id-grouping;
      uses ikev2-responder-id-grouping;
      uses ikev2-auth-grouping;
      leaf half-open-ike-sa-counter {
        type uint32;
        description
          "IKEv2 Cookie Mechanism Half-Open IKE-SA counter";
      }
      list optional-ctx {
        key "window-id";
        description
          "Optional Security Association CTX";
        leaf window-id {
          type uint32;
          description
            "Window ID";
        }
        uses ikev2-init-optional-grouping;
      }
    }
    description
      "Contain the operational data for IKEv2";
  }
} /* module ietf-ikev2 */
