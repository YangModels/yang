module ietf-nrp {
  yang-version 1.1;
  namespace "urn:ietf:params:xml:ns:yang:ietf-nrp";
  prefix nrp;

  import ietf-network {
    prefix nw;
    reference
      "RFC 8345: A YANG Data Model for Network Topologies";
  }
  import ietf-network-topology {
    prefix nt;
    reference
      "RFC 8345: A YANG Data Model for Network Topologies";
  }
  import ietf-routing-types {
    prefix rt-types;
    reference
      "RFC 8294: Common YANG Data Types for the Routing Area";
  }
  import ietf-te-types {
    prefix te-types;
    reference
      "RFC 8776: Traffic Engineering Common YANG Types";
  }
  import ietf-te-packet-types {
    prefix te-packet-types;
    reference
      "RFC 8776: Traffic Engineering Common YANG Types";
  }
  import ietf-srv6-types {
    prefix srv6-types;
  }
  import ietf-inet-types {
    prefix inet;
    reference
      "RFC 6991: Common YANG Data Types";
  }
  import ietf-access-control-list {
    prefix acl;
    reference
      "RFC 8519: YANG Data Model for Network Access Control Lists
       (ACLs)";
  }

  organization
    "IETF TEAS Working Group";
  contact
    "
     WG Web: <http://tools.ietf.org/wg/teas/>
     WG List:<mailto:teas@ietf.org>

     Editor: Bo Wu <lana.wubo@huawei.com>
           : Dhruv Dhody <dhruv.ietf@gmail.com>";
  description
    "This YANG module defines a network data module for
     NRP(Network Resource Partition).

     Copyright (c) 2022 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  revision 2022-01-29 {
    description
      "This is the initial version of NRP YANG model.";
    reference
      "RFC XXX: A YANG Data Model for Network Resource Partition";
  }

  identity link-partition-type {
    description
      "Base identity for interface partition type.";
  }

  identity virtual-sub-interface-partition {
    base link-partition-type;
    description
      "Identity for virtual interface or sub-interface, e.g. FlexE.";
  }

  identity queue-partition {
    base link-partition-type;
    description
      "Identity for queue partition type.";
  }

  identity nrp-dataplane-type {
    description
      "Base identity for NRP data plane type.";
  }

  identity nrp-dataplane-ipv6 {
    base nrp-dataplane-type;
    description
      "Identity for NRP specific packet forwarding of IPv6.";
  }

  identity nrp-dataplane-mpls {
    base nrp-dataplane-type;
    description
      "Identity for NRP specific packet forwarding of MPLS.";
  }

  identity nrp-dataplane-sr-mpls {
    base nrp-dataplane-type;
    description
      "Identity for NRP specific packet forwarding of SR MPLS.";
  }

  identity nrp-dataplane-srv6 {
    base nrp-dataplane-type;
    description
      "Identity for NRP specific packet forwarding of SRv6.";
  }

  /*
   * Groupings
   */

  grouping nrp-bandwidth-reservation {
    description
      "Grouping for NRP bandwidth reservation.";
    container bandwidth-reservation {
      description
        "Container for NRP bandwidth reservation.";
      choice bandwidth-type {
        description
          "Choice of bandwidth reservation type.";
        case bandwidth-value {
          leaf bandwidth-value {
            type uint64;
            units "bps";
            description
              "Bandwidth allocation for the NRP as absolute value.";
          }
        }
        case bandwidth-percentage {
          leaf bandwidth-percent {
            type rt-types:percentage;
            description
              "Bandwidth allocation for the NRP as a percentage
               of a link.";
          }
        }
      }
    }
  }

  grouping nrp-control-plane-attributes {
    description
      "Grouping for NRP control plane attributes.";
    container control-plane {
      description
        "The container of NRP control plane mechanisms.";
      container topology-ref {
        description
          "Container for topology reference.";
        container igp-topology-ref {
          description
            "Container for IGP topology reference.";
          uses nw:network-ref;
          leaf multi-topology-id {
            type uint32;
            description
              "The MT-id of an NRP.";
          }
          leaf flex-algo-id {
            type uint32;
            description
              "The flex-algo-id of an NRP.";
          }
        }
        uses te-types:te-topology-identifier;
      }
    }
  }

  grouping nrp-data-plane-attributes {
    description
      "Grouping for NRP data plane attributes.";
    container data-plane {
      description
        "The data plane mechanisms of an NRP. The forwarding plane
         could be MPLS, IPv6, SRv6, or SR-MPLS.";
      container global-resource-identifier {
        description
          "The container of global NRP data-plane ID.";
        container nrp-dataplane-ipv6-type {
          description
            "The container of IPv6 based NRP data-plane identifier.";
          leaf nrp-dp-value {
            type inet:ipv6-address;
            description
              "Indicates the IPv6 NRP data-plane identifier.";
          }
        }
        container nrp-dataplane-mpls-type {
          description
            "The container of MPLS based NRP data-plane identifier.";
          leaf nrp-dp-value {
            type uint32;
            description
              "Indicates MPLS metadata values to identify MPLS NRP
               data plane identifier, e.g. Ancillary data.";
          }
        }
      }
      container nrp-aware-dp {
        description
          "The container of SR based NRP data-plane identifier.";
        container nrp-aware-srv6-type {
          presence "Enables SRv6 data plane type.";
          description
            "The container of SRv6 based NRP data-plane identifier.";
        }
        container nrp-aware-sr-mpls-type {
          presence "Enables SR MPLS data plane type.";
          description
            "The container of SR MPLS based NRP data-plane identifier.";
        }
      }
    }
  }

  grouping nrp-traffic-steering-policy {
    description
      "The grouping of the NRP traffic steering policy.";
    container steering-policy {
      description
        "The container of a policy set
         matching an NRP traffic classifier.";
      leaf-list color-id {
        type uint32;
        description
          "A list of color ID for NRP traffic steering based on
           SR policy.";
      }
      leaf-list acl-ref {
        type leafref {
          path "/acl:acls/acl:acl/acl:name";
        }
        description
          "A list of ACL for NRP traffic classification.";
      }
    }
  }

  grouping nrp-aware-id {
    description
      "The grouping of NRP aware SR ID.";
    container nrp-aware-srv6 {
      description
        "The container of SRv6 based NRP data plane identifier.";
      leaf nrp-dp-value {
        type srv6-types:srv6-sid;
        description
          "Indicates the SRv6 SID value as the NRP data plane
           identifier.";
      }
    }
    container nrp-aware-sr-mpls {
      description
        "The container of SR MPLS based NRP data plane identifier.";
      leaf nrp-dp-value {
        type rt-types:mpls-label;
        description
          "Indicates the SR MPLS ID value as the NRP data plane
           identifier.";
      }
    }
  }

  grouping nrp-topology-attributes {
    description
      "NRP global attributes.";
    container nrp {
      description
        "Containing NRP topology attributes.";
      leaf nrp-id {
        type uint32;
        description
          "NRP identifier.";
      }
      leaf nrp-name {
        type string;
        description
          "NRP Name.";
      }
      uses nrp-bandwidth-reservation;
      uses nrp-control-plane-attributes;
      uses nrp-data-plane-attributes;
      uses nrp-traffic-steering-policy;
    }
    // nrp
  }

  // nrp-node-attributes

  grouping nrp-node-attributes {
    description
      "NRP node scope attributes.";
    container nrp {
      description
        "Containing NRP attributes.";
      uses nrp-aware-id;
    }
  }

  // nrp-node-attributes

  grouping nrp-link-attributes {
    description
      "NRP link scope attributes.";
    container nrp {
      description
        "Containing NRP attributes.";
      leaf link-partition-type {
        type identityref {
          base link-partition-type;
        }
        description
          "Indicates the resource partition type of a link.";
      }
      uses nrp-bandwidth-reservation;
      uses nrp-aware-id;
    }
  }

  // nrp-statistics

  grouping statistics-per-nrp {
    description
      "Statistics attributes per NRP.";
  }

  // nrp-node-statistics

  grouping statistics-per-node {
    description
      "Statistics attributes per NRP node.";
  }

  // one-way-performance-metrics

  grouping one-way-performance-bandwidth {
    description
      "Grouping for one-way performance bandwidth.";
    leaf one-way-available-bandwidth {
      type rt-types:bandwidth-ieee-float32;
      units "bytes per second";
      default "0x0p0";
      description
        "Available bandwidth that is defined to be NRP link
         bandwidth minus bandwidth utilization. For a
         bundled link, available bandwidth is defined to be the
         sum of the component link available bandwidths.";
    }
    leaf one-way-utilized-bandwidth {
      type rt-types:bandwidth-ieee-float32;
      units "bytes per second";
      default "0x0p0";
      description
        "Bandwidth utilization that represents the actual
         utilization of the link (i.e. as measured in the router).
         For a bundled link, bandwidth utilization is defined to
         be the sum of the component link bandwidth
         utilizations.";
    }
  }

  // nrp-link-statistics

  grouping nrp-statistics-per-link {
    description
      "Statistics attributes per NRP link.";
    container statistics {
      config false;
      description
        "Statistics for NRP link.";
      leaf admin-status {
        type te-types:te-admin-status;
        description
          "The administrative state of the link.";
      }
      leaf oper-status {
        type te-types:te-oper-status;
        description
          "The current operational state of the link.";
      }
      uses one-way-performance-bandwidth;
      uses te-packet-types:one-way-performance-metrics-packet;
    }
  }

  augment "/nw:networks/nw:network/nw:network-types" {
    description
      "Defines the NRP topology type.";
    container nrp {
      presence "Indicates NRP topology";
      description
        "The presence identifies the NRP type.";
    }
  }

  augment "/nw:networks/nw:network" {
    when 'nw:network-types/nrp:nrp' {
      description
        "Augment only for NRP topology.";
    }
    description
      "Augment NRP configuration and state.";
    uses nrp-topology-attributes;
  }

  augment "/nw:networks/nw:network/nw:node" {
    when '../nw:network-types/nrp:nrp' {
      description
        "Augment only for NRP topology.";
    }
    description
      "Augment node configuration and state.";
    uses nrp-node-attributes;
  }

  augment "/nw:networks/nw:network/nt:link" {
    when '../nw:network-types/nrp:nrp' {
      description
        "Augment only for NRP topology.";
    }
    description
      "Augment link configuration and state.";
    uses nrp-link-attributes;
    uses nrp-statistics-per-link;
  }
}
