module ietf-trill {
  yang-version 1;
  namespace "urn:ietf:params:xml:ns:yang:trill";
  //namespace need to be assigned by IANA
  prefix trill;

  organization "IETF TRILL Working Group";
  description "TRILL Yang Module";
  revision 2015-08-06{
    description "03 version, as per RFC6325";
    reference "draft-ietf-trill-yang-03";
  }
  typedef port-mode {
    type enumeration {
      enum access {
        value "0";
        description "Access Port";
      }
      enum p2p {
        value "1";
        description "P2P Hello Link";
      }
      enum trunk {
        value "2";
        description "Trunk Port";
      }
      enum hybrid {
        value "3";
        description "Both Trunk and Access Port";
      }
    }
    description "Trill Port Mode.";
  }
  typedef drb-state {
    type enumeration {
      enum non-drb {
        value "0";
        description "Non-DRB Port";
      }
      enum drb {
        value "1";
        description "DRB Port";
      }
      enum down {
        value "2";
        description "Down Port";
      }
      enum suspended {
         value "3";
         description "Suspended Port";
      }
    }
    description "Port State in DRB Election Process.";
  }
  typedef peer-state {
    type enumeration {
      enum report {
        value "0";
        description "report state";
      }
      enum detect {
        value "1";
        description "detect state";
      }
      enum down {
        value "2";
        description "down state";
      }
      enum 2way {
        value "3";
        description "2way state";
      }
    }
    description "TRILL Neighbour State.";
  }
  typedef authen-mode {
    type enumeration {
      enum "simple" {
        value "0";
        description "Indicates that the password is transmitted
        in plaintext";
      }
      enum "md5" {
        value "1";
        description "Indicates that the password is transmitted
        after encryption by MD5.";
      }
      enum "keychain" {
        value "2";
        description "Indicates that the password is a keychain
        which varies with time.";
      }
    }
  }
  grouping authen-para {
    leaf authen-mode {
      type authen-mode;
      description "authentication-mode ";
    }
    leaf cipher-or-plain {
      type boolean;
      description "0 indicates that the password is in ciphertext,
      1 indicates that the password is in plaintext";
    }
    leaf password-key {
      type string;
      description "The value is a string of case-sensitive
      characters, spaces not supported. The password range varies
      with the authentication mode. When the authentication mode
      is simple, the value is a string of 1 to 16 characters
      in simple text, or a string of 32 characters in ciphertext.
      When the authentication mode is md5, the value is a string
      of 1 to 255 characters in simple text, or a string of 32 to
      392 characters in ciphertext.";
    }

    leaf password {
      type string;
      description "The value is a string of case-sensitive
      characters, spaces not supported. The password range
      varies with the authentication mode. 
      When the authentication mode is simple,
      the password ranges from 1 to 16 characters. When the
      authentication mode is md5, the password ranges
      from 1 to 255 characters.";
    }
    leaf keychain {
      type string;
      description "The name is keychain name which is a string
      of 1 to 47 case-insensitive characters, spaces not supported.";
    }
    description "TRILL protocol authentication configurations.";
  }
  typedef conflict-state {
    type enumeration {
      enum "S" {
        value "0";
        description "Nickname suspended";
      }
      enum "A" {
        value "1";
        description "Nickname advertised";
      }
    }
  }
  typedef static-flag{
    type enumeration {
      enum "S" {
        value "0";
        description "Manually configured";
      }
      enum "D" {
        value "1";
        description "Dynamic generated";
      }
    }
    description "Static or dynamic nickname flag.";
  }

  container trill-site {
      leaf max-loadbalance-num {
      default "32";
      type uint8 {
        range "1..max";
      }
      description "The maximum number of equal-cost
      routes for load-balancing.";
    }
    leaf bandwidth-reference {
      default "20000000";
      type uint32 {
        range "1..2147483648";
      }
      description "Sets the bandwidth reference value
      for a TRILL interface. Unit:M bit/s.
      Cost of the interface = Bandwidth reference
      value/Interface bandwidth";
    }
    leaf native-confidence {
      default "32";
      type uint8;
      description "The confidence in { MAC, VLAN, local port }
      triples learned from locally received native frames";
    }
    leaf remote-confidence {
      default "32";
      type uint8;
      description "The confidence in { MAC, VLAN, remote RBridge}
      triples learned from decapsulating frames";
    }
    leaf min-link-mtu {
      default "1470";
      type uint16 {
        range "1..max";
      }
      description "Minimum link MTU";
    }
    leaf mtu-probes {
      default "3";
      type uint8 {
        range "1..max";
      }
      description "The number of failed MTU-probes";
    }
    container lsp-timer {
      leaf lspLife {
        default "1200";
        type uint16 {
          range "2..max";
        }
        description "LSP aging timer.Unit:Second";
      }
      leaf lsp-refresh {
        default "900";
        type uint16 {
          range "1..65534";
        }
        description "LSP refresh timer.Unit:Second";
      }
      leaf lsp-generation {
        default "2";
        type uint8 {
          range "1..120";
        }
        description "LSP generate timer.Unit:Second";
      }
    }
    container lsp-snp-authen {
      uses authen-para;
      description "Authentication information for LSPs and SNPs";
    }
    container tree-para {
      leaf nick-number {
        default "1";
        type uint16 {
          range "1..256";
        }
        description "Nickname number";
      }
      leaf tree-number {
        default "1";
        type uint16 {
          range "1..max";
        }
        description "Distribution tree number";
      }
    }

    leaf-list net-entity {
      type string;
      description "TRILL network entity";
    }

    container nicknames {
      list nickname {
        key "nickName";
        leaf nickName {
          type uint16 {
            range "1..65471";
          }
        }
        leaf priority {
          default "192";
          type uint8 {
            range "128..max";
          }
        }
        leaf root-priority {
          default "32768";
          type uint16 {
            range "1..max";
          }
        }
      }
      description "Nicknames and the associated properties";
    }
    container trill-ports {
      list trill-port{
        key "ifName";
        leaf ifName {
          type string;
          description "trill interface";
        }
        leaf port-mode {
          default "p2p";
          type port-mode;
          description "TRILL Port Mode";
        }
        container hello-authen {
          uses authen-para;
          description "Authentication information for Hellos";
        }
        leaf csnp-timer {
          default "10";
          type uint16 {
            range "1..max";
          }
        }
        leaf hello {
          default "10";
          type uint8 {
            range "3..max";
          }
        }
        leaf holding-multiplier {
          default "3";
          type uint16 {
            range "3..1000";
          }
        }
        leaf lsp-retransmit {
          default "5";
          type uint16 {
            range "1..300";
          }
        }
        container lsp-throttle {
          leaf throttleInterval {
            default "50";
            type uint16 {
              range "1..10000";
            }
            description "The interval timer between
            two LSP messages.Unit:ms";
          }
          leaf count-number {
            default "10";
            type uint16 {
              range "1..1000";
            }
            description "The max messages number being
            sent each time.Unit:ms";
          }
        }
        leaf inhibition-timer {
          default "30";
          type uint8 {
            range "0..30";
          }
          description "The inhibition time for the port
          when root bridge changes.Unit:Second";
        }

        container drb-config {
          leaf drb-priority {
            default "64";
            type uint8 {
              range "0..127";
            }
          }
          leaf holding-timer {
            default "10";
            type uint8 {
              range "3..255";
            }
          }
        }
        leaf mac-learning-flag {
          default "true";
          type boolean;
          description "if learning MAC address from locally
          received native frames";
        }
        leaf trill-frame-receive-flag {
          default "false";
          type boolean;
          description "if receiving of TRILL frames from
          non IS-IS adjacency";
        }
        leaf cost {
          default "0";
          type uint32 {
            range "0..16777215";
          }
          description "link cost";
        }
        leaf enabled-vlans {
          type binary{
            length "1..512";
          }
        }
        leaf announcing-vlans {
          type binary{
            length "1..512";
          }
        }
        leaf forwarding-vlans {
          type binary{
            length "1..512";
          }
        }
        leaf designated-vlan {
          type uint16{
            range "1..4096";
          }
        }
      }
    }

    container vlan-para {
      list vlan-config{
        key vlan-id;

        leaf vlan-id {
          type uint16 {
            range "1..4096";
          }
        }
        leaf participation-flag {
          default "false";
          type boolean;
        }
        leaf priority {
          default "64";
          type uint8 {
            range "0..127";
          }
        }
        leaf holdingTimer {
          default "10";
          type uint8 {
            range "3..max";
          }
        }
      }
    }

   container trill-route-infos {
     list  trill-route-info {
       key "nickname nexthop";
       config "false";

       leaf nickname {
         config "false";
         type uint32;
       }
       leaf cost {
         config "false";
         type uint32;
       }
       leaf out-interface {
         config "false";
         type string;
       }
       leaf out-vlan {
         config "false";
         type uint32;
       }
       leaf nexthop {
         config "false";
         type string;
       }
       leaf hop-count {
         config "false";
         type uint32;
       }
     }
   }

   container trill-mroute-infos {
     list trill-mroute-info {
       description "Distribution pruning tree route table;
       For non-pruning tree, VLAN is set to be 0XFFFF";
       key "vlan root-nickname";
       config "false";

       leaf vlan {
         type uint16;
       }
       leaf root-nickname {
         type uint16;
       }
       leaf hop-count {
         type uint16;
       }
       list trill-mroute-outinterface-info {
         key "out-interface out-vlan";

         leaf out-interface {
           type "string";
         }
         leaf out-vlan {
           type "uint32";
         }
       }
     }
   }

   container trill-rpf-check-infos {
     list trill-rpf-check-info {
       key "ingress-nickname tree-nickname";
       config "false";

       leaf ingress-nickname {
         type "uint16";
       }
       leaf tree-nickname {
         type "uint16";
       }
       leaf interface-name {
         type "string";
       }
       leaf neighbor-mac {
         type "string";
       }
       leaf out-vlan {
         type "uint16";
       }
     }
   }

   container trill-peer-infos {
     list trill-peer-info {
       key "host-name circuit-id";
       config "false";

       leaf host-name {
         type "string";
         description "Peer RBridge name";
       }
       leaf interface-name {
         type "string";
       }
       leaf circuit-id {
         type "string";
       }
       leaf status {
         type peer-state;
       }
       leaf holdTime {
         type "uint32";
       }
       leaf priority {
         type "string";
       }
     }
   }

   container trill-lsdb-infos{
     list trill-lsdb-info{
       key "lspid";
       config "false";

       leaf lspid {
         type string;
       }
       leaf seqence-number {
         type string;
       }
       leaf checksum {
         type string;
       }
       leaf lsp-length {
         type uint32 {
           range "0..2000";
         }
       }

       leaf lsp-flags {
         type bits {
           bit attbit {
             position 0;
           }
           bit partition-bit {
             position 1;
           }
           bit overload-bit {
             position 2;
           }
         }
         default "attbit";
       }

       leaf holdtime {
         type string;
       }
       leaf local-lsp {
         type boolean;
       }
     }
   }

   container trill-nickname-infos {
     list trill-nickname-info {
       key "nickname systemid";
       config "false";

       leaf nickname {
         type uint32;
       }
       leaf priority {
         type uint32;
       }
       leaf root-priority {
         type uint32;
       }
       leaf systemid {
         type string;
       }
       leaf conflict-state {
         type conflict-state;
       }
       leaf static-flag {
         type static-flag;
       }
       leaf is-local {
         type boolean;
       }
     }
   }
   container trill-statistics {
     config "false";
     container interface-stat {
       leaf up-num {
         type uint32;
       }
       leaf down-num {
         type uint32;
       }
     }
     container pktstatistics {
       leaf report-num {
         type uint32;
       }
       leaf detect-num {
         type uint32;
       }
       leaf twoway-num {
         type uint32;
       }
     }
     leaf unicast-routes-num {
       type uint32;
     }
     leaf multicast-routes-num {
       type uint32;
     }
     leaf rpf-entrys-num {
       type uint32;
     }
     leaf remote-nicknames-num {
       type uint32;
     }
     leaf lsdb-lsps-num {
       type uint32;
     }
     leaf self-lsps-num {
       type uint32;
     }
     leaf multicast-trees-num {
       type uint32;
     }
     leaf unicast-nodes-num {
       type uint32;
     }
     leaf multicast-nodes-num {
       type uint32;
     }
   }

   container pkt-statistics {
     list pkt-statistic {
       key "interface-name";
       config "false";

       leaf interface-name {
         type string;
       }
       leaf sent-hellos-num {
         type uint32;
       }
       leaf recved-hellos-num {
         type uint32;
       }
       leaf sent-lsps-num {
        type uint32;
       }
       leaf recved-lsps-num {
         type uint32;
       }
       leaf sent-csnps-num {
         type uint32;
       }
       leaf recved-csnps-num {
         type uint32;
       }
       leaf sent-psnps-num {
         type uint32;
       }
       leaf recved-psnps-num {
         type uint32;
       }
       leaf lsp-retransmissions-num {
         type uint32;
       }
       leaf drb-elections-num {
         type uint32;
       }
     }
   }
 }
}
