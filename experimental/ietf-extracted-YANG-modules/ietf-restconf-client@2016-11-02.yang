module ietf-restconf-client {
  yang-version 1.1;

  namespace "urn:ietf:params:xml:ns:yang:ietf-restconf-client";
  prefix "rcc";

/*
  import ietf-inet-types {
    prefix inet;
    reference
      "RFC 6991: Common YANG Data Types";
  }

  //import ietf-netconf-acm {
  //  prefix nacm;
  //  reference
  //    "RFC 6536: Network Configuration Protocol (NETCONF)
  //     Access Control Model";
  //}

  import ietf-x509-cert-to-name {
    prefix x509c2n;
    reference
      "RFC 7407: A YANG Data Model for SNMP Configuration";
  }

  import ietf-tls-client {
    prefix ts;
    revision-date 2016-11-02; // stable grouping definitions
    reference
      "RFC ZZZZ: TLS Client and Server Models";
  }
*/
  organization
   "IETF NETCONF (Network Configuration) Working Group";

  contact
   "WG Web:   <http://tools.ietf.org/wg/netconf/>
    WG List:  <mailto:netconf@ietf.org>

    WG Chair: Mehmet Ersue
              <mailto:mehmet.ersue@nsn.com>

    WG Chair: Mahesh Jethanandani
              <mailto:mjethanandani@gmail.com>

    Editor:   Kent Watsen
              <mailto:kwatsen@juniper.net>";

  description
   "This module contains a collection of YANG definitions for
    configuring RESTCONF servers.

    Copyright (c) 2014 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2016-11-02" {
    description
     "Initial version";
    reference
     "RFC XXXX: RESTCONF Client and Server Models";
  }

  // Features

  feature tls-initiate {
    description
     "The tls-initiate feature indicates that the RESTCONF client
      supports initiating TLS connections to RESTCONF servers.";
    reference
     "RFC YYYY: RESTCONF Protocol";
  }

  feature tls-listen {
    description
     "The tls-listen feature indicates that the RESTCONF client
      supports opening a port to listen for incoming RESTCONF
      server call-home TLS connections.";
    reference
     "RFC AAAA: NETCONF Call Home and RESTCONF Call Home";
  }

  container restconf-client {
    description
      "Top-level container for RESTCONF client configuration.";
    container initiate {
      if-feature tls-initiate;
      description
        "Configures client intiating underlying TCP connections.";
    }
    container listen {
      if-feature tls-listen;
      description
        "Configures client accepting call-home TCP connections.";
    }
  }

}
