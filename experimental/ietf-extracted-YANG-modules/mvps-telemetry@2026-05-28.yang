module mvps-telemetry {
  yang-version 1.1;
  namespace "urn:ietf:params:xml:ns:yang:mvps-telemetry";
  prefix mvpst;

  import ietf-yang-types { prefix yang; }

  organization "Catellix Research";
  contact "Leonardo Melegassi <melegassi@catellix.com>";
  description
    "Export notification for MVPS coherence events.  Read-only
     telemetry; carries no configuration or actuation.";
  revision 2026-05-28 {
    description "Initial -00 revision.";
    reference "draft-melegassi-opsawg-mvps-telemetry-export-00";
  }

  typedef hex64 {
    type string {
      pattern '[0-9a-f]{64}';
    }
    description "Lowercase hex SHA-256 digest (64 chars).";
  }

  notification mvps-coherence-event {
    description "One MVPS operational event.";
    leaf event-id        { type hex64;        mandatory true; }
    leaf event-type {
      type enumeration {
        enum alarm; enum byzantine; enum phase;
        enum vantage; enum anchor;
      }
      mandatory true;
    }
    leaf severity {
      type enumeration {
        enum emergency; enum alert; enum critical; enum error;
        enum warning;   enum notice; enum info;    enum debug;
      }
      mandatory true;
    }
    leaf event-time     { type yang:date-and-time; mandatory true; }
    leaf bundle-seq     { type uint64;          mandatory true; }
    leaf d2             { type decimal64 { fraction-digits 3; } }
    leaf phi-d          { type decimal64 { fraction-digits 3; } }
    leaf vantage-count  { type uint16; }
    leaf byzantine-frac { type decimal64 { fraction-digits 3; } }
    leaf phase {
      type enumeration {
        enum NOMINAL; enum DEGRADED; enum ALARM; enum BYZANTINE;
        enum MPLS_CAMOUFLAGE_SUSPECTED;
      }
    }
    leaf path-fingerprint { type hex64; }
    leaf log-seq          { type uint64; }
    leaf log-record-hash  { type hex64; }
    leaf anchor-head      { type string; }
    leaf audit            { type boolean; default false; }
  }
}
