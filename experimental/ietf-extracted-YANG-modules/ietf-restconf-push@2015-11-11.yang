module ietf-restconf-push {
  namespace "urn:ietf:params:xml:ns:yang:ietf-restconf-push";

  prefix "rc-push";

  import ietf-datastore-push {
    prefix ds-push;
  }

  organization
   "IETF NETCONF (Network Configuration) Working Group";

  contact
   "WG Web:     <http://tools.ietf.org/wg/netconf/>
    WG List:    <mailto:netconf@ietf.org>

    WG Chair:   Mahesh Jethanandani
                <mailto:mjethanandani@gmail.com >

    WG Chair:   Mehmet Ersue
                <mailto:mehmet.ersue@nokia.com>

    Editor:   Eric Voit
              <mailto:evoit@cisco.com>

    Editor:   Alexander Clemm
              <mailto:alex@cisco.com>

    Editor:   Ambika Prasad Tripathy
              <mailto:ambtripa@cisco.com>

    Editor:   Einar Nilsen-Nygaard
              <mailto:einarnn@cisco.com>

    Editor:   Alberto Gonzalez Prieto
              <mailto:albertgo@cisco.com>";

  description
   "This module contains conceptual YANG specifications for
    Restconf datastore push.";

  revision 2015-11-11 {
    description
      "Initial revision.";
    reference "restconf YANG Datastore push";
  }

  grouping subscription-qos {
    description
     "This grouping describes Quality of Service information
      concerning a subscription.  This information is passed to lower
      layers for transport priortization and treatment";
    leaf subscription-priority {
      type uint8;
      description
       "Relative priority for a subscription.   Allows an underlying
        transport layer perform informed load balance allocations
        between various subscriptions";
    }
    leaf subscription-dependency {
      type string;
      description
       "Provides the Subscription ID of a parent subscription.
        Information associated with the parent should always be
        streamed to a Subscriber before that from a dependent
        subscription";
    }
  }

  augment "/ds-push:subscription-config/" +
           "ds-push:datastore-push-subscription" {
    description
      "Aguments configured subscriptions with QoS parameters.";
    uses subscription-qos;
  }

  augment "/ds-push:subscriptions/" +
           "ds-push:datastore-push-subscription" {
    description
      "Aguments the list of currently active subscriptions
        with QoS parameters.";
    uses subscription-qos;
  }

  augment "/ds-push:create-subscription/" +
           "ds-push:input" {
    description
      "Aguments the create subscription rpc with QoS parameters.";
    uses subscription-qos;
  }

  augment "/ds-push:modify-subscription/" +
           "ds-push:input" {
    description
      "Aguments the modify subscription rpc with QoS parameters.";
    uses subscription-qos;
  }
}
