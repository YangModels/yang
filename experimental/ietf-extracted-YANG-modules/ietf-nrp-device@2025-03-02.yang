module ietf-nrp-device {
  yang-version 1.1;
  namespace "urn:ietf:params:xml:ns:yang:ietf-nrp-device";
  prefix nrp-dev;

  /* Import IETF interface module */

  import ietf-interfaces {
    prefix if;
    reference
      "RFC8343: A YANG Data Model for Interface Management";
  }

  /* Import NRPs module */

  import ietf-nrp {
    prefix nrp;
    reference
      "RFCXXXX: YANG Data Models for Network Resource
                Partitions (NRPs)";
  }

  organization
    "IETF Traffic Engineering Architecture and Signaling (TEAS)
     Working Group";
  contact
    "WG Web:   <https://datatracker.ietf.org/wg/teas/>
     WG List:  <mailto:teas@ietf.org>

     Editor:   Bo Wu
               <mailto:lana.wubo@huawei.com>

     Editor:   Dhruv Dhody
               <mailto:dhruv.ietf@gmail.com>

     Editor:   Vishnu Pavan Beeram
               <mailto:vbeeram@juniper.net>

     Editor:   Tarek Saad
               <mailto:tsaad.net@gmail.com>

     Editor:   Shaofu Peng
               <mailto:peng.shaofu@zte.com.cn>";
  description
    "This YANG module defines a data model for Network Resource
     Partitions (NRPs) device configurations and states. The model
     fully conforms to the Network Management Datastore
     Architecture (NMDA).

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  // RFC Ed.: replace XXXX with actual RFC number and
  // remove this note.
  // RFC Ed.: update the date below with the date of RFC
  // publication and remove this note.

  revision 2025-03-02 {
    description
      "Initial revision.";
    reference
      "RFCXXXX: YANG Data Models for Network Resource
                Partitions (NRPs)";
  }

  /*
   * Grouping - NRP QoS Per-Hop Behavior (PHB) profile
   */

  grouping qos-phb-profile {
    description
      "Grouping for NRP QoS Per-Hop Behavior (PHB) profile.";
    leaf phb-profile {
      type leafref {
        path
          "/nrp-policies/qos-profiles/phb-profile-identifier/id";
      }
      description
        "PHB profile identifier, specifying the forwarding treatment
         of packets belonging to a specific NRP selector identifier,
         such as bandwidth control, congestion control
         (e.g., Section 3.4 of [RFC3644]).
         The PHB may be standard PHB, such as Assured
         Forwarding (AF), Expedited Forwarding (EF), or
         a customized local policy, such as 'High', 'Low',
         'Standard'.";
    }
  }

  /* NRP device configuraiton */

  container nrp-policies {
    description
      "Container for nrp policies.";
    uses nrp:qos-profiles;
    list nrp-policy {
      key "name";
      unique "nrp-id";
      description
        "List of NRP policies.";
      leaf name {
        type string;
        description
          "A string that uniquely identifies the NRP policy.";
      }
      leaf nrp-id {
        type uint32;
        description
          "A 32-bit ID that uniquely identifies the NRP
           created by the enforcement of this NRP policy.";
      }
      uses nrp:resource-reservation;
      uses nrp:selector-id;
      uses qos-phb-profile;
      uses nrp:igp-congruent;
      /* NRP Interface Configuration Data */
      container interfaces {
        description
          "NRP interfaces global configuration.";
        list interface {
          key "interface";
          description
            "The list of interfaces enabled for NRP.";
          leaf interface {
            type if:interface-ref;
            description
              "NRP interface name.";
          }
          uses nrp:resource-reservation;
          uses nrp:selector-id;
          uses qos-phb-profile;
        }
      }
    }
  }
}
