module ietf-dmm-fpcp {
    namespace "urn:ietf:params:xml:ns:yang:ietf-dmm-fpcp";
    prefix fpcp;

    import ietf-inet-types { prefix inet; }

    organization "IETF DMM Working Group";
    contact "Satoru Matsushima <satoru.matsushima@g.softbank.co.jp>";

    description
    "This module contains YANG definition for
     Forwarding Policy Configuration Protocol.(FPCP)";

    revision 2015-07-06 {
        description "Changes based on -01 version of FPCP draft.";
        reference "draft-ietf-dmm-fpc-cpdp-01";
    }

    typedef fpcp-port-id {
        type uint32;
        description "PRT_ID";
    }

    typedef fpcp-property-id {
        type uint8;
        description "PRT_PROP_ID";
    }

    typedef fpcp-rule-id {
        type uint8;
        description "PRT_RULE_ID";
    }

    identity tunnel-type {
        description
        "Base identity from which specific use of
         tunnels are derived.";
    }

    identity fpcp-tunnel-type {
        base "tunnel-type";
        description
        "Base identity from which specific tunnel
         types in FPCP uses are derived.";
    }

    identity ip-in-ip {
        base "fpcp-tunnel-type";
        description "IP-in-IP tunnel";
    }

    identity gtp {
        base "fpcp-tunnel-type";
        description "GTP-U tunnel";
    }

    identity gre {
        base "fpcp-tunnel-type";
        description "GRE tunnel";
    }

    identity service-function {
        description
        "Base identity from which specific
         service function types are derived.";
    }

    identity ip-protocol {
        description
        "Base identity from which specific
         IP protocol types are derived.";
    }

    identity qos-type {
        description
        "Base identity from which specific
         uses of QoS types are derived.";
    }

    identity fpcp-qos-type {
        base "qos-type";
        description
        "Base identity from which specific
         QoS types in FPCP uses are derived.";
    }

    identity fpcp-qos-type-gbr {
        base "fpcp-qos-type";
        description
        "A QoS Type for Guaranteed Bit Rate (GBR).";
    }

    identity fpcp-qos-type-mbr {
        base "fpcp-qos-type";
        description
        "A QoS Type for Maximum Bit Rate (MBR).";
    }

    grouping fpcp-client {
        description "CLI_ID to identify FPCP Client";
        leaf carrier-id {
            type uint16;
            description "Carrier ID";
        }
        leaf network-id {
            type uint16;
            description "Network ID";
        }
        leaf client-id {
            type uint32;
            mandatory true;
            description "Client ID";
        }
    }

    grouping fpcp-agent {
        description "AGT_ID to identify FPCP Agent";
        leaf carrier-id {
            type uint16;
            description "Carrier ID";
        }
        leaf network-id {
            type uint16;
            description "Network ID";
        }
        leaf agent-id {
            type uint32;
            mandatory true;
            description "Agent ID";
        }
    }

    grouping dpn {
        description "DPN_ID to identify Data-Plane Node";
        leaf carrier-id {
            type uint16;
            description "Carrier ID";
        }
        leaf network-id {
            type uint16;
            description "Network ID";
        }
        leaf dpn-id {
            type uint32;
            mandatory true;
            description "DPN ID";
        }
    }

    grouping tunnel-endpoints {
        description
        "PROP_TUN property as a set of tunnel endpoints";
        leaf tunnel-type {
            type identityref {
                base "fpcp-tunnel-type";
            }
            description "Tunnel Type";
        }
        leaf remote-address {
            type inet:ip-address;
            description "Remote endpoint";
        }
        leaf local-address {
            type inet:ip-address;
            description "Local endpoint";
        }
    }

    grouping gtp-attributes {
        description
        "GTP_CONF as GTP tunnel specific attributes";
        leaf remote-teid {
            type uint32;
            description "TEID of remote-endpoint";
        }
        leaf local-teid {
            type uint32;
            description "TEID of local-endpoint";
        }
    }

    grouping gre-attributes {
        description
        "GRE_CONF as GRE tunnel specific attribute";
        leaf key {
            type uint32;
            description "GRE_KEY";
        }
    }

    grouping rewriting-properties {
        description
        "PROP_REWR. TBD for which type of rewriting functions
         need to be defined";
        leaf type {
            type identityref {
                base service-function;
            }
            description "The type of service-function";
        }
    }

    grouping qos-properties {
        description "PROP_QOS";
        leaf qos-type {
            type identityref {
                base "fpcp-qos-type";
            }
            description "QoS Type";
        }
        leaf bandwidth {
            type uint32;
            description "";
        }
    }

    grouping fpcp-identifier-attributes {
        description
        "Identifiers of protocol attributes";
        container client {
            description "Client ID";
            uses fpcp-client;
        }
        container agent {
            description "Agent ID";
            uses fpcp-agent;
        }
        list nodes {
            key dpn-id;
            uses dpn;
            description "DPN ID";
        }
    }

    grouping fpcp-traffic-descriptor {
        description
        "Traffic descriptor group collects parameters to
         identify target traffic flow.";
        leaf rule-id {
            type fpcp-rule-id;
            description "PRT_RULE_ID";
        }
        leaf destination-ip {
            type inet:ip-prefix;
            description "Rule of destination IP";
        }
        leaf source-ip {
            type inet:ip-prefix;
            description "Rule of source IP";
        }
        leaf protocol {
            type identityref {
                base "ip-protocol";
            }
            description "Rule of protocol";
        }
        leaf destination-port {
            type inet:port-number;
            description "Rule of destination port";
        }
        leaf source-port {
            type inet:port-number;
            description "Rule of source port";
        }
    }

    grouping fpcp-port-properties {
        description
        "A set of port property attributes";
        leaf property-id {
            type fpcp-property-id;
            description "Property ID";
        }
        container endpoints {
            description "Tunnel Endpoint";
            uses tunnel-endpoints;
        }
        container qos {
            description "QoS Type";
            uses qos-properties;
        }
        container rewriting {
            description "Rewriting function";
            uses rewriting-properties;
        }
        choice tunnel {
            description "Tunnel-Type";
            case gtp-u {
                when "tunnel-type = 'gtp'" {
                    description "In case of GTP-U is tunnel-type";
                }
                uses gtp-attributes;
            }
            case gre {
                when "tunnel-type = 'gre'" {
                    description "In case of GRE is tunnel-type";
                }
                uses gre-attributes;
            }
        }
    }

    // Port Entries

    container port-entries {
        description
        "This container binds set of traffic-descriptor and
         port properties to a port and lists them as a port entry.";
        list port-entry {
            key port-id;
            description "List of port entries";
            leaf port-id {
                type fpcp-port-id;
                description "Port-ID";
            }
            container identifier {
                description "Attributes set of Identifiers";
                uses fpcp-identifier-attributes;
            }
            list trafic-descriptor {
                key rule-id;
                description "Rule and traffic-descriptor";
                uses fpcp-traffic-descriptor;
            }
            list properties {
                key property-id;
                description "Attributes set of properties";
                uses fpcp-port-properties;
            }
        }
    }

    // PRT_ADD

    rpc port_add {
        description "PRT_ADD";
        input {
            list adding-ports {
                description "Ports that are added to an agent";
                leaf port-id {
                    type fpcp-port-id;
                    description "Port-ID";
                }
                container trafic-descriptor {
                    description "Rule and traffic-descriptor";
                    uses fpcp-traffic-descriptor;
                }
                list properties {
                    key property-id;
                    description "Attributes set of properties";
                    uses fpcp-port-properties;
                }
            }
        }
    }

    // PRT_DEL

    rpc port_delete {
        description "PRT_DEL";
        input {
            list deleting-ports {
                description "Ports that are deleted from an agent";
                leaf deleting-port {
                    type fpcp-port-id;
                    description "Deleting port-id";
                }
            }
        }
    }

    // PROP_ADD

    rpc port_property_add {
        description "PROP_ADD";
        input {
            list adding-properties {
                description "Properties that are added to an agent";
                leaf target-port {
                    type fpcp-port-id;
                    description "Port-ID";
                }
                list properties {
                    key property-id;
                    description "Attributes set of properties";
                    uses fpcp-port-properties;
                }
            }
        }
    }

    // PROP_MOD

    rpc port_property_modify {
        description "PROP_MOD";
        input {
            list modifying-properties {
                description
                "Properties that are modified in an agent";
                leaf target-port {
                    type fpcp-port-id;
                    mandatory true;
                    description
                    "Target port-id of modifying properties";
                }
                list properties {
                    key property-id;
                    description "Attributes set of properties";
                    uses fpcp-port-properties;
                }
            }
        }
    }

    // PROP_DEL

    rpc port_property_delete {
        description "PROP_DEL";
        input {
            list deleting-property {
                description
                "Target port/property-id of deleting properties";
                leaf port-id {
                    type fpcp-port-id;
                    mandatory true;
                    description "Port ID";
                }
                leaf property-id {
                    type fpcp-property-id;
                    mandatory true;
                    description "Property ID";
                }
            }
        }
    }

    // RULE_ADD

    rpc rule_add {
        description
        "TBD for input parameters of which RULE_ADD includes
         but now just traffic-descriptor.";
        input {
            list adding-rules {
                description "Rules that are added to an agent";
                leaf target-port {
                    type fpcp-port-id;
                    mandatory true;
                    description "Target port-id of adding rule";
                }
                list port-rules {
                    description "Added rule";
                    uses fpcp-traffic-descriptor;
                }
            }
        }
    }
    // RULE_MOD

    rpc rule_modify {
        description
        "TBD for input parameters of which RULE_MOD includes
         but now just traffic-descriptor.";
        input {
            list modifying-rules {
                description "Rules that are modified in an agent";
                leaf target-port {
                    type fpcp-port-id;
                    mandatory true;
                    description "Target port-id of modifying rule";
                }
                list port-rule {
                    description "Modified rule";
                    uses fpcp-traffic-descriptor;
                }
            }
        }
    }

    // RULE_DEL

    rpc rule_delete {
        description
        "TBD for input parameters of which RULE_DEL includes
         but now just traffic-descriptor.";
        input {
            list deleting-rules {
                description "Rules that are deleted from an agent";
                leaf target-port {
                    type fpcp-port-id;
                    mandatory true;
                    description "Target port-id of deleting rule";
                }
                list target-rules {
                    description "Deleting rules";
                    leaf target-rule-id {
                        type fpcp-rule-id;
                        mandatory true;
                        description "Rule ID";
                    }
                }
            }
        }
    }

    // EVENT_REG

    rpc event_register {
        description
        "TBD for registered parameters included in EVENT_REG.";
    }

    // PROBE

    rpc probe {
        description
        "TBD for retrieved parameters included in PROBE.";
    }

    // NOTIFY

    notification notify {
        description
        "TBD for which status and event are reported to client.";
    }
}
