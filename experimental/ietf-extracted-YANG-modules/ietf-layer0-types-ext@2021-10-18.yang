module ietf-layer0-types-ext {
  namespace "urn:ietf:params:xml:ns:yang:ietf-layer0-types-ext";
  prefix "l0-types-ext";

  organization
    "IETF CCAMP Working Group";
  contact
    "WG Web: <http://tools.ietf.org/wg/ccamp/>
     WG List: <mailto:ccamp@ietf.org>

     Editor: Dieter Beller
       <mailto:Dieter.Beller@nokia.com>

     Editor: Sergio Belotti
       <mailto:Sergio.Belotti@nokia.com>

     Editor: Italo Busi
       <mailto:Italo.Busi@huawei.com>

     Editor: Haomian Zheng
       <mailto:zhenghaomian@huawei.com>";

     // Additional contacts TBA (contributors)

  description
    "Description to be added!!!

     Copyright (c) 2021 IETF Trust and the persons identified
     as authors of the code.  All rights reserved.

     Redistribution and use in source and binary forms, with
     or without modification, is permitted pursuant to, and
     subject to the license terms contained in, the Simplified
     BSD License set forth in Section 4.c of the IETF Trust's
     Legal Provisions Relating to IETF Documents
     (http://trustee.ietf.org/license-info).

     This version of this YANG module is part of RFC XXXX; see
     the RFC itself for full legal notices.";

  revision "2021-10-18" {
    description
      "Initial Version";
    reference
      "RFC XXXX: A YANG Data Model for Layer 0 Types - Revision 2";
  }

/*
 * Identities
 */

  identity modulation {
    description "base identity for modulation type";
  }

  identity QPSK {
    base modulation;
    description
      "QPSK (Quadrature Phase Shift Keying) modulation";
  }

  identity DP-QPSK {
    base modulation;
    description
      "DP-QPSK (Dual Polarization Quadrature
       Phase Shift Keying) modulation";
  }

  identity QAM8 {
    base modulation;
    description
      "8QAM (8-State Quadrature Amplitude Modulation) modulation";
  }

  identity QAM16 {
    base modulation;
    description
      "QAM16 (Quadrature Amplitude Modulation)";
  }

  identity DP-QAM8 {
    base modulation;
    description
      "DP-QAM8 (Dual Polarization Quadrature Amplitude Modulation)";
  }

  identity DC-DP-QAM8 {
    base modulation;
    description
      "DC DP-QAM8 (Dual Carrier Dual Polarization Quadrature
       Amplitude Modulation)";
  }

  identity DP-QAM16 {
    base modulation;
    description
      "DP-QAM16 (Dual Polarization Quadrature Amplitude
       Modulation)";
  }

  identity DC-DP-QAM16 {
    base modulation;
    description
      "DC DP-QAM16 (Dual Carrier Dual Polarization Quadrature
       Amplitude Modulation)";
  }

  identity fec-type {
    description
      "Base identity from which specific FEC
      (Forward Error Correction) type identities are derived.";
  }

  identity g-fec {
    base fec-type;
    description
      "G-FEC (Generic-FEC)";
  }
  identity e-fec {
    base fec-type;
    description
      "E-FEC (Enhanced-FEC)";
  }
  identity no-fec {
    base fec-type;
    description
      "No FEC";
  }

  identity reed-solomon {
    base fec-type;
    description
      "Reed-Solomon error correction";
  }

  identity hamming-code {
    base fec-type;
    description
      "Hamming Code error correction";
  }

  identity golay {
    base fec-type;
      description "Golay error correction";
  }

  identity line-coding {
    description
      "base line-coding class";
    reference
      "ITU-T G.698.2-201811 section 7";
  }

  identity line-coding-NRZ-2p5G {
    base line-coding;
    description
      "ITU-T G.698.2-201811 section 7 table 8-1";
  }

  identity line-coding-NRZ-OTU1 {
    base line-coding;
    description
      "ITU-T G.698.2-201811 section 7 table 8-2";
  }

  identity line-coding-NRZ-10G {
    base line-coding;
    description
      "ITU-T G.698.2-201811 section 7 table 8-3/8-5";
  }

  identity line-coding-NRZ-OTU2 {
    base line-coding;
    description
      "ITU-T G.698.2-201811 section 7 table 8-4/8-6";
  }

  identity wavelength-assignment {
    description
      "Wavelength selection base";
    reference
      "RFC6163:Framework for GMPLS and Path Computation Element
      (PCE) Control of Wavelength Switched Optical Networks (WSONs)";
  }

  identity unspecified-wavelength-assignment {
    base wavelength-assignment;
    description
      "No method specified";
  }

  identity first-fit-wavelength-assignment {
    base wavelength-assignment;
    description
      "All the available wavelengths are numbered,
       and this WA (Wavelength Assignment) method chooses
       the available wavelength with the lowest index";
  }

  identity random-wavelength-assignment {
    base wavelength-assignment;
    description
      "This WA method chooses an available
       wavelength randomly";
  }

  identity least-loaded-wavelength-assignment {
    base wavelength-assignment;
    description
      "This WA method selects the wavelength that
       has the largest residual capacity on the most loaded
       link along the route (in multi-fiber networks)";
  }

  identity term-type {
    description
      "Termination type";
    reference
      "ITU-T G.709: Interfaces for the Optical Transport Network";
  }

  identity term-phys {
    base term-type;
    description
      "Physical layer termination";
  }
  identity term-otu {
    base term-type;
    description
      "OTU (Optical Transport Unit) termination";
  }

  identity term-odu {
    base term-type;
    description
      "ODU (Optical Data Unit) termination";
  }

  identity term-opu {
    base term-type;
    description
      "OPU (Optical Payload Unit) termination";
  }

  identity otu-type {
    description
      "Base identity from which specific OTU identities are derived";
    reference
      "ITU-T G.709: Interfaces for the Optical Transport Network";
  }

  identity OTU1 {
    base otu-type;
    description
      "OTU1 (2.66 Gb/s)";
  }

  identity OTU1e {
    base otu-type;
    description
      "OTU1e (11.04 Gb/s)";
  }

  identity OTU1f {
    base otu-type;
    description
      "OTU1f (11.27 Gb/s)";
  }

  identity OTU2 {
    base otu-type;
    description
      "OTU2 (10.70 Gb/s)";
  }
  identity OTU2e {
    base otu-type;
    description
      "OTU2e (11.09 Gb/s)";
  }

  identity OTU2f {
    base otu-type;
    description
      "OTU2f (11.31G)";
  }

  identity OTU3 {
    base otu-type;
    description
      "OTU3 (43.01 Gb/s)";
  }

  identity OTU3e1 {
    base otu-type;
    description
      "OTU3e1 (44.57 Gb/s)";
  }

  identity OTU3e2 {
    base otu-type;
    description
      "OTU3e2 (44.58 Gb/s)";
  }

  identity OTU4 {
    base otu-type;
    description
      "OTU4 (111.80 Gb/s)";
  }

  identity OTUCn {
    base otu-type;
    description
      "OTUCn (n x 105.25 Gb/s)";
  }

  identity type-power-mode {
    description
      "power equalization mode used within the
       OMS and its elements";
  }

  identity power-spectral-density {
    base type-power-mode;
    description
      "all elements must use power spectral density (W/Hz)";
  }

  identity carrier-power {
    base type-power-mode;
    description
      "all elements must use power (dBm)";
  }

/*
 * Typedefs
 */

  typedef operational-mode {
    type string;
    description
      "Organization/vendor specific mode that guarantees
      interoperability.";
    reference "ITU-T G.698.2 (11/2018)";
  }

  typedef standard-mode {
    type string;
    description
      "ITU-T G.698.2 standard mode that guarantees
       interoperability.
       It must be an string with the following format:
       B-DScW-ytz(v) where all these attributes
       are conformant
       to the ITU-T recomendation";
    reference "ITU-T G.698.2 (11/2018)";
  }

  typedef organization-identifier {
    type string;
    description
      "vendor/organization identifier that uses a private mode
      out of already defined in G.698.2 ITU-T application-code";
    reference
      "RFC7581: Routing and Wavelength Assignment Information
       Encoding for Wavelength Switched Optical Networks";
  }

  typedef frequency-thz {
      type decimal64 {
        fraction-digits 6;
      }
      units THz;
      description
        "The DWDM frequency in THz, e.g., 193.112500";
      reference
        "RFC6205: Generalized Labels for
        Lambda-Switch-Capable (LSC) Label Switching Routers";
  }
  typedef frequency-ghz {
      type decimal64 {
        fraction-digits 3;
      }
      units GHz;
      description
        "The DWDM frequency in GHz, e.g., 193112.500";
      reference
        "RFC6205: Generalized Labels for
        Lambda-Switch-Capable (LSC) Label Switching Routers";
  }

  typedef dbm-t {
    type int32;
    units ".01dbm";
    description
      "Amplifiers and Transceivers Power in dBm.";
  }

  typedef snr {
    type decimal64 {
      fraction-digits 2;
    }
    units "dB@0.1nm";
    description
      "(Optical) Signal to Noise Ratio measured over 0.1 nm
      resolution bandwidth";
  }

  typedef fiber-type {
    type enumeration {
      enum G.652 {
      description "G.652 Standard Singlemode Fiber";
      }
      enum G.654 {
        description "G.654 Cutoff Shifted Fiber";
      }
      enum G.653 {
        description "G.653 Dispersion Shifted Fiber";
      }
      enum G.655 {
        description "G.655 Non-Zero Dispersion Shifted Fiber";
      }
      enum G.656 {
        description "G.656 Non-Zero Dispersion for Wideband
               Optical Transport";
      }
      enum G.657 {
        description "G.657 Bend-Insensitive Fiber";
      }
    }
    description
      "ITU-T based fiber-types";
  }

/*
 * Groupings
 */

 /* supported inverse multiplexing capabilities such as
    max. OTSiG:OTSi cardinality
    It is a transponder attribute not transceiver
  */

 /*    leaf multiplexing-cap {
      type uint32;
    config false;
      description "supported inverse multiplexing capabilities
       such as max. OTSiG:OTSi cardinality";
    }
  */

  grouping transceiver-capabilities {
    description
      "This grouping is intended to be use for reporting the
       capabilities of a transceiver.";

    container supported-modes {
      description
        "Transceiver's supported modes.";
      list supported-mode {
        key "mode-id";
        config false;
        description "list of supported transceiver's modes.";
        leaf mode-id {
          type string {
            length "1..255";
          }
          description "ID for the supported transceiver's mode.";
        }
        choice mode {
          mandatory true;
          description
            "Indicates whether the transceiver's mode is a standard
             mode, an organizational mode or an explicit mode.";
          case G.698.2 {
            uses standard-mode;
          }
          case organizational-mode {
            container organizational-mode {
              description
                "The set of attributes for an organizational mode";
              uses organizational-mode;
              uses common-organizational-explicit-mode;
            }  // container organizational-mode
          }
          case explicit-mode {
            container explicit-mode {
               description
                 "The set of attributes for an explicit mode";
              container supported-modes {
                description
                  "Container for all the standard and organizational
                   modes supported by the transceiver's explicit
                   mode.";
                leaf-list supported-application-codes {
                  type leafref {
                    path "../../../mode-id";
                  }
                  must "../../../../"
                     + "supported-mode[mode-id=current()]/"
                     + "standard-mode" {
                    description
                      "The pointer is only for application codes
                       supported by transceiver.";
                  }
                  description
                    "List of pointers to the application codes
                     supported by the transceiver's explicit mode.";
                }
                leaf-list supported-organizational-modes {
                  type leafref {
                    path "../../../mode-id";
                  }
                  must "../../../../"
                     + "supported-mode[mode-id=current()]/"
                     + "organizational-mode" {
                    description
                      "The pointer is only for organizational modes
                       supported by transceiver.";
                  }
                  description
                    "List of pointers to the organizational modes
                     supported by the transceiver's explicit mode.";
                }
              }  // container supported-modes
              uses common-explicit-mode;
              uses common-organizational-explicit-mode;
            }  // container explicit-mode
          } // end of case explicit-mode
        } // end of choice
      }  // list supported-modes
    }  // container supported-modes
  }  // grouping transceiver-capabilities

  grouping standard-mode {
    description
      "ITU-T G.698.2 standard mode that guarantees interoperability.
       It must be an string with the following format:
       B-DScW-ytz(v) where all these attributes are conformant
       to the ITU-T recomendation";

    leaf standard-mode {
      type standard-mode;
      config false;
      description
        "G.698.2 standard mode";
    }
  }

  grouping organizational-mode {
    description
      "Transponder operational mode supported by organizations or
       vendor";

    leaf operational-mode {
      type operational-mode;
      config false;
      description
        "configured organization- or vendor-specific
         application identifiers (AI) supported by the transponder";
    }
    leaf organization-identifier {
      type organization-identifier;
      config false;
      description
      "organization identifier that uses organizational
         mode";
    }
  }

  grouping cd-pmd-penalty {
    description "entries of table; triplet chromatic
    dispersion, polarization mode dispersion and
    associated penalty";

    leaf chromatic-dispersion {
      type decimal64 {
        fraction-digits 2;
        range "0..max";
      }
      units "ps/nm";
      config false;
      mandatory true;
      description "chromatic dispersion";
    }
    leaf polarization-mode-dispersion {
      type decimal64 {
        fraction-digits 2;
        range "0..max";
      }
      units "ps";
      config false;
      mandatory true;
      description "Polarization mode dispersion";
    }
    leaf penalty {
      type decimal64 {
        fraction-digits 2;
        range "0..max";
      }
      units "dB";
      config false;
      mandatory true;
      description "Associated penalty on the receiver";
    }
  }

  grouping pdl-penalty {
    description
      "entries of table; pair of values polarization dependent loss
      and associated penalty";

    leaf max-polarization-dependent-loss {
      type decimal64 {
        fraction-digits 2;
      }
      units "dB";
      config false;
      mandatory true;
      description
        "Maximum acceptable accumulate polarization dependent loss";
    }
    leaf penalty {
      type uint8;
      units "dB";
      config false;
      mandatory true;
      description "Associated penalty on the receiver";
    }
  }

/*
 * This grouping represent the list of attributes related to
 * optical impairment limits for explicit mode
 * (min OSNR, max PMD, max CD, max PDL, Q-factor limit, etc.)
 * In case of standard and operational mode the attributes are
 * implicit
 */

  grouping common-explicit-mode {
    description "Attributes capabilities related to
    explicit mode of an optical transceiver";

    leaf line-coding-bitrate {
      type identityref {
        base line-coding;
      }
      config false;
      description "Bit rate/line coding of optical tributary signal";
      reference
        "ITU-T G.698.2 section 7.1.2";
    }
    leaf max-polarization-mode-dispersion {
      type decimal64 {
        fraction-digits 2;
        range "0..max";
      }
      units "ps";
      config false;
      description
        "Maximum acceptable accumulated polarization mode
         dispersion on the receiver";
    }
    leaf max-chromatic-dispersion {
      type decimal64 {
        fraction-digits 2;
        range "0..max";
      }
      units "ps/nm";
      config false;
      description
        "Maximum acceptable accumulated chromatic dispersion
         on the receiver";
    }
    list chromatic-and-polarization-dispersion-penalty {
      config false;
      description
        "Optional penalty associated with a given accumulated
         CD and PMD.
         This list of triplet cd, pmd, penalty can be used to
         sample the function penalty = f(CD, PMD).";
      uses cd-pmd-penalty ;
    }
    leaf max-diff-group-delay  {
           type int32;
           config false;
           description "Maximum Differential group delay of this mode
                        for this lane";
    }
    list max-polarization-dependent-loss-penalty {
      config false;
      description
        "Optional penalty associated with the maximum acceptable
        accumulated polarization dependent loss.
         This list of pair pdl and penalty can be used to
         sample the function pdl = f(penalty).";
      uses pdl-penalty ;
    }
    leaf available-modulation-type {
      type identityref {
      base modulation;
      }
      config false;
      description
        "Modulation type the specific transceiver in the list
         can support";
    }
    leaf  min-OSNR {
      type snr;
      config false;
      description "min OSNR measured over 0.1 nm
      resolution bandwidth:
      if received OSNR at minimum Rx-power is lower than MIN-OSNR,
      an increased level of bit-errors post-FEC needs
      to be expected.";
      // change resolution BW from 12.5 GHz to 0.1 nm
    }
    leaf  min-Q-factor {
      type int32;
      units "dB";
      config false;
      description "min Qfactor at FEC threshold";
    }
    leaf available-baud-rate {
      type uint32;
      units Bd;
      config false;
      description
        "Baud-rate the specific transceiver in
        the list can support.
         Baud-rate is the unit for
         symbol rate or modulation rate
         in symbols per second or
         pulses per second.
         It is the number of distinct symbol
         changes (signal events) made to the
         transmission medium
         per second in a digitally
         modulated signal or a line code";
    }
    leaf roll-off {
      type decimal64 {
        fraction-digits 4;
        range "0..1";
      }
      config false;
      description
        "the roll-off factor (beta with values from 0 to 1)
        identifies how the real signal shape exceed
        the baud rate. If=0 it is exactly matching
        the baud rate.If=1 the signal exceeds the
        50% of the baud rate at each side.";
    }
    leaf min-carrier-spacing {
      type frequency-ghz;
      config false;
      description
        "This attribute specifies the minimum nominal difference
        between the carrier frequencies of two homogeneous OTSis
        (which have the same optical characteristics but the central
        frequencies) such that if they are placed next to each other
        the interference due to spectrum overlap between them can be
        considered negligible.

        In case of heterogeneous OTSi it is up to path computation
        engine to determine the minimum distance between the carrier
        frequency of the two adjacent OTSi.";
    }
    leaf available-fec-type {
      type identityref {
        base fec-type;
      }
      config false;
      description "Available FEC";
    }
    leaf fec-code-rate {
      type decimal64 {
        fraction-digits 8;
        range "0..max";
      }
      config false;
      description "FEC-code-rate";
    }
    leaf fec-threshold {
      type decimal64 {
        fraction-digits 8;
        range "0..max";
      }
      config false;
      description
        "Threshold on the BER, for which FEC
         is able to correct errors";
    }
  } // grouping common-explicit-mode

  grouping common-organizational-explicit-mode {
    description "Common capability attributes limit range
    in case of operational mode and explicit mode.
    These attributes are supported separately in
    case of application codes";

/* transmitter tuning range (f_tx-min, f_tx-max) */
    leaf min-central-frequency {
      type frequency-thz;
      config false;
      description
        "This parameter indicates the minimum frequency for the
        transmitter tuning range.";
    }
    leaf max-central-frequency {
      type frequency-thz;
      config false;
      description
        "This parameter indicates the maximum frequency for the
        transmitter tuning range.";
    }

/* transmitter-tunability-grid */

    leaf central-frequency-step {
      type frequency-ghz;
      config false;
      description
        "This parameter indicates the transmitter tunability grid as
        the distance between two adjacent carrier frequencies of
        the transmitter tuning range.";
    }

/* supported transmitter power range [p_tx-min, p_tx_max] */

    leaf tx-channel-power-min {
      type dbm-t;
      config false;
      description "The minimum output power of this interface";
    }
    leaf tx-channel-power-max {
      type dbm-t;
      config false;
      description "The maximum output power of this interface";
    }

/* supported receiver power range [p_rx-min, p_rx_max] */

     leaf rx-channel-power-min {
      type dbm-t;
      config false;
      description "The minimum input power of this interface";
    }
    leaf rx-channel-power-max {
      type dbm-t;
      config false;
      description "The maximum input power of this interface";
    }

    leaf rx-total-power-max {
      type dbm-t;
      config false;
      description "Maximum rx optical power for
      all the channels";
    }

  } // grouping common-organizational-explicit-mode

/* This grouping represent the list of configured parameters */
/* values independent of operational mode */

  grouping common-transceiver-configured-param {
    description "Capability of an optical transceiver";

    leaf otsi-carrier-frequency {
        type frequency-thz;
         description
           "OTSi carrier frequency, equivalent to the
           actual configured transmitter frequency";
    }
    leaf tx-channel-power {
        type dbm-t;
        description "The current channel transmit power";
    }
    leaf rx-channel-power {
        type dbm-t;
        config false;
        description "The current channel received power ";
    }
    leaf rx-total-power {
        type dbm-t;
        config false;
        description "Current total received power";
    }
  } // grouping for configured attributes out of mode

  grouping l0-tunnel-attributes {
    description
      "Parameters for Layer0 (WSON or Flexi-Grid) Tunnels.";
    leaf fec-type {
      type identityref {
        base fec-type;
      }
      description
        "FEC type.";
    }
    leaf termination-type {
      type identityref {
        base term-type;
      }
      description
        "Termination type.";
    }
    leaf bit-stuffing {
      type boolean;
      description
        "Bit stuffing enabled/disabled.";
    }
  }

  grouping l0-path-constraints {
    description
      "Global named path constraints configuration
       grouping for Layer0 (WSON or Flexi-Grid) paths.";
    leaf wavelength-assignment {
      type identityref {
        base wavelength-assignment;
      }
      description "Wavelength Allocation Method";
    }
  }

  grouping frequency-range {
    description
      "The parameters that define a frequency range.";
    leaf lower-frequency {
      type frequency-thz;
      mandatory true;
      description
        "The lower frequency boundary of the
        frequency range.";
    }
    leaf upper-frequency {
      type frequency-thz;
      must '. > ../lower-frequency' {
        error-message
          "The upper frequency must be greater than the lower
          frequency.";
      }
      mandatory true;
      description
        "The upper frequency boundary of the
        frequency range.";
    }
  }
}
