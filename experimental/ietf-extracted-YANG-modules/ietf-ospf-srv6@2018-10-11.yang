module ietf-ospf-srv6 {
  namespace "urn:ietf:params:xml:ns:"
          + "yang:ietf-ospf-srv6";
  prefix ospf-srv6;

  import ietf-yang-types {
    prefix "yang";
  }

  import ietf-routing {
    prefix "rt";
  }

  import ietf-ospfv3-extended-lsa {
    prefix "ospfv3-e-lsa";
  }

  import ietf-ospf {
    prefix "ospf";
  }

  import iana-routing-types {
    prefix "iana-rt-types";
  }

  import ietf-inet-types {
    prefix "inet";
  }

  organization
   "IETF OSPF - OSPF Working Group";

  contact
    "WG List:  &lt;mailto:spring@ietf.org&gt;
        Zhibo Hu
          &lt;mailto:huzhibo@huawei.com&gt;
        Jiajia Dong
          &lt;mailto:dongjiajia@huawei.com&gt;
    ";

  description
    "The YANG module defines a generic configuration model for
    Segment IPV6 routing OSPFv3 extensions common across all of the vendor
    implementations.";

  revision 2018-10-11 {
    description
        "Initial revision.";
    reference "RFC XXXX";
  }

  /* Identities */
  identity SRV6_END_FUNC_TYPE {
    description
    "Base identity type for srv6 endpoint function code points.";
  }

  identity SRV6_END_FUNC_NO_PSP_USP {
    base "SRV6_END_FUNC_TYPE";
    description
    "End (no PSP, no USP).";
  }
  identity SRV6_END_FUNC_PSP {
    base "SRV6_END_FUNC_TYPE";
    description
    "End with PSP.";
  }

  identity SRV6_END_FUNC_USP {
    base "SRV6_END_FUNC_TYPE";
    description
    "END with USP.";
  }

  identity SRV6_END_FUNC_PSP_USP {
    base "SRV6_END_FUNC_TYPE";
    description
    "END with PSP & USP.";
  }

  identity SRV6_END_T_FUNC_NO_PSP_USP {
    base "SRV6_END_FUNC_TYPE";
    description
    "End.T (no PSP, no USP).";
  }

  identity SRV6_END_T_FUNC_PSP {
    base "SRV6_END_FUNC_TYPE";
    description
    "End.T with PSP.";
  }

  identity SRV6_END_T_FUNC_USP {
    base "SRV6_END_FUNC_TYPE";
    description
    "End.T with USP.";
  }

  identity SRV6_END_T_FUNC_PSP_USP {
    base "SRV6_END_FUNC_TYPE";
    description
    "End.T with PSP & USP.";
  }

  identity SRV6_END_X_FUNC_NO_PSP_USP {
    base "SRV6_END_FUNC_TYPE";
    description
    "End.x (no PSP, no USP).";
  }

  identity SRV6_END_X_FUNC_PSP {
    base "SRV6_END_FUNC_TYPE";
    description
    "End.x with PSP.";
  }

  identity SRV6_END_X_FUNC_USP {
    base "SRV6_END_FUNC_TYPE";
    description
    "End.x with USP.";
  }

  identity SRV6_END_X_FUNC_PSP_USP {
    base "SRV6_END_FUNC_TYPE";
    description
    "End.x with PSP & USP.";
  }

  identity SRV6_END_FUNC_DX6 {
    base "SRV6_END_FUNC_TYPE";
    description
    "End.DX6 function.";
  }

  identity SRV6_END_FUNC_DT6 {
    base "SRV6_END_FUNC_TYPE";
    description
    "End.DT6 function.";
  }

  identity SRV6_END_FUNC_OTP {
    base "SRV6_END_FUNC_TYPE";
    description
    "END.OTP .";
  }

  /* typedef */
  typedef srv6-sid-value {
    type inet:ipv6-address-no-zone;
    description
      "16 Octets encoded sid value.";
  }

  /* Features */
  feature srv6-ti-lfa {
    description
     "Enhance SRv6 FRR with ti-lfa
     support";
  }

  /* Groupings */
  grouping srv6-msd {
    description
      "means to advertise to advertise node/link specific values for
       Maxium Sid Depths(MSD) of various types";
    container v6-max-value-srh {
      description
      "Maximum SRv6 SID Depths.";
      leaf max-segments-left {
        type uint8;
        description
        "The maximum value of 'SL' field in the SRH of a received packet.";
      }
      leaf max-end-pop {
        type uint8;
        description
        "The maximum number of SIDS in the top SRH in an SRH stack to which
         the router can apply 'PSP' or 'USP'.";
      }
      leaf max-t-insert {
        type uint8;
        description
        "The maximum number of SIDs can be inserted as port of the 'T.insert'
         behavior.";
      }
      leaf max-t-encap {
        type uint8;
        description
        "The maximum number of SIDs can be included as part of the 'T.Encap'
         behavior.";
      }
      leaf max-end-d {
        type uint8;
        description
          "The maximum number of SIDs in an SRH when performing decapsulation
            associated with 'End.Dx' functions (e.g., 'End.DX6' and 'End.DT6').";
      }
    }
  }

  grouping srv6-capabilities {
    description
    "SRV6 capability grouping.";
    container srv6-capability {
      description
        "SRv6 capability.";
      leaf flags {
        type bits {
          bit e-flag {
            position 0;
            description
            "If set, then router is able to
             apply T.Encap operation as specified in
             [filsfils-spring-srv6-network-programming].";
          }
          bit o-flag {
            position 1;
            description
            "If set, then the router is able to
             use of the O-bit in the Segment Routing Header(SRH)
             as defined in [draft-ietf-6man-segment-routing-header].";
          }
        }
        description
        "Flags.";
      }

      container srv6-msd-value {
        description
        "Maximum SRv6 SID Depths.";
        leaf max-segments-left {
          type uint8;
          description
          "The maximum value of 'SL' field in the SRH of a received packet.";
        }
        leaf max-end-pop {
          type uint8;
          description
          "The maximum number of SIDS in the top SRH in an SRH stack to which
           the router can apply 'PSP' or 'USP'.";
        }
        leaf max-t-insert {
          type uint8;
          description
          "The maximum number of SIDs can be inserted as port of the 'T.insert'
           behavior.";
        }
        leaf max-t-encap {
          type uint8;
          description
          "The maximum number of SIDs can be included as part of the 'T.Encap'
           behavior.";
        }
        leaf max-end-d {
          type uint8;
          description
            "The maximum number of SIDs in an SRH when performing decapsulation
              associated with 'End.Dx' functions (e.g., 'End.DX6' and 'End.DT6').";
        }
      }
    }
  }

  grouping srv6-endpoint-func {
     description
      "This group defines srv6 endpoint function";
    container endpoint-func {
      description
        "Srv6 Endpoint function Descriptor.";
      leaf fuc-flags {
        type uint8;
        description
          "No function flags are currently being defined.";
      }
      leaf endpoint-func {
        type identityref {
         base ospf-srv6:SRV6_END_FUNC_TYPE;
        }
        description
          "The endpoint function.";
      }
      leaf undefined-endpoint-func {
        type uint16;
        description
          "Unknown endpoint func value.";
      }
    }
  }

  grouping srv6-end-sid {
    description
    "SRv6 Segment Identifier(SID) with Endpoint functions.";
    leaf flags {
      type uint8;
      description
        "NO flags are currently being defined.";
    }

    uses srv6-endpoint-func;

    leaf sid {
      type srv6-sid-value;
      description
        "SRV6 sid value.";
    }
    // sub-sub-tlvs not yet defined
  }

  grouping srv6-node-sid {
    description
      "This group defines srv6 node sid tlv.";
    uses srv6-endpoint-func;

    leaf sid-flags {
      type uint8;
      description
        "NO sid flags are currently being defined.";
    }

    leaf sid-size {
      type uint8;
      description
        "Number of bits in the SID field";
    }

    leaf sid {
      type srv6-sid-value;
      description
        "SRV6 sid value.";
    }

    leaf neighbor-router-id {
       type yang:dotted-quad;
       description
         "Neighbor router ID.This is only
          used on LAN adjacencies.";
    }

    // sub-tlvs
  }

  grouping srv6-endx-sid {
    description
    "SRv6 sid associated with an adjacency.";

    uses srv6-endpoint-func;

    leaf sid-flags {
      type uint8;
      description
        "NO sid flags are currently being defined.";
    }

    leaf sid-size {
      type uint8;
      description
        "Number of bits in the SID field";
    }

    leaf sid {
      type srv6-sid-value;
      description
        "SRV6 sid value.";
    }

    leaf neighbor-router-id {
       type yang:dotted-quad;
       description
         "Neighbor router ID.This is only
          used on LAN adjacencies.";
    }

    // sub-tlvs
  }

  /* Cfg */
  augment "/rt:routing/" +
          "rt:control-plane-protocols/rt:control-plane-protocol"+
          "/ospf:ospf" {
    when "/rt:routing/rt:control-plane-protocols/"+
         "rt:control-plane-protocol/rt:type = 'ospf:ospfv3'" {
      description
        "This augment OSPF routing protocol when used";
    }
    description
      "This augments OSPF protocol configuration
       with SRv6.";

    container srv6-cfg{
      leaf enable{
        type boolean;
        default "false";
        description
          "Enables SRv6
           protocol extensions.";
      }

      leaf persistent-end-x-sid{
        type boolean;
        default "false";
        description
          "Enable the persistent nature of End.X sid";
      }
      description
        "Configuration about OSPF segment-routing IPv6.";
    }
  }

  augment "/rt:routing/" +
          "rt:control-plane-protocols/rt:control-plane-protocol"+
          "/ospf:ospf/ospf:areas/ospf:area/ospf:interfaces/ospf:interface"+
          "/ospf:fast-reroute"{
    when "/rt:routing/rt:control-plane-protocols/"+
         "rt:control-plane-protocol/rt:type = 'ospf:ospfv3'"{
      description
        "This augment OSPF routing protocol when used";
    }
    description
      "This augments OSPF IPFRR with IPV6 TILFA.";

    container srv6-ti-lfa {

      if-feature srv6-ti-lfa;
      leaf enable {
        type boolean;
        description
          "Enables SRv6 TI-LFA computation.";
      }

      description
        "SRv6 TILFA configuration.";
    }
  }

  /* Database */
  augment "/rt:routing/"
           + "rt:control-plane-protocols/rt:control-plane-protocol/"
           + "ospf:ospf/ospf:areas/ospf:area/"
           + "ospf:database/"
           + "ospf:area-scope-lsa-type/ospf:area-scope-lsas/"
           + "ospf:area-scope-lsa/ospf:version/ospf:ospfv3/"
           + "ospf:ospfv3/ospf:body/ospf:router-information" {
    when "/rt:routing/rt:control-plane-protocols/"+
         "rt:control-plane-protocol/rt:type = 'ospf:ospfv3'" {
      description
        "This augment OSPFv3 routing protocol when used";
    }
    description
     "This augments OSPFv3 protocol router capability.";
      uses srv6-capabilities;
  }

  augment "/rt:routing/"
           + "rt:control-plane-protocols/rt:control-plane-protocol/"
           + "ospf:ospf/ospf:areas/ospf:area/"
           + "ospf:database/"
           + "ospf:area-scope-lsa-type/ospf:area-scope-lsas/"
           + "ospf:area-scope-lsa/ospf:version/ospf:ospfv3/"
           + "ospf:ospfv3/ospf:body/ospfv3-e-lsa:e-router/"
           + "ospfv3-e-lsa:e-router-tlvs/ospfv3-e-lsa:link-tlv/"
           + "ospfv3-e-lsa:sub-tlvs" {
    when "/rt:routing/rt:control-plane-protocols/"+
         "rt:control-plane-protocol/rt:type = 'ospf:ospfv3'" {
    }
    description
     "This augments OSPFv3 protocol neighbor.";
    container srv6-endx-sids-sub-tlv {
      description
        "This defines svr6 end-x sids for the adjacency.";
      list endx-sid {
        key "sid";
        uses srv6-endx-sid;
        description
           "List of end-x sids.";
      }
    }
  }

  augment "/rt:routing/"
           + "rt:control-plane-protocols/rt:control-plane-protocol/"
           + "ospf:ospf/ospf:areas/ospf:area/"
           + "ospf:database/"
           + "ospf:area-scope-lsa-type/ospf:area-scope-lsas/"
           + "ospf:area-scope-lsa/ospf:version/ospf:ospfv3/"
           + "ospf:ospfv3/ospf:body/ospf:router-information" {
    when "/rt:routing/rt:control-plane-protocols/"+
         "rt:control-plane-protocol/rt:type = 'ospf:ospfv3'" {
      description
      "This augment OSPFv3 routing protocol when used.";
    }
    description
     "This augment OSPFv3 routing protocol when used";
    container srv6-node-sids {
      description
         "This defines srv6 node sid tlvs.";
      list srv6-node-sids {
        key "sid";
        uses srv6-node-sid;
        description
          "List of srv6 node sids.";
      }
    }
  }
  /* Notifications */
}
