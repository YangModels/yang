submodule ietf-bgp-rib-attributes {
  yang-version 1.1;
  belongs-to ietf-bgp {
    prefix bgp;
  }

  // import some basic types

  import ietf-bgp-types {
    prefix ibt;
    reference
      "RFC XXXX: YANG Model for Border Gateway Protocol (BGP-4).";
  }
  import iana-bgp-community-types {
    prefix bct;
    reference
      "RFC XXXX: YANG Model for Border Gateway Protocol (BGP-4).";
  }
  import ietf-bgp-community-types {
    prefix ibct;
    reference
      "RFC XXXX: YANG Model for Border Gateway Protocol (BGP-4).";
  }
  import ietf-inet-types {
    prefix inet;
    reference
      "RFC 9911: Common YANG Data Types.";
  }
  import ietf-yang-semver {
    prefix ysv;
    reference
      "I-D.ietf-netmod-yang-semver: YANG Semantic Versioning";
  }

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This submodule contains common data definitions for BGP
     attributes for use in BGP RIB tables.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-10-16 {
    description
      "Initial version";
    ysv:version 0.0.9;
    reference
      "RFC XXXX: YANG Model for Border Gateway Protocol (BGP-4).";
  }

  grouping bgp-as-path-segment {
    description
      "Data for representing BGP AS-PATH segment";

    leaf type {
      type ibt:as-path-segment-type;
      description
        "The type of AS-PATH segment";
    }
    leaf-list member {
      type inet:as-number;
      description
        "List of the AS numbers in the AS-PATH segment";
    }
  }

  grouping bgp-unknown-attr-top {
    description
      "Unknown path attributes that are not expected to be shared
       across route entries, common to LOC-RIB and Adj-RIB";
    container unknown-attributes {
      description
        "Unknown path attributes that were received in the UPDATE
         message which contained the prefix.";

      list unknown-attribute {
        key "attr-type";
        description
          "This list contains received attributes that are
           unrecognized or unsupported by the local router. The list
           may be empty.";

        leaf optional {
          type boolean;
          description
            "Defines whether the attribute is optional (if
             set to true) or well-known (if set to false).
             Set in the high-order bit of the BGP attribute
             flags octet.";
          reference
            "RFC 4271: A Border Gateway Protocol 4 (BGP-4).";
        }

        leaf transitive {
          type boolean;
          description
            "Defines whether an optional attribute is transitive
             (if set to true) or non-transitive (if set to false).
             For well-known attributes, the transitive flag must be
             set to true. Set in the second high-order bit of the BGP
             attribute flags octet.";
          reference
            "RFC 4271: A Border Gateway Protocol 4 (BGP-4).";
        }

        leaf partial {
          type boolean;
          description
            "Defines whether the information contained in the
             optional transitive attribute is partial (if set to
             true) or complete (if set to false). For well-known
             attributes and for optional non-transitive attributes,
             the partial flag must be set to false. Set in the third
             high-order bit of the BGP attribute flags octet.";
          reference
            "RFC 4271: A Border Gateway Protocol 4 (BGP-4).";
        }

        leaf extended {
          type boolean;
          description
            "Defines whether the attribute length is one octet
             (if set to false) or two octets (if set to true). Set in
             the fourth high-order bit of the BGP attribute flags
             octet.";
          reference
            "RFC 4271: A Border Gateway Protocol 4 (BGP-4).";
        }
        leaf attr-type {
          type uint8;
          description
            "1-octet value encoding the attribute type code";
          reference
            "RFC 4271: A Border Gateway Protocol 4 (BGP-4).";
        }

        leaf attr-len {
          type uint16;
          description
            "One or two octet attribute length field indicating the
             length of the attribute data in octets.  If the Extended
             Length attribute flag is set, the length field is 2
             octets, otherwise it is 1 octet";
          reference
            "RFC 4271: A Border Gateway Protocol 4 (BGP-4).";
        }

        leaf attr-value {
          type binary {
            length "0..65535";
          }
          description
            "Raw attribute value, not including the attribute
             flags, type, or length.  The maximum length
             of the attribute value data is 2^16-1 per the max value
             of the attr-len field (2 octets).";
          reference
            "RFC 4271: A Border Gateway Protocol 4 (BGP-4).";
        }
      }
    }
  }

  grouping bgp-adj-rib-attr-state {
    description
      "Path attributes that are not expected to be shared across
       route entries, specific to Adj-RIB";
    leaf path-id {
      type uint32;
      description
        "When the BGP speaker supports advertisement of multiple
         paths for a prefix, the path identifier is used to
         uniquely identify a route based on the combination of the
         prefix and path id.  In the Adj-RIB-In, the path-id value is
         the value received in the update message.   In the Loc-RIB,
         if used, it should represent a locally generated path-id
         value for the corresponding route.  In Adj-RIB-Out, it
         should be the value sent to a neighbor when add-paths is
         used, i.e., the capability has been negotiated.";
      reference
        "RFC 7911: Advertisement of Multiple Paths in BGP.";
    }
  }

  grouping bgp-community-attr-state {
    description
      "Common definition of BGP community attributes";
    leaf-list community {
      type union {
        type bct:bgp-well-known-community-type;
        type ibct:bgp-std-community-type;
      }
      description
        "List of standard or well-known BGP community
         attributes.";
    }
  }

  grouping ext-community-attributes {
    description
      "A grouping for all extended community parameters.";

    leaf-list ext-community {
      type bct:bgp-ext-community-type;
      description
        "List of BGP extended community attributes. The received
         extended community may be an explicitly modeled
         type or unknown, represented by an 8-octet value
         formatted according to RFC 4360.";
      reference
        "RFC 4360: BGP Extended Communities Attribute.";
    }

    leaf-list ext-community-raw {
      type string {
        pattern 'raw:([0-9A-F][0-9A-F]:){7}[0-9A-F][0-9A-F]';
      }
      description
        "Extended community type in raw format only, encoded as
         raw:(hex-octet):(hex-octet):...:(hex-octet) with 8
         hex-encoded octets.";
    }
  }

  grouping ipv6-ext-community-attributes {
    description
      "A grouping for all IPv6 extended community parameters.";

    leaf-list ipv6-ext-community {
      type bct:bgp-ipv6-ext-community-type;
      description
        "List of BGP IPv6 extended community attributes. The received
         IPv6 extended community may be an explicitly modeled
         type or unknown, represented by an 20-octet value
         formatted according to RFC 5701.";
      reference
        "RFC 5701: IPv6 Address Specific BGP Extended Community
         Attribute, Section 3.";
    }

    leaf-list ipv6-ext-community-raw {
      type string {
        pattern 'ipv6-raw:'
             + '([0-9A-Fa-f][0-9A-Fa-f]:){19}'
             + '[0-9A-Fa-f][0-9A-Fa-f]';
      }
      description
        "IPv6 extended community type in raw format only, encoded as
         ipv6-raw:(hex-octet):(hex-octet):...:(hex-octet) with 20
         hex-encoded octets.";
    }
  }

  grouping large-community-attributes {
    description
      "A grouping for all large community parameters.";

    leaf-list large-community {
      type ibct:bgp-large-community-type;
      description
        "List of BGP large community attributes.";
      reference
        "RFC 8092: BGP Large Communities Attribute.";
    }
  }
}
