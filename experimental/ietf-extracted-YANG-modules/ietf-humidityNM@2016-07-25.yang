module ietf-humidityNM{

yang-version 1.1;  // needed for action

namespace
            "urn:ietf:params:xml:ns:yang:ietf-humidityNM";

prefix humid;

            organization
            "IPSO";

            contact
            "WG Web:   http://tools.ietf.org/wg/core/
            WG List:  mailto:core@ietf.org

            WG Chair: Carsten Bormann
            mailto:cabo@tzi.org

            WG Chair: Jaime Jimenez
            mailto:jaime.jimenez@ericsson.com

            Editor:   Peter van der Stok
            mailto:consultancy@vanderstok.org

            Editor:   Jaime Jimenez
            mailto:jaime.jimenez@ericsson.com";

            description
  "This module contains information about the
operation of the IPSO LWM2M humidity sensor with ID 3304.

Copyright (c) 2016 IETF Trust and the persons identified as
authors of the code.  All rights reserved.

Redistribution and use in source and binary forms, with or
without modification, is permitted pursuant to, and subject
to the license terms contained in, the Simplified BSD License
set forth in Section 4.c of the IETF Trust's Legal Provisions
Relating to IETF Documents
      (http://trustee.ietf.org/license-info).

This version of this YANG module is part of RFC XXXX; see
the RFC itself for full legal notices.";

            revision "2016-07-25" {
            description "Initial revision.";
            reference
            "I-D:draft-vanderstok-core-yang-lwm2m:
YANG language applied to the LWM2M IPSO humidity sensor
specification";
            }

            list IPSO-humidity {
            key instance;
            config   false;   //  should be same as key leaf
            description
            "3304: The humidity sensor is composed of
              a set of instances";
            leaf instance {
            type uint16{
            range "0..1";   // only one instance zero (0)
            }
            config false;    // R access
            mandatory "true";
            description
            "the number of the humidity sensor instance";
            }
            leaf Sensor_Value  {
            type decimal64{    // YANG has no float
            fraction-digits 2;
            range "10.0 .. 66.6";}
            units "Defined by 'Units' resource";
            config false;    // R access
            mandatory "true";
            description
            "5700: Last or Current Measured Value
               from the Sensor";
            }
            leaf Units {
            type string;
            units "Defined by 'Units' resource";
            config false;    // R access
            description
            "5701: Measurement unit definition
                e.g. 'Cel' for temperature in Celsius";
            }
            leaf Min_Measured_Value {
            type decimal64{    // YANG has no float
            fraction-digits 2;
            range "10.0 .. 66.6";}
            units "Defined by 'Units' resource";
            config false;    // R access
            description
            "5601: The minimum value measured by
               the sensor since power ON or reset";
            }
            leaf Max_Measured_Value {
            type decimal64{    // YANG has no float
            fraction-digits 2;
            range "10.0 .. 66.6";}
            units "Defined by 'Units' resource";
            config false;    // R access
            description
            "5602: The maximum value measured
                by the sensor since power ON or reset";
            }
            leaf Min_Range_Value {
            type decimal64{    // YANG has no float
            fraction-digits 2;
            range "10.0 .. 66.6";}
            units "Defined by 'Units' resource";
            config false;    // R access
            description
            "5603: The minimum value that can be measured
               by the sensor";
            }
            leaf Max_Range_Value{
            type decimal64{    // YANG has no float
            fraction-digits 2;
            range "10.0 .. 66.6";}
            units "Defined by 'Units' resource";
            config false;    // R access
            description
            "5604: The maximum value that can be measured
               by the sensor";
            }
            action Reset_Min_and_Max_measured_values {
            // E access: this is an RPC
            // without input and output parameter
            description
            "5605: Reset the Min and Max measured values
               to current value";
            }  // rpc
            }  // list ID3304
            } // module ietf-yang-humidity
