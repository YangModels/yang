module ietf-vpn-common {
  yang-version 1.1;
  namespace "urn:ietf:params:xml:ns:yang:ietf-vpn-common";
  prefix vpn-common;

  import ietf-netconf-acm {
    prefix nacm;
    reference
      "RFC 8341: Network Configuration Access Control Model";
  }
  import ietf-routing-types {
    prefix rt-types;
    reference
      "RFC 8294: Common YANG Data Types for the Routing Area";
  }
  import ietf-yang-types {
    prefix yang;
    reference
      "Section 3 of RFC 6991";
  }

  organization
    "IETF OPSA (Operations and Management Area) Working Group";
  contact
    "WG Web:   <https://datatracker.ietf.org/wg/opsawg/>
     WG List:  <mailto:opsawg@ietf.org>

     Editor:  Samier Barguil
              <mailto:samier.barguilgiraldo.ext@telefonica.com>
     Editor:  Oscar Gonzalez de Dios
              <mailto:oscar.gonzalezdedios@telefonica.com>

     Editor:  Mohamed Boucadair
              <mailto:mohamed.boucadair@orange.com>

     Author:  Qin Wu
              <mailto:bill.wu@huawei.com>";
  description
    "This YANG module defines a common module that is meant
     to be reused by various VPN-related modules (e.g.,
     Layer 3 VPN Service Model (L3SM), Layer 2 VPN Service
     Model (L2SM), Layer 3 VPN Network Model (L3NM), Layer 2
     VPN Network Model (L2NM)).

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2020-09-15 {
    description
      "Initial revision.";
    reference
      "RFC XXXX: A Layer 2/3 VPN Common YANG Model";
  }

  /* Features */

  feature cloud-access {
    description
      "Indicates support of the VPN to connect to a Cloud
       Service Provider (CSP).";
  }

  feature lag-interface {
    description
      "Indicates the support of link aggregation between
       VPN site network accesses.";
  }

  feature site-diversity {
    description
      "Indicates the support of site diversity constraints
       in the customer premises. An example of these
       constraints may be to avoid connecting
       a site network access to the same Provider
       Edge as a target site network access.";
  }

  feature dot1q {
    description
      "Indicates the support of the 'dot1q'
       encapsulation.";
    reference
      "IEEE Std 802.1Q: Bridges and Bridged Networks";
  }

  feature qinq {
    description
      "Indicates the support of the 'qinq'
       encapsulation.";
    reference
      "IEEE Std 802.1ad: Provider Bridges";
  }

  feature vxlan {
    description
      "Indicates the support of the 'vxlan'
       encapsulation.";
    reference
      "RFC 7348: Virtual eXtensible Local Area  Network (VXLAN):
                 A Framework for Overlaying Virtualized Layer 2
                 Networks over Layer 3 Networks";
  }

  feature qinany {
    description
      "Indicates the support of the 'qinany'
       encapsulation.";
  }

  feature multicast {
    description
      "Indicates multicast capabilities support in a VPN.";
    reference
      "RFC 6513: Multicast in MPLS/BGP IP VPNs";
  }

  feature ipv4 {
    description
      "Indicates IPv4 support in a VPN.";
  }

  feature ipv6 {
    description
      "Indicates IPv6 support in a VPN.";
  }

  feature carrierscarrier {
    description
      "Indicates support of Carrier-of-Carrier VPNs.";
    reference
      "Section 9 of RFC 4364";
  }

  feature extranet-vpn {
    description
      "Indicates support of extranet VPNs. That is,
       the capability of a VPN to access a list of
       other VPNs.";
  }

  feature fast-reroute {
    description
      "Indicates support of Fast Reroute (FRR).";
  }

  feature qos {
    description
      "Indicates support of Classes of Services (CoSes).";
  }

  feature encryption {
    description
      "Indicates support of encryption.";
  }

  feature rtg-ospf {
    description
      "Indicates support of the OSPF routing protocol.";
    reference
      "RFC 4577: OSPF as the Provider/Customer Edge Protocol
                 for BGP/MPLS IP Virtual Private Networks
                 (VPNs)";
  }

  feature rtg-ospf-sham-link {
    description
      "This feature indicates the support of OSPF sham links.";
    reference
      "Section 4.2.7 of RFC 4577";
  }

  feature rtg-bgp {
    description
      "Indicates support of BGP as the Provider/Customer
       Edge protocol.";
  }

  feature rtg-rip {
    description
      "Indicates support of RIP as the Provider/Customer
       Edge protocol.";
  }

  feature rtg-vrrp {
    description
      "Indicates support of the Virtual Router Redundancy
       Protocol (VRRP) between a cutsomer LAN and the PE.";
  }

  feature rtg-isis {
    description
      "Indicates the support of IS-IS as the Provider/Customer
       Edge protocol.";
  }

  feature bfd {
    description
      "Indicates support of Bidirectional Forwarding Detection
       (BFD) between the CE and the PE.";
    reference
      "RFC 5880: Bidirectional Forwarding Detection (BFD)";
  }

  feature bearer-reference {
    description
      "Indicates support of the bearer reference access
       constraint. That is, the reuse of a network connection
       that was already ordered to the SP apart from the IP VPN
       site.";
  }
  feature input-bw {
    description
      "Indicates the support of the input bandwidth in a VPN.";
  }

  /* Typedef */

  typedef vpn-id {
    type string;
    description
      "Defines an identifier that is used as
       a service identifier, for example.";
  }

  typedef address-family {
    type enumeration {
      enum ipv4 {
        description
          "IPv4 address family.";
      }
      enum ipv6 {
        description
          "IPv6 address family.";
      }
    }
    description
      "Defines a type for the address family.";
  }

  //L2xMs

  typedef ccm-priority-type {
    type uint8 {
      range "0..7";
    }
    description
      "A 3-bit priority value to be used in the VLAN tag,
       if present in the transmitted frame.";
  }

  typedef control-mode {
    type enumeration {
      enum peer {
        description
          "'peer' mode, i.e., participate in the protocol towards
           the CE.  Peering is common for LACP and the Ethernet
           Local Management Interface (E-LMI) and, occasionally,
           for LLDP.  For VPLSs and VPWSs, the subscriber can also
           request that the SP peer enable spanning tree.";
      }
      enum tunnel {
        description
          "'tunnel' mode, i.e., pass to the egress or destination
           site.  For EPLs, the expectation is that L2CP frames are
           tunneled.";
      }
      enum discard {
        description
          "'discard' mode, i.e., discard the frame.";
      }
    }
    description
      "Defines the type of control mode on L2CP protocols.";
  }

  typedef neg-mode {
    type enumeration {
      enum full-duplex {
        description
          "Defines full-duplex mode.";
      }
      enum auto-neg {
        description
          "Defines auto-negotiation mode.";
      }
    }
    description
      "Defines the type of negotiation mode.";
  }

  /* Identities */

  identity routing-protocol-type {
    description
      "Base identity for routing protocol type.";
  }

  identity ospf {
    base routing-protocol-type;
    description
      "Identity for OSPF protocol type.";
  }

  identity bgp {
    base routing-protocol-type;
    description
      "Identity for BGP protocol type.";
  }

  identity static {
    base routing-protocol-type;
    description
      "Identity for static routing protocol type.";
  }

  identity rip {
    base routing-protocol-type;
    description
      "Identity for RIP protocol type.";
  }

  identity isis {
    base routing-protocol-type;
    description
      "Identity for IS-IS protocol type.";
  }

  identity vrrp {
    base routing-protocol-type;
    description
      "Identity for VRRP protocol type.

       This is to be used when LANs are directly connected
       to PE routers.";
  }

  identity direct {
    base routing-protocol-type;
    description
      "Identity for direct protocol type.

       This is to be used when LANs are directly connected
       to PE routers and and must be advertised in the VPN.";
  }

  identity bw-direction {
    description
      "Identity for the bandwidth direction.";
  }

  identity input-bw {
    base bw-direction;
    description
      "Identity for the input bandwidth.";
  }

  identity output-bw {
    base bw-direction;
    description
      "Identity for the output bandwidth.";
  }

  identity bw-type {
    description
      "Identity of the bandwidth type.";
  }

  identity bw-per-cos {
    base bw-type;
    description
      "Bandwidth is per CoS.";
  }

  identity bw-per-port {
    base bw-type;
    description
      "Bandwidth is per site network access.";
  }

  identity bw-per-site {
    base bw-type;
    description
      "Bandwidth is per site.  It is applicable to
       all the site network accesses within a site.";
  }

  identity bw-per-svc {
    base bw-type;
    description
      "Bandwidth is per VPN service.";
  }

  identity qos-profile-direction {
    description
      "Base identity for the QoS profile direction.";
  }

  identity site-to-wan {
    base qos-profile-direction;
    description
      "Identity for Site-to-WAN direction.";
  }
  identity wan-to-site {
    base qos-profile-direction;
    description
      "Identity for WAN-to-Site direction.";
  }

  identity both {
    base qos-profile-direction;
    description
      "Identity for both WAN-to-Site and Site-to-WAN
       directions.";
  }

  identity customer-application {
    description
      "Base identity for customer applications.";
  }

  identity web {
    base customer-application;
    description
      "Identity for a aWeb application (e.g., HTTP, HTTPS).";
  }

  identity mail {
    base customer-application;
    description
      "Identity for a mail application.";
  }

  identity file-transfer {
    base customer-application;
    description
      "Identity for a file transfer application
       (e.g., FTP, SFTP).";
  }

  identity database {
    base customer-application;
    description
      "Identity for a database application.";
  }

  identity social {
    base customer-application;
    description
      "Identity for a social-network application.";
  }
  identity games {
    base customer-application;
    description
      "Identity for a gaming application.";
  }

  identity p2p {
    base customer-application;
    description
      "Identity for a peer-to-peer application.";
  }

  identity network-management {
    base customer-application;
    description
      "Identity for a management application
       (e.g., Telnet, syslog, SNMP).";
  }

  identity voice {
    base customer-application;
    description
      "Identity for a voice application.";
  }

  identity video {
    base customer-application;
    description
      "Identity for a video conference application.";
  }

  identity embb {
    base customer-application;
    description
      "Identity for an enhanced Mobile Broadband (eMBB)
       application.  Note that an eMBB application demands
       network performance with a wide variety of
       characteristics, such as data rate, latency,
       loss rate, reliability, and many other parameters.";
  }

  identity urllc {
    base customer-application;
    description
      "Identity for an Ultra-Reliable and Low Latency
       Communications (URLLC) application.  Note that a
       URLLC application demands network performance
       with a wide variety of characteristics, such as latency,
       reliability, and many other parameters.";
  }

  identity mmtc {
    base customer-application;
    description
      "Identity for a massive Machine Type
       Communications (mMTC) application.  Note that an
       mMTC application demands network performance
       with a wide variety of characteristics, such as data
       rate, latency, loss rate, reliability, and many
       other parameters.";
  }

  identity ie-type {
    description
      "Defines Import-Export routing profiles.
       Those profiles can be reused between VPN nodes.";
  }

  identity import {
    base ie-type;
    description
      "Import a routing profile.";
  }

  identity export {
    base ie-type;
    description
      "Export a routing profile.";
  }

  identity import-export {
    base ie-type;
    description
      "Import/Export a routing profile.";
  }

  identity site-network-access-type {
    description
      "Base identity for site-network-access type.";
  }

  identity point-to-point {
    base site-network-access-type;
    description
      "Identity for point-to-point connections.";
  }
  identity multipoint {
    base site-network-access-type;
    description
      "Identity for multipoint connections.
       Example: Ethernet broadcast segment.";
  }

  identity pseudowire {
    base site-network-access-type;
    description
      "Identity for pseudowire connections.";
  }

  identity loopback {
    base site-network-access-type;
    description
      "Identity for loopback connections.";
  }

  identity operational-status {
    description
      "Base identity for the operational status.";
  }

  identity operational-state-up {
    base operational-status;
    description
      "Operational status is UP/Enabled.";
  }

  identity operational-state-down {
    base operational-status;
    description
      "Operational status is DOWN/Disabled.";
  }

  identity operational-state-unknown {
    base operational-status;
    description
      "Operational status is UNKNOWN.";
  }

  identity administrative-status {
    description
      "Base identity for administrative status.";
  }

  identity administrative-state-up {
    base administrative-status;
    description
      "Administrative status is UP/Enabled.";
  }

  identity administrative-state-down {
    base administrative-status;
    description
      "Administrative status is DOWN/Disabled.";
  }

  identity administrative-state-testing {
    base administrative-status;
    description
      "Administrative status is up for testing purposes.";
  }

  identity administrative-state-pre-deployment {
    base administrative-status;
    description
      "Administrative status is pre-deployment phase.
       That is prior to the actual deployment of a service.";
  }

  identity encapsulation-type {
    description
      "Base identity for the encapsulation type.";
  }

  identity priority-tagged {
    base encapsulation-type;
    description
      "Identity for the priority-tagged interface.";
  }

  identity dot1q {
    base encapsulation-type;
    description
      "Identity for the support of the 'dot1q'
       encapsulation.";
  }

  identity qinq {
    base encapsulation-type;
    description
      "Identity for the support of the 'qinq'
       encapsulation.";
  }
  identity qinany {
    base encapsulation-type;
    description
      "Identity for the support of the 'qinany'
       encapsulation.";
  }

  identity vxlan {
    base encapsulation-type;
    description
      "Identity for the support of the 'vxlan'
       encapsulation.";
  }

  identity ethernet-type {
    base encapsulation-type;
    description
      "Identity of the Ethernet encapsulation type.";
  }

  identity vlan-type {
    base encapsulation-type;
    description
      "Identity of the VLAN encapsulation.";
  }

  identity untagged-int {
    base encapsulation-type;
    description
      "Identity of the untagged interface type.";
  }

  identity tagged-int {
    base encapsulation-type;
    description
      "Identity of the tagged interface type.";
  }

  identity lag-int {
    base encapsulation-type;
    description
      "Identity of the Link Aggregation Group (LAG)
       interface type.";
    reference
      "IEEE Std. 802.1AX: Link Aggregation";
  }

  identity tag-type {
    description
      "Base identity of the tag types.";
  }

  identity c-vlan {
    base tag-type;
    description
      "A CVLAN tag, normally using the 0x8100 Ethertype.";
  }

  identity s-vlan {
    base tag-type;
    description
      "An SVLAN tag.";
  }

  identity c-s-vlan {
    base tag-type;
    description
      "Uses both a CVLAN tag and an SVLAN tag.";
  }

  identity protocol-type {
    description
      "Base identity for Protocol Type.";
  }

  identity gre {
    base protocol-type;
    description
      "GRE encapsulation.";
    reference
      "RFC 1701: Generic Routing Encapsulation (GRE)
       RFC 1702: Generic Routing Encapsulation over IPv4 networks
       RFC 7676: IPv6 Support for Generic Routing Encapsulation
                 (GRE)";
  }

  identity ldp {
    base protocol-type;
    description
      "Transport based on LDP.";
    reference
      "RFC 3086: LDP Specification";
  }

  identity sr {
    base protocol-type;
    description
      "Transport based on SR.";
    reference
      "RFC 8660: Segment Routing with the MPLS Data Plane
       RFC 8663: MPLS Segment Routing over IP
       RFC 8754: IPv6 Segment Routing Header (SRH)";
  }

  identity sr-te {
    base protocol-type;
    description
      "Transport based on SR-TE.";
    reference
      "RFC 8426: Recommendations for RSVP-TE and Segment Routing (SR)
                 Label Switched Path (LSP) Coexistence";
  }

  identity rsvp-te {
    base protocol-type;
    description
      "Transport based on RSVP-TE.";
    reference
      "RFC 2205: Resource ReSerVation Protocol (RSVP) --
                 Version 1 Functional Specification";
  }

  identity bgp-lu {
    base protocol-type;
    description
      "Transport based on BGP-LU.";
    reference
      "RFC 8277: Using BGP to Bind MPLS Labels to Address
                 Prefixes";
  }

  identity unknown {
    base protocol-type;
    description
      "Not known protocol type.";
  }

  identity vpn-topology {
    description
      "Base identity of the VPN topology.";
  }

  identity any-to-any {
    base vpn-topology;
    description
      "Identity for any-to-any VPN topology.";
  }

  identity hub-spoke {
    base vpn-topology;
    description
      "Identity for Hub-and-Spoke VPN topology.";
  }

  identity hub-spoke-disjoint {
    base vpn-topology;
    description
      "Identity for Hub-and-Spoke VPN topology
       where Hubs cannot communicate with each other.";
  }

  identity custom {
    base vpn-topology;
    description
      "Identity of a custom VPN topology where Hubs
       can act as Spoke for certain parts of
       the network or Spokes as Hubs.";
  }

  identity role {
    description
      "Base identity of a site or a node role.";
  }

  identity any-to-any-role {
    base role;
    description
      "Identity of any-to-any IP VPN.";
  }

  identity spoke-role {
    base role;
    description
      "A node or a site is acting as a Spoke IP VPN.";
  }

  identity hub-role {
    base role;
    description
      "A node or a site isacting as a Hub IP VPN.";
  }

  identity custom-role {
    base role;
    description
      "A node or a site is custom role in the VPN.";
  }

  identity vpn-signaling-type {
    description
      "Identity of VPN signaling types";
  }

  identity l2vpn-bgp {
    base vpn-signaling-type;
    description
      "Identity of Layer 2 VPNs using BGP";
    reference
      "RFC 6624: Layer 2 Virtual Private Networks Using BGP for
                 Auto-Discovery and Signaling";
  }

  identity evpn-bgp {
    base vpn-signaling-type;
    description
      "Identity of BGP Ethernet VPNs.";
    reference
      "RFC 7432: BGP MPLS-Based Ethernet VPN";
  }

  identity t-ldp {
    base vpn-signaling-type;
    description
      "Identity of Targeted Label Distribution Protocol.";
    reference
      "RFC 5036: LDP Specification";
  }

  identity h-vpls {
    base vpn-signaling-type;
    description
      "Identity of hierarchical VPLS.";
    reference
      "RFC 4762: Virtual Private LAN Service (VPLS) Using
                 Label Distribution Protocol (LDP)
                 Signaling";
  }

  identity l2tp {
    base vpn-signaling-type;
    description
      "Identity of l2tp.";
  }

  identity service-type {
    description
      "Identity of service type.";
  }

  identity l3vpn {
    base service-type;
    description
      "Identity of L3VPN service.";
  }

  identity vpws {
    base service-type;
    description
      "Identity of the Point-to-point Virtual Private
       Wire Service (VPWS) service type.";
  }

  identity pwe3 {
    base service-type;
    description
      "Identity of the Pseudowire Emulation Edge to Edge
       (PWE3) service type.";
  }

  identity ldp-l2tp-vpls {
    base service-type;
    description
      "Identity of the LDP-based or L2TP-based multipoint
       Virtual Private LAN Service (VPLS) service type.
       This VPLS uses LDP-signaled Pseudowires
       or L2TP-signaled Pseudowires.";
  }

  identity bgp-vpls {
    base service-type;
    description
      "Identity of the BGP-based multipoint VPLS service type.
       This VPLS uses a BGP control plane.";
    reference
      "RFC 4761:  Virtual Private LAN Service (VPLS) Using
                 BGP for Auto-Discovery and Signaling
       RFC 6624: Layer 2 Virtual Private Networks Using BGP for
                 Auto-Discovery and Signaling";
  }

  identity vpws-evpn {
    base service-type;
    description
      "Identity of the VPWS service type using EVPNs.";
    reference
      "RFC 8214: Virtual Private Wire Service Support
                 in Ethernet VPN";
  }

  identity pbb-evpn {
    base service-type;
    description
      "Identity of Provider Backbone Bridging (PBB) EVPNs.";
    reference
      "RFC 7623: Provider Backbone Bridging Combined
                 with Ethernet VPN (PBB-EVPN)";
  }

  identity vxlan-peer-mode {
    description
      "Base identity for the VXLAN peer mode.";
  }

  identity static-mode {
    base vxlan-peer-mode;
    description
      "Identity for VXLAN access in the static mode.";
  }

  identity bgp-mode {
    base vxlan-peer-mode;
    description
      "Identity for VXLAN access by BGP EVPN learning.";
  }

  identity multicast-gp-address-mapping {
    description
      "Identity for multicast group mapping type.";
  }

  identity static-mapping {
    base multicast-gp-address-mapping;
    description
      "Identity for static mapping, i.e., attach the interface
       to the multicast group as a static member.";
  }
  identity dynamic-mapping {
    base multicast-gp-address-mapping;
    description
      "Identity for dynamic mapping, i.e., an interface was added
       to the multicast group as a result of snooping.";
  }

  identity multicast-tree-type {
    description
      "Base identity for multicast tree type.";
  }

  identity ssm-tree-type {
    base multicast-tree-type;
    description
      "Identity for SSM tree type.";
  }

  identity asm-tree-type {
    base multicast-tree-type;
    description
      "Identity for ASM tree type.";
  }

  identity bidir-tree-type {
    base multicast-tree-type;
    description
      "Identity for bidirectional tree type.";
  }

  identity multicast-rp-discovery-type {
    description
      "Base identity for RP discovery type.";
  }

  identity auto-rp {
    base multicast-rp-discovery-type;
    description
      "Base identity for Auto-RP discovery type.";
  }

  identity static-rp {
    base multicast-rp-discovery-type;
    description
      "Base identity for static type.";
  }

  identity bsr-rp {
    base multicast-rp-discovery-type;
    description
      "Base identity for BSR discovery type.";
  }

  identity tf-type {
    description
      "Identity for the traffic type.";
  }

  identity multicast-traffic {
    base tf-type;
    description
      "Identity for multicast traffic.";
  }

  identity broadcast-traffic {
    base tf-type;
    description
      "Identity for broadcast traffic.";
  }

  identity unknown-unicast-traffic {
    base tf-type;
    description
      "Identity for unknown unicast traffic.";
  }

  identity bundling-type {
    description
      "The base identity for the bundling type.  It supports
       multiple CE-VLANs associated with an L2VPN service or
       all CE-VLANs associated with an L2VPN service.";
  }

  identity multi-svc-bundling {
    base bundling-type;
    description
      "Identity for multi-service bundling, i.e.,
       multiple CE-VLAN IDs can be associated with an
       L2VPN service at a site.";
  }

  identity one2one-bundling {
    base bundling-type;
    description
      "Identity for one-to-one service bundling, i.e.,
       each L2VPN can be associated with only one CE-VLAN ID
       at a site.";
  }

  identity all2one-bundling {
    base bundling-type;
    description
      "Identity for all-to-one bundling, i.e., all CE-VLAN IDs
       are mapped to one L2VPN service.";
  }

  /* Grouping */

  grouping vpn-description {
    leaf vpn-id {
      type vpn-common:vpn-id;
      description
        "VPN identifier.
         This identifier has a local meaning.";
    }
    leaf vpn-name {
      type string;
      description
        "A name used to refer to the VPN.";
    }
    leaf vpn-description {
      type string;
      description
        "Textual description of a VPN service.";
    }
    leaf customer-name {
      type string;
      description
        "Name of the customer that actually uses the VPN service.";
    }
    description
      "Provides common VPN information.";
  }

  grouping vpn-profile-cfg {
    container valid-provider-identifiers {
      list cloud-identifier {
        if-feature "cloud-access";
        key "id";
        leaf id {
          type string;
          description
            "Identification of cloud service.
             Local administration meaning.";
        }
        description
          "List for Cloud Identifiers.";
      }
      list encryption-profile-identifier {
        key "id";
        leaf id {
          type string;
          description
            "Identification of the SP encryption profile
             to be used.  Local administration meaning.";
        }
        description
          "List for encryption profile identifiers.";
      }
      list qos-profile-identifier {
        key "id";
        leaf id {
          type string;
          description
            "Identification of the QoS Profile to be used.
             Local administration meaning.";
        }
        description
          "List for QoS Profile Identifiers.";
      }
      list bfd-profile-identifier {
        key "id";
        leaf id {
          type string;
          description
            "Identification of the SP BFD Profile to be used.
             Local administration meaning.";
        }
        description
          "List for BFD Profile identifiers.";
      }
      list forwarding-profile-identifier {
        key "id";
        leaf id {
          type string;
          description
            "Identification of the Forwrding Profile Filter to be used.
             Local administration meaning.";
        }
        description
          "List for Forwrding Profile identifiers.";
      }
      list routing-profile-identifier {
        key "id";
        leaf id {
          type string;
          description
            "Identification of the routing Profile to be used
             by the routing-protocols within sites, vpn-
             network-accesses or vpn-nodes for refering
             vrf-import/export policies.
             This identifier has a local meaning.";
        }
        description
          "List for Routing Profile Identifiers.";
      }
      nacm:default-deny-write;
      description
        "Container for Valid Provider Identifies.";
    }
    description
      "Grouping for VPN Profile configuration.";
  }

  grouping status-timestamp {
    leaf status {
      type identityref {
        base operational-status;
      }
      description
        "Operations status";
    }
    leaf last-updated {
      type yang:date-and-time;
      description
        "Indicates the actual date and time of the service
         status change.";
    }
    description
      "This grouping defines some operational
       parameters for the service.";
  }

  grouping service-status {
    container status {
      container admin-status {
        leaf status {
          type identityref {
            base administrative-status;
          }
          description
            "Administrative service status.";
        }
        leaf last-updated {
          type yang:date-and-time;
          description
            "Indicates the actual date and time of the service
             status change.";
        }
        description
          "Administrative service status.";
      }
      container oper-status {
        config false;
        uses status-timestamp;
        description
          "Operational service status.";
      }
      description
        "Service status.";
    }
    description
      "Service status grouping.";
  }

  grouping svc-transport-encapsulation {
    container underlay-transport {
      leaf-list type {
        type identityref {
          base protocol-type;
        }
        ordered-by user;
        description
          "Protocols used to deliver a VPN service.";
      }
      description
        "Container for the Transport underlay.";
    }
    description
      "This grouping defines the type of underlay transport
       for VPN service.";
  }

  grouping rt-rd {
    leaf rd {
      type union {
        type rt-types:route-distinguisher;
        type empty;
      }
      description
        "Route distinguisher value. If this leaf has not been
         configured, the server will auto-assign a route
         distinguisher value and use that value operationally.
         This calculated value is available in the operational
         state.

         Use the empty type to indicate RD has no value and
         is not to be aouto-assigned.";
    }
    container vpn-targets {
      description
        "Set of route-targets to match for import and export routes
         to/from VRF";
      uses vpn-route-targets;
    }
    description
      "Grouping for RT and RD.";
  }

  grouping vpn-route-targets {
    description
      "A grouping that specifies Route Target import-export rules
       used in a BGP-enabled VPN.";
    list vpn-target {
      key "id";
      leaf id {
        type int8;
        description
          "Identifies each VPN Target";
      }
      list route-targets {
        key "route-target";
        leaf route-target {
          type rt-types:route-target;
          description
            "Route Target value";
        }
        description
          "List of Route Targets.";
      }
      leaf route-target-type {
        type rt-types:route-target-type;
        mandatory true;
        description
          "Import/export type of the Route Target.";
      }
      description
        "L3VPN route targets. AND/OR Operations are available
         based on the RTs assigment.";
    }
    reference
      "RFC 4364: BGP/MPLS IP Virtual Private Networks (VPNs)
       RFC 4664: Framework for Layer 2 Virtual Private Networks
                 (L2VPNs)";
    container vpn-policies {
      description
        "VPN policies";
      leaf import-policy {
        type string;
        description
          "Defines the import policy.";
      }
      leaf export-policy {
        type string;
        description
          "Defines the export policy.";
      }
    }
  }

  grouping vpn-node-group {
    container groups {
      list group {
        key "group-id";
        leaf group-id {
          type string;
          description
            "Group-id the vpn-node belongs to.";
        }
        description
          "List of group-ids.";
      }
      description
        "Groups the vpn node and network access belongs to.";
    }
    description
      "Grouping definition to assign
       group-ids to group or network access.";
  }
}
