module ietf-te-packet-types {
  yang-version 1.1;
  namespace "urn:ietf:params:xml:ns:yang:ietf-te-packet-types";
  prefix te-packet-types;

  import ietf-yang-types {
    prefix yang;
    reference
      "RFC 9911: Common YANG Data Types";
  }
  import ietf-te-types {
    prefix te-types;
    reference
      "RFC XXXX: Common YANG Data Types for Traffic Engineering";
  }

  organization
    "IETF Traffic Engineering Architecture and Signaling (TEAS)
     Working Group";
  contact
    "WG Web:   <https://datatracker.ietf.org/wg/teas/>
     WG List:  <mailto:teas@ietf.org>

     Editor:   Tarek Saad
               <mailto:tsaad.net@gmail.com>

     Editor:   Rakesh Gandhi
               <mailto:rgandhi@cisco.com>

     Editor:   Vishnu Pavan Beeram
               <mailto:vishnupavan.ietf@gmail.com>

     Editor:   Xufeng Liu
               <mailto:xufeng.liu.ietf@gmail.com>

     Editor:   Igor Bryskin
               <mailto:i_bryskin@yahoo.com>";
  description
    "This YANG module contains a collection of generally useful YANG
     data type definitions specific to Packet Traffic Engineering
     (TE).

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF published modules can be found
     at the YANG Parameters registry group
     (https://www.iana.org/assignments/yang-parameters).

     This version of this YANG module is part of RFC XXXX; see
     the RFC itself for full legal notices.";

  revision 2026-05-08 {
    description
      "This revision adds the following new identities:
       - bandwidth-profile-type;
       - link-metric-delay-variation;
       - link-metric-loss;
       - path-metric-delay-variation;
       - path-metric-loss.

       This revision adds the following new groupings:
       - bandwidth-profile-parameters;
       - te-packet-path-bandwidth;
       - te-packet-link-bandwidth.

       This revision provides also few editorial changes.";
    reference
      "RFC XXXX: Common YANG Data Types for Traffic Engineering";
  }
  revision 2020-06-10 {
    description
      "Latest revision of TE MPLS types.";
    reference
      "RFC 8776: Common YANG Data Types for Traffic Engineering";
  }

  /*
   * Identities
   */

  identity bandwidth-profile-type {
    description
      "Bandwidth Profile Types";
  }

  identity mef-10 {
    base bandwidth-profile-type;
    description
      "MEF 10 Bandwidth Profile";
    reference
      "MEF 10.3: Ethernet Services Attributes Phase 3";
  }

  identity rfc-2697 {
    base bandwidth-profile-type;
    description
      "RFC 2697 Bandwidth Profile";
    reference
      "RFC 2697: A Single Rate Three Color Marker";
  }

  identity rfc-2698 {
    base bandwidth-profile-type;
    description
      "RFC 2698 Bandwidth Profile";
    reference
      "RFC 2698: A Two Rate Three Color Marker";
  }

  // Derived identities from te-types:link-metric-type

  identity link-metric-delay-variation {
    base te-types:link-metric-type;
    description
      "The Unidirectional Delay Variation Metric,
       measured in units of microseconds.";
    reference
      "RFC 7471: OSPF Traffic Engineering (TE) Metric Extensions,
                 Section 4.3
       RFC 8570: IS-IS Traffic Engineering (TE) Metric Extensions,
                 Section 4.3";
  }

  identity link-metric-loss {
    base te-types:link-metric-type;
    description
      "The Unidirectional Link Loss Metric,
       measured in units of 0.000003%.";
    reference
      "RFC 7471: OSPF Traffic Engineering (TE) Metric Extensions,
                 Section 4.4
       RFC 8570: IS-IS Traffic Engineering (TE) Metric Extensions,
                 Section 4.4";
  }

  // Derived identities from te-types:path-metric-type

  identity path-metric-delay-variation {
    base te-types:path-metric-type;
    description
      "The Path Delay Variation Metric,
       measured in units of microseconds.";
    reference
      "RFC 8233: Extensions to the Path Computation Element
                 Communication Protocol (PCEP) to Compute
                 Service-Aware Label Switched Paths (LSPs),
                 Section 3.1.2";
  }

  identity path-metric-loss {
    base te-types:path-metric-type;
    description
      "The Path Loss Metric, measured in units of 0.000003%.";
    reference
      "RFC 8233: Extensions to the Path Computation Element
                 Communication Protocol (PCEP) to Compute
                 Service-Aware Label Switched Paths (LSPs),
                 Section 3.1.3";
  }

  identity backup-protection-type {
    description
      "Base identity for the backup protection type.";
  }

  identity backup-protection-link {
    base backup-protection-type;
    description
      "Backup provides link protection only.";
  }

  identity backup-protection-node-link {
    base backup-protection-type;
    description
      "Backup offers node (preferred) or link protection.";
  }

  identity bc-model-type {
    description
      "Base identity for the Diffserv-TE Bandwidth Constraints
       Model type.";
    reference
      "RFC 4124: Protocol Extensions for Support of Diffserv-aware
                 MPLS Traffic Engineering";
  }

  identity bc-model-rdm {
    base bc-model-type;
    description
      "Russian Dolls Bandwidth Constraints Model type.";
    reference
      "RFC 4127: Russian Dolls Bandwidth Constraints Model for
                 Diffserv-aware MPLS Traffic Engineering";
  }

  identity bc-model-mam {
    base bc-model-type;
    description
      "Maximum Allocation Bandwidth Constraints Model type.";
    reference
      "RFC 4125: Maximum Allocation Bandwidth Constraints Model for
                 Diffserv-aware MPLS Traffic Engineering";
  }

  identity bc-model-mar {
    base bc-model-type;
    description
      "Maximum Allocation with Reservation Bandwidth Constraints
       Model type.";
    reference
      "RFC 4126: Max Allocation with Reservation Bandwidth
                 Constraints Model for Diffserv-aware MPLS Traffic
                 Engineering & Performance Comparisons";
  }

  /*
   * Typedefs
   */

  typedef te-bandwidth-requested-type {
    type enumeration {
      enum specified-value {
        description
          "Bandwidth value is explicitly specified.";
      }
      enum specified-profile {
        description
          "Bandwidth profile is explicitly specified.";
      }
      enum auto {
        description
          "Bandwidth is automatically computed.";
      }
    }
    description
      "Enumerated type for specifying whether bandwidth is
       explicitly specified or automatically computed.";
  }

  typedef te-class-type {
    type uint8;
    description
      "Diffserv-TE Class-Type.
       Defines a set of Traffic Trunks crossing a link that is
       governed by a specific set of bandwidth constraints.

       Class-Type is used for the purposes of link bandwidth
       allocation, constraint-based routing, and admission control.";
    reference
      "RFC 4124: Protocol Extensions for Support of Diffserv-aware
                 MPLS Traffic Engineering";
  }

  typedef bc-type {
    type uint8 {
      range "0..7";
    }
    description
      "Diffserv-TE bandwidth constraints as defined in RFC 4124.";
    reference
      "RFC 4124: Protocol Extensions for Support of Diffserv-aware
                 MPLS Traffic Engineering";
  }

  typedef bandwidth-kbps {
    type uint64;
    units "kilobits per second";
    description
      "Bandwidth values, expressed in kilobits per second.";
  }

  typedef bandwidth-mbps {
    type uint64;
    units "megabits per second";
    description
      "Bandwidth values, expressed in megabits per second.";
  }

  typedef bandwidth-gbps {
    type uint64;
    units "gigabits per second";
    description
      "Bandwidth values, expressed in gigabits per second.";
  }

  /*
   * Groupings
   */

  grouping performance-metrics-attributes-packet {
    description
      "Contains Performance Metrics (PM) information.";
    reference
      "RFC 7471: OSPF Traffic Engineering (TE) Metric Extensions
       RFC 8570: IS-IS Traffic Engineering (TE) Metric Extensions
       RFC 7823: Performance-Based Path Selection for Explicitly
                 Routed Label Switched Paths (LSPs) Using TE Metric
                 Extensions";
    uses te-types:performance-metrics-attributes {
      augment "performance-metrics-one-way" {
        description
          "Performance Metrics (PM) one-way packet-specific
           augmentation for a generic PM grouping.";
        leaf one-way-min-delay {
          type uint32 {
            range "0..16777215";
          }
          units "microseconds";
          description
            "One-way minimum delay or latency.";
        }
        leaf one-way-min-delay-normality {
          type te-types:performance-metrics-normality;
          default "normal";
          description
            "One-way minimum delay or latency normality.";
        }
        leaf one-way-max-delay {
          type uint32 {
            range "0..16777215";
          }
          units "microseconds";
          description
            "One-way maximum delay or latency.";
        }
        leaf one-way-max-delay-normality {
          type te-types:performance-metrics-normality;
          default "normal";
          description
            "One-way maximum delay or latency normality.";
        }
        leaf one-way-delay-variation {
          type uint32 {
            range "0..16777215";
          }
          units "microseconds";
          description
            "One-way delay variation.";
          reference
            "RFC 5481: Packet Delay Variation Applicability
                       Statement, Section 4.2";
        }
        leaf one-way-delay-variation-normality {
          type te-types:performance-metrics-normality;
          default "normal";
          description
            "One-way delay variation normality.";
          reference
            "RFC 7471: OSPF Traffic Engineering (TE) Metric
                       Extensions
             RFC 8570: IS-IS Traffic Engineering (TE) Metric
                       Extensions
             RFC 7823: Performance-Based Path Selection for
                       Explicitly Routed Label Switched Paths (LSPs)
                       Using TE Metric Extensions";
        }
        leaf one-way-packet-loss {
          type decimal64 {
            fraction-digits 6;
            range "0..50.331642";
          }
          units "percent";
          description
            "One-way packet loss as a percentage of the total traffic
             sent over a configurable interval.

             The finest precision is 0.000003%.";
          reference
            "RFC 8570: IS-IS Traffic Engineering (TE) Metric
                       Extensions, Section 4.4";
        }
        leaf one-way-packet-loss-normality {
          type te-types:performance-metrics-normality;
          default "normal";
          description
            "Packet loss normality.";
          reference
            "RFC 7471: OSPF Traffic Engineering (TE) Metric
                       Extensions
             RFC 8570: IS-IS Traffic Engineering (TE) Metric
                       Extensions
             RFC 7823: Performance-Based Path Selection for
                       Explicitly Routed Label Switched Paths (LSPs)
                       Using TE Metric Extensions";
        }
      }
      augment "performance-metrics-two-way" {
        description
          "Performance Metrics (PM) two-way packet-specific
           augmentation for a generic PM grouping.";
        reference
          "RFC 7471: OSPF Traffic Engineering (TE) Metric Extensions
           RFC 8570: IS-IS Traffic Engineering (TE) Metric Extensions
           RFC 7823: Performance-Based Path Selection for Explicitly
                     Routed Label Switched Paths (LSPs) Using TE
                     Metric Extensions";
        leaf two-way-min-delay {
          type uint32 {
            range "0..16777215";
          }
          units "microseconds";
          default "0";
          description
            "Two-way minimum delay or latency.";
        }
        leaf two-way-min-delay-normality {
          type te-types:performance-metrics-normality;
          default "normal";
          description
            "Two-way minimum delay or latency normality.";
          reference
            "RFC 7471: OSPF Traffic Engineering (TE) Metric
                       Extensions
             RFC 8570: IS-IS Traffic Engineering (TE) Metric
                       Extensions
             RFC 7823: Performance-Based Path Selection for
                       Explicitly Routed Label Switched Paths (LSPs)
                       Using TE Metric Extensions";
        }
        leaf two-way-max-delay {
          type uint32 {
            range "0..16777215";
          }
          units "microseconds";
          default "0";
          description
            "Two-way maximum delay or latency.";
        }
        leaf two-way-max-delay-normality {
          type te-types:performance-metrics-normality;
          default "normal";
          description
            "Two-way maximum delay or latency normality.";
          reference
            "RFC 7471: OSPF Traffic Engineering (TE) Metric
                       Extensions
             RFC 8570: IS-IS Traffic Engineering (TE) Metric
                       Extensions
             RFC 7823: Performance-Based Path Selection for
                       Explicitly Routed Label Switched Paths (LSPs)
                       Using TE Metric Extensions";
        }
        leaf two-way-delay-variation {
          type uint32 {
            range "0..16777215";
          }
          units "microseconds";
          default "0";
          description
            "Two-way delay variation.";
          reference
            "RFC 5481: Packet Delay Variation Applicability
                       Statement, Section 4.2";
        }
        leaf two-way-delay-variation-normality {
          type te-types:performance-metrics-normality;
          default "normal";
          description
            "Two-way delay variation normality.";
          reference
            "RFC 7471: OSPF Traffic Engineering (TE) Metric
                       Extensions
             RFC 8570: IS-IS Traffic Engineering (TE) Metric
                       Extensions
             RFC 7823: Performance-Based Path Selection for
                       Explicitly Routed Label Switched Paths (LSPs)
                       Using TE Metric Extensions";
        }
        leaf two-way-packet-loss {
          type decimal64 {
            fraction-digits 6;
            range "0..50.331642";
          }
          units "percent";
          default "0";
          description
            "Two-way packet loss as a percentage of the total traffic
             sent over a configurable interval.

             The finest precision is 0.000003%.";
        }
        leaf two-way-packet-loss-normality {
          type te-types:performance-metrics-normality;
          default "normal";
          description
            "Two-way packet loss normality.";
        }
      }
    }
  }

  grouping one-way-performance-metrics-packet {
    description
      "One-way packet Performance Metrics (PM) throttle grouping.";
    leaf one-way-min-delay {
      type uint32 {
        range "0..16777215";
      }
      units "microseconds";
      default "0";
      description
        "One-way minimum delay or latency.";
    }
    leaf one-way-max-delay {
      type uint32 {
        range "0..16777215";
      }
      units "microseconds";
      default "0";
      description
        "One-way maximum delay or latency.";
    }
    leaf one-way-delay-variation {
      type uint32 {
        range "0..16777215";
      }
      units "microseconds";
      default "0";
      description
        "One-way delay variation.";
    }
    leaf one-way-packet-loss {
      type decimal64 {
        fraction-digits 6;
        range "0..50.331642";
      }
      units "percent";
      default "0";
      description
        "One-way packet loss as a percentage of the total traffic
         sent over a configurable interval.

         The finest precision is 0.000003%.";
    }
  }

  grouping one-way-performance-metrics-gauge-packet {
    description
      "One-way packet Performance Metrics (PM) throttle grouping.

       This grouping is used to report the same metrics defined in
       the one-way-performance-metrics-packet grouping, using gauges
       instead of uint32 data types and referencing IPPM RFCs
       instead of IGP-TE RFCs.";
    leaf one-way-min-delay {
      type yang:gauge64;
      units "microseconds";
      description
        "One-way minimum delay or latency.";
    }
    leaf one-way-max-delay {
      type yang:gauge64;
      units "microseconds";
      description
        "One-way maximum delay or latency.";
      reference
        "RFC 7679: A One-Way Delay Metric for IP Performance
                   Metrics (IPPM)";
    }
    leaf one-way-delay-variation {
      type yang:gauge64;
      units "microseconds";
      description
        "One-way delay variation.";
      reference
        "RFC 3393: IP Packet Delay Variation Metric for IP
                   Performance Metrics (IPPM)";
    }
    leaf one-way-packet-loss {
      type decimal64 {
        fraction-digits 5;
        range "0..100";
      }
      description
        "The ratio of packets dropped to packets transmitted between
         two endpoints.";
      reference
        "RFC 7680: A One-Way Loss Metric for IP Performance
                   Metrics (IPPM)";
    }
  }

  grouping two-way-performance-metrics-packet {
    description
      "Two-way packet Performance Metrics (PM) throttle grouping.";
    leaf two-way-min-delay {
      type uint32 {
        range "0..16777215";
      }
      units "microseconds";
      default "0";
      description
        "Two-way minimum delay or latency.";
    }
    leaf two-way-max-delay {
      type uint32 {
        range "0..16777215";
      }
      units "microseconds";
      default "0";
      description
        "Two-way maximum delay or latency.";
    }
    leaf two-way-delay-variation {
      type uint32 {
        range "0..16777215";
      }
      units "microseconds";
      default "0";
      description
        "Two-way delay variation.";
    }
    leaf two-way-packet-loss {
      type decimal64 {
        fraction-digits 6;
        range "0..50.331642";
      }
      units "percent";
      default "0";
      description
        "Two-way packet loss as a percentage of the total traffic
         sent over a configurable interval.

         The finest precision is 0.000003%.";
    }
  }

  grouping two-way-performance-metrics-gauge-packet {
    description
      "Two-way packet Performance Metrics (PM) throttle grouping.

       This grouping is used to report the same metrics defined in
       the two-way-performance-metrics-packet grouping, using gauges
       instead of uint32 data types and referencing IPPM RFCs
       instead of IGP-TE RFCs.";
    leaf two-way-min-delay {
      type yang:gauge64;
      units "microseconds";
      description
        "Two-way minimum delay or latency.";
      reference
        "RFC 2681: A Round-trip Delay Metric for IPPM";
    }
    leaf two-way-max-delay {
      type yang:gauge64;
      units "microseconds";
      description
        "Two-way maximum delay or latency.";
      reference
        "RFC 2681: A Round-trip Delay Metric for IPPM";
    }
    leaf two-way-delay-variation {
      type yang:gauge64;
      units "microseconds";
      description
        "Two-way delay variation.";
      reference
        "RFC 5481: Packet Delay Variation Applicability Statement";
    }
    leaf two-way-packet-loss {
      type decimal64 {
        fraction-digits 5;
        range "0..100";
      }
      description
        "The ratio of packets dropped to packets transmitted between
         two endpoints.";
    }
  }

  grouping performance-metrics-throttle-container-packet {
    description
      "Packet Performance Metrics (PM) threshold grouping.";
    uses te-types:performance-metrics-throttle-container {
      augment "throttle/threshold-out" {
        description
          "Performance Metrics (PM) threshold-out packet
           augmentation for a generic grouping.";
        uses one-way-performance-metrics-packet;
        uses two-way-performance-metrics-packet;
      }
      augment "throttle/threshold-in" {
        description
          "Performance Metrics (PM) threshold-in packet augmentation
           for a generic grouping.";
        uses one-way-performance-metrics-packet;
        uses two-way-performance-metrics-packet;
      }
      augment "throttle/threshold-accelerated-advertisement" {
        description
          "Performance Metrics (PM) accelerated advertisement packet
           augmentation for a generic grouping.";
        uses one-way-performance-metrics-packet;
        uses two-way-performance-metrics-packet;
      }
    }
  }

  grouping bandwidth-profile-parameters {
    description
      "Common parameters to define bandwidth profiles, also known as
       traffic profiles in RFC 2475, that may be used to specify the
       temporal properties of a packet stream (e.g., MPLS-TE LSPs),
       e.g., as specified in MEF 10, RFC 2697 or RFC 2698.";
    reference
      "RFC 2475: An Architecture for Differentiated Services
       MEF 10.3: Ethernet Services Attributes Phase 3
       RFC 2697: A Single Rate Three Color Marker
       RFC 2698: A Two Rate Three Color Marker";
    leaf cir {
      type uint64;
      units "bits per second";
      description
        "Committed Information Rate (CIR).";
    }
    leaf cbs {
      type uint64;
      units "bytes";
      description
        "Committed Burst Size (CBS).";
    }
    leaf eir {
      type uint64;
      units "bits per second";
      description
        "Excess Information Rate (EIR).";
    }
    leaf ebs {
      type uint64;
      units "bytes";
      description
        "Excess Burst Size (EBS).";
    }
    leaf pir {
      type uint64;
      units "bits per second";
      description
        "Peak Information Rate (PIR).";
    }
    leaf pbs {
      type uint64;
      units "bytes";
      description
        "Peak Burst Size (PBS).";
    }
  }

  grouping te-packet-path-bandwidth {
    description
      "Bandwidth attributes for TE Packet paths.";
    container packet-bandwidth {
      description
        "Bandwidth attributes for TE Packet paths.";
      leaf specification-type {
        type te-bandwidth-requested-type;
        description
          "The bandwidth specification type, either explicitly
           specified or automatically computed.";
      }
      leaf set-bandwidth {
        when "../specification-type = 'specified-value'" {
          description
            "When the bandwidth value is explicitly specified.";
        }
        type bandwidth-kbps;
        description
          "Set the bandwidth value explicitly, e.g., using offline
           calculation.";
      }
      container bandwidth-profile {
        when "../specification-type = 'specified-profile'" {
          description
            "When the bandwidth profile is explicitly specified.";
        }
        description
          "Set the bandwidth profile attributes explicitly.";
        leaf bandwidth-profile-name {
          type string;
          description
            "Name of Bandwidth Profile.";
        }
        leaf bandwidth-profile-type {
          type identityref {
            base bandwidth-profile-type;
          }
          description
            "Type of Bandwidth Profile.";
        }
        uses bandwidth-profile-parameters;
      }
      leaf class-type {
        type te-types:te-ds-class;
        description
          "The Class-Type of traffic transported by the LSP.";
        reference
          "RFC 4124: Protocol Extensions for Support of
                     Diffserv-aware MPLS Traffic Engineering,
                     Section 4.3.1";
      }
      leaf signaled-bandwidth {
        type te-packet-types:bandwidth-kbps;
        config false;
        description
          "The currently signaled bandwidth of the LSP.

           In the case where the bandwidth is specified
           explicitly, then this will match the value of the
           set-bandwidth leaf.

           In the cases where the bandwidth is dynamically
           computed by the system, the current value of the
           bandwidth should be reflected.";
      }
    }
  }

  grouping te-packet-link-bandwidth {
    description
      "Bandwidth attributes for Packet TE links.";
    leaf packet-bandwidth {
      type uint64;
      units "bits per second";
      description
        "Bandwidth value for Packet TE links.";
    }
  }
}
