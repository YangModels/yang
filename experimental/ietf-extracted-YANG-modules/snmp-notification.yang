submodule snmp-notification {

  belongs-to snmp {
    prefix snmp;
  }

  include snmp-common;
  include snmp-target;
  include snmp-target-params;

  reference
    "RFC3413: Simple Network Management Protocol (SNMP) Applications
     SNMP-NOTIFICATION-MIB";

  revision 2010-10-17 {
    description
      "Initial revision.";
  }

  augment /snmp:snmp/snmp:target {
    leaf notify-profile {
      if-feature snmp:notification-filter;
      type leafref {
        path "/snmp/notify-profile/name";
      }
    }
  }

  augment /snmp:snmp {

    list notify {

      key name;

      description
        "Targets that will receive notifications.";
      reference "SNMP-NOTIFY-MIB.snmpNotifyTable";

      leaf name {
        type snmp:identifier;
        description
          "An arbitrary name for the list entry.";
        reference "SNMP-NOTIFY-MIB.snmpNotifyName";
      }
      leaf tag {
        type leafref {
          path "/snmp/target/tag";
        }
        mandatory true;
        description
          "Target tag, selects a set of notification targets.";
        reference "SNMP-NOTIFY-MIB.snmpNotifyTag";
      }
      leaf type {
        type enumeration {
          enum trap { value 1; }
          enum inform { value 2; }
        }
        must
          '. != inform or '
        + 'not(/snmp/target[tag = current()/../name]'
        + '      /../usm[../engine-id] != '
        + '    /snmp/target[tag = current()/../name]/../usm)' {
          error-message
            "When inform is configured, all v3 targets must have an
             engine-id configured.";
        }
        default trap;
        description "Defines the notification type to be generated.";
        reference "SNMP-NOTIFY-MIB.snmpNotifyType";
      }
    }

    list notify-profile {
      if-feature snmp:notification-filter;
      key name;

      description
        "Notification filter profiles associated with targets.";
      reference "SNMP-NOTIFY-MIB.snmpNotifyFilterProfileTable";

      leaf name {
        type snmp:identifier;
        description "Name of the filter profile";
        reference "SNMP-NOTIFY-MIB.snmpNotifyFilterProfileName";
      }
      list subtree {
        key "oids";

        reference "SNMP-NOTIFY-MIB.snmpNotifyFilterTable";

        leaf oids {
          type wildcard-object-identifier;
          description
            "A family of subtrees included in this filter.";
          reference "SNMP-NOTIFY-MIB.snmpNotifyFilterSubtree
                     SNMP-NOTIFY-MIB.snmpNotifyFilterMask";
        }

        choice type {
          mandatory true;
          leaf included {
            type empty;
            description
              "The family of subtrees is included in the filter.";
          }
          leaf excluded {
            type empty;
            description
              "The family of subtrees is excluded from the filter.";
          }
          reference "SNMP-NOTIFY-MIB.snmpNotifyFilterType";
        }
      }
    }
  }
}
