module ietf-ucpe {
  namespace "urn:ietf:params:xml:ns:yang:ietf-ucpe";
  prefix ietf-ucpe;

  organization "SFR";
  contact
    "Dmytro Shytyi
     EMail:ietf.dmytro@shytyi.net";
  description
     "This is a Network Function Virtualization (NFV) YANG
     service model.

     Copyright (c) 2019 IETF Trust and the persons identified as
     authors of the code.  All rights reserved.
     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2019-10-19 {
    description
      "Yang model was cleaned.Ietf interfaces added";
    reference "draft-shytyi-opsawg-vysm-04";
  }
  revision 2019-09-16 {
    description
      "Added 0day config for VNFs.
       Yang model modified according
       to the received comments.";
    reference "draft-shytyi-opsawg-vysm-00";
  }
  revision 2018-01-07 {
    description
      "Initial revision.";
    reference "draft-shytyi-netmod-vysm-01";
  }

    list ucpe {
      key "name";
      leaf name {
        type string;
        description
          "Device identificator";
        }
        description
          "Name of the instance of the service";
      list links {
        key "link";
        leaf link {
          type string {
            pattern "[a-zA-Z0-9]*";
          }
          description
            "Name of the virtual link from the pool of
             the links";
        }
        description
          "Pool of the virtual links that connect
           VMs and Interfaces";
      }
      list switches {
        key "switch";
        leaf switch {
          type string;
          description
            "Name of the forwarding domain";
        }
        list ports {
          key "port";
          leaf port {
            type uint64 {
              range "10..15";
            }
            description
              "Name of the connector";
          }
          leaf name {
            type string;
            description
              "Name of the subconnector";
          }
          leaf link {
            type leafref {
              path "../../../links/link";
            }
            description
              "Link that is connected to the switch
               via port";
          }
          description
            "Set of the connectors the forwarding
             domain has";
        }
        description
          "Set of the forwarding domains";
      }
      list vms {
        key "vm";
        leaf vm {
          type string {
            pattern "[a-zA-Z]*";
          }
          description
            "Name of the Virtual Machine";
        }
        list ports {
          key "port";
          leaf port {
            type string;
            description
              "Name of the connector";
          }
          leaf name {
            type string;
            description
              "Name of the subconnector";
          }
          leaf link {
            type leafref {
              path "../../../links/link";
            }
            description
              "Link that connects the VM with a
               switch or Interface via connector";
          }
          description
            "Set of Virtual Machine connectors";
        }
        leaf ram {
          type uint64;
          description
            "Size of RAM to allocate for the
             Guest OS";
        }
        leaf cpu {
          type uint64;
          description
            "Number of vCPUs to allocate for the
             Guest OS";
        }
        list storages {
          key "id";
          leaf id {
            type string;
            description
              "Name of the Storage";
          }
          leaf location {
            type string;
            description
              "External location where the image is
               saved.";
          }
          description
            "Virtual storge of the image for the
             Virtual Machine";
        }
        container day0-config {
          leaf location {
            type string;
            description
              "0day configuration location";
          }
          leaf day0-var-path {
            type string;
            description
              "path of the file that contains the
               0day variables";
          }
          list variable {
            key "name";
            leaf name {
              type string;
              description
                "variable name";
            }
            leaf value {
              type string;
              description
                "variable value";
            }
            description
              "name:value";

          }
          description
            "0day configuration:init config";
        }
        description
          "Set of the Virtual Machines configured on
           the universal Customer-Premises Equipment";
      }
    }
  }
