module ietf-yang-package-types {
  yang-version 1.1;
  namespace "urn:ietf:params:xml:ns:yang:ietf-yang-package-types";
  prefix "pkg-types";

  import ietf-yang-revisions {
    prefix rev;
    reference "XXXX: Updated YANG Module Revision Handling";
  }

  import ietf-yang-semver  {
    prefix ys;
    reference "XXXX: YANG Semantic Versioning";
  }

  import ietf-yang-types {
    prefix yang;
    rev:recommended-min-date 2019-07-21;
    reference "RFC 6991bis: Common YANG Data Types.";
  }

  import ietf-inet-types {
    prefix inet;
    rev:recommended-min-date 2013-07-15;
    reference "RFC 6991: Common YANG Data Types.";
  }

  import ietf-module-tags {
    prefix tags;
    // RFC Ed. Fix revision once revision date of
    // ietf-module-tags.yang is known.
    reference "RFC XXX: YANG Module Tags.";
  }

  organization
    "IETF NETMOD (Network Modeling) Working Group";

  contact
    "WG Web:   <http://tools.ietf.org/wg/netmod/>
     WG List:  <mailto:netmod@ietf.org>

     Author:   Rob Wilton
               <mailto:rwilton@cisco.com>";

  description
    "This module provides type and grouping definitions for YANG
     packages.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.
  // RFC Ed.: replace XXXX with actual RFC number and remove this
  // note.
  revision 2025-03-03 {
    ys:version 0.5.0;
    description
      "Initial revision";
    reference
      "RFC XXXX: YANG Packages";
  }

  /*
   * Typedefs
   */

  typedef pkg-name {
    type yang:yang-identifier;
    description
      "Package names are typed as YANG identifiers.";
  }

  typedef pkg-version {
    type ys:version;
    description
      "Packages are versioning used YANG Semver version labels.";
  }

  typedef version-or-rev-date {
    type union {
      type rev:revision-date;
      type ys:version;
    }
    description
      "Identifies a module by YANG semantic version or revision date";
  }

  typedef scoped-feature {
    type string {
      pattern '[a-zA-Z_][a-zA-Z0-9\-_.]*:[a-zA-Z_][a-zA-Z0-9\-_.]*';
    }
    description
      "Represents a feature name scoped to a particular module,
       identified as the '<module-name>:<feature-name>', where both
       <module-name> and <feature-name> are YANG identifier strings,
       as defiend by Section 12 or RFC 6020.";
    reference
      "RFC XXXX, YANG Packages.";
  }

  /*
   * Groupings
   */
  grouping yang-pkg-identification-leafs {
    description
      "Parameters for identifying a specific version of a YANG
       package";

    leaf name {
      type pkg-name;
      mandatory true;
      description
        "The YANG package name.";
    }

    leaf version {
      type pkg-version;
      mandatory true;
      description
        "Uniquely identies a particular version of a YANG package.

         Follows the definition for revision labels defined in
         draft-verdt-nemod-yang-module-versioning, section XXX";
    }
  }

  grouping yang-pkg-instance {
    description
      "Specifies the data node for a full YANG package instance
       represented either on a server or as a YANG instance data
       document.";
    uses yang-pkg-identification-leafs;
    leaf timestamp {
      type yang:date-and-time;
      description
        "An optional timestamp for when this package was created.
         This does not need to be unique across all versions of a
         package.";
    }

    leaf organization {
      type string;
      description "Organization responsible for this package";
    }

    leaf contact {
      type string;
      description
        "Contact information for the person or organization to whom
         queries concerning this package should be sent.";
    }

    leaf description {
      type string;
      description "Provides a description of the package";
    }

    leaf reference {
      type string;
      description "Allows for a reference for the package";
    }

    leaf complete {
      type boolean;
      default true;
      description
        "Indicates whether the schema defined by this package is
         referentially complete.  I.e. all module imports can be
         resolved to a module explicitly defined in this package or
         one of the included packages.";
    }

    leaf-list tag {
      type tags:tag;
      description
        "Tags associated with a YANG package.  Module tags defined in
         XXX, ietf-netmod-module-tags can be used here but with the
         modification that the tag applies to the entire package
         rather than a specific module.  See the IANA 'YANG Module
         Tag Prefix' registry for reserved prefixes and the IANA
         'YANG Module IETF Tag' registry for IETF standard tags.";
    }

    leaf-list supported-feature {
      type scoped-feature;
      description
        "Lists features from any modules included in the package that
         MUST be supported by any server implementing the package.

         Features already specified in a 'supported-feature' list of
         any included package MUST also be supported by server
         implementations and do not need to be repeated in this list.

         All other features defined in modules included in the
         package are OPTIONAL to implement.

         Features are identified using <module-name>:<feature-name>.";
    }

    list included-package {
      key "name";
      description
        "An entry in this list represents a package that is included
         as part of the package definition, or an indirectly included
         package that is changed in a non backwards compatible way.

         It can be used to resolve inclusion of conflicting package
         versions by explicitly specifying which package version is
         used.

         If included packages implement different revisions
         of the same module, then an explicit entry in the
         module list MUST be provided to select the specific module
         revision 'implemented' by this package definition.

         For import-only modules, the 'replaces-revision' leaf-list
         can be used to select the specific module revisions used by
         this package.";
      reference
        "XXX";

      uses yang-pkg-identification-leafs;

      leaf-list location {
        type inet:uri;
        description
          "Contains a URL that represents where an instance data file
           for this YANG package can be found.
           This leaf will only be present if there is a URL available
           for retrieval of the schema for this entry.

           If multiple locations are provided, then the first
           location in the leaf-list MUST be the definitive location
           that uniquely identifies this package";
      }

    }

    list module {
      key "name";
      description
        "An entry in this list represents a module that must be
         implemented by a server implementing this package, as per
         RFC 7950 section 5.6.5, with a particular set of supported
         features and deviations.

         A entry in this list overrides any module revision
         'implemented' by an included package.  Any replaced module
         revision SHOULD also be listed in the 'replaces-revision'
         list.";
      reference
        "RFC 7950: The YANG 1.1 Data Modeling Language.";

      leaf name {
        type yang:yang-identifier;
        mandatory true;
        description
          "The YANG module name.";
      }

      leaf version {
        type version-or-rev-date;
        mandatory true;
        description
          "Identifies the module version.  If available, the YANG
           Semantic Version SHOULD be used, otherwise the YANG module
           revision date is used.";
      }

      leaf-list location {
        type inet:uri;
        description
          "Contains a URL that represents the YANG schema resource
           for this module.

           This leaf will only be present if there is a URL available
           for retrieval of the schema for this entry.";
      }

      list submodule {
        key "name";
        description
          "Each entry represents one submodule within the
           parent module.";

        leaf name {
          type yang:yang-identifier;
          description
            "The YANG submodule name.";
        }

        leaf version {
          type version-or-rev-date;
          mandatory true;
          description
            "The YANG submodule revision date or YANG Semantic version.

             If the parent module include statement for this submodule
             includes a revision date then it MUST match the revision
             date specified here or it MUST match the revision-date
             associated with the version specified here.";
        }

        leaf-list location {
          type inet:uri;
          description
            "Contains a URL that represents the YANG schema resource
             for this submodule.

             This leaf will only be present if there is a URL
             available for retrieval of the schema for this entry.";
        }

      }

    }

    list import-only-module {
      key "name version";
      description
        "An entry in this list indicates that the server imports
         reusable definitions from the specified revision of the
         module, but does not implement any protocol accessible
         objects from this revision.
         Multiple entries for the same module name MAY exist.  This
         can occur if multiple modules import the same module, but
         specify different revision-dates in the import statements.";

      leaf name {
        type yang:yang-identifier;
        mandatory true;
        description
          "The YANG module name.";
      }

      leaf version {
        type version-or-rev-date;
        mandatory true;
        description
          "Identifies the module version.  If available, the YANG
           Semantic Version SHOULD be used, otherwise the YANG module
           revision date is used.";
      }

      leaf-list replaces-version {
        type version-or-rev-date;
        description
          "Gives the version of an import-only-module defined in an
           included package that is replaced by this
           import-only-module version.";
      }

      leaf-list location {
        type inet:uri;
        description
          "Contains a URL that represents the YANG schema resource
           for this module.

           This leaf will only be present if there is a URL available
           for retrieval of the schema for this entry.";
      }

      list submodule {
        key "name";
        description
          "Each entry represents one submodule within the
           parent module.";

        leaf name {
          type yang:yang-identifier;
          description
            "The YANG submodule name.";
        }

        leaf version {
          type version-or-rev-date;
          mandatory true;
          description
            "The YANG submodule revision date or YANG Semantic version.

             If the parent module include statement for this submodule
             includes a revision date then it MUST match the revision
             date specified here or it MUST match the revision-date
             associated with the version specified here.";
        }

        leaf-list location {
          type inet:uri;
          description
            "Contains a URL that represents the YANG schema resource
             for this submodule.

             This leaf will only be present if there is a URL
             available for retrieval of the schema for this entry.";
        }
      }
    }

    list mounted {
      key "mount-path";
      description
        "An entry in this list represents a package that will be
         found mounted in the schema at the specified mount path.

         For a given mount path, the set of mounted package
         versions is the union of all packages mounted at the
         given mount point.  Any conflicting package versions
         MUST be explicitly resolved via an entry in the
         mounted/packages of the package definition.

         A mount path with specific keys MUST also includes any
         mounted packages without specific keys.";

      leaf "mount-path" {
        type string;
        description
          "This path identifies a mount point in the schema.

           This leaf is encoded as a JSON style encoded
           instance-identifier (regardless of whether the format
           used to encode the YANG instance data), as specified in
           RFC 7951, section 6.11, except that keys are optional.

           For optional keys, the name and value of the key is
           excluded from the key list.

           Mount paths MUST only be used for schema mount points
           defined in the package schema.

           For example, if an example module 'ex-module' defines a
           mount point under list entry'/modules/module/' then a
           mount path of

           - '/modules/module[name=foo]' would indicate the mounted
             package schema for only the 'foo' entry in the module
             list.  Each entry in the list could have a different
             mounted schema specified.

           - '/modules/module[]' would indicate that the same
             mounted package schema is available for all list
             entries in the module list.";
      }

      list packages {
        key "name";
        description
          "The package that will be mounted at the specified mount
           path";
        uses yang-pkg-identification-leafs;

        leaf-list location {
          type inet:uri;
          description
            "Contains a URL that represents where an instance data
             file for this YANG package can be found.

             This leaf will only be present if there is a URL
             available for retrieval of the schema for this entry.

             If multiple locations are provided, then the first
             location in the leaf-list MUST be the definitive
             location to retreive the package definition.";
        }
      }
    }
  }
}
