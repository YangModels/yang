module ietf-acl {
  yang-version 1;

  namespace "urn:ietf:params:xml:ns:yang:ietf-acl";

  prefix access-control-list;

  import ietf-yang-types {
    prefix "yang";

  }

  import ietf-packet-fields {
    prefix "packet-fields";
  }

  organization
    "IETF NETMOD (NETCONF Data Modeling Language) Working Group";

  contact
    "WG Web: http://tools.ietf.org/wg/netmod/
    WG List: netmod@ietf.org

    WG Chair: Juergen Schoenwaelder
    j.schoenwaelder@jacobs-university.de

    WG Chair: Tom Nadeau
    tnadeau@lucidvision.com

    Editor: Dean Bogdanovic
    deanb@juniper.net

    Editor: Kiran Agrahara Sreenivasa
    kkoushik@brocade.com

    Editor: Lisa Huang
    yihuan@cisco.com

    Editor: Dana Blair
    dblair@cisco.com";

  description
    "This YANG module defines a component that describing the
    configuration of Access Control Lists (ACLs).

    Copyright (c) 2015 IETF Trust and the persons identified as
    the document authors.  All rights reserved.

    Redistribution and use in source and binary forms, with or
    without modification, is permitted pursuant to, and subject
    to the license terms contained in, the Simplified BSD
    License set forth in Section 4.c of the IETF Trust's Legal
    Provisions Relating to IETF Documents
    (http://trustee.ietf.org/license-info).

    This version of this YANG module is part of RFC XXXX; see
    the RFC itself for full legal notices.";

    // RFC Ed.: replace XXXX with actual RFC number and remove this
    // note.

  revision 2015-03-04 {
    description "Base model for Network Access Control List (ACL).";
    reference
      "RFC XXXX: Network Access Control List (ACL)
      YANG Data  Model";
  }

  identity access-control-list-base {
    description "Base access control list type for all access control list type
      identifiers.";
  }

  identity IP-access-control-list {
    base "access-control-list:access-control-list-base";
    description "IP-access control list is common name for layer 3 and 4 access
    control list types. It is common among vendors to call 3-tupple or 5 tupple
    IP access control lists";
  }

  identity eth-access-control-list {
    base "access-control-list:access-control-list-base";
    description "Ethernet access control list is name for layer 2 Ethernet
    technology access control list types, like 10/100/1000baseT or WiFi
    access control list";
  }

  typedef access-control-list-type {
    type identityref {
      base "access-control-list-base";
    }
    description
      "This type is used to refer to an Access Control List
      (ACL) type";
  }

  typedef access-control-list-ref {
    type leafref {
      path "/access-lists/access-list/access-control-list-name";
    }
    description "This type is used by data models that need to referenced an
      access control list";

  }

  container access-lists {
    description
      "This is top level container for Access Control Lists. It can have one
        or more Access Control List.";

    list access-list {
      key access-control-list-name;
      description "An access list (acl) is an ordered list of
        access list entries (ACE). Each access control entries has a
        list of match criteria, and a list of actions.
        Since there are several kinds of access control lists
        implemented with different attributes for
        each and different for each vendor, this
        model accommodates customizing access control lists for
        each kind and for each vendor.";

      leaf access-control-list-name {
        type string;
        description "The name of access-list. A device MAY restrict the length
        and value of this name, possibly space and special characters are not
        allowed.";
      }

      leaf access-control-list-type {
        type access-control-list-type;
        description "Type of access control list. When this
        type is not explicitely specified, if vendor implementation permits,
        the access control entires in the list can be mixed,
        by containing L2, L3 and L4 entries";
      }

      container access-control-list-oper-data {
        config false;
        description "Overall access control list operational data";

        choice targets{
          description "List of targets where access control list is applied";
          leaf-list interface-name {
            type string;
            description "Interfaces where access control list is applied";
          }
        }
      }

      container access-list-entries {
        description "The access-list-entries container contains
          a list of access-list-entry(ACE).";

        list access-list-entry {
          key rule-name;
          ordered-by user;
          description "List of access list entries(ACE)";
          leaf rule-name {
              type string;
              description "Entry name.";
          }

          container matches {
            description "Define match criteria";
            choice access-list-entries-type {
              description "Type of access list entry.";
              case access-list-entries-ip {
                uses packet-fields:access-control-list-ip-header-fields;
                choice access-list-entries-ip-version {
                  description "Choice of IP version.";
                  case access-list-entries-ipv4 {
                    uses packet-fields:access-control-list-ipv4-header-fields;
                  }
                  case access-list-entries-ipv6 {

                   uses packet-fields:access-control-list-ipv6-header-fields;
                  }
                }
              }
              case access-list-entries-eth {
                description "Ethernet MAC address entry.";
                uses packet-fields:access-control-list-eth-header-fields;
              }
            }
            uses packet-fields:metadata;
          }

          container actions {
            description "Define action criteria";
            choice packet-handling {
              default deny;

              description "Packet handling action.";
              case deny {
                leaf deny {
                  type empty;
                  description "Deny action.";

                }
              }
              case permit {
                leaf permit {
                  type empty;
                  description "Permit action.";
                }
              }
            }
          }

          container access-list-entries-oper-data {
            config false;

            description "Per access list entries operational data";
            leaf match-counter {
              type yang:counter64;
              description "Number of matches for an access list entry";
            }
          }
        }
      }
    }
  }
}
