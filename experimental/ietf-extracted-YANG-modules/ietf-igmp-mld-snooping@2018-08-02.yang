module ietf-igmp-mld-snooping {
  yang-version 1.1;
  namespace "urn:ietf:params:xml:ns:yang:ietf-igmp-mld-snooping";
  // replace with IANA namespace when assigned
  prefix ims;

  import ietf-inet-types {
    prefix "inet";
  }

  import ietf-yang-types {
    prefix "yang";
  }

  import ietf-interfaces {
    prefix "if";
  }

  import ietf-l2vpn {
    prefix "l2vpn";
  }

  import ietf-network-instance {
    prefix "ni";
  }

  import ieee802-dot1q-bridge {
    prefix "dot1q";
  }
  organization
    "IETF PIM Working Group";

  contact
    "WG Web:   <http://tools.ietf.org/wg/pim/>
     WG List:  <mailto:pim@ietf.org>

     Editors:  Hongji Zhao
               <mailto:hongji.zhao@ericsson.com>

               Xufeng Liu
               <mailto:xufeng.liu.ietf@gmail.com>

               Yisong Liu
               <mailto:liuyisong@huawei.com>

               Anish Peter
               <mailto:anish.ietf@gmail.com>

               Mahesh Sivakumar
               <mailto:sivakumar.mahesh@gmail.com>

    ";

  description
    "The module defines a collection of YANG definitions common for
     all Internet Group Management Protocol (IGMP) and Multicast
     Listener Discovery (MLD) Snooping devices.

     Copyright (c) 2018 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2018-08-02 {
    description
      "Initial revision.";
    reference
      "RFC XXXX: A YANG Data Model for IGMP and MLD Snooping";
  }
  /*
   * Features
   */

  feature immediate-leave {
    description
      "Support configuration of immediate-leave.";
  }

  feature join-group {
    description
      "Support configuration of join-group.";
  }

  feature require-router-alert {
    description
      "Support configuration of require-router-alert.";
  }

  feature static-l2-multicast-group {
    description
      "Support configuration of L2 multicast static-group.";
  }

  feature static-mrouter-interface {
    description
      "Support configuration of mrouter interface.";
  }

  feature rpc-clear-groups {
    description
      "Support clearing statistics by RPC for IGMP & MLD snooping.";
  }

  feature explicit-tracking {
    description
      "Support configuration of per instance explicit-tracking.";
  }

  feature exclude-lite {
    description
      "Support configuration of per instance exclude-lite.";
  }

    /*
     * Typedefs
     */
  typedef igmp-snooping-instance-ref {
    type leafref {
      path "/igmp-snooping-instances/igmp-snooping-instance/name";
    }
    description
      "This type is used by data models that need to reference
       IGMP snooping instance.";
  }

  typedef mld-snooping-instance-ref {
    type leafref {
      path "/mld-snooping-instances/mld-snooping-instance/name";
    }
    description
      "This type is used by data models that need to reference
       MLD snooping instance.";
    }

  typedef l2vpn-instance-ac-ref {
    type leafref {
      path "/ni:network-instances/ni:network-instance"+
      "/l2vpn:endpoint/l2vpn:name";
    }
    description "l2vpn-instance-ac-ref";
  }

  typedef l2vpn-instance-pw-ref {
    type leafref {
      path "/ni:network-instances/ni:network-instance"+
       "/l2vpn:endpoint/l2vpn:name";
    }
    description "l2vpn-instance-pw-ref";
  }

  typedef source-ipv4-addr-type {
    type union {
      type enumeration {
        enum '*' {
          description
          "Any source address.";
        }
      }
      type inet:ipv4-address;
    }
    description
      "Multicast source IPV4 address type.";
  } // source-ipv4-addr-type

  typedef source-ipv6-addr-type {
    type union {
      type enumeration {
        enum '*' {
          description
          "Any source address.";
        }
      }
      type inet:ipv6-address;
    }
    description
      "Multicast source IPV6 address type.";
  } // source-ipv6-addr-type

      /*
       * Groupings
       */

  grouping general-state-attributes {

    description "General State attributes";

      container received {
        config false;
        description "Statistics of received IGMP and MLD snooping
        related packets.";

        uses general-statistics-sent-received;
      }
      container sent {
        config false;
        description "Statistics of sent IGMP and MLD snooping
        related packets.";

        uses general-statistics-sent-received;
      }

  } // general-state-attributes

  grouping instance-config-attributes-igmp-snooping {
    description "IGMP snooping configuration for each"+
     "BRIDGE or L2VPN instance.";

    uses instance-config-attributes-igmp-mld-snooping;

    leaf querier-source {
      type inet:ipv4-address;
      description "Use the IGMP snooping querier to support IGMP
        snooping in a VLAN where PIM and IGMP are not configured.
       The IPV4 address is used as source address in messages.";
    }

    list static-l2-multicast-group {
      if-feature static-l2-multicast-group;
      key "group source-addr";
      description
        "A static multicast route, (*,G) or (S,G).";

      leaf group {
        type inet:ipv4-address;
        description
        "Multicast group IPV4 address";
      }

      leaf source-addr {
        type source-ipv4-addr-type;
        description
          "Multicast source IPV4 address.";
      }

      leaf-list bridge-outgoing-interface {
        when "../../type = 'bridge'";
        type if:interface-ref;
        description "Outgoing interface in BRIDGE forwarding";
      }

      leaf-list l2vpn-outgoing-ac {
        when "../../type = 'l2vpn'";
        type l2vpn-instance-ac-ref;
        description "Outgoing AC in L2VPN forwarding";
      }

      leaf-list l2vpn-outgoing-pw {
        when "../../type = 'l2vpn'";
        type l2vpn-instance-pw-ref;
        description "Outgoing PW in L2VPN forwarding";
      }
    } // static-l2-multicast-group
  } // instance-config-attributes-igmp-snooping

  grouping instance-config-attributes-igmp-mld-snooping {
    description
      "IGMP and MLD snooping configuration of each VLAN.";

    leaf enable {
      type boolean;
      default false;
        description
          "Set the value to true to enable IGMP and MLD snooping in the
VLAN instance.";
    }

    leaf forwarding-mode {
      type enumeration {
        enum "mac" {
          description
          "MAC-based lookup mode";
        }
        enum "ip"  {
          description
          "IP-based lookup mode";
        }
      }
      default "ip";
      description "The default forwarding mode is ip";
    }

    leaf explicit-tracking {
      if-feature explicit-tracking;
      type boolean;
      default false;
      description "Tracks IGMP & MLD snooping v3 membership reports
       from individual hosts. It contributes to saving network
       resources and shortening leave latency.";
    }

    leaf exclude-lite {
      if-feature exclude-lite;
      type boolean;
     default false;
      description
        "lightweight IGMPv3 and MLDv2 protocols, which simplify the
         standard versions of IGMPv3 and MLDv2.";
      reference "RFC5790";
    }

    leaf send-query {
      type boolean;
      default false;
      description "Enable quick response for topo changes.
        To support IGMP snooping in a VLAN where PIM and IGMP are
        not configured. It cooperates with param querier-source. ";
    }

    leaf immediate-leave {
      if-feature immediate-leave;
      type empty;
      description
        "When immediate leave is enabled, the IGMP software assumes
       that no more than one host is present on each VLAN port.";
    }

    leaf last-member-query-interval {
      type uint16 {
        range "1..65535";
      }
      units seconds;
      default 1;
      description
        "Last Member Query Interval, which may be tuned to modify
         the leave latency of the network.";
      reference "RFC3376. Sec. 8.8.";
    }

    leaf query-interval {
      type uint16;
      units seconds;
      default 125;
      description
        "The Query Interval is the interval between General Queries
         sent by the Querier.";
      reference "RFC3376. Sec. 4.1.7, 8.2, 8.14.2.";
    }

    leaf query-max-response-time {
      type uint16;
      units seconds;
      default 10;
      description
        "Query maximum response time specifies the maximum time
         allowed before sending a responding report.";
      reference "RFC3376. Sec. 4.1.1, 8.3, 8.14.3.";
    }

    leaf require-router-alert {
      if-feature require-router-alert;
      type boolean;
     default false;
      description
        "When the value is true, router alert should exist
       in the IP head of IGMP or MLD packet.";
    }

    leaf robustness-variable {
      type uint8 {
        range "1..7";
      }
      default 2;
      description
        "Querier's Robustness Variable allows tuning for the
       expected packet loss on a network.";
      reference "RFC3376. Sec. 4.1.6, 8.1, 8.14.1.";
    }

    leaf version {
      type uint8 {
        range "1..3";
      }
     default 2;
      description "IGMP and MLD snooping version.";
    }

    leaf-list static-bridge-mrouter-interface {
      when "../type = 'bridge'";
      if-feature static-mrouter-interface;
      type if:interface-ref;
      description "static mrouter interface in BRIDGE forwarding";
    }

    leaf-list static-l2vpn-mrouter-interface-ac {
      when "../type = 'l2vpn'";
      if-feature static-mrouter-interface;
      type if:interface-ref;
      description "static mrouter interface whose type is interface
       in L2VPN forwarding";
    }

    leaf-list static-l2vpn-mrouter-interface-pw {
      when "../type = 'l2vpn'";
      if-feature static-mrouter-interface;
      type l2vpn-instance-pw-ref;
      description "static mrouter interface whose type is PW
       in L2VPN forwarding";
    }
  } // instance-config-attributes-igmp-mld-snooping

  grouping instance-config-attributes-mld-snooping {
    description "MLD snooping configuration of each VLAN.";

    uses instance-config-attributes-igmp-mld-snooping;

    leaf querier-source {
      type inet:ipv6-address;
      description
        "Use the MLD snooping querier to support MLD snooping where
      PIM and MLD are not configured. The IPV6 address is used as
      the source address in messages.";
    }

    list static-l2-multicast-group {
      if-feature static-l2-multicast-group;
      key "group source-addr";
      description
        "A static multicast route, (*,G) or (S,G).";

      leaf group {
        type inet:ipv6-address;
        description
          "Multicast group IPV6 address";
      }

      leaf source-addr {
        type source-ipv6-addr-type;
        description
          "Multicast source IPV6 address.";
      }

      leaf-list bridge-outgoing-interface {
       when "../../type = 'bridge'";
       type if:interface-ref;
       description "Outgoing interface in BRIDGE forwarding";
      }

      leaf-list l2vpn-outgoing-ac {
       when "../../type = 'l2vpn'";
       type l2vpn-instance-ac-ref;
       description "Outgoing AC in L2VPN forwarding";
      }

      leaf-list l2vpn-outgoing-pw {
       when "../../type = 'l2vpn'";
       type l2vpn-instance-pw-ref;
       description "Outgoing PW in L2VPN forwarding";
      }
    } // static-l2-multicast-group
  } // instance-config-attributes-mld-snooping

  grouping instance-state-group-attributes-igmp-mld-snooping {
    description
      "Attributes for both IGMP and MLD snooping groups.";

    leaf mac-address {
      type yang:phys-address;
      description "Destination MAC address for L2 multicast.";
    }

    leaf expire {
      type uint32;
      units seconds;
      description
      "The time left before multicast group timeout.";
    }

    leaf up-time {
      type uint32;
      units seconds;
      description
        "The time elapsed since L2 multicast record created.";
    }
  } // instance-state-group-attributes-igmp-mld-snooping

  grouping instance-state-attributes-igmp-snooping {
    description
      "State attributes for IGMP snooping for each instance.";

    uses instance-state-attributes-igmp-mld-snooping;

    list group {

      key "address";

      config false;

      description "IGMP snooping information";

      leaf address {
        type inet:ipv4-address;
        description
          "Multicast group IPV4 address";
      }

      uses instance-state-group-attributes-igmp-mld-snooping;

      leaf last-reporter {
        type inet:ipv4-address;
        description
          "Address of the last host which has sent report to join
           the multicast group.";
      }

      list source {
        key "address";
        description "Source IPV4 address for multicast stream";
        leaf address {
          type inet:ipv4-address;
          description "Source IPV4 address for multicast stream";
        }

        uses instance-state-source-attributes-igmp-mld-snooping;

        leaf last-reporter {
          type inet:ipv4-address;
          description
            "Address of the last host which has sent report
          to join the multicast group.";
        }

        list host {
          if-feature explicit-tracking;
          key "host-address";
          description
            "List of multicast membership hosts
             of the specific multicast source-group.";

          leaf host-address {
            type inet:ipv4-address;
            description
              "Multicast membership host address.";
          }
          leaf host-filter-mode {
            type enumeration {
              enum "include" {
                description
                  "In include mode";
              }
              enum "exclude" {
                description
                  "In exclude mode.";
              }
            }
            description
              "Filter mode for a multicast membership
               host may be either include or exclude.";
          }
        }// list host

      } // list source
    } // list group
  } // instance-state-attributes-igmp-snooping

  grouping instance-state-attributes-igmp-mld-snooping {

    description
      "State attributes for IGMP & MLD snooping instance.";

    leaf entries-count {
      type uint32;
     config false;
      description
       "The number of L2 multicast entries in IGMP & MLD snooping";
    }

    leaf-list bridge-mrouter-interface {
      when "../type = 'bridge'";
      type if:interface-ref;
      config false;
      description "mrouter interface in BRIDGE forwarding";
    }

    leaf-list l2vpn-mrouter-interface-ac {
      when "../type = 'l2vpn'";
      type if:interface-ref;
      config false;
      description "mrouter interface whose type is interface
       in L2VPN forwarding";

    }

    leaf-list l2vpn-mrouter-interface-pw {
      when "../type = 'l2vpn'";
      type l2vpn-instance-pw-ref;
      config false;
      description "mrouter interface whose type is PW
       in L2VPN forwarding";
    }
  } // instance-config-attributes-igmp-mld-snooping

  grouping instance-state-attributes-mld-snooping {
    description
      "State attributes for MLD snooping of each VLAN.";

    uses instance-state-attributes-igmp-mld-snooping;

    list group {
      key "address";
      config false;
      description "MLD snooping statistics information";

      leaf address {
        type inet:ipv6-address;
        description
          "Multicast group IPV6 address";
      }

      uses instance-state-group-attributes-igmp-mld-snooping;

      leaf last-reporter {
        type inet:ipv6-address;
        description
          "Address of the last host which has sent report
         to join the multicast group.";
      }

      list source {
        key "address";
        description "Source IPV6 address for multicast stream";

      leaf address {
          type inet:ipv6-address;
          description "Source IPV6 address for multicast stream";
        }
        uses instance-state-source-attributes-igmp-mld-snooping;

        leaf last-reporter {
         type inet:ipv6-address;
         description
          "Address of the last host which has sent report
         to join the multicast group.";
        }

        list host {
          if-feature explicit-tracking;
          key "host-address";
          description
            "List of multicast membership hosts
             of the specific multicast source-group.";

          leaf host-address {
            type inet:ipv6-address;
            description
              "Multicast membership host address.";
          }
          leaf host-filter-mode {
            type enumeration {
              enum "include" {
                description
                  "In include mode";
              }
              enum "exclude" {
                description
                  "In exclude mode.";
              }
            }
            description
              "Filter mode for a multicast membership
               host may be either include or exclude.";
          }
        }// list host
      } // list source
    } // list group
  } // instance-state-attributes-mld-snooping

  grouping instance-state-source-attributes-igmp-mld-snooping {
    description
      "State attributes for IGMP & MLD snooping instance.";

    leaf-list bridge-outgoing-interface {
      when "../../../type = 'bridge'";
      type if:interface-ref;
      description "Outgoing interface in BRIDGE forwarding";
    }
    leaf-list l2vpn-outgoing-ac {
      when "../../../type = 'l2vpn'";
      type l2vpn-instance-ac-ref;
      description "Outgoing AC in L2VPN forwarding";
    }

    leaf-list l2vpn-outgoing-pw {
      when "../../../type = 'l2vpn'";
      type l2vpn-instance-pw-ref;
      description "Outgoing PW in L2VPN forwarding";
    }

    leaf up-time {
      type uint32;
      units seconds;
      description "The time elapsed since L2 multicast
        record created";
    }

    leaf expire {
      type uint32;
      units seconds;
      description
        "The time left before multicast group timeout.";
    }

    leaf host-count {
      if-feature explicit-tracking;
      type uint32;
      description
        "The number of host addresses.";
    }
  } // instance-state-source-attributes-igmp-mld-snooping

  grouping general-statistics-error {
    description
      "A grouping defining statistics attributes for errors.";

    leaf checksum {
      type yang:counter64;
      description
        "The number of checksum errors.";
    }
    leaf too-short {
      type yang:counter64;
      description
        "The number of messages that are too short.";
    }
  } // general-statistics-error
  grouping general-statistics-sent-received {
    description
      "A grouping defining statistics attributes.";

      leaf query {
        type yang:counter64;
        description
          "The number of query messages.";
      }
      leaf membership-report-v1 {
        type yang:counter64;
        description
          "The number of membership report v1 messages.";
      }
      leaf membership-report-v2 {
        type yang:counter64;
        description
          "The number of membership report v2 messages.";
      }
      leaf membership-report-v3 {
        type yang:counter64;
        description
          "The number of membership report v3 messages.";
      }
      leaf leave {
        type yang:counter64;
        description
          "The number of leave messages.";
      }
      leaf non-member-leave {
        type yang:counter64;
        description
          "The number of non member leave messages.";
      }
      leaf pim {
        type yang:counter64;
        description
          "The number of pim hello messages.";
      }
  } // general-statistics-sent-received

  grouping interface-endpoint-attributes-igmp-snooping {

    description "interface attributes for IGMP snooping";

    list host {

      if-feature explicit-tracking;

      key "host-address";
      config false;

      description
       "List of multicast membership hosts
       of the specific multicast source-group.";

      leaf host-address {
        type inet:ipv4-address;
        description
          "Multicast membership host address.";
      }
      leaf host-filter-mode {
        type enumeration {
          enum "include" {
            description
              "In include mode";
          }
          enum "exclude" {
            description
              "In exclude mode.";
          }
        }
        description
          "Filter mode for a multicast membership
           host may be either include or exclude.";
      }
    }// list host
  } // interface-endpoint-attributes-igmp-snooping

  grouping interface-endpoint-attributes-mld-snooping {

    description "interface endpoint attributes MLD snooping";

    list host {

      if-feature explicit-tracking;

      key "host-address";

      config false;

      description
        "List of multicast membership hosts
        of the specific multicast source-group.";

      leaf host-address {
        type inet:ipv6-address;
        description
          "Multicast membership host address.";
      }
      leaf host-filter-mode {
        type enumeration {
          enum "include" {
            description
              "In include mode";
          }
          enum "exclude" {
            description
              "In exclude mode.";
          }
        }
        description
        "Filter mode for a multicast membership
           host may be either include or exclude.";
      }
    }// list host
  } // interface-endpoint-attributes-mld-snooping

      /*
       * igmp-snooping-instance
       */
  container igmp-snooping-instances {
    description
     "igmp-snooping-instance list";

    list igmp-snooping-instance {
      key "name";
      description
        "IGMP snooping instance to configure the igmp-snooping.";

      leaf name {
        type string;
        description
          "Name of the igmp-snooping-instance";
      }

      leaf type {
        type enumeration {
          enum "bridge" {
            description "BRIDGE";
          }
          enum "l2vpn" {
           description "L2VPN";
          }
        }
        description "The type indicates BRIDGE or L2VPN.";
      }

     uses instance-config-attributes-igmp-snooping;

      uses instance-state-attributes-igmp-snooping;
    } //igmp-snooping-instance
  } //igmp-snooping-instances

  /*
       * mld-snooping-instance
       */

  container mld-snooping-instances {
    description
      "mld-snooping-instance list";

    list mld-snooping-instance {
      key "name";
      description
        "MLD snooping instance to configure the mld-snooping.";

      leaf name {
        type string;
        description
          "Name of the mld-snooping-instance";
      }

      leaf type {
        type enumeration {
          enum "bridge" {
            description "BRIDGE";
         }
          enum "l2vpn" {
            description "L2VPN";
         }
        }
        description "The type indicates BRIDGE or L2VPN.";
      }

      uses instance-config-attributes-mld-snooping;

      uses instance-state-attributes-mld-snooping;

    } //mld-snooping-instance
  } //mld-snooping-instances

 /* augments */

  augment "/dot1q:bridges/dot1q:bridge" {
    description
      "Reference IGMP & MLD snooping instance in BRIDGE scenario";

    leaf igmp-snooping-instance {
      type igmp-snooping-instance-ref;
      description
      "Configure IGMP snooping instance under bridge view";
    }
    leaf mld-snooping-instance {
      type mld-snooping-instance-ref;
      description
      "Configure MLD snooping instance under bridge view";
    }
  }

  augment "/dot1q:bridges/dot1q:bridge"+
    "/dot1q:component/dot1q:bridge-vlan/dot1q:vlan" {
    description
      "Refrence IGMP & MLD snooping instance in BRIDGE scenario";

    leaf igmp-snooping-instance {
      type igmp-snooping-instance-ref;
      description
       "Configure IGMP snooping instance under VLAN view";
    }

    leaf mld-snooping-instance {
      type mld-snooping-instance-ref;
      description
       "Configure MLD snooping instance under VLAN view";
    }
  }

  augment "/ni:network-instances/ni:network-instance"+
    "/ni:ni-type/l2vpn:l2vpn" {

    description
     "Reference IGMP & MLD snooping instance in L2VPN scenario";

    leaf igmp-snooping-instance {
      type igmp-snooping-instance-ref;
      description
       "Configure IGMP snooping instance in L2VPN scenario";
    }
    leaf mld-snooping-instance {
      type mld-snooping-instance-ref;
      description
       "Configure MLD snooping instance in L2VPN scenario";
    }
  }
  augment "/if:interfaces/if:interface" {
    description
     "Augment interface for referencing attributes
      which only fit for interface view.";

    container igmp-mld-snooping {
      description
        "igmp-mld-snooping related attributes under interface view";

      leaf enable {
        type boolean;
        default false;
        description
          "Set the value to true to enable IGMP and MLD snooping
           in the VLAN instance.";
      }

      leaf version {
        type uint8 {
          range "1..3";
        }
      default 2;
        description "IGMP and MLD snooping version.";
      }

      leaf type {
        type enumeration {
          enum "bridge" {
            description "BRIDGE";
          }
          enum "l2vpn" {
            description "L2VPN";
          }
        }
        description "The type indicates BRIDGE or L2VPN.";
      }

      container static-mrouter-interface {
        description
          "Container for choice static-mrouter-interface";

        choice static-mrouter-interface {
          description
            "Configure static multicast router interface
          under the interface view";

          case bridge {
            when "../type = 'bridge'" {
              description
                "Applies to BRIDGE scenario.";
            }
         description
              "Applies to BRIDGE scenario.";

              leaf bridge-name {
                type string;
                description
                  "The name for a bridge.
               Each interface belongs to only one bridge.";

              }
              leaf-list vlan-id {
                type uint32;
                description
                  "The VLAN ids for bridge. If you don't specify
              VLAN id here, the interface serves as the mrouter
              interface for all the VLANs in this bridge.";
              }
          }
          case l2vpn {
            when "../type = 'l2vpn'" {
              description
                "Applies to L2VPN scenario.";
            }

            description
              "Applies to L2VPN scenario.";

            leaf l2vpn-instance-name {
              type string;
              description
                "The L2VPN instance name applied in the interface";

            }
          }
        } // choice static-mrouter-interface
      }  // container static-mrouter-interface

      container static-l2-multicast-group {
        description
          "Container for static-l2-multicast-group";

        choice static-l2-multicast-group {
          description
            "Configure static l2 multicast group
          under interface view";

          case bridge {
            when "../type = 'bridge'" {
              description
                "Applies to BRIDGE scenario.";
            }

            description
              "Applies to BRIDGE scenario.";

            leaf bridge-name {
              type string;
              description
                "bridge name.";
            }

            list bridge-group-v4 {
              key "group source-addr";
              description
                "A static multicast route, (*,G) or (S,G).";

              leaf group {
                type inet:ipv4-address;
                description
                  "Multicast group IPV4 address";
              }

              leaf source-addr {
                type source-ipv4-addr-type;
                description
                  "Multicast source IPV4 address.";
              }

              leaf-list vlan-id {
                type uint32;
                description
                  "VLAN id.";
              }
            }

            list bridge-group-v6 {
              key "group source-addr";
              description
                "A static multicast route, (*,G) or (S,G).";

              leaf group {
                type inet:ipv6-address;
                description
                  "Multicast group IPV6 address";
              }

              leaf source-addr {
                type source-ipv6-addr-type;
                description
                  "Multicast source IPV6 address.";
              }
              leaf-list vlan-id {
                type uint32;
                description
                  "VLAN id.";
              }
            }
          } // case bridge

          case l2vpn {

            when "../type = 'l2vpn'" {
              description
                "Applies to L2VPN scenario.";
            }
            description
              "Applies to L2VPN scenario.";

            list l2vpn-group-v4 {
              key "group source-addr";
              description
             "A static multicast route, (*,G) or (S,G).";

              leaf group {
                type inet:ipv4-address;
                description
                  "Multicast group IPV4 address";
              }

              leaf source-addr {
                type source-ipv4-addr-type;
                description
                  "Multicast source IPV4 address.";
              }

              leaf l2vpn-instance-name {
                type string;
                description
                  "L2VPN instance name applied in the interface";
              }
            }

            list l2vpn-group-v6 {

              key "group source-addr";

              description
                "A static multicast route, (*,G) or (S,G).";

              leaf group {
                type inet:ipv6-address;
                description
                  "Multicast group IPV6 address";
              }

              leaf source-addr {
                type source-ipv6-addr-type;
                description
                  "Multicast source IPV6 address.";
              }

              leaf l2vpn-instance-name {
                type string;
                description
                  "L2VPN instance name applied in the interface";
              }
            }
          }
        } //choice static-l2-multicast-group
      } // container static-l2-multicast-group

      container statistics {
        config false;
        description
          "A collection of interface-related statistics objects.";

        uses general-state-attributes;
      }
    }
  }

 /*  RPCs  */

  rpc clear-igmp-snooping-groups {
    if-feature rpc-clear-groups;
    description
      "Clears the specified IGMP snooping cache tables.";

    input {

      leaf name {
        type string;
        description
          "Name of the igmp-snooping-instance";
      }

      leaf group {
        type inet:ipv4-address;
        description
          "Multicast group IPv4 address.
           If it is not specified, all IGMP snooping group tables
         are cleared.";
      }

      leaf source {
        type inet:ipv4-address;
        description
          "Multicast source IPv4 address.
           If it is not specified, all IGMP snooping source-group
         tables are cleared.";
      }
    }
  } // rpc clear-igmp-snooping-groups

  rpc clear-mld-snooping-groups {
    if-feature rpc-clear-groups;
    description
      "Clears the specified MLD snooping cache tables.";

    input {
      leaf name {
        type string;
        description
          "Name of the mld-snooping-instance";
      }

      leaf group {
        type inet:ipv6-address;
        description
          "Multicast group IPv6 address.
           If it is not specified, all MLD snooping group tables are
           cleared.";
      }

      leaf source {
        type inet:ipv6-address;
        description
          "Multicast source IPv6 address.
           If it is not specified, all MLD snooping source-group
         tables are cleared.";
      }
    }
  } // rpc clear-mld-snooping-groups
}
