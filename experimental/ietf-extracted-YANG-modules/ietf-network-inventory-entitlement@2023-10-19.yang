module ietf-network-inventory-entitlement {
  yang-version 1.1;
  namespace "urn:ietf:params:xml:ns:yang:ietf-network-inventory-entitlement";
  prefix nie;

  import ietf-network-inventory {
    prefix ni;
    reference
      "RFCxxxx: IETF Network Inventory";
  }

  organization
    "IETF Network Inventory YANG (ivy) Working Group";
  contact
    "WG Web:   <https://datatracker.ietf.org/wg/ivy>
     WG List:  <mailto:inventory-yang@ietf.org>

     Editor: Bo Wu
          <lana.wubo@huawei.com>
     Editor: Cheng Zhou
          <zhouchengyjy@chinamobile.com>
     Editor: Qin Wu
          <bill.wu@huawei.com>
     Editor: Mohamed Boucadair
          <mohamed.boucadair@orange.com>";
  description
    "This YANG module defines a model for retrieving network inventory
        entitlements.

     Copyright (c) 2023 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2023-10-19 {
    description
      "Initial version";
    reference
      "RFC XXXX: A YANG Data Model for Network Inventory Entitlement.";
  }

  grouping entitl-ref-list {
    description
      "Defines a grouping to a reference list of entitlement.";
    leaf-list entitle-ref {
      type leafref {
        path "/nie:entitlements/nie:entitlement/nie:entitlement-id";
      }
      config false;
      description
        "Defines a reference to a list of entitlement.";
    }
  }

  /* Main blocks */

  container entitlements {
    config false;
    description
      "The top-level container for the list of entitlements
       of the network inventory.";
    list entitlement {
      key "entitlement-id";
      description
        "List of entitlements.";
      leaf entitlement-id {
        type string;
        description
          "entitlement ID. A string that uniquelly identifies the
           entitlement. ";
      }
      leaf entitlement-type {
        type string;
        description
          "The entitlement type.";
      }
      leaf mfg-name {
        type string;
        description
          "The name of the manufacturer of this entitlement";
      }
      leaf serial-number {
        type string;
        description
          "The vendor-specific serial number string for the
              entitlement";
      }
      leaf entitlement-data {
        type union {
          type binary;
          type string;
        }
        description
          "The contents of the licence (if required) .";
      }
      leaf active {
        type boolean;
        default "false";
        description
          "The activation state of the entitlement.";
      }
      leaf issue-date {
        type uint64;
        description
          "The date and time at which the entitlement was issued.";
      }
      leaf expiration-date {
        type uint64;
        description
          "The date and time at which the entitlement will expire.";
      }
      leaf in-use {
        type boolean;
        description
          "The entitlement is in use.";
      }
      leaf expired {
        type boolean;
        description
          "The entitlement has expired.";
      }
      leaf valid {
        type boolean;
        description
          "The entitlement is valid. Can be activated in the system
           or platform.";
      }
      leaf-list network-elements-ref {
        type string;
        description
          "The list of the the references of network elements.";
      }
      leaf-list ne-components-ref {
        type string;
        description
          "The list of the references of the components.";
      }
    }
  }

  augment "/ni:network-elements/ni:network-element" {
    description
      "Introduces new network type for network inventory.";
    uses entitl-ref-list;
  }

  augment "/ni:network-elements/ni:network-element/"
        + "ni:components/ni:component" {
    description
      "Introduces new network type for network inventory.";
    uses entitl-ref-list;
  }
}
