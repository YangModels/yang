module ietf-ns-underlay-path {
  yang-version 1.1;
  namespace
    "urn:ietf:params:xml:ns:yang:ietf-ns-underlay-path";
  prefix "ns-path";

  import ietf-network {
    prefix "nw";
    reference
     "RFC 8345: A YANG Data Model for Network Topologies";
  }
  import ietf-network-topology {
    prefix "nt";
    reference
     "RFC 8345: A YANG Data Model for Network Topologies";
  }

  import ietf-network-slice-service {
    prefix "ietf-nss";
    reference
      "draft-ietf-teas-ietf-network-slice-nbi-yang-25:
       A YANG Data Model for the RFC 9543 Network Slice Service";
  }

  organization
    "IETF TEAS Working Group";
  contact
    "WG Web: <http://tools.ietf.org/wg/teas/>
     WG List: <mailto:teas@ietf.org>

     Editor: Xufeng Liu
             <mailto:xufeng.liu.ietf@gmail.com>
     Editor: Italo Busi
             <mailto:italo.busi@huawei.com>

     Editor: Aihua Guo
             <mailto:aihuaguo.ietf@gmail.com>

     Editor: Sergio Belotti
             <mailto:sergio.belotti@nokia.com>

     Editor: Luis M. Contreras
             <mailto:luismiguel.contrerasmurillo@telefonica.com>";

  description
    "This module defines a base YANG data model for configuring
     the underlay path of connectivity intent over a customer
     intent topology for RFC9543 network slices.

     The model fully conforms to the Network Management Datastore
     Architecture (NMDA).

     Copyright (c) 2023 IETF Trust and the persons
     identified as authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX; see
     the RFC itself for full legal notices.";

  revision 2025-07-03 {
    description "Initial revision";
    reference
      "RFC XXXX: IETF Network Slice Topology YANG Data Model";
  }

  /*
   * Groupings
   */
  grouping underlay-path {
    description
      "Underlay explicit path within a customer intent
       topology.";

    container underlay-path {
      description
        "Defines an underlay explicit path within specific
         customer intent topology.";

      uses nw:network-ref;

      list path-element {
       key "index";
       description
         "List of path elements.";
       leaf index {
         type uint32;
         description
           "Index of the hop within the underlay path.";
       }
       leaf is-strict-hop {
         type boolean;
         description
           "Indicate whether the hop is strict or loose";
       }
       choice type {
         description
           "Type of the hop.";
         case node-hop {
           leaf node-id {
             type nw:node-id;
             description
               "Node identifier.";
           }
         }
         case link-hop {
           leaf link-id {
             type nt:link-id;
             description
               "Link identifier.";
           }
         }
         case tp-hop {
           leaf tp-id {
             type nt:tp-id;
             description
               "Termination Point (TP) identifier.";
           }
         }
       }
      }
    }
  }

  /*
   * Augmented data nodes
   */
  augment "/ietf-nss:network-slice-services" +
          "/ietf-nss:slice-service" +
          "/ietf-nss:connection-groups" +
          "/ietf-nss:connection-group" +
          "/ietf-nss:slo-sle-policy" +
          "/ietf-nss:custom" +
          "/ietf-nss:service-slo-sle-policy" +
          "/ietf-nss:sle-policy" +
          "/ietf-nss:path-constraints" {
    description
      "Underlay path for connection group.";

    uses underlay-path;
  }

  augment "/ietf-nss:network-slice-services" +
          "/ietf-nss:slice-service" +
          "/ietf-nss:connection-groups" +
          "/ietf-nss:connection-group" +
          "/ietf-nss:connectivity-construct" +
          "/ietf-nss:slo-sle-policy" +
          "/ietf-nss:custom" +
          "/ietf-nss:service-slo-sle-policy" +
          "/ietf-nss:sle-policy" +
          "/ietf-nss:path-constraints" {
    description
      "Underlay path for connectivity construct.";

    uses underlay-path;
  }

  augment "/ietf-nss:network-slice-services" +
          "/ietf-nss:slice-service" +
          "/ietf-nss:connection-groups" +
          "/ietf-nss:connection-group" +
          "/ietf-nss:connectivity-construct" +
          "/ietf-nss:type" +
          "/ietf-nss:a2a" +
          "/ietf-nss:a2a-sdp" +
          "/ietf-nss:slo-sle-policy" +
          "/ietf-nss:custom" +
          "/ietf-nss:service-slo-sle-policy" +
          "/ietf-nss:sle-policy" +
          "/ietf-nss:path-constraints" {
    description
      "Underlay path for a2a connectivity constructs.";

    uses underlay-path;
  }
}
