module ietf-bier-rpcs {
        namespace "urn:ietf:params:xml:ns:yang:ietf-bier-rpcs";
        prefix bier-rpcs;

        import ietf-bier {
    prefix bier;
    }

        import ietf-bier-te{
    prefix bier-te;
        }

        import ietf-connectionless-oam-methods {
    prefix coam-methods;
        }

        import ietf-inet-types {
    prefix "inet";
        }

        import ietf-interfaces {
    prefix if;
        }

        import ietf-multicast-information {
      prefix multicast-info;
        }

        organization
        "IETF BIER(Bit Indexed Explicit Replication ) Working Group";

        contact
                "WG List:  <mailto:bier@ietf.org>
                WG Chair: Tony Przygienda
                                <mailto:tonysietf@gmail.com>
                WG Chair: Greg Shepherd
                                <mailto:gjshep@gmail.com>
                Editor:   Ran Chen
                                <mailto:chen.ran@zte.com.cn>
                Editor:   Min Gu
                                <mailto:gu.min@zte.com.cn>

                ";

                description
                "The YANG module defines BIER RPCs data model.";
        revision 2018-08-28{
                description
                "01 revision";
                reference "RFC XXXX: YANG module defines BIER RPCs data model.";
        }

                revision 2018-02-08{
                description
                "00 revision";
                reference "RFC XXXX: YANG module defines BIER RPCs data model.";
        }

        typedef reply-mode {
    type enumeration{
      enum "do not Reply"{
        value 1;
          description
            "reply mode is do not reply";
      }
      enum "reply via IPv4/IPv6 UDP packet"{
        value 2;
          description
            "reply mode is via IPv4/IPv6 UDP packet.";
      }
      enum "reply via BIER-TE packet"{
        value 3;
          description
            "reply mode is via BIER-TE packet.";
      }
    }
                description "Reply mode.";
        }

        grouping general-multicast {
                description "The general multicast address information.";
                leaf source-address {
                        type inet:ip-address;
                        description "The address of multicast source. The value set to zero
        means that the receiver interests in all source that relevant to
        one group.";
                }
                leaf source-wildcard {
                        type uint8;
                        description "The wildcard information of source.";
                }
                leaf group-address {
                        type inet:ip-address;
                        description "The address of multicast group.";
                }
                leaf group-wildcard {
                        type uint8;
                        description "The wildcard information of group.";
                }
        }

        grouping m-addr {
                description "The vpn multicast information.";
                leaf vpn-id {
                        type uint32;
                        description "The vpn-id of the multicast flow.
                        If there is global instance, the vpnid value should be zero.";
                }
                uses general-multicast;
        }

        grouping bier-address{
    description
      "bier test point address.";

        choice bier-address {
        case bfrs {
      description "use bfrs as address.";
      leaf bier-bsl{
        type bier:bsl;
        description
          "bier bitstringlength.";
      }
      leaf bier-subdomainid {
        type bier:sub-domain-id;
        description
          "bier sub-domain id.";
      }
      leaf bfir {
          type bier:bfr-id;
                description
          "bier bfir id.";
      }
      list bier-bfers {
        key bier-bfrid;
        leaf bier-bfrid {
        type bier:bfr-id;
          description
          "bier bfr identifier.";
                        }
                        description
        "bier BFERs.";
      }
        }
        case m-addr {
      description "use multicast flow address as address.";
      uses multicast-info:m-addr;
        }
        description "BIER address."     ;
        }

        list target-bfers {
                        key bier-bfrid;
                        leaf bier-bfrid {
                        type bier:bfr-id;
                                description
          "bier bfr identifier.";
      }
      description
                                "target BFERs.";
                }

                leaf reply-mode{
      type reply-mode;
                        description
        "reply mode.";
    }

        }

        grouping bier-te-address{
    description
      "bier-te test point address.";
    leaf bier-te-subdomainid {
      type bier:sub-domain-id;
        description
        "bier-te sub-domain id.";
    }
    list bier-te-bp-info {
        key "bier-te-bsl";
                description
              "bier-te bitpositions information.";
                leaf bier-te-bsl{
                  type bier:bsl;
                  description
                        "bier bitstringlength.";
                }
                list bitstring{
                  key "si";
                  description
                        "The bitstring of BIER-TE path.";
                  leaf si {
                        type bier:si;
                        description
                        "The set identifier of this forwarding item.";
                  }
                  list bitpositions {
                        key "bitposition";
                        description
                        "the list of bitposition information.";
                        leaf bitposition{
                        type bier-te:bit-string;
                          description
                          "the bitposition information.";
                        }
                  }
                }
                list fec-stack-type{
                  key "si";
                  description
                        "The FEC stack info.";
                  leaf si {
                        type bier:si;
                        description
                        "The set identifier of this forwarding item.";
                  }
                  list fec-stack-info {
                        key "bitposition";
                        description
                        "the choice of fec stack type.";
                        leaf bitposition{
                          type bier-te:bit-string;
                          description
                          "the bitposition information.";
                        }
                        choice fec-stack-type{
                          mandatory true;
                          case connected {
                                description "The type of adjacency is connected. Mostly connected interfaces.";
                                leaf local-bfr{
                                  type inet:ip-address;
                                  description
                                        "the local bfr identifier.";
                                }
                                leaf local-interface{
                                  type if:interface-ref;
                                  description
                                        "the local interface.";
                                }
                          }
                          case routed {
                                description "The type of adjacency is routed. Mostly not connected interfaces.";
                                leaf routed-bfr{
                                  type inet:ip-address;
                                  description
                                        "the loopback address of bfr.";
                                }
                          }
                          case local-decap {
                                description "Means that the packet should be decapsulated and forward out BIER domain.";
                                leaf bfer{
                                  type inet:ip-address;
                                  description
                                        "bfer indentifier.";
                                }
                          }
                          description "FEC stack type.";
                        }
                  }
                }

    }

    leaf reply-mode-te{
      type reply-mode;
      description
        "the reply mode.";
    }

  }
  identity tp-address-technology-type {
    description
      "Test point address type";
  }

        identity bier-address-type {
    base tp-address-technology-type;
    description
      "bier address address type";
        }

        identity bier-te-address-type {
    base tp-address-technology-type;
    description
      "bier te address address type";
        }

        augment /coam-methods:continuity-check/coam-methods:input/coam-methods:destination-tp{
        description
                "augment the connectionless oam methods yang for input CC destination test point address";
                container bier-address {
                uses bier-address;
                description
                        "bier Address.";
                }

                container bier-te-address {
                uses bier-te-address;
                description
                        "bier te Address.";
                }
                }

                augment /coam-methods:continuity-check/coam-methods:output/coam-methods:src-test-point{
                description
                "augment the connectionless oam methods yang for output CC source test point address";

                container bier-address {
                uses bier-address;
                description
                        "bier Address.";
                }

                container bier-te-address {
                uses bier-te-address;
                description
                        "bier te Address.";
                }
                }
                augment /coam-methods:continuity-check/coam-methods:output/coam-methods:dest-test-point{
                description
                "augment the connectionless oam methods yang for output CC destination test point address";
                container bier-address {
                uses bier-address;
                description
                        "bier Address.";
                }

                container bier-te-address {
                uses bier-te-address;
                description
                        "bier te Address.";
                }
                }
                augment  /coam-methods:path-discovery/coam-methods:input/coam-methods:destination-tp {
                description
                "augment the connectionless oam methods yang for input path-discovery destination test point address";
                container bier-address {
                uses bier-address;
                description
                        "bier Address.";
                }

                container bier-te-address {
                uses bier-te-address;
                description
                        "bier te Address.";
                }
                }

                augment /coam-methods:path-discovery/coam-methods:output/coam-methods:src-test-point{
                description
                "augment the connectionless oam methods yang for output path-discovery src test point address";
                container bier-address {
                uses bier-address;
                description
                        "bier Address.";
                }

                container bier-te-address {
                uses bier-te-address;
                description
                        "bier te Address.";
                }
                }

                augment "/coam-methods:path-discovery/coam-methods:output/coam-methods:dest-test-point"{
                description
                "augment the connectionless oam methods yang for output path-discovery destination test point address";
                container bier-address {
                uses bier-address;
                description
                        "bier Address.";
                }

                container bier-te-address {
                uses bier-te-address;
                description
                        "bier te Address.";
                }
                }

                augment /coam-methods:path-discovery/coam-methods:output/coam-methods:path-trace-info/coam-methods:path-trace-info-list{
                description
                "augment the connectionless oam methods yang for output path trace info.";
                container bier-address {
                uses bier-address;
                description
                        "bier Address.";
                }

                container bier-te-address {
                uses bier-te-address;
                description
                        "bier te Address.";
                }

        container bier-te-address {
                uses bier-te-address;
                description
                        "bier te Address.";
                }
                container bier-response{
                        leaf ttl{
                                type int16;
                                description
                                "TTL is ";
                                }
                        leaf responder-bfr{
                                type inet:ip-address;
                                description
                                "Responder bfr.";
                                }
                        description
                                "Bier response.";
                        }

                }

}
