module ietf-supa-policy {
  namespace "urn:ietf:params:xml:ns:yang:ietf-supa-policy";
  // replace with IANA namespace when assigned
  prefix policy;

  import ietf-inet-types {
    prefix inet;
  }

  organization "IETF";
  contact
    "Editor: Maoke Chen";

  description
    "This YANG module defines a component that describing
     the ECA policy data model refining from SGPIM and EPRIM.";

     Terms and Acronyms

  revision 2015-07-22 {
    description
    "Initial revision.";
    reference
        " ECA Policy YANG Data Model refining from SGPIM and
     EPRIM";
  }

container supa-policy{
  description
    "Top level class of policy  model that can be integrated into
     another model";
  leaf supa-policy-name {
        type string;
        description
          "The name of policy";
      }
  leaf supa-policy-type {
        type enumeration {
      enum local {
        description "local";
      }
      enum global {
        description "globe";
          }
        }
    }
  leaf applicable-service-type {
    type enumeration {
       enum local {
         description "local";
       }
       enum globe {
         description "globe";
       }
     }
  }

  leaf supa-policy-priority {
    type uint8;
  }

  container supa-policy-validity-period {
    description
    "The validity time period of the policy will define the
     start time and end time of the policy on a daily or monthly
     fashion periodicity. ";
    leaf start {
      type yang:date-and-time;
    }
    leaf end {
      type yang:date-and-time;
    }
    leaf duration {
      type uint32;
    }
    leaf periodicity {
      type enumeration {
        enum daily {
          description "daily";
        }
        enum monthly {
          description "monthly";
        }
      }
    }
  }

  container supa-policy-atomic {
    description
    "A sub class of policy which define a Policy that can be
     used in a stand-alone manner";
    container supa-ECA-policy-rule {
      description "The event-condition-action policy rule";

      leaf policy-rule-deploy-status {
        type enumeration {
          enum 0{
            description "undefined";
          }
          enum 1{
            description "deployed and enabled";
          }
          enum 2{
            description "deployed and in test";
          }
          enum 3{
            description "deployed but not enabled";
          }
          enum 4{
            description "ready to be deployed";
          }
          enum 5{
            description "not deployed";
          }
        }
      }

      leaf policy-rule-exec-status {
        type enumeration {
          enum 0{
            description "undefined";
          }
          enum 1{
            description "executed and SUCEEDED (operational mode)";
          }
          enum 2{
            description "executed and FAILED (operational mode)";
          }
          enum 3{
            description "currently executing (operational mode)";
          }
          enum 4{
            description "executed and SUCEEDED (test mode)";
          }
          enum 5{
            description "executed and FAILED (test mode)";
          }
          enum 6{
            description "currently executing (test mode)";
          }
        }
      }

      container supa-ECA-policy-rule-atomic {
        description "A SUPAECAPolicyRuleAtomic class
        represents a SUPA ECA Policy Rule that can operate as
        a single, stand-alone, manageable object.";
      }
      container supa-ECA-policy-rule-composite {
        description "A SUPAECAPolicyRuleComposite class
        represents a SUPA ECA Policy
        Rule as a hierarchy of Policy objects, where the
        hierarchy contains
        instances of a SUPAECAPolicyRuleAtomic and/or
        SUPAECAPolicyRuleComposite object.";
      }
    }
    container supa-ECA-component{
      leaf has-policy-events {
        type boolean;
        description
        "An event or a set of events that trigger the evaluation
      of policy: This is the trigger for the service management
      application to evaluate if a policy needs to be applied.
      For example a user action to provision a new VPN service
      can be an event.";
      }
      leaf has-policy-conditions {
        type boolean;
        description
         "A set of conditions that need to be satisfied for the
      policy to be applicable: This enables service management
      to select the right policy by validating the conditions
      against the current network state.";
      }
      leaf has-policy-actions {
        type boolean;
        description
         "A set of actions that should be triggered as part of the
      policy execution: This enables the service management to
      provision the service.";
      }
    }
  }

  container supa-policy-composite {
    description "SUPA Policy Composite is used to build
    hierarchies of Policies";
  }

  container supa-policy-statement {
    description
      "A SUPA Policy Statement is an abstract class that contains
    an individual or group of related functions; this set of
    functions defines a set of actions to take. Examples of
    actions include getting information, stating facts about the
    system being managed, writing a change to a configuration of
    one or more managed objects, and querying information about
    one or more managed objects.";

    container supa-encoded-clause{
      description "SUPAEncodedClause, which is a mechanism to
      directly encode the content of the SUPAPolicyStatement
      into a set of attributes";

      leaf supa-clause-content {
        description "This is a mandatory string attribute, and
        defines the content of this encoded clause of this
        clause. It works with another attribute of the
        SUPAEncodedClause class, called supaClauseFormat,
        which defines how to interpret this attribute. These
        two attributes form a tuple, and together enable a
        machine to understand the syntax and value of the
       encoded clause for the object instance of this class.";

        type string;
      }
      leaf supa-clause-format {
        description "This is a mandatory string attribute, and
        defines the format of this encoded clause. It works
        with another attribute of the SUPAEncodedClause class,
        called supaClauseContent, which defines the content
        (i.e., the value) of the encoded clause.";

        type string;
      }
    }
    container supa-boolean-clause{
      description "SUPABooleanClause, which defines a
      SUPAPolicyStatement as a set of one or more clauses;
      multiple clauses may be combined with Boolean AND and OR
      operators. This defines a SUPAPolicy as a completely
      reusable set of SUPAPolicy objects that are structured in
      an ECA form";

      container supa-boolean-clause-atomic {
        description "This is a mandatory abstract class that
        represents a SUPABooleanClause that can operate as a
        single, stand-alone, manageable object.";

        leaf supa-policy-variable {
          type string;
          description "The definition of the variable";
        }
        leaf supa-policy-operator {
          type enumeration {
            enum 0 {
              description "Equal to";
            }
            enum 1 {
              description "Larger than";
            }
            enum 2 {
              description "Less than";
            }
          }
        }
        leaf supa-policy-value {
          type uint32;
          description "Vaule of the variable";
        }
      }
    }
  }

  leaf supa-policy-target {
    description "SUPAPolicyTarget is an abstract class that
    defines a set of managed objects that may be affected by the
    actions of a SUPAPolicyStatement.";

    type string;
  }
  container supa-policy-term {
    description "The principal subclasses of SUPAPolicyTerm that
    are defined in this version of this document are
    SUPAPolicyVariable, SUPAPolicyOperator, and SUPAPolicyValue.
    These terms enable generic statements to be created from a
    set of reusable terms.";

    leaf supa-policy-variable {
      type string;
      description "The definition of the variable";
    }
    leaf supa-policy-operator {
      type enumeration {
        enum 0 {
          description "Equal to";
        }
        enum 1 {
          description "Larger than";
        }
        enum 2 {
          description "Less than";
        }
      }
    }
    leaf supa-policy-value {
      type uint32;
      description "The value of the variable";
    }
  }

  leaf supa-policy-metadata {
    type uint32;
 }
}
}<CODE ENDS>
