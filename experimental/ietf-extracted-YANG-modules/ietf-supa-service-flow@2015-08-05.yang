module ietf-supa-service-flow { 
  namespace "urn:ietf:params:xml:ns:yang:ietf-supa-policy"; 
  // replace with IANA namespace when assigned 
  prefix flow; 

  import ietf-yang-types { 
    prefix yang; 
  } 

  import eca-policy-0910 { 
    prefix supa; 
  } 
  organization "IETF"; 
  contact 
    "Editor: Maoke Chen"; 

  description 
    "This YANG module defines a component that describing 
     the specific ECA policy data model for service flow 
     refining from SGPIM and EPRIM. 

     Terms and Acronyms 
     "; 

  revision 2015-08-05 ; 

  //flow filter parameters for a flow  
  augment "/supa:supa-policy/supa:supa-poliy-
target/supa:instance"{ 
    container flowFilter{ 
      leaf dscp { 
        description 
          "dscp value of the indicated flow"; 
        type uint32; 
        config "true"; 
        default "0"; 
      } 
      leaf src-ip-addr{ 
        description 
          "source ip addresses of the flow"; 
        type string; 
        config "true"; 
        default "0.0.0.0/0"; 
      } 
      leaf dst-ip-addr{ 
        description 
          "destination ip addresses of the flow"; 
        type string; 
        config "true"; 
        default "0.0.0.0/0"; 
      } 
      leaf src-port{ 
        description 
          "source port number of the flow"; 
        type uint32; 
        config "true"; 
      } 
      leaf dst-port{ 
        description 
          "destination port number of the flow"; 
        type uint32; 
        config "true"; 
      } 
    } 
  } 
  //Add condition clauses into the condition list  
  augment "/supa:supa-policy/supa:supa-policy-
statement/supa:condition-list" { 
    container condition-bandwidth{ 
      leaf bandwidth{ 
        description 
          "The flow bandwidth, unit is Mbps"; 
        type uint32; 
      } 
      leaf threshold{ 
        description 
          "The threshold to trigger the action."; 
        type uint32; 
      } 
    }  
  } 
  //action node is depending on the condition 
  augment "/supa:supa-policy/supa:supa-policy-
statement/supa:action-list" { 
    description 
      "The augment of the action node is only valid when the 
      condition is evaluated as TRUE"; 
         when "/ietf-supa-policy/supa-policy/supa-policy-
         statement/condition-list/condition-
         bandwidth/bandwidth>/ietf-supa-policy/supa-policy/supa-
         policy-statement/condition-list/condition-
         bandwidth/threshold"; 
    container action-redirect{ 
      leaf cir { 
        description 
          "Committed information rate"; 
        type uint32; 
      } 
      leaf pir { 
        description 
          "Peak information rate"; 
        type uint32; 
      } 
      leaf Cbs { 
        description 
          "Committed burst size"; 
        type uint32; 
      } 
      leaf Pbs { 
        description 
          "Peak burst size"; 
        type uint32; 
      } 
    } 
  } 
}
