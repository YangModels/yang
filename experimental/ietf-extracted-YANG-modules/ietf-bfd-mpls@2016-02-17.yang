module ietf-bfd-mpls {
  namespace "urn:ietf:params:xml:ns:yang:ietf-bfd-mpls";
  // replace with IANA namespace when assigned
  prefix "bfd-mpls";

  import ietf-bfd {
    prefix "bfd";
  }

  import ietf-inet-types {
    prefix "inet";
  }

  import ietf-routing {
    prefix "rt";
  }
  organization "IETF BFD Working Group";

  contact
    "WG Web:   <http://tools.ietf.org/wg/bfd>
     WG List:  <rtg-bfd@ietf.org>
     WG Chair: Jeff Haas
     WG Chair: Reshad Rahman
     Editor:   Lianshu Zheng and Reshad Rahman";
  description
    "This module contains the YANG definition for BFD parameters for
     MPLS LSPs as per RFC5884.";

  revision 2016-02-17 {
    description "Initial revision.";
    reference "RFC XXXX: A YANG data model for BFD over MPLS LSPs";
  }

  identity bfd-encap-gach {
    base bfd:bfd-encap-type;
    description
      "BFD with G-ACh encapsulation as per RFC5586.";
  }

  identity bfd-encap-ip-gach {
    base bfd:bfd-encap-type;
    description
      "BFD with IP and G-ACh encapsulation as per RFC5586.";
  }

  grouping bfd-encap-cfg {
    description "Configuration for BFD encapsulation";

    leaf encap {
      type identityref {
        base bfd:bfd-encap-type;
      }
      default bfd:bfd-encap-ip;
      description "BFD encapsulation";
    }
  }

  grouping bfd-mpls-dest-address {
    description "Destination address as per RFC5884";

    leaf mpls-dest-address {
      type inet:ip-address;
      config "false";
      description
        "Destination address as per RFC5884.
         Needed if IP encapsulation is used";
    }
  }

  augment "/bfd:bfd" {
    description "BFD augmentation for MPLS";
    container mpls {
      description "BFD MPLS top level container";

      container config {
        description "BFD MPLS configuration container";

        container egress {
          description "Egress configuration";

          uses bfd:bfd-grouping-base-cfg-parms;

          uses bfd:bfd-auth-parms;
        }
      }

      container oper {
        config "false";
        description "BFD MPLS operational container";
        uses bfd:bfd-session-statistics;
      }
    }
  }

  augment "/rt:routing/rt:routing-instance/rt:routing-protocols/"
    + "rt:routing-protocol/bfd:bfd" {
    description "BFD augmentation for MPLS.";

    container mpls {
      description "BFD MPLS container";

      container config {
        description "BFD MPLS configuration container";

        container session-cfg {
          description "BFD MPLS session configuration";
          list sessions {
            key "mpls-fec";
            description "List of BFD MPLS sessions";
            leaf mpls-fec {
              type inet:ip-address;
              description "MPLS FEC";
            }

            uses bfd:bfd-grouping-common-cfg-parms;
          }
        }
      }
      container oper {
        config "false";
        description "BFD MPLS operational container";
        uses bfd:bfd-session-statistics;

        list session-group {
          key "mpls-fec";
          description
            "BFD MPLS group of sessions. A group of sessions is" +
            "for 1 FEC, each session has a different field in " +
            "UDP/IP hdr for ECMP.";
          leaf mpls-fec {
            type inet:ip-address;
            description "MPLS-FEC";
          }
          list sessions {
            key "local-discriminator";
            description
              "The BFD sessions for an MPLS FEC. Local " +
              "discriminator is unique for each session in the " +
              "group.";
            uses bfd:bfd-all-session;

            uses bfd-mpls:bfd-mpls-dest-address;
          }
        }
      }
    }
  }

  notification bfd-mpls-notification {
    description
      "Notification for BFD over MPLS FEC session state change. " +
      "An implementation may rate-limit notifications, e.g. when a" +
      "session is continuously changing state.";

    uses bfd:bfd-notification-parms;

    leaf routing-instance {
      type rt:routing-instance-ref;
      description "Routing instance";
    }

    leaf mpls-dest-address {
      type inet:ip-address;
      description
        "Destination address as per RFC5884.
         Needed if IP encapsulation is used";
    }
  }
}
