module ietf-yang-package-types {
  yang-version 1.1;
  namespace "urn:ietf:params:xml:ns:yang:ietf-yang-package-types";
  prefix "pkg-types";

  import ietf-yang-revisions {
    prefix rev;
    reference "XXXX: Updated YANG Module Revision Handling";
  }

  import ietf-yang-types {
    prefix yang;
    rev:revision-or-derived 2013-07-15;
    reference "RFC 6991: Common YANG Data Types.";
  }

  import ietf-inet-types {
    prefix inet;
    reference "RFC 6991: Common YANG Data Types.";
  }

  import ietf-module-tags {
    prefix tags;
    reference "RFC XXX: YANG Module Tags.";
  }

  organization
    "IETF NETMOD (Network Modeling) Working Group";

  contact
    "WG Web:   <http://tools.ietf.org/wg/netmod/>
     WG List:  <mailto:netmod@ietf.org>

     Author:   Rob Wilton
               <mailto:rwilton@cisco.com>";

  description
    "This module provides type and grouping definitions for YANG
     packages.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.
  // RFC Ed.: replace XXXX with actual RFC number and remove this
  // note.
  revision 2019-09-11 {
    rev:revision-label 0.1.0;
    description
      "Initial revision";
    reference
      "RFC XXXX: YANG Packages";
  }

  /*
   * Typedefs
   */
  typedef pkg-identifier {
    type yang:yang-identifier;
    description
      "Package identifiers are typed as YANG identifiers.";
  }

  typedef scoped-feature {
    type string {
      pattern '[a-zA-Z_][a-zA-Z0-9\-_.]*:[a-zA-Z_][a-zA-Z0-9\-_.]*';
    }
    description
      "Represents a feature name scoped to a particular module,
       identified as the '<module-name>:<feature-name>', where both
       <module-name> and <feature-name> are YANG identifier strings,
       as defiend by Section 12 or RFC 6020.";
    reference
      "RFC XXXX, YANG Packages.";
  }

  typedef sha-256-hash {
    type string {
      length "64";
      pattern "[0-9a-fA-F]*";
    }
    description
      "A SHA-256 hash represented as a hexadecimal string.

       Used as the checksum for modules, submodules and packages in a
       YANG package definition.

       For modules and submodules the SHA-256 hash is calculated on
       the contents of the YANG file defining the module/submodule.

       For packages the SHA-256 hash is calculated on the file
       containing the YANG instance data document holding the package
       definition";
  }

  /*
   * Groupings
   */

  grouping yang-pkg-identification-leafs {
    description
      "Parameters for identifying a specific version of a YANG
       package";

    leaf name {
      type pkg-identifier;
      mandatory true;
      description
        "The YANG package name.";
    }

    leaf version {
      type rev:revision-label;
      mandatory true;
      description
        "Uniquely identies a particular version of a YANG package.

         Follows the definition for revision labels defined in
         draft-verdt-nemod-yang-module-versioning, section XXX";
    }
  }

  grouping yang-pkg-common-leafs {
    description
      "Defines definitions common to all YANG package definitions.";

    leaf timestamp {
      type yang:date-and-time;

      description
        "An optional timestamp for when this package was created.
         This does not need to be unique across all versions of a
         package.";
    }

    leaf organization {
      type string;

      description "Organization responsible for this package";
    }

    leaf contact {
      type string;

      description
        "Contact information for the person or organization to whom
         queries concerning this package should be sent.";
    }

    leaf description {
      type string;

      description "Provides a description of the package";
    }

    leaf reference {
      type string;

      description "Allows for a reference for the package";
    }

    leaf-list location {
      type inet:uri;
      description
        "Contains a URL that represents where an instance data file
         for this YANG package can be found.

         This leaf will only be present if there is a URL
         available for retrieval of the schema for this entry.

         If multiple locations are provided, then the first location
         in the leaf-list MUST be the definitive location that
         uniquely identifies this package";
    }

    leaf complete {
      type boolean;
      default true;
      description
        "Indicates whether the schema defined by this package is
         referentially complete.  I.e. all module imports can be
         resolved to a module explicitly defined in this package or
         one of the included packages.";
    }

    leaf local {
      type boolean;
      default false;
      description
        "Defines that the package definition is local to the server,
         and the name of the package MAY not be unique, and the
         package definition MAY not be available in an offline file.

         Local packages can be used when the schema for the device
         can be changed at runtime through the addition or removal of
         software packages, or hot fixes.";
    }

    leaf previous-version {
      type rev:revision-label;
      description
        "The previous package version that this version has been
         derived from.  This leaf allows a full version history graph
         to be constructed if required.";
    }

    leaf nbc-changes {
      type boolean;
      default false;
      description
        "Indicates whether the defined package version contains
         non-backwards-compatible changes relative to the package
         version defined in the 'previous-version' leaf.";
    }

    leaf-list tag {
      type tags:tag;
      description
        "Tags associated with a YANG package.  Module tags defined in
         XXX, ietf-netmod-module-tags can be used here but with the
         modification that the tag applies to the entire package
         rather than a specific module.  See the IANA 'YANG Module
         Tag Prefix' registry for reserved prefixes and the IANA
         'YANG Module IETF Tag' registry for IETF standard tags.";
    }

    leaf-list mandatory-feature {
      type scoped-feature;
      description
        "Lists features from any modules included in the package that
         MUST be supported by any server implementing the package.

         Features already specified in a 'mandatory-feature' list of
         any included package MUST also be supported by server
         implementations and do not need to be repeated in this list.

         All other features defined in modules included in the
         package are OPTIONAL to implement.

         Features are identified using <module-name>:<feature-name>";
    }

    list included-package {
      key "name version";
      description
        "An entry in this list represents a package that is included
         as part of the package definition, or an indirectly included
         package that is changed in a non backwards compatible way.
         It can be used to resolve inclusion of conflicting package
         versions by explicitly specifying which package version is
         used.

         If included packages implement different revisions or
         versions of the same module, then an explicit entry in the
         module list MUST be provided to select the specific module
         version 'implemented' by this package definition.

         If the schema for any packages that are included, either
         directly or indirectly via another package include, are
         changed in any non-backwards-compatible way then they MUST
         be explicitly listed in the included-packages list with the
         'nbc-modified' leaf set to true.

         For import-only modules, the 'replaces-revision' leaf-list
         can be used to select the specific module versions used
         by this package.";
      reference
        "XXX";

      uses yang-pkg-identification-leafs;

      leaf-list replaces-version {
        type rev:revision-label;
        description
          "Gives the version of an included package version that
           is replaced by this included package revision.";
      }

      leaf nbc-modified {
        type boolean;
        default false;
        description
          "Set to true if any data nodes in this package are modified
           in a non backwards compatible way, either through the use
           of deviations, or because one of the modules has been
           replaced by an incompatible revision.  This could also
           occur if a module's revision was replaced by an earlier
           revision that had the effect of removing some data
           nodes.";
      }

      leaf-list location {
        type inet:uri;
        description
          "Contains a URL that represents where an instance data file
           for this YANG package can be found.
           This leaf will only be present if there is a URL available
           for retrieval of the schema for this entry.

           If multiple locations are provided, then the first
           location in the leaf-list MUST be the definitive location
           that uniquely identifies this package";
      }

      leaf checksum {
        type pkg-types:sha-256-hash;
        description
          "The SHA-256 hash calculated on the textual package
           definition, represented as a hexadecimal string.";
      }
    }
  }
}
