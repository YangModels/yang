module lora {

    namespace "urn:lora";
    prefix lo;

         import ietf-interfaces {
       prefix if;
      }

    organization
      "Acklio";

    contact
      "Alexander Pelov
     a@ackl.io";
    "Ana Minaburo
     ana@minaburo.com";

    description
      "This module contains a collection of YANG definitions for
   configuring the LORA () network interface.

   Copyright (c) 2015 IETF Trust and the persons identified as
   authors of the code. All right reserved.

   Redistribution and use in source binary forms, with or
   without modification, is permitted pursuant to, and subject
   to the license terms contained in, the Simplified BSD License
   Relating to IETF Documents
   (http://trustee.ietf.org/license-info)

   <!--This version of this YANG module is part of
   draft-pelov-yang-lora; see the draft itself for
   full legal notices.";-->

    revision 2015-11-01 {
      description
        "Initial Description";
      reference
        "LoRa MAC Class A Specification R3.1 by Semtech";
    }

    grouping mode {
       leaf channel-bandwidth {
                type enumeration {
                       enum 125 { value 0; }
                       enum 150 { value 1; }
                       enum 500 { value 2; }
         }
    }

       leaf coding-rate {
                type enumeration {
                        enum 4_5 { value 1; }
                        enum 4_6 { value 2; }
                        enum 4_7 { value 3; }
                        enum 4_b { value 4; }
                }
        }

        leaf spreading-factor {
                type uint8 {
                    range "6 .. 12";
          }
        }

    }

    augment "/if:interfaces/if:interface" {
         // To be defined later
         when "if:type = 'ianaift:lora'";

         container lora {
          uses mode;
            container physical-layer {
              leaf preamble-length {
                  type int32;
                  default 7;
               }

              leaf channel-frequency-range {
                  mandatory true;
                  type enumeration {
                    enum europe;
                    enum usa;
                    enum japan;
                    enum china;
                   }
                }

              leaf channel {
                  type uint8 {
                       range "0..10";
                     }
                 }

              leaf symbol-timeout {
                  type uint32;
                     }
                 }

           container mac-layer {
              leaf payload-encryption {
                  type boolean;
                  default "false";
                     }

              leaf delay {
                  type int32;
                     }

               leaf fixed-length-payload {
                  type boolean;
                  default "false";
               }
            }
         }
    }
}
