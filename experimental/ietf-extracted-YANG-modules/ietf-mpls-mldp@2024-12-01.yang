module ietf-mpls-mldp {
  yang-version 1.1;

  namespace "urn:ietf:params:xml:ns:yang:ietf-mpls-mldp";
  prefix "mldp";

  import ietf-inet-types {
    prefix "inet";
    reference "RFC 6991: Common YANG Data Types";
  }

  import ietf-interfaces {
    prefix "if";
    reference "RFC 8343: A YANG Data Model for Interface Management";
  }

  import ietf-mpls-ldp {
    prefix "ldp";
    reference "RFC 9070: YANG Data Model for MPLS LDP";
  }

  import ietf-routing {
    prefix "rt";
    reference
      "RFC 8349: A YANG Data Model for Routing Management (NMDA
       version)";
  }

  import ietf-routing-types {
    prefix "rt-types";
    reference
      "RFC 8294: Common YANG Data Types for the Routing Area";
  }

  organization
    "IETF MPLS Working Group";
  contact
    "WG Web:   <http://tools.ietf.org/wg/mpls/>
     WG List:  <mailto:mpls@ietf.org>

     Editor:   Kamran Raza
               <mailto:skraza@cisco.com>

     Editor:   Xufeng Liu
               <mailto:xufeng.liu.ietf@gmail.com>

     Editor:   Santosh Esale
               <mailto:santosh_easale@berkeley.edu>

     Editor:   Loa Andersson
               <mailto:loa@pi.nu>

     Editor:   Jeff Tantsura
               <mailto:jefftant.ietf@gmail.com>";

  description
    "This YANG module defines the essential components for the
     management of Multiprotocol Label Switching (MPLS) Multipoint
     LDP (mLDP).

     The types and groupings defined in this module are intended exclusively
     for use within this module itself or any other module that augments this
     module.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

     // RFC Editor: replace XXXX with actual RFC number and remove
     // this note

  revision 2024-12-01 {
    // RFC Editor: replace the above date 2024-12-01 with the date of
    // publication and remove this note.
    description
      "Addressing YANG doctors review comments";
    reference
      "RFC XXXX: Base YANG Data Model for MPLS mLDP";
     // RFC Editor: replace XXXX with actual RFC number and remove
     // this note
  }

  revision 2021-11-11 {
    description
      "Initial revision.";
    reference
      "RFC XXXX: Base YANG Data Model for MPLS mLDP";
     // RFC Editor: replace XXXX with actual RFC number and remove
     // this note
  }

  /*
   * Typedefs
   */
  typedef multipoint-type {
    type enumeration {
      enum p2mp {
        description "Point to multipoint";
      }
      enum mp2mp {
        description "Multipoint to multipoint";
      }
    }
    description
      "The type of a multipoint LSP: either Point to multipoint
       (p2mp) or Multipoint to multipoint (mp2mp)";
  }

  typedef lsp-mbb-role {
    type enumeration {
      enum none {
        description "Make-before-break (MBB) is not enabled.";
      }
      enum active {
        description "This LSP is active.";
      }
      enum inactive {
        description "This LSP is inactive.";
      }
    }
    description
      "This type represents the Make-before-break
       role of an LSP.";
  }

  /*
   * Groupings
   */
  grouping mldp-capabilities-base {
    description
      "A grouping describing the protocol capabilities of mLDP as specified
       in RFC6388";

    container p2mp {
      description
        "Configuration and state information for the
         point-to-multipoint capability";
      leaf enabled {
        type boolean;
        description
          "'true' to enable the point-to-multipoint capability";
      }
    }
    container mp2mp {
      description
        "Configuration and state information for the
         multipoint-to-multipoint capability";
      leaf enabled {
        type boolean;
        description
          "'true' to enable the multipoint-to-multipoint capability";
      }
    }
    container make-before-break {
      description
        "Configuration and state information for the
         make-before-break capability.";
      leaf enabled {
        type boolean;
        description
          "'true' to enable the make-before-break capability";
      }
      leaf switchover-delay {
        type uint16;
        units seconds;
        description
          "Switchover delay (in seconds) for activating an inactive element";
      }
      leaf timeout {
        type uint16;
        units seconds;
        description
         "To prevent waiting indefinitely for the MBB Notification to arrive,
          a timeout should be applied. As soon as the timer expires,
          the MBB procedures, same as those applied at the receipt of an MBB
          notification,  are applied on the inactive element.";
      }
    }
  } // mldp-capabilities-base

  grouping  mldp-binding-label-peer-state-attributes {
    description
      "mLDP label binding per peer attributes";
    leaf direction {
      type ldp:downstream-upstream;
      description
        "Downstream or upstream label binding";
    }
    leaf advertisement-type {
      type ldp:advertised-received;
      description
        "Advertised (outbound) or received label (inbound) binding";
    }
    leaf label {
      type rt-types:mpls-label;
      description
        "Advertised (outbound) or received (inbound) label";
    }
    leaf mbb-status {
      when "../direction = 'upstream'" {
        description
          "This leaf is used for MBB upstream direction only.";
      }
      type lsp-mbb-role;
      description
        "The MBB status of this LSP";
    }
  } // mldp-binding-label-peer-state-attributes

  grouping  mldp-binding-label-state-attributes {
    description
      "mLDP label binding attributes";
    list peer {
      key "direction peer advertisement-type";
      description
        "List of peers with bindings exchnaged (sent and/or received)";
      leaf peer {
        type leafref {
          path
            "../../../../../../../../../../../ldp:peers/ldp:peer/"
          + "ldp:lsr-id";
        }
        description
          "[m]LDP peer from which this binding is received, or
           to which this binding is advertised.";
      }
      uses mldp-binding-label-peer-state-attributes;
    } // peer
  } // mldp-binding-label-state-attributes

  /*
   * Configuration data and operational state data nodes
   */
  augment "/rt:routing/rt:control-plane-protocols/"
    + "rt:control-plane-protocol/ldp:mpls-ldp/ldp:global/"
    + "ldp:capability" {
    description "Augmentation for mLDP global capability";
    container mldp {
      description
        "This container contains the configuration and state
         information for multipoint LDP capabilities.";
      uses mldp-capabilities-base;
    }
  }

  /*
   * Operational state data nodes
   */
  augment "/rt:routing/rt:control-plane-protocols/"
    + "rt:control-plane-protocol/ldp:mpls-ldp/ldp:peers/ldp:peer/"
    + "ldp:received-peer-state/ldp:capability" {
    description
      "Augmentation for mLDP received peer state capability";
    container mldp {
      description
        "Operational state information for the protocol capabilities
         of mLDP peer";

      container p2mp {
        description
          "Operatiobal state information for the point-to-multipoint
           capability of a peer";
        leaf is-capable {
          type boolean;
          description
            "'true' when point-to-multipoint capability is received from peer";
        }
      }
      container mp2mp {
        description
          "Operational state information for the
           multipoint-to-multipoint capability of a peer";
        leaf is-capable {
          type boolean;
          description
            "'true' when multipoint-to-multipoint capability is received from peer";
        }
      }
      container make-before-break {
        description
          "Operational state information for the make-before-break
           capability of a peer";
        leaf is-capable {
          type boolean;
          description
           "'true' when make-before-break capability is received from peer";
        }
      }
    } // mldp
  }

  /*
   * Global augmentation
   */
  augment "/rt:routing/rt:control-plane-protocols/"
    + "rt:control-plane-protocol/ldp:mpls-ldp/ldp:global" {
    description "mLDP global augmentation.";
    container mldp {
      description
        "mLDP attributes at per instance level. Defining
         attributes here does not enable any MP capabilities.
         MP capabilities need to be explicitly enabled under
         capability container";

      leaf enabled {
        type boolean;
        description
          "'true' to enable mLDP protocol";
      }

      container address-families {
        description
          "Per-address-family configuration and operational state.
           The address family can be either IPv4 or IPv6.";

        container ipv4 {
          presence "Enables IPv4 mLDP support unless the
                   'enabled' leaf is set to 'false'.";
          description
                 "Containing data related to the IPv4 address family.";
          leaf enabled {
            type boolean;
            default "true"; // TBD
            description
                   "'false' to disable the IPv4 address family.";
          }

          container roots {
            config false;
            description
              "IPv4 multicast LSP roots";
            list root {
              key "root-address";
              description
                "List of roots for configured multicast LSPs";

              leaf root-address {
                type inet:ipv4-address;
                description
                  "Root address.";
              }

              leaf is-self {
                type boolean;
                description
                  "The node itself is the root node.";
              }

              list reachability {
                key "address interface";
                description
                  "Root reachability information in form of a next-hop";
                leaf address {
                  type inet:ipv4-address;
                  description
                    "The next-hop address to reach root";
                }
                leaf interface {
                  type if:interface-ref;
                  description
                    "The next-hop interface to reach root";
                }
                leaf peer {
                  type leafref {
                    path
                      "../../../../../../../../ldp:peers/"
                      + "ldp:peer/ldp:lsr-id";
                  }
                  description
                    "LDP peer associated with the nexthop (address, interface)";
                }
              }

              container bindings {
                description
                  "mLDP FEC-label bindings";
                container opaque-element-lspid {
                  description
                    "Generic LSP identifier opaque element FEC-label bindings container";
                  reference
                    "RFC6388: Label Distribution Protocol
                     Extensions for Point-to-Multipoint and
                     Multipoint-to-Multipoint Label Switched
                     Paths.";
                  list fec-label {
                    key
                      "lsp-id";
                    description
                      "List of FEC-label bindings";
                    leaf lsp-id {
                      type uint32;
                      description "LSP identifier";
                    }
                    leaf multipoint-type {
                      type multipoint-type;
                      description
                        "The type of multipoint: p2mp or mp2mp";
                    }
                    uses mldp-binding-label-state-attributes;
                  } // fec-label
                } // opaque-element-lspid
              } // bindings
            } // list root
          } // roots

          container configured-leaf-lsps {
            description
              "Configured multicast LSPs.";
            container opaque-element-lspid {
              description
                 "Generic LSP identifier opaque element FEC-label bindings container";
              reference
                "RFC6388: Label Distribution Protocol
                 Extensions for Point-to-Multipoint and
                 Multipoint-to-Multipoint Label Switched
                 Paths.";
              list fec-label {
                key
                  "root-address lsp-id";
                description
                  "List of FEC to label bindings.";
                leaf root-address {
                  type inet:ipv4-address;
                  description
                    "Root address";
                }
                leaf lsp-id {
                  type uint32;
                  description "LSP identifier";
                }
                leaf multipoint-type {
                  type multipoint-type;
                  description
                    "The type of multipoint: p2mp or mp2mp";
                }
              } // fec-label
            } // opaque-element-lspid
          } // configured-leaf-lsps
        } // ipv4
      } // list address-family
    } // mldp
  }

  // KAMI: TODO REVIEW

  /*
   * Notifications
   */
  notification mpls-mldp-fec-event {
    description
      "Notification event for a change of FEC status";
    leaf event-type {
      type ldp:oper-status-event-type;
      description "Event type";
    }
    choice opaque-element {
      description
        "The type of opaque value element";
      case opaque-element-lspid {
        container opaque-element-lspid {
          description
            "Generic LSP identifier opaque element";
          reference
            "RFC6388: Label Distribution Protocol
             Extensions for Point-to-Multipoint and
             Multipoint-to-Multipoint Label Switched
             Paths.";
          leaf root-address {
            type inet:ip-address;
            description
              "Root address.";
          }
          leaf lsp-id {
            type uint32;
            description "LSP identifier";
          }
          leaf multipoint-type {
            type multipoint-type;
            description
              "The type of multipoint: p2mp or mp2mp";
          }
        } // container opaque-element-lspid
      }
    }
  }
}
