module youpi {
    namespace "http://ackl.io/youpi";

    prefix "youpi";

    organization
        "Acklio";

    contact
        "Ivaylo Petrov
        <mailto:ivaylo@ackl.io>";

    description
        "This module defines the extentions used by youpi.";

    revision 2019-07-22 {
        description "Initial revision.";
    }

    /**
     *
     * Extension for Binary data to CBOR mapping.
     *
     **/
    extension position {
        argument object;
    }

    extension fieldIndex {
        argument object;
    }

    extension condition {
        argument object;
    }

    extension multiplier {
        argument object;
    }

    extension offset {
        argument object;
    }

    extension units-subject {
        argument object;
    }

    extension js {
        argument object;
    }
}
