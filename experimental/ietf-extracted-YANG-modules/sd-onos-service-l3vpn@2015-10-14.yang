module sd-onos-service-l3vpn { 
  namespace "urn:onos:l3vpn"; 
  prefix l3vpn ; 

  import ietf-inet-types{ 
     prefix inet;  
  } 
  import ietf-yang-types { 
    prefix yang-types; 
  } 
  import sd-onos-service-types { 
    prefix service-types; 
  } 
  import sd-onos-common-types { 
    prefix types; 
  } 
  organization "";  
  contact ""; 
  revision "2015-10-14" {description "revised revision.";} 

  container service { 
    container l3vpn-cfg { 
      list vpn-cfg { 
        key name; 
        uses l3vpn; 
      } 
    } 
       container service-paths { 
            list  service-path{ 
                key "service-id source-ne-id source-ac-id   
               destination-ne-id destination-ac-id"; 
                uses service-types:service-path; 
            } 
        } 
  } 

  grouping l3vpn { 
    leaf name { 
                        mandatory true; 
      description "name of snc eline." ; 
      type string ; 
    } 
    leaf id { 
                        mandatory true; 
      description "ID of snc eline." ; 
      type uint32 ; 
    } 
    leaf user-label { 
      description "user label of snc eline." ; 
      type string ; 
    } 
    leaf parent-ncd-id { 
      description "parent ncd id." ; 
      type string ; 
    } 

    leaf admin-status { 
      type types:admin-status; 
    } 
    leaf operate-status { 
      type types:operate-status; 
    } 
    uses service-type-grouping; 
    container acess-information { 

      list access-circuit { 
        key "id"; 
        uses service-types:l3-ac; 
      } 
    } 

    container protect-policy{ 
      description "L3VPN Service protect policy." ; 
      uses service-types:protect-policy; 
    } 
    container tunnel-service { 
      description "tunnel service." ; 
      uses service-types:tunnel-service; 
    }  
  } 

  grouping service-type-grouping { 
    leaf service-topology { 
      description "service topology type." ; 
      default full-mesh; 
      type enumeration { 
        enum full-mesh { 
          value 1 ; 
          description "full-mesh." ; 
        } 
        enum hub-spoke { 
          value 2 ; 
          description "hub-spoke." ; 
        } 
      } 
    } 
  } 

  rpc create-l3vpn-instance { 
    input { 
      container l3vpn-instance { 
        uses l3vpn; 
      } 
    } 
  } 

  rpc delete-l3vpn-instance { 
    input { 
      leaf l3vpn-id { 
        type string; 
      } 
    } 
  } 

  rpc close-l3vpn { 
      input { 
          leaf l3vpn-id { 
              type string; 
          } 
          container ac-status { 
              list acs{ 
                  key "id"; 
                  leaf id { 
                      type string; 
                  } 
                  leaf admin-status { 
                      type types:admin-status; 
                  }                     
              } 
          } 
      } 
  }   
  rpc modify-l3vpn-instance-basic { 
    input { 
      leaf l3vpn-id { 
        type string; 
      } 
      leaf user-label { 
        type string ; 
      } 
    } 
  } 

  rpc modify-l3vpn-instance-ac-qos { 
    input { 
      leaf l3vpn-id { 
        type string; 
      } 
      container ac-qos { 
        list acs{ 
            key "id"; 
            leaf id { 
                type string; 
            } 
            container qos-policy {   
                container qos-if-cars {          
                    list qos-if-car { 
                       key "direction"; 
                       uses service-types:qos-if-car; 
                    } 
                } 
            }                     
         } 
      } 
    } 
  } 

  rpc modify-l3vpn-instance-connection { 
    input { 
      leaf l3vpn-id { 
        type string; 
      } 
      container ac-connection { 
        list acs{ 
          leaf id { 
            description "ac id." ; 
            type string ; 
          } 
          container connection { 
            description "CE to PE  connection." ; 
            uses service-types:connection; 
          } 
        } 
      } 
    } 
  } 
rpc inquire-l3vpn-instance-work-path { 
     input { 
            leaf service-id { 
              type string; 
            } 
            leaf ingress-ne-id {            
              type string ; 
            } 
            leaf destination-ne-id {            
              type string ; 
            } 
            leaf ingress-ac-id {            
              type string ; 
            } 
            leaf destination-ac-id {            
              type string ; 
            }   
            leaf path-layer { 
               type string ; 
            } 
            leaf path-role { 
               type string ; 
            }             
    } 
    output { 
        container service-path { 
          leaf service-id { 
            type string; 
          } 
          leaf ingress-ne-id {            
            type string ; 
          } 
          leaf destination-ne-id {             
            type string ; 
          } 
          leaf ingress-ac-id {            
            type string ; 
          } 
          leaf destination-ac-id {             
            type string ; 
          }  
          leaf path-layer { 
             type string ; 
          } 
          leaf path-role { 
               type string ; 
          }              
            list path-list { 
                key "ne-id"; 
                leaf ne-id { 
                   type string; 
                } 
                leaf ingress-ltp-id { 
                   type string; 
                } 
                leaf backward-peer-id { 
                   type string; 
                }  
                leaf egress-ltp-id { 
                   type string; 
                } 
                leaf forward-peer-id { 
                   type string; 
                } 
            }  
         }  
    } 
  } 
}
