module ietf-cmis-control-primitive {
  yang-version 1.1;
  namespace "urn:ietf:params:xml:ns:yang:ietf-cmis-control-primitive";
  prefix cmis-ctrl-pm;

  import ietf-interfaces {
    prefix if;
  }

  organization
    "IETF CCAMP Working Group";

  contact
    "WG Web:   <http://tools.ietf.org/wg/ccamp/>
    WG List:  <mailto:ccamp@ietf.org>

    Editor:   Shunsuke Homma
      <mailto:shunsuke.homma.ietf@gmail.com>

    Editor:   Hitoshi Irino
      <mailto:hitoshi.irino.ntt@gmail.com>";

  description
    "This YANG module defines a data model for the management
    of CMIS (Common Management Interface Specification) pages
    as specified by OIF with RPC. It enables configuration and
    retrieval of CMIS page data, including access types and
    value fields, to support the management of pluggable optical
    modules via NETCONF or RESTCONF.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.

    Copyright (c) 2025 IETF Trust and the persons identified
    as authors of the code.  All rights reserved.

    Redistribution and use in source and binary forms, with or
    without modification, is permitted pursuant to, and
    subject to the license terms contained in, the Revised
    BSD License set forth in Section 4.c of the IETF Trust's
    Legal Provisions Relating to IETF Documents
    (http://trustee.ietf.org/license-info).

    This version of this YANG module is part of RFC XXXX
    (https://www.rfc-editor.org/info/rfcXXXX); see the RFC itself
    for full legal notices.";

// RFC Ed.: replace XXXX with actual RFC number and remove this note

    revision "2025-04-21" {
      description
        "Initial revision.";
      reference
        "RFC XXXX: A YANG Data Model for CMIS Access and Control";
    }

    augment "/if:interfaces/if:interface" {
      description "Add primitive CMIS read/write actions under interface.";

      action cmis-read {
        description "Read CMIS register under this interface.";
        input {
          leaf page {
            type uint8;
            mandatory true;
            description "The number of the CMIS page.";
          }
          leaf bank {
            type uint8;
            mandatory true;
            description "The bank of the CMIS page.";
          }
          leaf offset {
            type uint8;
            mandatory true;
            description "The memory address of the value.";
          }
          leaf size {
            type uint8;
            default 1;
            description "The memory size of the value.";
          }
        }
        output {
          leaf data {
            type binary;
            description "Raw register data.";
          }
        }
      }

      action cmis-write {
        description "Write CMIS register under this interface.";
        input {
          leaf page {
            type uint8;
            mandatory true;
            description "The number of the CMIS page.";
          }
          leaf bank {
            type uint8;
            mandatory true;
            description "The bank of the CMIS page.";
          }
          leaf offset {
            type uint8;
            mandatory true;
            description "The memory address of the value.";
          }
          leaf data {
            type binary;
            mandatory true;
            description "Data to write.";
          }
        }
      }
    }
}
