module ietf-yp-current-period {
  yang-version 1.1;
  namespace "urn:ietf:params:xml:ns:yang:ietf-yp-current-period";
  prefix yp-cp;

  import ietf-subscribed-notifications {
    prefix sn;
    reference
      "RFC 8639: A YANG Data Model for Subscriptions to
                 Event Notifications";
  }
  import ietf-yang-push {
    prefix yp;
    // RFC Ed.: remove revision-date, needed here for datatracker
    // to properly validate the module, because the latest version
    // on the server is not the ratified one and validation fails.
    revision-date 2019-09-09;
    reference
      "RFC 8641: Subscriptions to YANG Datastores.";
  }

  organization
    "IETF OPSAWG (Operations and Management Area Working Group)";
  contact
    "WG Web:   <https://datatracker.ietf.org/wg/opsawg/>
     WG List:  <mailto:opsawg@ietf.org>
     Author:   Benoit Claise   <mailto:benoit@everything-ops.net>
     Author:   Jean Quilbeuf   <mailto:jean.quilbeuf@huawei.com>
     Author:   Diego R. Lopez  <mailto:diego.r.lopez@telefonica.com>
     Author:   Ignacio Dominguez Martinez-Casanueva
     <mailto:i.domingumar@gmail.com>
     Author:   Thomas Graf     <mailto:thomas.graf@swisscom.com>";
  description
    "This module augments ietf-subscribed-notifications and
     ietf-yang-push with the current-period leaf reporting the actual
     collection period, as opposed to the configured one.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.";

  revision 2026-06-27 {
    description
      "Initial revision";
    reference
      "RFC XXXX: A Data Manifest for Contextualized Telemetry Data";
  }

  augment "/sn:subscriptions/sn:subscription" {
    description
      "Adds current collection period";
    leaf current-period {
      when '../yp:periodic';
      type yp:centiseconds;
      config false;
      description
        "Period between two successive data collections, in the
         current state. May differ from the configured period if
         the platform increases the collection period
         automatically due to overload.";
    }
  }
}
