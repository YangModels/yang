module ietf-ns-topo {
  yang-version 1.1;
  namespace
    "urn:ietf:params:xml:ns:yang:ietf-ns-topo";
  prefix "ns-topo";

  import ietf-network {
    prefix "nw";
    reference
     "RFC 8345: A YANG Data Model for Network Topologies";
  }
  import ietf-network-topology {
    prefix "nt";
    reference
     "RFC 8345: A YANG Data Model for Network Topologies";
  }
  import ietf-te-types {
    prefix "te-types";
    reference
      "RFC 8776: Traffic Engineering Common YANG Types";
  }

  import ietf-network-slice-service {
    prefix "ietf-nss";
    reference
      "draft-ietf-teas-ietf-network-slice-nbi-yang-00:
       IETF Network Slice Service YANG Model";
  }

  organization
    "IETF CCAMP Working Group";
  contact
    "WG Web: <http://tools.ietf.org/wg/ccamp/>
     WG List: <mailto:ccamp@ietf.org>

     Editor: Xufeng Liu
             <mailto:xufeng.liu.ietf@gmail.com>

     Editor: Italo Busi
             <mailto:italo.busi@huawei.com>

     Editor: Aihua Guo
             <mailto:aihuaguo.ietf@gmail.com>

     Editor: Sergio Belotti
             <mailto:sergio.belotti@nokia.com>

     Editor: Luis M. Contreras
             <mailto:luismiguel.contrerasmurillo@telefonica.com>";

  description
    "This module defines a base YANG data model for configuring
     generic network slices in optical transport networks, e.g.,
     Optical Transport Network (OTN).

     The model fully conforms to the Network Management Datastore
     Architecture (NMDA).

     Copyright (c) 2023 IETF Trust and the persons
     identified as authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX; see
     the RFC itself for full legal notices.";

  revision 2023-03-11 {
    description "Initial revision";
    reference
      "RFC XXXX: IETF Network Slice Topology YANG Data Model";
  }

  /*
   * Identities
   */
  identity resize-option {
    description
      "Base identity for link or connectivity resizing options";
  }

  identity resize-none {
    base resize-option;
    description
      "Not resizable";
  }

  identity resize-with-hit {
    base resize-option;
    description
      "Resizable with traffic hits";
  }

  identity resize-hitless {
    base resize-option;
    description
      "Hitless resizable";
  }

  /*
   * Groupings
   */

  grouping ns-topo-slo-sle-policy {
    description
      "Policy grouping for Transport Network Slices.";

    leaf optimization-criterion {
        type identityref {
          base te-types:objective-function-type;
        }
        description
          "Optimization criterion applied to this topology.";
    }
    leaf resize-requirement {
      type identityref {
        base resize-option;
      }
      description
        "Indicates resizing requirments";
    }
    leaf service-info {
      type string;
      description
        "Describe type of services running on the slice. It may be
         useful information to help the slice controller to
         optimize resource allocation";
    }
  }

  grouping ns-topo-steering-constraints {
    description
      "Policy grouping for specifying steering constraints for
       Transport Network Slices.";

    leaf disjointness {
      type te-types:te-path-disjointness;
      description
        "Indicate the level of disjointness for slice
         resources.";
    }
  }

  /*
   * Augmented data nodes
   */
  /* network type augments */
  augment "/nw:networks/nw:network/nw:network-types" {
    description
      "Defines the Network Slice topology type.";
    container network-slice {
      presence "Indicates Network Slice topology";
      description
        "Its presence identifies the Network Slice type.";
    }
  }

  /* network topology augments */
  augment "/nw:networks/nw:network" {
    when "./nw:network-types/ns-topo:network-slice" {
      description "Augment only for Network Slice topology.";
    }
    description "Augment topology configuration and state.";
    uses ietf-nss:service-slo-sle-policy;
  }

  augment "/nw:networks/nw:network" +
          "/ns-topo:slo-sle-policy" +
          "/ns-topo:custom" +
          "/ns-topo:service-slo-sle-policy" {
    when "../nw:network-types/ns-topo:network-slice" {
      description "Augment only for Network Slice topology.";
    }
    description "Augment topology configuration and state.";
    uses ns-topo-slo-sle-policy;
  }

  augment "/nw:networks/nw:network" +
          "/ns-topo:slo-sle-policy" +
          "/ns-topo:custom" +
          "/ns-topo:service-slo-sle-policy" +
    "/ns-topo:steering-constraints" {
    when "../../nw:network-types/ns-topo:network-slice" {
      description "Augment only for Network Slice topology.";
    }
    description "Augment topology configuration and state.";
    uses ns-topo-steering-constraints;
  }

  /* network node augments */
  augment "/nw:networks/nw:network/nw:node" {
    when "../nw:network-types/ns-topo:network-slice" {
      description "Augment only for Network Slice topology.";
    }
    description "Augment node configuration and state.";
    uses ietf-nss:service-slo-sle-policy;
  }

  augment "/nw:networks/nw:network/nw:node" +
          "/ns-topo:slo-sle-policy" +
          "/ns-topo:custom" +
          "/ns-topo:service-slo-sle-policy" {
    when "../../nw:network-types/ns-topo:network-slice" {
      description "Augment only for Network Slice topology.";
    }
    description "Augment node configuration and state.";
    uses ns-topo-slo-sle-policy;
  }

  augment "/nw:networks/nw:network/nw:node" +
          "/ns-topo:slo-sle-policy" +
          "/ns-topo:custom" +
          "/ns-topo:service-slo-sle-policy" +
    "/ns-topo:steering-constraints" {
    when "../../../nw:network-types/ns-topo:network-slice" {
      description "Augment only for Network Slice topology.";
    }
    description
    "Augment IETF network slice services to include steering
       constraints for nodes.";
    uses ns-topo-steering-constraints;
  }

  /* network node's termination point augments */
  augment "/nw:networks/nw:network/nw:node" +
          "/nt:termination-point" {
    when "../../nw:network-types/ns-topo:network-slice" {
      description "Augment only for Network Slice topology.";
    }
    description "Augment node configuration and state.";

  uses ietf-nss:service-slo-sle-policy;
  }

  augment "/nw:networks/nw:network/nw:node" +
          "/nt:termination-point" +
          "/ns-topo:slo-sle-policy" +
          "/ns-topo:custom" +
          "/ns-topo:service-slo-sle-policy" {
    when "../../../nw:network-types/ns-topo:network-slice" {
      description "Augment only for Network Slice topology.";
    }
    description "Augment node configuration and state.";

    uses ns-topo-slo-sle-policy;
  }

  /* network link augments */
  augment "/nw:networks/nw:network/nt:link" {
    when "../nw:network-types/ns-topo:network-slice" {
      description "Augment only for Network Slice topology.";
    }
    description "Augment link configuration and state.";
    uses ietf-nss:service-slo-sle-policy;
  }

  augment "/nw:networks/nw:network/nt:link" +
          "/ns-topo:slo-sle-policy" +
          "/ns-topo:custom" +
          "/ns-topo:service-slo-sle-policy" {
    when "../../nw:network-types/ns-topo:network-slice" {
      description "Augment only for Network Slice topology.";
    }
    description "Augment link configuration and state.";
    uses ns-topo-slo-sle-policy;
  }

  augment "/nw:networks/nw:network/nt:link" +
          "/ns-topo:slo-sle-policy" +
          "/ns-topo:custom" +
          "/ns-topo:service-slo-sle-policy" +
          "/ns-topo:steering-constraints" {
    when "../../../nw:network-types/ns-topo:network-slice" {
      description "Augment only for Network Slice topology.";
    }
    description
    "Augment IETF network slice services to include steering
       constraints for links within a resource-based transport
       network slice.";
    uses ns-topo-steering-constraints;
  }
}
