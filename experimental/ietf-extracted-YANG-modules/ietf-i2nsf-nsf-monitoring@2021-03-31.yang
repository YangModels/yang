module ietf-i2nsf-nsf-monitoring {
  yang-version 1.1;
  namespace
    "urn:ietf:params:xml:ns:yang:ietf-i2nsf-nsf-monitoring";
  prefix
    nsfmi;
  import ietf-inet-types{
    prefix inet;
    reference
      "Section 4 of RFC 6991";
  }
  import ietf-yang-types {
    prefix yang;
    reference
      "Section 3 of RFC 6991";
  }
  import ietf-i2nsf-policy-rule-for-nsf {
    prefix nsfi;
  }
  organization
    "IETF I2NSF (Interface to Network Security Functions)
     Working Group";
  contact
    "WG Web: <http://tools.ietf.org/wg/i2nsf>
     WG List: <mailto:i2nsf@ietf.org>

     Editor: Jaehoon Paul Jeong
     <mailto:pauljeong@skku.edu>

     Editor: Patrick Lingga
     <mailto:patricklink@skku.edu>";

  description
    "This module is a YANG module for I2NSF NSF Monitoring.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision "2021-03-31" {
    description "Initial revision";
    reference
      "RFC XXXX: I2NSF NSF Monitoring YANG Data Model";

    // RFC Ed.: replace XXXX with an actual RFC number and remove
    // this note.
  }

  /*
   * Typedefs
   */

  typedef severity {
    type enumeration {
      enum critical {
        description
          "The 'critical' severity level indicates that
           an immediate corrective action is required.
           A 'critical' severity is reported when a service
           becomes totally out of service and must be restored.";
      }
      enum high {
        description
          "The 'high' severity level indicates that
           an urgent corrective action is required.
           A 'high' severity is reported when there is
           a severe degradation in the capability of the
           service and its full capability must be restored.";
      }
      enum middle {
        description
          "The 'middle' severity level indicates the
           existence of a non-service-affecting fault
           condition and corrective action should be done
           to prevent a more serious fault. The 'middle'
           severity is reported when the detected problem
           is not degrading the capability of the service but
           might happen if not prevented.";
      }
      enum low {
        description
          "The 'low' severity level indicates the detection
           of a potential fault before any effect is felt.
           The 'low' severity is reported when an action should
           be done before a fault happen.";
      }
    }
    description
      "An indicator representing severity level. The severity level
       starting from the highest are critical, high, middle, and
       low.";
    reference
      "RFC 8632: A YANG Data Model for Alarm Management -
       The severity levels are defined.";
  }

  typedef log-action {
    type enumeration {
      enum allow {
        description
          "If action is allowed";
      }
      enum alert {
        description
          "If action is alert";
      }
      enum block {
        description
          "If action is block";
      }
      enum discard {
        description
          "If action is discarded";
      }
      enum declare {
        description
          "If action is declared";
      }
      enum block-ip {
        description
          "If action is block-ip";
      }
      enum block-service{
        description
          "If action is block-service";
      }
    }
    description
      "The type representing action for logging.";
  }

  typedef dpi-type{
    type enumeration {
      enum file-blocking{
        description
          "DPI for blocking file";
      }
      enum data-filtering{
        description
          "DPI for filtering data";
      }
      enum application-behavior-control{
        description
          "DPI for controlling application behavior";
      }
    }
    description
      "The type of deep packet inspection.";
  }

  typedef operation-type{
    type enumeration {
      enum login{
        description
          "Login operation";
      }
      enum logout{
        description
          "Logout operation";
      }
      enum configuration{
        description
          "Configuration operation";
      }
    }
    description
      "The type of operation done by a user
       during a session.";
  }

  typedef login-mode{
    type enumeration {
      enum root{
        description
          "Root login-mode";
      }
      enum user{
        description
          "User login-mode";
      }
      enum guest{
        description
          "Guest login-mode";
      }
    }
    description
      "The authorization login-mode done by a user.";
  }

  /*
   * Identity
   */

  identity characteristics {
    description
      "Base identity for monitoring information
       characteristics";
  }
  identity acquisition-method {
    base characteristics;
    description
      "The type of acquisition-method. It can be multiple
       types at once.";
  }
  identity subscription {
    base acquisition-method;
    description
      "The acquisition-method type is subscription.";
  }
  identity query {
    base acquisition-method;
    description
      "The acquisition-method type is query.";
  }
  identity emission-type {
    base characteristics;
    description
      "The type of emission-type.";
  }
  identity periodical {
    base emission-type;
    description
      "The emission-type type is periodical.";
  }
  identity on-change {
    base emission-type;
    description
      "The emission-type type is on-change.";
  }
  identity dampening-type {
    base characteristics;
    description
      "The type of dampening-type.";
  }
  identity no-dampening {
    base dampening-type;
    description
      "The dampening-type is no-dampening.";
  }
  identity on-repetition {
    base dampening-type;
    description
      "The dampening-type is on-repetition.";
  }
  identity none {
    base dampening-type;
    description
      "The dampening-type is none.";
  }
  identity authentication-mode {
    description
      "User authentication mode types:
       e.g., Local Authentication,
       Third-Party Server Authentication,
       Authentication Exemption, or Single Sign-On (SSO)
       Authentication.";
  }
  identity local-authentication {
    base authentication-mode;
    description
      "Authentication-mode : local authentication.";
  }
  identity third-party-server-authentication {
    base authentication-mode;
    description
      "If authentication-mode is
       third-party-server-authentication";
  }
  identity exemption-authentication {
    base authentication-mode;
    description
      "If authentication-mode is
       exemption-authentication";
  }
  identity sso-authentication {
    base authentication-mode;
    description
      "If authentication-mode is
       sso-authentication";
  }
  identity alarm-type {
    description
      "Base identity for detectable alarm types";
  }
  identity mem-usage-alarm {
    base alarm-type;
    description
      "A memory alarm is alerted.";
  }
  identity cpu-usage-alarm {
    base alarm-type;
    description
      "A CPU alarm is alerted.";
  }
  identity disk-usage-alarm {
    base alarm-type;
    description
      "A disk alarm is alerted.";
  }
  identity hw-failure-alarm {
    base alarm-type;
    description
      "A hardware alarm is alerted.";
  }
  identity ifnet-state-alarm {
    base alarm-type;
    description
      "An interface alarm is alerted.";
  }
  identity event-type {
    description
      "Base identity for detectable event types";
  }
  identity access-denied {
    base event-type;
    description
      "The system event is access-denied.";
  }
  identity config-change {
    base event-type;
    description
      "The system event is config-change.";
  }
  identity attack-type {
    description
      "The root ID of attack-based notification
       in the notification taxonomy";
  }
  identity system-attack-type {
    base attack-type;
    description
      "This ID is intended to be used
       in the context of system events.";
  }
  identity nsf-attack-type {
    base attack-type;
    description
      "This ID is intended to be used
       in the context of NSF event.";
  }
  identity botnet-attack-type {
    base nsf-attack-type;
    description
      "This indicates that this attack type is botnet.
       The usual semantic and taxonomy is missing
       and a name is used.";
  }
  identity virus-type {
    base nsf-attack-type;
    description
      "The type of virus. It caan be multiple types at once.
       This attack type is associated with a detected
       system-log virus-attack.";
  }
  identity trojan {
    base virus-type;
    description
      "The detected virus type is trojan.";
  }
  identity worm {
    base virus-type;
    description
      "The detected virus type is worm.";
  }
  identity macro {
    base virus-type;
    description
      "The detected virus type is macro.";
  }
  identity intrusion-attack-type {
    base nsf-attack-type;
    description
      "The attack type is associated with a detected
       system-log intrusion.";
  }
  identity brute-force {
    base intrusion-attack-type;
    description
      "The intrusion type is brute-force.";
  }
  identity buffer-overflow {
    base intrusion-attack-type;
    description
      "The intrusion type is buffer-overflow.";
  }
  identity web-attack-type {
    base nsf-attack-type;
    description
      "The attack type is associated with a detected
       system-log web-attack.";
  }
  identity command-injection {
    base web-attack-type;
    description
      "The detected web attack type is command injection.";
  }
  identity xss {
    base web-attack-type;
    description
      "The detected web attack type is XSS.";
  }
  identity csrf {
    base web-attack-type;
    description
      "The detected web attack type is CSRF.";
  }
  identity flood-type {
    base nsf-attack-type;
    description
      "Base identity for detectable flood types";
  }
  identity syn-flood {
    base flood-type;
    description
      "A SYN flood is detected.";
  }
  identity ack-flood {
    base flood-type;
    description
      "An ACK flood is detected.";
  }
  identity syn-ack-flood {
    base flood-type;
    description
      "A SYN-ACK flood is detected.";
  }
  identity fin-rst-flood {
    base flood-type;
    description
      "A FIN-RST flood is detected.";
  }
  identity tcp-con-flood {
    base flood-type;
    description
      "A TCP connection flood is detected.";
  }
  identity udp-flood {
    base flood-type;
    description
      "A UDP flood is detected.";
  }
  identity icmp-flood {
    base flood-type;
    description
      "Either an ICMPv4 or ICMPv6 flood is detected.";
  }
  identity icmpv4-flood {
    base flood-type;
    description
      "An ICMPv4 flood is detected.";
  }
  identity icmpv6-flood {
    base flood-type;
    description
      "An ICMPv6 flood is detected.";
  }
  identity http-flood {
    base flood-type;
    description
      "An HTTP flood is detected.";
  }
  identity https-flood {
    base flood-type;
    description
      "An HTTPS flood is detected.";
  }
  identity dns-query-flood {
    base flood-type;
    description
      "A DNS query flood is detected.";
  }
  identity dns-reply-flood {
    base flood-type;
    description
     "A DNS reply flood is detected.";
  }
  identity sip-flood {
    base flood-type;
    description
      "An SIP flood is detected.";
  }

  identity req-method {
    description
      "A set of request types (if applicable).
       For instance, PUT or GET in HTTP.";
  }
  identity put-req {
    base req-method;
    description
      "The detected request type is PUT.";
  }
  identity get-req {
    base req-method;
    description
      "The detected request type is GET.";
  }
  identity filter-type {
    description
      "The type of filter used to detect an attack,
       for example, a web-attack.  It can be applicable to
       more than web-attacks.  It can be more than one type.";
  }
  identity whitelist {
    base filter-type;
    description
      "The applied filter type is whitelist.";
  }
  identity blacklist {
    base filter-type;
    description
      "The applied filter type is blacklist.";
  }
  identity user-defined {
   base filter-type;
    description
      "The applied filter type is user-defined.";
  }
  identity malicious-category {
    base filter-type;
    description
      "The applied filter is malicious category.";
  }
  identity unknown-filter {
    base filter-type;
    description
      "The applied filter is unknown.";
  }

  identity access-mode {
    description
      "Base identity for detectable access mode.";
  }
  identity ppp {
    base access-mode;
    description
      "Access-mode: ppp";
  }
  identity svn {
    base access-mode;
    description
      "Access-mode: svn";
  }
  identity local {
    base access-mode;
    description
      "Access-mode: local";
  }

  identity protocol-type {
    description
      "An identity used to enable type choices in leaves
       and leaflists with respect to protocol metadata.";
  }
  identity tcp {
    base ipv4;
    base ipv6;
    description
      "TCP protocol type.";
    reference
      "RFC 793: Transmission Control Protocol";
  }
  identity udp {
    base ipv4;
    base ipv6;
    description
      "UDP protocol type.";
    reference
      "RFC 768: User Datagram Protocol";
  }
  identity icmp {
    base ipv4;
    base ipv6;
    description
      "General ICMP protocol type.";
    reference
      "RFC 792: Internet Control Message Protocol
       RFC 4443: Internet Control Message Protocol
       (ICMPv6) for the Internet Protocol Version 6
       (IPv6) Specification";
  }
  identity icmpv4 {
    base ipv4;
    description
      "ICMPv4 protocol type.";
    reference
      "RFC 791: Internet Protocol
       RFC 792: Internet Control Message Protocol";
  }
  identity icmpv6 {
    base ipv6;
    description
      "ICMPv6 protocol type.";
    reference
      "RFC 8200: Internet Protocol, Version 6 (IPv6)
       RFC 4443: Internet Control Message Protocol (ICMPv6)
       for the Internet Protocol Version 6 (IPv6)
       Specification";
  }
  identity ip {
    base protocol-type;
    description
      "General IP protocol type.";
    reference
      "RFC 791: Internet Protocol
       RFC 8200: Internet Protocol, Version 6 (IPv6)";
  }
  identity ipv4 {
    base ip;
    description
      "IPv4 protocol type.";
    reference
      "RFC 791: Internet Protocol";
  }
  identity ipv6 {
    base ip;
    description
      "IPv6 protocol type.";
    reference
      "RFC 8200: Internet Protocol, Version 6 (IPv6)";
  }
  identity http {
    base tcp;
    description
      "HTPP protocol type.";
    reference
      "RFC 2616: Hypertext Transfer Protocol";
  }
  identity ftp {
    base tcp;
    description
      "FTP protocol type.";
    reference
      "RFC 959: File Transfer Protocol";
  }

  /*
   * Grouping
   */

  grouping common-monitoring-data {
    description
      "A set of common monitoring data that is needed
      as the basic information.";
    leaf message {
      type string;
      description
        "This is a freetext annotation for
         monitoring a notification's content.";
    }
    leaf vendor-name {
      type string;
      description
        "The name of the NSF vendor";
    }
    leaf nsf-name {
      type string;
      description
        "The name (or IP) of the NSF generating the message.";
    }
    leaf severity {
      type severity;
      description
        "The severity of the alarm such as critical, high,
         middle, low.";
    }
  }
  grouping characteristics {
    description
      "A set of characteristics of a notification.";
    leaf acquisition-method {
      type identityref {
        base acquisition-method;
      }
      description
        "The acquisition-method for characteristics";
    }
    leaf emission-type {
      type identityref {
        base emission-type;
      }
     description
        "The emission-type for characteristics";
    }
    leaf dampening-type {
      type identityref {
        base dampening-type;
      }
      description
        "The dampening-type for characteristics";
    }
  }
  grouping i2nsf-system-alarm-type-content {
    description
      "A set of contents for alarm type notification.";
    leaf usage {
      type uint8 {
        range "0..100";
      }
      units "percent";
      description
        "Specifies the used percentage";
    }
    leaf threshold {
      type uint8 {
        range "0..100";
      }
      units "percent";
      description
        "The threshold percentage triggering the alarm or
         the event";
    }
  }
  grouping i2nsf-system-event-type-content {
    description
      "System event metadata associated with system events
       caused by user activity.";
    leaf user {
      type string;
      mandatory true;
      description
        "The name of a user";
    }
    leaf group {
      type string;
      mandatory true;
      description
        "The group to which a user belongs.";
    }
    leaf login-ip-addr {
      type inet:ip-address;
      mandatory true;
      description
        "The login IPv4 (or IPv6) address of a user.";
    }
    leaf authentication {
      type identityref {
        base authentication-mode;
      }
      description
        "The authentication-mode for authentication";
    }
  }
  grouping i2nsf-nsf-event-type-content {
    description
      "A set of common IPv4 (or IPv6)-related NSF event
       content elements";
    leaf dst-ip {
      type inet:ip-address;
      description
        "The destination IPv4 (IPv6) address of the packet";
    }
    leaf dst-port {
      type inet:port-number;
      description
        "The destination port of the packet";
    }
    leaf rule-name {
      type leafref {
        path
          "/nsfi:i2nsf-security-policy/nsfi:system-policy/nsfi:rules/nsfi:rule-name";
      }
      mandatory true;
      description
        "The name of the rule being triggered";
    }
    leaf raw-info {
      type string;
      description
        "The information describing the packet
         triggering the event.";
    }
  }
  grouping i2nsf-nsf-event-type-content-extend {
    description
      "A set of extended common IPv4 (or IPv6)-related NSF
       event content elements";
    uses i2nsf-nsf-event-type-content;
    leaf src-ip {
      type inet:ip-address;
      description
        "The source IPv4 (or IPv6) address of the packet";
    }
    leaf src-port {
      type inet:port-number;
      description
        "The source port of the packet";
    }
    leaf src-zone {
      type string {
        length "1..100";
        pattern "[0-9a-zA-Z ]*";
      }
      description
        "The source security zone of the packet";
    }
    leaf dst-zone {
      type string {
        length "1..100";
        pattern "[0-9a-zA-Z ]*";
      }
      description
        "The destination security zone of the packet";
    }
  }
  grouping log-action {
    description
      "A grouping for logging action.";
    leaf action {
      type log-action;
      description
        "Action type: allow, alert, block, discard, declare,
         block-ip, block-service";
    }
  }
  grouping attack-rates {
    description
      "A set of traffic rates for monitoring attack traffic
       data";
    leaf attack-rate {
      type uint32;
      units "pps";
      description
        "The PPS rate of attack traffic";
    }
    leaf attack-speed {
      type uint32;
      units "bps";
      description
        "The BPS speed of attack traffic";
    }
  }
  grouping traffic-rates {
    description
      "A set of traffic rates for statistics data";
    leaf total-traffic {
      type yang:counter32;
      description
        "Total traffic";
    }
    leaf in-traffic-average-rate {
      type uint32;
      units "pps";
      description
        "Inbound traffic average rate in packets per second (pps)";
    }
    leaf in-traffic-peak-rate {
      type uint32;
      units "pps";
      description
        "Inbound traffic peak rate in packets per second (pps)";
    }
    leaf in-traffic-average-speed {
      type uint32;
      units "bps";
      description
        "Inbound traffic average speed in bits per second (bps)";
    }
    leaf in-traffic-peak-speed {
      type uint32;
      units "bps";
      description
        "Inbound traffic peak speed in bits per second (bps)";
    }
    leaf out-traffic-average-rate {
      type uint32;
      units "pps";
      description
        "Outbound traffic average rate in packets per second (pps)";
    }
    leaf out-traffic-peak-rate {
      type uint32;
      units "pps";
      description
       "Outbound traffic peak rate in packets per Second (pps)";
    }
    leaf out-traffic-average-speed {
      type uint32;
      units "bps";
      description
        "Outbound traffic average speed in bits per second (bps)";
    }
    leaf out-traffic-peak-speed {
      type uint32;
      units "bps";
      description
        "Outbound traffic peak speed in bits per second (bps)";
    }
  }
  grouping i2nsf-system-counter-type-content{
    description
      "A set of counters for an interface traffic data.";
    leaf interface-name {
      type string;
      description
        "Network interface name configured in an NSF";
    }
    leaf in-total-traffic-pkts {
      type yang:counter32;
      description
        "Total inbound packets";
    }
    leaf out-total-traffic-pkts {
      type yang:counter32;
      description
        "Total outbound packets";
    }
    leaf in-total-traffic-bytes {
      type uint64;
      units "bytes";
      description
        "Total inbound bytes";
    }
    leaf out-total-traffic-bytes {
      type uint64;
      units "bytes";
      description
        "Total outbound bytes";
    }
    leaf in-drop-traffic-pkts {
      type yang:counter32;
      description
        "Total inbound drop packets";
    }
    leaf out-drop-traffic-pkts {
      type yang:counter32;
      description
        "Total outbound drop packets";
    }
    leaf in-drop-traffic-bytes {
      type uint64;
      units "bytes";
      description
        "Total inbound drop bytes";
    }
    leaf out-drop-traffic-bytes {
      type uint64;
      units "bytes";
      description
        "Total outbound drop bytes";
    }
    uses traffic-rates;
  }
  grouping i2nsf-nsf-counters-type-content{
    description
      "A set of contents of a policy in an NSF.";
    leaf policy-name {
      type leafref {
        path
          "/nsfi:i2nsf-security-policy/nsfi:system-policy/nsfi:system-policy-name";
      }
      mandatory true;
      description
        "The name of the policy being triggered";
    }
    leaf src-user{
      type string;
      description
        "User who generates the policy";
    }
  }

  grouping enable-notification {
    description
      "A grouping for enabling or disabling notification";
    leaf enabled {
      type boolean;
      default "true";
      description
        "Enables or Disables the notification.
         If 'true', then the notification is enabled.
         If 'false, then the notification is disabled.";
    }
  }

  grouping dampening {
    description
      "A grouping for dampening period of notification.";
    leaf dampening-period {
      type uint32;
      units "centiseconds";
      default "0";
      description
        "Specifies the minimum interval between the assembly of
         successive update records for a single receiver of a
         subscription.  Whenever subscribed objects change and
         a dampening-period interval (which may be zero) has
         elapsed since the previous update record creation for
         a receiver, any subscribed objects and properties
         that have changed since the previous update record
         will have their current values marshalled and placed
         in a new update record.";
      reference
        "RFC 8641:  Subscription to YANG Notifications for
         Datastore Updates - Section 5.";
    }
  }

  /*
   * Feature Nodes
   */

  feature i2nsf-nsf-detection-ddos {
    description
      "This feature means it supports I2NSF nsf-detection-ddos
       notification";
  }
  feature i2nsf-nsf-detection-virus {
    description
      "This feature means it supports I2NSF nsf-detection-virus
       notification";
  }
  feature i2nsf-nsf-detection-intrusion {
    description
      "This feature means it supports I2NSF nsf-detection-intrusion
       notification";
  }
  feature i2nsf-nsf-detection-botnet {
    description
      "This feature means it supports I2NSF nsf-detection-botnet
       notification";
  }
  feature i2nsf-nsf-detection-web-attack {
    description
      "This feature means it supports I2NSF nsf-detection-web-attack
       notification";
  }
  feature i2nsf-nsf-log-dpi {
    description
      "This feature means it supports I2NSF nsf-log-dpi
       notification";
  }
  feature i2nsf-nsf-log-vuln-scan {
    description
      "This feature means it supports I2NSF nsf-log-vuln-scan
       notification";
  }

  /*
   * Notification nodes
   */

  notification i2nsf-event {
    description
      "Notification for I2NSF Event.";
    choice sub-event-type {
      description
        "This choice must be augmented with cases for each allowed
         sub-event. Only 1 sub-event will be instantiated in each
         i2nsf-event message. Each case is expected to define one
         container with all the sub-event fields.";
      case i2nsf-system-detection-alarm {
        container i2nsf-system-detection-alarm{
          description
            "This notification is sent, when a system alarm
             is detected.";
          leaf alarm-category {
            type identityref {
             base alarm-type;
            }
            description
              "The alarm category for
               system-detection-alarm notification";
          }
          leaf component-name {
            type string;
            description
              "The hardware component responsible for generating
               the message. Applicable for Hardware Failure
               Alarm.";
          }
          leaf interface-name {
            type string;
            description
              "The interface name responsible for generating
               the message. Applicable for Network Interface
               Failure Alarm.";
          }
          leaf interface-state {
            type enumeration {
              enum down {
                description
                  "The interface state is down.";
              }
              enum up {
                description
                  "The interface state is up.";
              }
              enum congested {
                description
                  "The interface state is congested.";
              }
            }
            description
              "The state of the interface (i.e., up, down, congested).
              Applicable for Network Interface Failure Alarm.";
          }
          uses characteristics;
          uses i2nsf-system-alarm-type-content;
          uses common-monitoring-data;
        }
      }

      case i2nsf-system-detection-event {
        container i2nsf-system-detection-event {
          description
            "This notification is sent when a security-sensitive
             authentication action fails.";
          leaf event-category {
           type identityref {
              base event-type;
            }
            description
              "The event category for system-detection-event";
          }
          uses characteristics;
          uses i2nsf-system-event-type-content;
          uses common-monitoring-data;
        }
      }

      case i2nsf-traffic-flows {
        container i2nsf-traffic-flows {
          description
            "This notification is sent to inform about the traffic
             flows.";
          leaf src-ip {
            type inet:ip-address;
            description
              "The source IPv4 (or IPv6) address of the packet";
          }
          leaf dst-ip {
            type inet:ip-address;
            description
              "The destination IPv4 (or IPv6) address of the packet";
          }
          leaf protocol {
            type identityref {
              base protocol-type;
            }
            description
              "The protocol type for nsf-detection-intrusion
               notification";
          }
          leaf src-port {
            type inet:port-number;
            description
              "The source port of the packet";
          }
          leaf dst-port {
            type inet:port-number;
            description
              "The destination port of the packet";
          }
          leaf arrival-rate {
            type uint32;
            units "pps";
            description
              "The arrival rate of the packet in packets
              per second";
          }
          uses characteristics;
          uses common-monitoring-data;
        }
      }

      case i2nsf-nsf-detection-session-table {
        container i2nsf-nsf-detection-session-table {
          description
            "This notification is sent, when a session table
             event is detected.";
          leaf current-session {
            type uint32;
            description
              "The number of concurrent sessions";
          }
          leaf maximum-session {
            type uint32;
            description
              "The maximum number of sessions that the session
               table can support";
          }
          leaf threshold {
            type uint32;
            description
              "The threshold triggering the event";
          }
          uses common-monitoring-data;
        }
      }
    }
  }

  notification i2nsf-log {
    description
      "Notification for I2NSF log. The notification is generated
       from the logs of the NSF.";
    choice sub-logs-type {
      description
        "This choice must be augmented with cases for each allowed
         sub-logs. Only 1 sub-event will be instantiated in each
         i2nsf-logs message. Each case is expected to define one
         container with all the sub-logs fields.";
      case i2nsf-nsf-system-access-log {
        container i2nsf-nsf-system-access-log {
          description
            "The notification is sent, if there is a new system
             log entry about a system access event.";
          leaf login-ip {
            type inet:ip-address;
            mandatory true;
            description
              "Login IP address of a user";
          }
          leaf administrator {
            type string;
            description
              "Administrator that maintains the device";
          }
          leaf login-mode {
            type login-mode;
            description
              "Specifies the administrator log-in mode";
          }
          leaf operation-type {
            type operation-type;
            description
              "The operation type that the administrator executes";
          }
          leaf result {
            type string;
            description
              "Command execution result";
          }
          leaf content {
            type string;
            description
              "The Operation performed by an administrator after
               login";
          }
          uses characteristics;
          uses common-monitoring-data;
        }
      }

      case i2nsf-system-res-util-log {
        container i2nsf-system-res-util-log {
          description
            "This notification is sent, if there is a new log
             entry representing resource utilization updates.";
          leaf system-status {
             type string;
             description
              "The current systems running status";
          }
          leaf cpu-usage {
            type uint8;
            description
              "Specifies the relative size of CPU usage with
               respect to platform resources";
          }
          leaf memory-usage {
            type uint8;
            description
              "Specifies the size of memory usage.";
          }
          leaf disk-usage {
            type uint8;
            description
              "Specifies the size of disk usage";
          }
          leaf disk-left {
            type uint8;
            description
              "Specifies the size of disk left";
          }
          leaf session-num {
            type uint8;
            description
              "The total number of sessions";
          }
          leaf process-num {
            type uint8;
            description
              "The total number of process";
          }
          leaf in-traffic-rate {
            type uint32;
            units "pps";
            description
              "The total inbound traffic rate in pps";
          }
          leaf out-traffic-rate {
            type uint32;
            units "pps";
            description
               "The total outbound traffic rate in pps";
          }
          leaf in-traffic-speed {
            type uint32;
            units "bps";
            description
              "The total inbound traffic speed in bps";
          }
          leaf out-traffic-speed {
            type uint32;
            units "bps";
            description
              "The total outbound traffic speed in bps";
          }
          uses characteristics;
          uses common-monitoring-data;
        }
      }

      case i2nsf-system-user-activity-log {
        container i2nsf-system-user-activity-log {
          description
            "This notification is sent, if there is a new user
             activity log entry.";
          uses characteristics;
          uses i2nsf-system-event-type-content;
          uses common-monitoring-data;
          leaf access {
            type identityref {
              base access-mode;
            }
            description
              "The access type for system-user-activity-log
               notification";
          }
          leaf online-duration {
            type string;
            description
              "Online duration";
          }
          leaf logout-duration {
            type string;
            description
              "Lockout duration";
          }
          leaf additional-info {
            type string;
            description
              "User activities, e.g., Successful User Login,
               Failed Login attempts, User Logout, Successful User
               Password Change, Failed User Password Change, User
               Lockout, User Unlocking, and Unknown.";
          }
        }
      }
    }
  }

  notification i2nsf-nsf-event {
    description
      "Notification for I2NSF NSF Event. This notification is
       used for a specific NSF that supported such feature.";
    choice sub-event-type {
      description
      "This choice must be augmented with cases for each allowed
       sub-event. Only 1 sub-event will be instantiated in each
       i2nsf-event message. Each case is expected to define one
       container with all the sub-event fields.";
      case i2nsf-nsf-detection-ddos {
        if-feature "i2nsf-nsf-detection-ddos";
        container i2nsf-nsf-detection-ddos {
          description
            "This notification is sent, when a specific flood type
             is detected.";
          uses i2nsf-nsf-event-type-content;
          leaf attack-type {
            type identityref {
              base flood-type;
            }
            description
              "Any one of Syn flood, ACK flood, SYN-ACK flood,
               FIN/RST flood, TCP Connection flood, UDP flood,
               ICMP (i.e., ICMPv4 or ICMPv6) flood, HTTP flood,
               HTTPS flood, DNS query flood, DNS reply flood, SIP
               flood, etc.";
          }
          leaf start-time {
            type yang:date-and-time;
            mandatory true;
            description
              "The time stamp indicating when the attack started";
          }
          leaf end-time {
            type yang:date-and-time;
            mandatory true;
            description
              "The time stamp indicating when the attack ended";
          }
          leaf attack-src-ip {
            type inet:ip-address;
            description
              "The source IPv4 (or IPv6) addresses of attack
               traffic. If there are a large number of IPv4
               (or IPv6) addresses, then pick a certain number
               of resources according to different rules.";
          }
          leaf attack-dst-ip {
            type inet:ip-address;
            description
              "The destination IPv4 (or IPv6) addresses of attack
               traffic. If there are a large number of IPv4
               (or IPv6) addresses, then pick a certain number
               of resources according to different rules.";
          }
          uses attack-rates;
          uses log-action;
          uses characteristics;
          uses common-monitoring-data;
        }
      }
      case i2nsf-nsf-detection-virus {
        if-feature "i2nsf-nsf-detection-virus";
        container i2nsf-nsf-detection-virus {
          description
            "This notification is sent, when a virus is detected.";
          uses i2nsf-nsf-event-type-content-extend;
          leaf virus {
            type identityref {
              base virus-type;
            }
           description
              "The virus type for nsf-detection-virus notification";
          }
          leaf virus-name {
            type string;
            description
              "The name of the detected virus";
          }
          leaf file-type {
            type string;
            description
              "The type of file virus code is found in (if
               applicable).";
          }
          leaf file-name {
            type string;
            description
              "The name of file virus code is found in (if
               applicable).";
          }
          leaf os {
            type string;
            description
              "Simple OS information";
          }
          uses log-action;
          uses characteristics;
          uses common-monitoring-data;
        }
      }
      case i2nsf-nsf-detection-intrusion {
        if-feature "i2nsf-nsf-detection-intrusion";
        container i2nsf-nsf-detection-intrusion {
          description
            "This notification is sent, when an intrusion event
             is detected.";
          uses i2nsf-nsf-event-type-content-extend;
          leaf protocol {
            type identityref {
              base protocol-type;
            }
            description
              "The protocol type for nsf-detection-intrusion
               notification";
          }
          leaf app {
            type string;
            description
              "The employed application layer protocol";
          }
          leaf attack-type {
            type identityref {
              base intrusion-attack-type;
            }
            description
              "The sub attack type for intrusion attack";
          }
          uses log-action;
          uses attack-rates;
          uses characteristics;
          uses common-monitoring-data;
        }
      }
      case i2nsf-nsf-detection-botnet {
        if-feature "i2nsf-nsf-detection-botnet";
        container i2nsf-nsf-detection-botnet {
          description
            "This notification is sent, when a botnet event is
             detected.";
          uses i2nsf-nsf-event-type-content-extend;
          leaf attack-type {
            type identityref {
              base botnet-attack-type;
            }
           description
              "The attack type for botnet attack";
          }
          leaf protocol {
            type identityref {
              base protocol-type;
            }
            description
              "The protocol type for nsf-detection-botnet notification";
          }
          leaf botnet-name {
            type string;
            description
              "The name of the detected botnet";
          }
          leaf role {
            type string;
            description
              "The role of the communicating
               parties within the botnet";
          }
          uses log-action;
          leaf botnet-pkt-num{
            type uint8;
            description
              "The number of the packets sent to or from the detected botnet";
          }
          leaf os{
            type string;
            description
              "Simple OS information";
          }
          uses characteristics;
          uses common-monitoring-data;
        }
      }
      case i2nsf-nsf-detection-web-attack {
        if-feature "i2nsf-nsf-detection-web-attack";
        container i2nsf-nsf-detection-web-attack {
          description
            "This notification is sent, when an attack event is
             detected.";
          uses i2nsf-nsf-event-type-content-extend;
          leaf attack-type {
            type identityref {
              base web-attack-type;
            }
            description
              "Concrete web attack type, e.g., SQL injection,
               command injection, XSS, and CSRF.";
          }
          leaf request-method {
            type identityref {
              base req-method;
            }
            description
              "The method of requirement. For instance, PUT or
               GET in HTTP.";
          }
          leaf req-uri {
            type string;
            description
              "Requested URI";
          }
          leaf uri-category {
            type string;
            description
              "Matched URI category";
          }
          leaf-list filtering-type {
            type identityref {
              base filter-type;
            }
            description
              "URL filtering type, e.g., Blacklist, Whitelist,
               User-Defined, Predefined, Malicious Category,
               and Unknown";
          }
          leaf rsp-code {
            type string;
            description
              "Response code";
          }
          leaf req-clientapp {
            type string;
            description
              "The client application";
          }
          leaf req-cookies {
            type string;
            description
              "Cookies";
          }
          leaf req-host {
            type string;
            description
              "The domain name of the requested host";
          }
          uses characteristics;
          uses log-action;
          uses common-monitoring-data;
        }
      }
      case i2nsf-nsf-log-vuln-scan {
        if-feature "i2nsf-nsf-log-vuln-scan";
        container i2nsf-nsf-log-vuln-scan {
          description
            "This notification is sent, if there is a new
             vulnerability-scan report in the NSF log.";
          leaf vulnerability-id {
            type uint8;
            description
              "The vulnerability ID";
          }
          leaf victim-ip {
            type inet:ip-address;
            description
              "IPv4 (or IPv6) address of the victim host which
               has vulnerabilities";
          }
          leaf protocol {
            type identityref {
              base protocol-type;
            }
            description
              "The protocol type for nsf-log-vuln-scan
               notification";
          }
          leaf port-num {
            type inet:port-number;
              description
                "The port number";
          }
          leaf level {
            type severity;
            description
              "The vulnerability severity";
          }
          leaf os {
            type string;
            description
              "simple OS information";
          }
          leaf vulnerability-info {
            type string;
            description
              "The information about the vulnerability";
          }
          leaf fix-suggestion {
            type string;
            description
              "The fix suggestion to the vulnerability";
          }
          leaf service {
            type string;
            description
              "The service which has vulnerability in the victim
               host";
          }
          uses characteristics;
          uses common-monitoring-data;
        }
      }
      case i2nsf-nsf-log-dpi {
        if-feature "i2nsf-nsf-log-dpi";
        container i2nsf-nsf-log-dpi {
          description
            "This notification is sent, if there is a new DPI
             event in the NSF log.";
          leaf attack-type {
            type dpi-type;
            description
              "The type of the DPI";
          }
          uses characteristics;
          uses i2nsf-nsf-counters-type-content;
          uses common-monitoring-data;
        }
      }
    }
  }
  /*
   * Data nodes
   */
  container i2nsf-counters {
    config false;
    description
      "This is probably better covered by an import as this
       will not be notifications.  Counters are not very
       suitable as telemetry, maybe via periodic
       subscriptions, which would still violate the principle
       of least surprise.";
    list system-interface {
      key interface-name;
      description
        "Interface counters provide the visibility of traffic into and
         out of an NSF, and bandwidth usage.";
      uses characteristics;
      uses i2nsf-system-counter-type-content;
      uses common-monitoring-data;
    }
    list nsf-firewall {
      key policy-name;
      description
        "Firewall counters provide the visibility of traffic signatures,
         bandwidth usage, and how the configured security and bandwidth
         policies have been applied.";
      uses characteristics;
      uses i2nsf-nsf-counters-type-content;
      uses traffic-rates;
      uses common-monitoring-data;
    }
    list nsf-policy-hits {
      key policy-name;
      description
        "Policy Hit Counters record the number of hits that traffic
         packets match a security policy. It can check if policy
         configurations are correct or not.";
      uses characteristics;
      uses i2nsf-nsf-counters-type-content;
      uses common-monitoring-data;
      leaf hit-times {
        type yang:counter32;
        description
          "The number of times a policy is hit";
      }
    }
  }

  container i2nsf-monitoring-configuration {
    description
      "The container for configuring I2NSF monitoring.";
    container i2nsf-system-detection-alarm {
      description
        "The container for configuring I2NSF system-detection-alarm
         notification";
      uses enable-notification;
      list system-alarm {
        key alarm-type;
        description
          "Configuration for system alarm (i.e., CPU, Memory,
           and Disk Usage)";
        leaf alarm-type {
          type enumeration {
            enum CPU {
              description
                "To configure the CPU usage threshold to trigger the
                 CPU-USAGE-ALARM";
            }
            enum Memory {
              description
                "To configure the Memory usage threshold to trigger the
                 MEM-USAGE-ALARM";
            }
            enum Disk {
              description
                "To configure the Disk (storage) usage threshold to
                 trigger the DISK-USAGE-ALARM";
            }
          }
          description
            "Type of alarm to be configured";
        }
        leaf threshold {
          type uint8 {
            range "1..100";
          }
          units "percent";
          description
            "The configuration for threshold percentage to trigger
             the alarm. The alarm will be triggered if the usage
             is exceeded the threshold.";
        }
        uses dampening;
      }
    }
    container i2nsf-system-detection-event {
      description
        "The container for configuring I2NSF system-detection-event
         notification";
      uses enable-notification;
      uses dampening;
    }
    container i2nsf-traffic-flows {
      description
        "The container for configuring I2NSF traffic-flows
         notification";
      uses dampening;
      uses enable-notification;
    }
    container i2nsf-nsf-detection-ddos {
      if-feature "i2nsf-nsf-detection-ddos";
      description
        "The container for configuring I2NSF nsf-detection-ddos
         notification";
      uses enable-notification;
      uses dampening;
    }
    container i2nsf-nsf-detection-session-table-configuration {
      description
        "The container for configuring I2NSF nsf-detection-session-table
         notification";
      uses enable-notification;
      uses dampening;
    }
    container i2nsf-nsf-detection-virus {
      if-feature "i2nsf-nsf-detection-virus";
      description
        "The container for configuring I2NSF nsf-detection-virus
         notification";
      uses enable-notification;
      uses dampening;
    }
    container i2nsf-nsf-detection-intrusion {
      if-feature "i2nsf-nsf-detection-intrusion";
      description
        "The container for configuring I2NSF nsf-detection-intrusion
         notification";
      uses enable-notification;
      uses dampening;
    }
    container i2nsf-nsf-detection-botnet {
      if-feature "i2nsf-nsf-detection-botnet";
      description
        "The container for configuring I2NSF nsf-detection-botnet
         notification";
      uses enable-notification;
      uses dampening;
    }
    container i2nsf-nsf-detection-web-attack {
      if-feature "i2nsf-nsf-detection-web-attack";
      description
        "The container for configuring I2NSF nsf-detection-web-attack
         notification";
      uses enable-notification;
      uses dampening;
    }
    container i2nsf-nsf-system-access-log {
      description
        "The container for configuring I2NSF system-access-log
         notification";
      uses enable-notification;
      uses dampening;
    }
    container i2nsf-system-res-util-log {
      description
        "The container for configuring I2NSF system-res-util-log
         notification";
      uses enable-notification;
      uses dampening;
    }
    container i2nsf-system-user-activity-log {
      description
        "The container for configuring I2NSF system-user-activity-log
         notification";
      uses enable-notification;
      uses dampening;
    }
    container i2nsf-nsf-log-dpi {
      if-feature "i2nsf-nsf-log-dpi";
      description
        "The container for configuring I2NSF nsf-log-dpi
         notification";
      uses enable-notification;
      uses dampening;
    }
    container i2nsf-nsf-log-vuln-scan {
      if-feature "i2nsf-nsf-log-vuln-scan";
      description
        "The container for configuring I2NSF nsf-log-vuln-scan
         notification";
      uses enable-notification;
      uses dampening;
    }
    container i2nsf-counter {
      description
        "This is used to configure the counters
         for monitoring an NSF";
      leaf period {
        type uint16;
        units "minutes";
        default 0;
        description
          "The configuration for the period interval of reporting
           the counter. If 0, then the counter period is disabled.
           If value is not 0, then the counter will be reported
           following the period value.";
      }
    }
  }
}
