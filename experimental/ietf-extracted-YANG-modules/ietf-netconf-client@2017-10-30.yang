module ietf-netconf-client {
  yang-version 1.1;

  namespace "urn:ietf:params:xml:ns:yang:ietf-netconf-client";
  prefix "ncc";

  import ietf-inet-types {
    prefix inet;
    reference
      "RFC 6991: Common YANG Data Types";
  }

  import ietf-ssh-client {
    prefix ss;
    revision-date 2017-10-30; // stable grouping definitions
    reference
      "RFC YYYY: YANG Groupings for SSH Clients and SSH Servers";
  }

  import ietf-tls-client {
    prefix ts;
    revision-date 2017-10-30; // stable grouping definitions
    reference
      "RFC ZZZZ: YANG Groupings for TLS Clients and TLS Servers";
  }

  organization
   "IETF NETCONF (Network Configuration) Working Group";

  contact
   "WG Web:   <http://tools.ietf.org/wg/netconf/>
    WG List:  <mailto:netconf@ietf.org>

    Author:   Kent Watsen
              <mailto:kwatsen@juniper.net>

    Author:   Gary Wu
              <mailto:garywu@cisco.com>";

  description
   "This module contains a collection of YANG definitions for
    configuring NETCONF clients.

    Copyright (c) 2017 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2017-10-30" {
    description
     "Initial version";
    reference
     "RFC XXXX: NETCONF Client and Server Models";
  }

  // Features

  feature initiate {
    description
     "The 'initiate' feature indicates that the NETCONF client
      supports initiating NETCONF connections to NETCONF servers
      using at least one transport (e.g., SSH, TLS, etc.).";
  }

  feature ssh-initiate {
    description
     "The 'ssh-initiate' feature indicates that the NETCONF client
      supports initiating SSH connections to NETCONF servers.";
    reference
     "RFC 6242: Using the NETCONF Protocol over Secure Shell (SSH)";
  }

  feature tls-initiate {
    description
     "The 'tls-initiate' feature indicates that the NETCONF client
      supports initiating TLS connections to NETCONF servers.";
    reference
     "RFC 7589: Using the NETCONF Protocol over Transport
                Layer Security (TLS) with Mutual X.509
                Authentication";
  }

  feature listen {
    description
     "The 'listen' feature indicates that the NETCONF client
      supports opening a port to accept NETCONF server call
      home connections using at least one transport (e.g.,
      SSH, TLS, etc.).";
  }

  feature ssh-listen {
    description
     "The 'ssh-listen' feature indicates that the NETCONF client
      supports opening a port to listen for incoming NETCONF
      server call-home SSH connections.";
    reference
     "RFC 8071: NETCONF Call Home and RESTCONF Call Home";
  }

  feature tls-listen {
    description
     "The 'tls-listen' feature indicates that the NETCONF client
      supports opening a port to listen for incoming NETCONF
      server call-home TLS connections.";
    reference
     "RFC 8071: NETCONF Call Home and RESTCONF Call Home";
  }

  container netconf-client {
    uses netconf-client;
    description
      "Top-level container for NETCONF client configuration.";
  }

  grouping netconf-client {
    description
      "Top-level grouping for NETCONF client configuration.";

    container initiate {
      if-feature initiate;
      description
        "Configures client initiating underlying TCP connections.";
      list netconf-server {
        key name;
        min-elements 1;
        description
          "List of NETCONF servers the NETCONF client is to initiate
           connections to in parallel.";
        leaf name {
          type string;
          description
            "An arbitrary name for the NETCONF server.";
        }
        container endpoints {
          description
            "Container for the list of endpoints.";
          list endpoint {
            key name;
            min-elements 1;
            ordered-by user;
            description
              "A user-ordered list of endpoints that the NETCONF
               client will attempt to connect to in the specified
               sequence.  Defining more than one enables
               high-availability.";
            leaf name {
              type string;
              description
                "An arbitrary name for the endpoint.";
            }
            choice transport {
              mandatory true;
              description
                "Selects between available transports.";
              case ssh {
                if-feature ssh-initiate;
                container ssh {
                  description
                    "Specifies IP and SSH specific configuration for
                     the connection.";
                  leaf address {
                    type inet:host;
                    description
                     "The IP address or hostname of the endpoint.
                      If a domain name is configured, then the DNS
                      resolution should happen on each usage attempt.
                      If the DNS resolution results in multiple IP
                      addresses, the IP addresses will be tried
                      according to local preference order until a
                      connection has been established or until all
                      IP addresses have failed.";
                  }
                  leaf port {
                    type inet:port-number;
                    default 830;
                    description
                      "The IP port for this endpoint.  The NETCONF
                       client will use the IANA-assigned well-known
                       port for 'netconf-ssh' (830) if no value is
                       specified.";
                  }
                  uses ss:ssh-client-grouping;
                }
              } // end ssh
              case tls {
                if-feature tls-initiate;
                container tls {
                  description
                    "Specifies IP and TLS specific configuration for
                     the connection.";
                  leaf address {
                    type inet:host;
                    description
                      "The IP address or hostname of the endpoint.
                       If a domain name is configured, then the DNS
                       resolution should happen on each usage attempt.
                       If the DNS resolution results in multiple IP
                       addresses, the IP addresses will be tried
                       according to local preference order until a
                       connection has been established or until all
                       IP addresses have failed.";
                    }
                    leaf port {
                      type inet:port-number;
                      default 6513;
                      description
                        "The IP port for this endpoint. The NETCONF
                         client will use the IANA-assigned well-known
                         port for 'netconf-tls' (6513) if no value is
                         specified.";
                    }
                    uses ts:tls-client-grouping {
                      refine "client-identity/auth-type" {
                      mandatory true;
                       description
                         "NETCONF/TLS clients MUST pass some
                          authentication credentials.";
                     }
                   }
                 }
               } // end tls
             }
          }
        }

        container connection-type {
          description
           "Indicates the kind of connection to use.";
          choice connection-type {
            description
              "Selects between available connection types.";
            case persistent-connection {
              container persistent {
                presence true;
                description
                 "Maintain a persistent connection to the NETCONF
                  server. If the connection goes down, immediately
                  start trying to reconnect to it, using the
                  reconnection strategy.

                  This connection type minimizes any NETCONF server
                  to NETCONF client data-transfer delay, albeit at
                  the expense of holding resources longer.";
                leaf idle-timeout {
                  type uint32;
                  units "seconds";
                  default 86400;  // one day;
                  description
                    "Specifies the maximum number of seconds that a
                     a NETCONF session may remain idle. A NETCONF
                     session will be dropped if it is idle for an
                     interval longer than this number of seconds.
                     If set to zero, then the client will never drop
                     a session because it is idle.  Sessions that
                     have a notification subscription active are
                     never dropped.";
                }
                container keep-alives {
                  description
                    "Configures the keep-alive policy, to proactively
                     test the aliveness of the SSH/TLS server.  An
                     unresponsive SSH/TLS server will be dropped after
                     approximately max-attempts * max-wait seconds.";
                  reference
                    "RFC 8071: NETCONF Call Home and RESTCONF Call
                     Home, Section 3.1, item S6";
                  leaf max-wait {
                    type uint16 {
                      range "1..max";
                    }
                    units seconds;
                    default 30;
                    description
                     "Sets the amount of time in seconds after which
                      if no data has been received from the SSH/TLS
                      server, a SSH/TLS-level message will be sent
                      to test the aliveness of the SSH/TLS server.";
                  }
                  leaf max-attempts {
                    type uint8;
                    default 3;
                    description
                     "Sets the maximum number of sequential keep-alive
                      messages that can fail to obtain a response from
                      the SSH/TLS server before assuming the SSH/TLS
                      server is no longer alive.";
                  }
                }
              }
            }
            case periodic-connection {
              container periodic {
                presence true;
                description
                 "Periodically connect to the NETCONF server, so that
                  the NETCONF server may deliver messages pending for
                  the NETCONF client.  The NETCONF server must close
                  the connection when it is ready to release it. Once
                  the connection has been closed, the NETCONF client
                  will restart its timer until the next connection.";
                leaf idle-timeout {
                  type uint16;
                  units "seconds";
                  default 300; // five minutes
                  description
                    "Specifies the maximum number of seconds that a
                     a NETCONF session may remain idle. A NETCONF
                     session will be dropped if it is idle for an
                     interval longer than this number of seconds.
                     If set to zero, then the server will never drop
                     a session because it is idle.  Sessions that
                     have a notification subscription active are
                     never dropped.";
                }
                leaf reconnect-timeout {
                  type uint16 {
                    range "1..max";
                  }
                  units minutes;
                  default 60;
                  description
                   "Sets the maximum amount of unconnected time the
                    NETCONF client will wait before re-establishing
                    a connection to the NETCONF server.  The NETCONF
                    client may initiate a connection before this
                    time if desired (e.g., to set configuration).";
                }
              }
            }
          }
        }
        container reconnect-strategy {
          description
           "The reconnection strategy directs how a NETCONF client
            reconnects to a NETCONF server, after discovering its
            connection to the server has dropped, even if due to a
            reboot.  The NETCONF client starts with the specified
            endpoint and tries to connect to it max-attempts times
            before trying the next endpoint in the list (round
            robin).";
          leaf start-with {
            type enumeration {
              enum first-listed {
                description
                  "Indicates that reconnections should start with
                   the first endpoint listed.";
              }
              enum last-connected {
                description
                  "Indicates that reconnections should start with
                   the endpoint last connected to.  If no previous
                   connection has ever been established, then the
                   first endpoint configured is used.   NETCONF
                   clients SHOULD be able to remember the last
                   endpoint connected to across reboots.";
              }
            }
            default first-listed;
            description
             "Specifies which of the NETCONF server's endpoints the
              NETCONF client should start with when trying to connect
              to the NETCONF server.";
          }
          leaf max-attempts {
            type uint8 {
              range "1..max";
            }
            default 3;
            description
             "Specifies the number times the NETCONF client tries to
              connect to a specific endpoint before moving on to the
              next endpoint in the list (round robin).";
          }
        }
      } // end netconf-server
    } // end initiate

    container listen {
      if-feature listen;
      description
        "Configures client accepting call-home TCP connections.";

      leaf idle-timeout {
        type uint16;
        units "seconds";
        default 3600; // one hour
        description
          "Specifies the maximum number of seconds that a NETCONF
           session may remain idle. A NETCONF session will be dropped
           if it is idle for an interval longer than this number of
           seconds.  If set to zero, then the server will never drop
           a session because it is idle.  Sessions that have a
           notification subscription active are never dropped.";
      }

      list endpoint {
        key name;
        min-elements 1;
        description
          "List of endpoints to listen for NETCONF connections.";
        leaf name {
          type string;
          description
            "An arbitrary name for the NETCONF listen endpoint.";
        }
        choice transport {
          mandatory true;
          description
            "Selects between available transports.";
          case ssh {
            if-feature ssh-listen;
            container ssh {
              description
                "SSH-specific listening configuration for inbound
                 connections.";
              leaf address {
                type inet:ip-address;
                description
                 "The IP address to listen on for incoming call-home
                  connections.  The NETCONF client will listen on
                  all configured interfaces if no value is specified.
                  INADDR_ANY (0.0.0.0) or INADDR6_ANY (0:0:0:0:0:0:0:0
                  a.k.a. ::) MUST be used when the server is to listen
                  on all IPv4 or IPv6 addresses, respectively.";
              }
              leaf port {
                type inet:port-number;
                default 4334;
                description
                 "The port number to listen on for call-home
                  connections.  The NETCONF client will listen on the
                  IANA-assigned well-known port for 'netconf-ch-ssh'
                  (4334) if no value is specified.";
              }
              uses ss:ssh-client-grouping;
            }
          }
          case tls {
            if-feature tls-listen;
            container tls {
              description
                "TLS-specific listening configuration for inbound
                 connections.";
              leaf address {
                type inet:ip-address;
                description
                 "The IP address to listen on for incoming call-home
                  connections.  The NETCONF client will listen on
                  all configured interfaces if no value is specified.
                  INADDR_ANY (0.0.0.0) or INADDR6_ANY (0:0:0:0:0:0:0:0
                  a.k.a. ::) MUST be used when the server is to listen
                  on all IPv4 or IPv6 addresses, respectively.";
              }
              leaf port {
                type inet:port-number;
                default 4335;
                description
                 "The port number to listen on for call-home
                  connections.  The NETCONF client will listen on the
                  IANA-assigned well-known port for 'netconf-ch-tls'
                  (4335) if no value is specified.";
              }
              uses ts:tls-client-grouping {
                refine "client-identity/auth-type" {
                  mandatory true;
                  description
                    "NETCONF/TLS clients MUST pass some authentication
                     credentials.";
                }
              }
            }
          }
        } // end transport
      } // end endpoint
    } // end listen

  } // end netconf-client
}
