module ietf-te-mpls-topology {
  yang-version 1.1;
  namespace "urn:ietf:params:xml:ns:yang:ietf-te-mpls-topology";

  prefix "tet-mpls";

  import ietf-network {
    prefix "nw";
  }

  import ietf-network-topology {
    prefix "nt";
  }

  import ietf-te-topology {
    prefix "tet";
  }

  import ietf-te-topology-packet {
    prefix "tet-pkt";
  }

  import ietf-mpls-te-types {
    prefix "mte-types";
  }

  organization
    "Internet Engineering Task Force (IETF) TEAS WG";
  contact
    "WG Web:   <https://datatracker.ietf.org/wg/teas/>
     WG List:  <mailto:teas@ietf.org>

     Editor:   Italo Busi
               <mailto:italo.busi@huawei.com>

     Editor:   Haomian Zheng
               <mailto:zhenghaomian@huawei.com>

     Editor:   Aihua Guo
               <mailto:aihuaguo.ietf@gmail.com>

     Editor:   Xufeng Liu
               <mailto:xufeng.liu.ietf@gmail.com>

     Editor:   Vishnu Pavan Beeram
               <mailto:vbeeram@juniper.net>

     Editor:   Tarek Saad
               <mailto:tsaad@juniper.net>

     Editor:   Rakesh Gandhi
               <mailto:rgandhi@cisco.com>

     Editor:   Igor Bryskin
               <mailto:i_bryskin@yahoo.com>

     Editor:   Yanlei Zheng
               <mailto:zhengyanlei@chinaunicom.cn>";

  description
    "This module defines technology-specific MPLS-TE topology
     data model.

     Copyright (c) 2021 IETF Trust and the persons identified
     as authors of the code.  All rights reserved.

     Redistribution and use in source and binary forms, with
     or without modification, is permitted pursuant to, and
     subject to the license terms contained in, the Simplified
     BSD License set forth in Section 4.c of the IETF Trust's
     Legal Provisions Relating to IETF Documents
     (http://trustee.ietf.org/license-info).

     This version of this YANG module is part of RFC XXXX; see
     the RFC itself for full legal notices.";

  revision 2021-10-12 {
    description
      "Initial Version";
    reference
      "draft-busizheng-teas-yang-te-mpls-topology-02";
  }

  /*
   * Augmentations
   */

  augment "/nw:networks/nw:network/nw:network-types/"
        + "tet:te-topology/tet-pkt:packet" {
    description
      "Augment network types to include MPLS-TE Topology Type";
    container mpls-topology {
      presence
        "Indicates an MPLS-TE Topology Type.";
      description
        "Its presence indicates an MPLS-TE Topology";
    }
  }

  augment "/nw:networks/nw:network/nt:link/tet:te" {
    when "../../nw:network-types/tet:te-topology/"
       + "tet-pkt:packet/tet-mpls:mpls-topology"  {
      description
        "Augment MPLS-TE Topology.";
    }
    description
      "Augment TE Link.";

    leaf load-balancing-type {
      type mte-types:load-balancing-type;
      default 'per-flow';
      description
        "Indicates the type of load-balancing (per-flow or per-LSP)
         performed by the bundled TE Link.

         This leaf is not present when the TE Link is not bundled.";
    }  // leaf load-balancing-type
  }

  augment "/nw:networks/nw:network/nw:node/nt:termination-point/"
        + "tet:te" {
    when "../../../nw:network-types/tet:te-topology/"
       + "tet-pkt:packet/tet-mpls:mpls-topology" {
      description "Augment MPLS-TE Topology.";
    }
    description "Augment LTP.";

    leaf uhp-incapable {
      type empty;
      config false;
      description
        "When present, indicates that the LTP is not capable to
         support Ultimate Hop Popping (UHP).";
    }   // leaf uhp-incapable
  }
}
