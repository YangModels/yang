module ietf-isis-srv6 {
  namespace "urn:ietf:params:xml:ns:"
          + "yang:ietf-isis-srv6";
  prefix isis-srv6;

  import ietf-routing {
    prefix "rt";
  }

  import ietf-isis {
    prefix "isis";
  }

  import ietf-srv6-base {
    prefix "srv6";
  }

  import iana-routing-types {
    prefix "iana-rt-types";
  }

  import ietf-inet-types {
    prefix "inet";
  }

  organization
   "IETF ISIS Working Group";

  contact
    "WG List:  <mailto:spring@ietf.org>
    Author:    Zhibo Hu
               <mailto:huzhibo@huawei.com>
    Author:    Dan Ye
               <mailto:daye@cisco.com>
    Author:    Yingzhen Qu
               <mailto:yingzhen.qu@huawei.com>
    Author:    Jiajia Dong
               <mailto:dongjiajia@huawei.com>
    ";

  description
    "The YANG module defines a generic configuration model for
    Segment IPV6 routing ISIS extensions common across all of
    the vendor implementations.";

  revision 2018-07-31 {
    description
        "Initial revision.";
    reference "draft-bashandy-isis-srv6-extensions-03";
  }

  /* Identities */
  identity SRV6_END_FUNC_TYPE {
    description
    "Base identity type for srv6 endpoint function code points.";
  }

  identity SRV6_END_FUNC_NO_PSP_USP {
    base "SRV6_END_FUNC_TYPE";
    description
    "End (no PSP, no USP).";
  }

  identity SRV6_END_FUNC_PSP {
    base "SRV6_END_FUNC_TYPE";
    description
    "End with PSP.";
  }

  identity SRV6_END_FUNC_USP {
    base "SRV6_END_FUNC_TYPE";
    description
    "END with USP.";
  }

  identity SRV6_END_FUNC_PSP_USP {
    base "SRV6_END_FUNC_TYPE";
    description
    "END with PSP & USP.";
  }

  identity SRVT_END_T_FUNC_NO_PSP_USP {
    base "SRV6_END_FUNC_TYPE";
    description
    "End.T (no PSP, no USP).";
  }

  identity SRVT_END_T_FUNC_PSP {
    base "SRV6_END_FUNC_TYPE";
    description
    "End.T with PSP.";
  }

  identity SRVT_END_T_FUNC_USP {
    base "SRV6_END_FUNC_TYPE";
    description
    "End.T with USP.";
  }

  identity SRVT_END_T_FUNC_PSP_USP {
    base "SRV6_END_FUNC_TYPE";
    description
    "End.T with PSP & USP.";
  }

  identity SRV6_END_X_FUNC_NO_PSP_USP {
    base "SRV6_END_FUNC_TYPE";
    description
    "End.x (no PSP, no USP).";
  }

  identity SRV6_END_X_FUNC_PSP {
    base "SRV6_END_FUNC_TYPE";
    description
    "End.x with PSP.";
  }

  identity SRV6_END_X_FUNC_USP {
    base "SRV6_END_FUNC_TYPE";
    description
    "End.x with USP.";
  }

  identity SRV6_END_X_FUNC_PSP_USP {
    base "SRV6_END_FUNC_TYPE";
    description
    "End.x with PSP & USP.";
  }

  identity SRV6_END_FUNC_DX6 {
    base "SRV6_END_FUNC_TYPE";
    description
    "End.DX6 function.";
  }

  identity SRV6_END_FUNC_DT6 {
    base "SRV6_END_FUNC_TYPE";
    description
    "End.DT6 function.";
  }

  identity SRV6_END_FUNC_OTP {
    base "SRV6_END_FUNC_TYPE";
    description
    "END.OTP .";
  }

  /* typedef */
  typedef srv6-sid-value {
    type inet:ipv6-address-no-zone;
    description
      "16 Octets encoded sid value.";
  }

  /* Features */
  feature srv6-ti-lfa {
    description
     "Enhance SRv6 FRR with ti-lfa
     support";
  }
  /* Groupings */
  grouping srv6-msd {
    description
      "means to advertise to advertise node/link specific
       values for Maxium Sid Depths(MSD) of various types";
    container v6-msd {
      description
      "Maximum SRv6 SID Depths.";
      leaf max-segments-left {
        type uint8;
        description
        "The maximum value of 'SL' field in the SRH of a
         recevied packet.";
      }
      leaf max-end-pop {
        type uint8;
        description
        "The maximum number of SIDS in the topp SRH in an SRH
         stack to which the router can apply 'PSP' or 'USP'.";
      }
      leaf max-t-insert {
        type uint8;
        description
        "The maximum number of SIDs can be inserted as port of
         the 'T.insert' behavior.";
      }
      leaf max-t-encap {
        type uint8;
        description
        "The maximum number of SIDs can be included as part of
         the 'T.Encap' behavior.";
      }
      leaf max-end-d {
        type uint8;
        description
          "The maximum number of SIDs in an SRH when performing
           decapsulation associated with 'End.Dx' functions
           (e.g., 'End.DX6' and 'End.DT6').";
      }
    }
  }

  grouping srv6-capability {
    description
    "SRV6 capability grouping.";
    container v6-capability {
      description
        "SRv6 capability.";
      leaf flags {
        type bits {
          bit o-flag {
            position 1;
            description
            "If set, then the router is able to
             use of the O-bit in the Segment Routing Header(SRH)
             as defined in [draft-ietf-6man-segment-routing-header].";
          }
        }
        description
        "Flags.";
      }
    }
  }

  grouping srv6-endpoint-func {
     description
      "This group defines srv6 endpoint function";
    container endpoint-func {
      description
        "Srv6 Endpoint function Descriptor.";
      leaf flags {
        type uint8;
        description
          "No flags are currently being defined.";
      }
      leaf endpoint-func {
        type identityref {
         base isis-srv6:SRV6_END_FUNC_TYPE;
        }
        description
          "The endpoint function.";
      }
      leaf undefined-endpoint-func {
        type uint16;
        description
          "Unknown endpoint func value.";
      }
    }
  }

  grouping srv6-end-sid {
    description
    "SRv6 Segment Identifier(SID) with Endpoint functions.";
    leaf flags {
      type uint8;
      description
        "NO flags are currently being defined.";
    }

    uses srv6-endpoint-func;

    leaf sid {
      type srv6-sid-value;
      description
        "SRV6 sid value.";
    }
    // sub-sub-tlvs not yet defined
  }

  grouping srv6-locator {
    description
      "This group defines srv6 locator tlv.";
    leaf mt-id {
      type uint16 {
        range "0..4095";
      }
      description
        "Multitopology Identifier as defined in [RFC5120].";
    }
    leaf flags {
      type bits {
        bit d-flag {
          position 0;
          description
            "When the locator is leaked from level-2 to leve-1,
             the d-flag must be set.";
        }
      }
      description
        "Flags for srv6 locator tlv.";
    }

    leaf metric {
      type uint32;
      description
        "Metric value.";
    }
    leaf algorithm {
      type uint8;
      description
      "Associated algorithm.";
    }

    leaf loc-size {
      type uint8;
      description
        "Number of bits in the locator field.";
    }
    leaf locator {
      type inet:ipv6-address-no-zone;
      description
        "Advertised SRV6 locator.";
    }
    container srv6-end-sids {
      description
        "This contains list of srv6 end sids.";
      list end-sid {
        key "sid";
        description
          "List of SRV6 SRv6 Segment Identifiers (SID)
           with Endpoint functions.";
        uses srv6-end-sid;
      }
    }
    uses isis:prefix-reachability-attributes;
    uses isis:prefix-ipv4-source-router-id;
    uses isis:prefix-ipv6-source-router-id;
  }

  grouping srv6-end-x-sid {
    description
    "SRv6 sid associated with an adjacency.";

    leaf func-flags {
      type bits {
        bit b-flag {
          position 0;
          description
            "Backup flag. If set, the End.X sid is
             eligible for protection.";
        }

        bit s-flag {
          position 1;
          description
            "Set flag. When set, the End.X sid refers to
             a set of adjacencies (and therefore May be assigned
             to other adjacencies as well.";
        }

        bit p-flag {
          position 2;
          description
          "Persistent flag. When set, the End.X sid is persistently
           allocated, i.e., the End.x sid value remains consistent
           across router restart and/or interface flap.";
        }
      }
      description
          "Flags for srv6 end x sid.";
    }

    leaf algorithm {
      type uint8;
      description
        "Associated algorithm.";
    }

    leaf weight {
      type uint8;
      description
      "The value represents the weight of the End.X sid
       for the purpose of load balancing.";
    }

    uses srv6-endpoint-func;

    leaf sid {
      type srv6-sid-value;
      description
        "SRV6 sid value.";
    }

    leaf neighbor-id {
      type isis:system-id;
      description
        "Describes the system ID of the neighbor
         associated with the SID value. This is only
         used on LAN adjacencies.";
    }

    // sub-sub-tlvs
  }

  grouping srv6-adjacency-state {
    description
     "This group will extend adjacency state.";
    list end-x-sid {
      key value;
      config false;
      leaf value {
        type srv6-sid-value;
        description
         "Value of the Adj-SID.";
      }
      leaf weight {
        type uint8;
        description
         "Weight associated with
         the End.X SID.";
      }
      leaf protection-requested {
        type boolean;
        description
         "Set to True if the End.X SID
         must be protected.";
      }
      leaf persistent {
        type boolean;
        description
          "Persistent flag. When set, the End.X sid is persistently
           allocated, i.e., the End.X sid value remains consistent
           across router restart and/or interface flap.";
      }
      leaf algorithm {
        type uint8;
        description
        "Associated algorithm.";
      }
      uses srv6-endpoint-func;

      description
       "List of End.X Segment IDs.";
    }
  }
  /* Cfg */
  augment "/rt:routing/" +
          "rt:control-plane-protocols/rt:control-plane-protocol"+
          "/isis:isis" {
    when "/rt:routing/rt:control-plane-protocols/"+
         "rt:control-plane-protocol/rt:type = 'isis:isis'" {
      description
        "This augment ISIS routing protocol when used";
    }
    description
      "This augments ISIS protocol configuration
       with SRv6.";

    container srv6-cfg{
      leaf enable{
        type boolean;
        default "false";
        description
          "Enables SRv6
           protocol extensions.";
      }

      leaf default-locator {
        type boolean;
        default "false";
        description
          "Enable ISIS segment-routing IPv6 with default Locator.";
      }

      leaf locator-name {
        when "not(../default-locator='true')";
        type leafref {
          path "/rt:routing/srv6:srv6/srv6:locators/srv6:locator/srv6:name";
        }
        description
          "Enable ISIS segment-routing IPv6 with specified Locator.";
      }

      leaf persistent-end-x-sid{
        type boolean;
        default "false";
        description
          "Enable the persistent nature of End.X sid";
      }
      description
        "Configuration about ISIS segment-routing IPv6.";
    }
  }

  augment "/rt:routing/" +
          "rt:control-plane-protocols/rt:control-plane-protocol"+
          "/isis:isis/isis:interfaces/isis:interface"+
          "/isis:fast-reroute"{
    when "/rt:routing/rt:control-plane-protocols/"+
         "rt:control-plane-protocol/rt:type = 'isis:isis'"{
      description
        "This augment ISIS routing protocol when used";
    }
    description
      "This augments ISIS IPFRR with IPV6 TILFA.";

    container srv6-ti-lfa {

      if-feature srv6-ti-lfa;
      leaf enable {
        type boolean;
        description
          "Enables SRv6 TI-LFA computation.";
      }

      description
        "SRv6 TILFA configuration.";
    }
  }

  /* Operational states */
  augment "/rt:routing/" +
        "rt:control-plane-protocols/rt:control-plane-protocol"+
        "/isis:isis/isis:database/isis:level-db/isis:lsp"+
        "/isis:router-capabilities" {
     when "/rt:routing/rt:control-plane-protocols/"+
        "rt:control-plane-protocol/rt:type = 'isis:isis'" {
      description
        "This augment ISIS routing protocol when used";
    }
    description
     "This augments ISIS protocol router capability.";
      uses srv6-capability;
      uses srv6-msd;
  }

  augment "/rt:routing/" +
        "rt:control-plane-protocols/rt:control-plane-protocol"+
        "/isis:isis/isis:database/isis:level-db/isis:lsp"+
        "/isis:extended-is-neighbor/isis:neighbor" {
     when "/rt:routing/rt:control-plane-protocols/"+
        "rt:control-plane-protocol/rt:type = 'isis:isis'" {
      description
      "This augment ISIS routing protocol when used.";
    }
    description
     "This augments ISIS protocol neighbor.";
    container srv6-end-x-sids {
      description
        "This defines svr6 end-x sids for the adjacency.";
      list end-x-sid {
        key "sid";
        uses srv6-end-x-sid;
        description
           "List of end-x sids.";
      }
    }
  }
  augment "/rt:routing/" +
        "rt:control-plane-protocols/rt:control-plane-protocol"+
        "/isis:isis/isis:database/isis:level-db/isis:lsp"+
        "/isis:mt-is-neighbor/isis:neighbor" {
            when "/rt:routing/rt:control-plane-protocols/"+
        "rt:control-plane-protocol/rt:type = 'isis:isis'" {
      description
        "This augment ISIS routing protocol when used.";
    }
    description
      "This augments ISIS protocol neighbor.";
    container srv6-end-x-sids {
       description
        "This defines svr6 end-x sids for the adjacency.";
      list end-x-sid {
        key "sid";
        uses srv6-end-x-sid;
         description
           "List of end-x sids.";
      }
    }
  }

  augment "/rt:routing/" +
        "rt:control-plane-protocols/rt:control-plane-protocol"+
        "/isis:isis/isis:database/isis:level-db/isis:lsp" {
        when "/rt:routing/rt:control-plane-protocols/"+
        "rt:control-plane-protocol/rt:type = 'isis:isis'" {
      description
      "This augment ISIS routing protocol when used.";
    }
    description
     "This augments ISIS protocol LSDB.";
    container srv6-locators {
      description
         "This defines srv6 locator tlvs.";
      list locator {
        key "locator";
        uses srv6-locator;
        description
          "List of srv6 locators.";
      }
    }
  }

  augment "/rt:routing/" +
        "rt:control-plane-protocols/rt:control-plane-protocol"+
        "/isis:isis/isis:interfaces/isis:interface" +
        "/isis:adjacencies/isis:adjacency" {
    when "/rt:routing/rt:control-plane-protocols/"+
        "rt:control-plane-protocol/rt:type = 'isis:isis'" {
      description
      "This augment ISIS routing protocol when used.";
    }
    description
      "This augments ISIS protocol operational state
       with segment routing.";

    uses  srv6-adjacency-state;
  }

  /* Notifications */
}
