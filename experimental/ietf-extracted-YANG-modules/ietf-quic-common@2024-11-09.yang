module ietf-quic-common{
  yang-version 1.1;
  namespace
    "urn:ietf:params:xml:ns:yang:ietf-quic-common";
  prefix quiccmn;

  organization
    "IETF NETCONF (Network Configuration) Working Group";

  contact
    "WG List: NETCONF WG list <mailto:netconf@ietf.org>
     WG Web:  https://datatracker.ietf.org/wg/netconf
     Author:  Per Andersson <mailto:per.ietf@ionio.se>";

  description
    "This module defines a reusable grouping that is common for
     QUIC clients and QUIC servers. This grouping statement is
     used by both 'ietf-quic-client' and 'ietf-quic-server'
     modules.

     Copyright (c) 2024 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC AAAA
     (https://www.rfc-editor.org/info/rfcAAAA); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2024-11-09 {
    description
      "Initial version";
    reference
      "RFC AAAA: YANG Groupings for QUIC Clients and QUIC Servers";
  }

  // Groupings

  grouping transport-parameters {
    description
      "A reusable grouping for QUIC Transport Parameters.";
    reference
      "RFC 9000: QUIC: A UDP-Based Multiplexed and Secure Transport
       RFC 9002: QUIC Loss Detection and Congestion Control
       RFC 9312: Manageability of the QUIC Transport Protocol";

    leaf version { type uint32; }
    leaf initial-rtt { type uint32; }
    leaf congestion-control-algorithm { type string; }
    leaf max-idle-timeout { type uint32; }
    leaf initial-max-streams-bidi { type uint32; }
    leaf initial-max-streams-uni { type uint32; }
    leaf keep-alive-interval { type uint32; }
  }
}
