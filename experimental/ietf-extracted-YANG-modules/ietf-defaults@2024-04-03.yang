module ietf-defaults {
  yang-version 1.1;
  namespace
    "urn:ietf:params:xml:ns:netconf:default:1.0";
  prefix wd;

  import ietf-yang-metadata {
    prefix md;
    reference
      "RFC 7952: Defining and Using Metadata with YANG";
  }

  organization
    "IETF NETCONF (Network Configuration) Working Group";

  contact
    "WG Web:   https://datatracker.ietf.org/wg/netconf
     WG List:  NETCONF WG list <mailto:netconf@ietf.org>

     Authors:  Per Andersson <per.ietf@ionio.se>";

  description
    "This module defines the 'default' attribute in YANG
     previously only defined in XML Schema in RFC 6243 Section 6.

     Copyright (c) 2024 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2024-04-03 {
    description
      "Initial revision.";
    reference
      "RFC XXXX: YANG Model for the NETCONF default attribute";
  }

  md:annotation default {
    type boolean;
    description
      "This annotation is only relevant if the server supports the
       'report-all-tagged' defaults retrieval mode. For details see
       RFC 6243.";
    reference
      "RFC 6243: With-defaults Capability for NETCONF";
  }
}
