module ietf-ethernet-segment {
  namespace "urn:ietf:params:xml:ns:yang:ietf-ethernet-segment";
  prefix "es";

  import ietf-evpn {
    prefix "evpn";
  }

  organization  "ietf";
  contact       "ietf";
  description   "ethernet segment";

  revision "2015-10-15" {
    description "Initial revision";
    reference   "";
  }

  /* EVPN Ethernet Segment YANG Model */

  container ethernet-segments {
    description "ethernet-segment";
    list ethernet-segment {
      key "name";
      leaf name {
        type string;
        description "Name of the ethernet segment";
      }
      leaf esi {
        type empty;
        description "esi";
      }
      choice active-mode {
        mandatory true;
        description "Choice of active mode";
        case single-active {
          leaf single-active-mode {
            type empty;
            description "single-active-mode";
          }
        }
        case all-active {
          leaf all-active-mode {
            type empty;
            description "all-active-mode";
          }
        }
      }
      uses evpn:bgp-parameters-grp;
      container df-election {
        description "df-election";
        choice df-election-method {
          description "Choice of df election method";
          case highest-random-weight {
            leaf enable-hrw {
              type empty;
              description "enable-hrw";
            }
          }
        }
        leaf election-wait-time {
          type uint32;
          description "election-wait-time";
        }
      }
      description "An ethernet segment";
    }
  }
}
