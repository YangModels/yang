module ietf-mpls-te-types {

   namespace "urn:cisco:params:xml:ns:yang:ietf-mpls-te-types";

   /* Replace with IANA when assigned */
   prefix "mpls-te-types";

   import ietf-inet-types { prefix inet; }

   organization
     "IETF MPLS Working Group";

   contact
     "Rakesh Gandhi rgandhi@cisco.com
      Tarek Saad tsaad@cisco.com
      Robert Sawaya rsawaya@cisco.com";

   description
       "This module contains a collection of generally
        useful MPLS-TE specific
        derived YANG data types.";

   revision 2014-11-05 {
       description
           "Initial revision.";
   }

   /* Typedefs for MPLS-TE */

   typedef bc-model-type {
       description
          "Diff-Serve TE Bandwidth Constraint model type.";
       type enumeration {
           enum rdm {
               description
                   "Russian Doll bandwidth constraint
                   model type.";
           }
           enum mam {
               description
                   "Maximum Allocation bandwidth constraint
                   model type.";
           }
           enum mar {
               description
                   "Maximum Allocation with Reservation
                   bandwidth constraint model type.";
           }
       }
       default rdm;
   }

   typedef bandwidth-type {
       description "MPLS-TE tunnel bandwidth type";
       type enumeration {
           enum CT0;
           enum CT1;
           enum CT2;
           enum CT3;
           enum CT4;
           enum CT5;
           enum CT6;
           enum CT7;
       }
       default CT0;
   }

   typedef lsp-status-event-type {
       description "Tunnel LSP status event type.";
       type enumeration {
           enum bandwidth-change;
           enum insufficient-bandwidth;
           enum record-route;
           enum reroute;
           enum state;
           enum switchover;
       }
   }

   typedef bandwidth-unit-type {
       description "Bandwidth unit type.";
       type enumeration {
           enum Gbps;
           enum Mbps;
           enum Kbps;
       }
       default Kbps;
   }

   typedef backup-bandwidth-type {
       description "FRR backup tunnel bandwidth protection type.";
       type enumeration {
           enum BC0;
           enum BC1;
           enum BC2;
           enum BC3;
           enum BC4;
           enum BC5;
           enum BC6;
           enum BC7;
           enum BC-any;
       }
       default BC-any;
   }

   typedef tunnel-type {
       type enumeration {
           enum p2p {
               description
                   "MPLS-TE point-to-point tunnel type.";
           }
           enum p2mp {
               description
                   "MPLS-TE point-to-multipoint tunnel type.";
           }
       }
       default p2p;
       description
           "Possible MPLS-TE tunnel types, default is point-to-point.";
   }

   typedef hop-address-type {
       type inet:ip-address;
   }

   typedef hop-action-type {
       type enumeration {
           enum include-strict {
               description "Include strict hop.";
           }
           enum include-loose {
               description "Include loose hop.";
           }
           enum exclude {
               description "Exclude strict hop.";
           }
       }
       default "include-strict";
   }

   typedef bfd-type {
       type enumeration {
           enum classical {
               description "BFD classical session type.";
           }
           enum seamless {
               description "BFD seamless session type.";
           }
       }
       default "classical";
   }

   typedef path-metric-type {
       type enumeration {
           enum igp;
           enum te;
       }
       default igp;
       description "Path metric for CSPF.";
   }

   typedef path-tiebreaker-type {
       type enumeration {
           enum min-fill;
           enum max-fill;
           enum random;
       }
       default min-fill;
       description
           "Possible CSPF path tiebreakers for MPLS-TE tunnels.";
   }

   typedef bidir-association-type {
       type enumeration {
           enum corouted;
           enum non-corouted;
       }
       default non-corouted;
       description
           "Possible types of bidirectional tunnel association.";
   }

   typedef bfd-encap-mode-type {
       type enumeration {
           enum gal;
           enum ip;
       }
       default ip;
       description
           "Possible BFD transport modes when running over MPLS-TE
            LSPs.";
   }

   typedef affinity-action-type {
       type enumeration {
           enum include;
           enum exclude;
           enum include-strict;
           enum exclude-all;
       }
       description
           "Possible handling for affinity.";
   }

   typedef  path-computation-srlg-type {
       description "Path computation SRLG criteria.";
       type enumeration {
           enum srlg-none;
           enum srlg-strict;
           enum srlg-preferred;
           enum srlg-weighted;
       }
   }
}
