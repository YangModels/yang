module ietf-yang-push-noti-filter {
  yang-version 1.1;
  namespace "urn:ietf:params:xml:ns:yang:ietf-yang-push-noti-filter";
  prefix ypf;
  import ietf-subscribed-notifications {
    prefix sn;
  }
  import ietf-yang-push {
    prefix yp;
    revision-date 2019-09-09;
  }

  organization "IETF NETCONF(Network Configuration) Working Group";
  contact
    "ZTE Corporation &#xD;
      Nanjing Institute of ZTE Corporation&#xD;
      &#xD;
      No.68 Zijinghua Rd. Yuhuatai District, Nanjing, China&#xD;
      &#xD;
      Tel: +86-25-52870000";

  description
    "This module augments the YANG push subscription RPCs.

     Copyright (c) 2023 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents(https://trustee.ietf.org/license-info).

     This version of this YANG module is part of RFC XXXX; see the
     RFC itself for full legal notices.";

  revision 2024-05-31 {
    description
      "First revision";
    reference
      "RFC XXXX: Filter of Configuration Change Notifications
       Subscription";
  }

  augment "/sn:establish-subscription/sn:input/yp:update-trigger/" +
            "yp:on-change/yp:on-change" {
    leaf excluded-self-change {
      type enumeration {
        enum enable {
          description
            "Enable excluded-self-change.";
        }
        enum disable {
          description
            "Disable excluded-self-change.";
        }
      }
      description
        "Used to restrict a push-change-update notification that
        triggered by the subscriber self if need report to
        subscriber.";
    }

    description
      "This augmentation adds additional subscription parameters to
       the establish-subscription RPC.";
  }

  augment "/sn:modify-subscription/sn:input/yp:update-trigger/" +
            "yp:on-change/yp:on-change" {
    leaf excluded-self-change {
      type enumeration {
        enum enable {
          description
            "Enable excluded-self-change.";
        }
        enum disable {
          description
            "Disable excluded-self-change.";
        }
      }

      description
        "Used to restrict a push-change-update notification that
         triggered by the subscriber self if need report to subscriber.";
    }
    description
      "This augmentation adds additional subscription parameters to the
       modify-subscription RPC.";
  }
}
