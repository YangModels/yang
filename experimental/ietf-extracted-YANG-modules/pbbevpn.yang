module pbbevpn {
  namespace "urn:juniper:params:xml:ns:yang:pbbevpn";
  // replace with IANA namespace when assigned

  prefix pevpn;

  import ietf-interfaces {
    prefix if;
    //rfc7223-YANG Interface Management
  }
/*
  import ietf-inet-types {
    prefix inet;
    //rfc6991
  }
*/

  import ietf-yang-types {
    prefix yang;
  }

  description
    "This YANG module defines the generic configuration data for
     PBB EVPN Service.

     Terms and Acronyms
     EVN: Ethernet Virtual Network
     EVPN: Ethernet VPN
     I-SID: Service Instance Identifier
     B-VID: Backbone VLAN ID
     C-MAC: Customer/Client MAC
     B-MAC: Backbone MAC
     BEB: Backbone Edge Bridge
     ES: Ethernet Segment
     ESI: Ethernet Segment Identifier
     LSP: Label Switched Path
     MP2MP: Multipoint to Multipoint
     MP2P: Multipoint to Point
     P2MP: Point to Multipoint
     P2P: Point to Point
     PE: Provider Edge
     EVPN: Ethernet VPN
     EVI: EVPN Instance
    ";

  revision 2015-03-06 {
    description
      "Initial revision.";
  }

  /*
   * Configuring Ethernet Segment
   */
  container interfaces {
    list interface {
      key "name";
      leaf name {
        type leafref {
          path "/if:interfaces/if:interface/if:name";
        }
      }
      leaf esi {
        description
          "Specify the ethernet segment ID.";

        config "true";
        type string {
          length "24";
          pattern "(^00([0-9a-fA-F]){2}\.(([0-9a-fA-F]){4}\.){3}
          (([0-9a-fA-F]){4})$)";
        }
      }

      leaf redudancy-mode {
        description
          "Specify Redundancy mode, value are all-active (false),
           single-active (true)";
        config "true";
        type boolean;
      }

      leaf auto-source-bmac {
        description
          "Specify auto derived mode (true) ,
           manual bmac config (false)";
        config "true";
        type boolean;
      }

      leaf source-bmac {
         type yang:mac-address;
      }
    } /* End of Interface */
  } /* End of Container */

  /*
   * Configuring Service Classification
   */
  container logicalinterfaces {
    list interface {
      key "name";
      leaf name {
        type leafref {
          path "/if:interfaces/if:interface/if:name";
        }
      }
      leaf encap {
        description
          "Vlan ID";
        config "true";
         type uint16 {
           range "1..4094";
         }
      } /* End encap */
    }
  }

  /*
   * Configuring I-component
   */
  container i-component {
    list bridge-domain {
      description
        "Customer Bridge Domain.";
      config "true";
      type uint16;

      container member-interface {
        description
          "member interface.";
        config true;
        list memberifs {
          description
           "member interfaces.";
           config true;
           type if:interface-ref;
        }
      } /* End of member if*/
      leaf nvlanid {
        description
          "Normalized Vlan ID";
        config "true";
         type uint16 {
           range "1..4094";
         }
      }
      leaf isid {
        description
          "I-SID";
        config "true";
         type uint32 {
           range "1..16777215";
         }
      }
    } /*End of List */
    leaf peer-b-component {
      description
        "Peer Backbone Component.";
      config true;
      type string {
        length "24";
        pattern "(^00([0-9a-fA-F]){2}\.(([0-9a-fA-F]){4}\.){3}
        (([0-9a-fA-F]){4})$)";
      }
    } /*end of peer-b-component */
  }

  /* Configuring Bcomponent */
  container b-component {
    list b-bridge-domain {
      description
        "Backbone Bridge Domain.";
      config "true";
      type uint16;
      leaf nvlanid {
        description
          "Normalized Vlan ID";
        config "true";
         type uint16 {
           range "1..4094";
         }
      }
      list isid {
        description
          "I-SID";
        config "true";
        leaf isid {
          description
            "I-SID";
          config "true";
           type uint32 {
             range "1..16777215";
           }
        }
      }
    } /*End of List */

    leaf route-distinguisher {
      description
        "Route Distinguisher.";
      config true;
      type string;
    } /*end of route-distinguiher */
    leaf auto-route-target {
        description
          "Specify auto derived route target (true) ,
           manual route target (false)";
        config "true";
        type boolean;
    }

    leaf route-target {
      description
        "Route Target.";
        config true;
        type string;
    } /* end of route target. */

    leaf protocol {
      description
        "Protocol running on Backbone B-Comp.";
      config true;
      type enumeration {
        enum "evpn" {
          value 0;
        }
        enum "pbb-evpn" {
          value 1;
        }
      }
    }

    leaf control-word {
      description
        "Control Word.";
      config true;
      type boolean;
    }
  }
}
