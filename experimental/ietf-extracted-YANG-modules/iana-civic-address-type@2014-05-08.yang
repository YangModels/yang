submodule iana-civic-address-type {
  belongs-to "ietf-location" {
    prefix loc;
  }

  organization "IANA";
  contact
    "        Internet Assigned Numbers Authority

     Postal: ICANN
             4676 Admiralty Way, Suite 330
             Marina del Rey, CA 90292

     Tel:    +1 310 823 9358
     E-Mail: iana&iana.org";
  description
    "This YANG module defines the iana-civic-address-type typedef,
     which contains YANG definitions for IANA-registered civic
     address types.

     This YANG module is maintained by IANA, and reflects the
     'Civic Address Types (CAtypes)' registry.

     The latest revision of this YANG module can be obtained from
     the IANA web site.

     Requests for new values should be made to IANA via
     email (iana&iana.org).

     Copyright (c) 2014 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).";

  revision 2014-05-08 {
    description
      "Initial revision.";
  }

  typedef iana-civic-address-type {
    type string;
    description
      "A civic address type as defined by the IANA Civic Address 
       Types registry.";
  }

  typedef CA0 {
    type iana-civic-address-type;
    description
      "Language.";
  } 

  typedef A1 {
    type iana-civic-address-type;
    description
      "National subdivisions:
       state, canton, region, province, prefecture";
  }

  typedef A2 {
    type iana-civic-address-type;
    description
      "county, parish, gun (JP), district (IN)";
  }

  typedef A3 {
    type iana-civic-address-type;
    description
      "city, township, shi (JP)";
  }

  typedef A4 {
    type iana-civic-address-type;
    description
      "city division, borough, city district, ward, chou (JP)";
  }
  typedef A5 {
    type iana-civic-address-type;
    description
      "neighborhood, block";
  }

  typedef A6 {
    type iana-civic-address-type;
    description
      "group of streets below the neighborhood level";
  }

  typedef PRD {
    type iana-civic-address-type;
    description
      "leading street direction";
  }

  typedef POD {
    type iana-civic-address-type;
    description
      "trailing street suffix";
  }

  typedef STS {
    type iana-civic-address-type;
    description
      "street suffix or type";
  }

  typedef HNO {
    type iana-civic-address-type;
    description
      "house number";
  }

  typedef HNS {
    type iana-civic-address-type;
    description
      "house number suffix";
  }

  typedef LMK {
    type iana-civic-address-type;
    description
      "landmark or vanity address";
  }

  typedef LOC {
    type iana-civic-address-type;
    description
      "additional location information";
  }

  typedef NAM {
    type iana-civic-address-type;
    description
      "name (residence and office occupant)";
  }

  typedef PC {
    type iana-civic-address-type;
    description
      "postal/zip code";
  }

  typedef BLD {
    type iana-civic-address-type;
    description
      "building (structure)";
  }

  typedef UNIT {
    type iana-civic-address-type;
    description
      "unit (apartment, suite)";
  }

  typedef FLR {
    type iana-civic-address-type;
    description
      "floor";
  }

  typedef ROOM {
    type iana-civic-address-type;
    description
      "room number";
  }

  typedef PLC {
    type iana-civic-address-type;
    description
      "type of place";
  }

  typedef PCN {
    type iana-civic-address-type;
    description
      "postal community name";
  }

  typedef POBOX {
    type iana-civic-address-type;
    description
      "post office box (P.O. Box)";
  }

  typedef ADDCODE {
    type iana-civic-address-type;
    description
      "additional code";
  }

  typedef SEAT {
    type iana-civic-address-type;
    description
      "seat (desk, cubicle, workstation)";
  }

  typedef RD {
    type iana-civic-address-type;
    description
      "Primary road or street";
  }

  typedef RDSEC {
    type iana-civic-address-type;
    description
      "Road section";
  }

  typedef RDBR {
    type iana-civic-address-type;
    description
      "Road branch";
  }

  typedef RDSUBBR {
    type iana-civic-address-type;
    description
      "Road sub-branch";
  }

  typedef PRM {
    type iana-civic-address-type;
    description
      "Street name pre-modifier";
  }

  typedef POM {
    type iana-civic-address-type;
    description
      "Street name post-modifier";
  }

  typedef PN {
    type iana-civic-address-type;
    description
      "Post number that is attributed to a lamp post or utility
       pole.";
  }

  typedef MP {
    type iana-civic-address-type;
    description
      "Milepost: a marker indicating distance to or from a place
       (often a town).";
  }

  typedef STP {
    type iana-civic-address-type;
    description
      "Street Type Prefix.";
  }

  typedef HNP {
    type iana-civic-address-type;
    description
      "House Number Prefix.";
  }

  typedef STPS {
    type iana-civic-address-type;
    description
      "Separator between the existing Street Type Prefix (STP) and
       the Road Name (RD) elements.";
  }

  typedef LMKP {
    type iana-civic-address-type;
    description
      "Component part of a Complete Landmark Name.";
  }

  typedef CA128 {
    type iana-civic-address-type;
    description
      "script";
  }
}
