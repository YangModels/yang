module ietf-ioam {
  yang-version 1.1;
  namespace "urn:ietf:params:xml:ns:yang:ietf-ioam";
  prefix "ioam";

  import ietf-access-control-list {
    prefix "acl";
    reference
      "RFC 8519: YANG Data Model for Network Access Control
       Lists (ACLs)";
  }

  import ietf-interfaces {
    prefix "if";
    reference
      "RFC 8343: A YANG Data Model for Interface Management";
  }

  import ietf-lime-time-types {
    prefix "lime";
    reference
      "RFC 8532: Generic YANG Data Model for the Management of
       Operations, Administration, and Maintenance (OAM) Protocols
       That Use Connectionless Communications";
  }

  organization
    "IETF IPPM (IP Performance Metrics) Working Group";

  contact
    "WG Web: <https://datatracker.ietf.org/wg/ippm>
     WG List: <ippm@ietf.org>
     Editor: zhoutianran@huawei.com
     Editor: james.n.guichard@futurewei.com
     Editor: fbrockne@cisco.com
     Editor: srihari@cisco.com";

  description
    "This YANG module specifies a vendor-independent data
     model for the In Situ OAM (IOAM).

    Copyright (c) 2023 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.";

  revision 2023-02-10 {
    description "First revision.";
    reference "RFC XXXX: A YANG Data Model for In-Situ OAM";
  }

 /*
  * FEATURES
  */

  feature incremental-trace
  {
    description
      "This feature indicated that the incremental tracing option is
       supported";
    reference "RFC 9197: Data Fields for In-situ OAM";
  }

  feature preallocated-trace
  {
    description
      "This feature indicated that the preallocated tracing option is
       supported";
    reference "RFC 9197: Data Fields for In-situ OAM";
  }

  feature proof-of-transit
  {
    description
      "This feature indicated that the proof of transit option is
       supported";
    reference "RFC 9197: Data Fields for In-situ OAM";
  }

  feature edge-to-edge
  {
    description
      "This feature indicated that the edge to edge option is
       supported";
    reference "RFC 9197: Data Fields for In-situ OAM";
  }

 /*
  * IDENTITIES
  */
  identity filter {
    description
      "Base identity to represent a filter. A filter is used to
      specify the flow to apply the IOAM profile. ";
  }

  identity acl-filter {
    base filter;
    description
      "Apply ACL rules to specify the flow.";
  }

  identity protocol {
    description
      "Base identity to represent the carrier protocol. It's used to
       indicate what layer and protocol the IOAM data is embedded.";
  }

  identity ipv6 {
    base protocol;
    description
      "The described IOAM data is embedded in IPv6 protocol.";
    reference "RFC XXXX: In-situ OAM IPv6 Options";
  }

  identity nsh  {
    base protocol;
    description
      "The described IOAM data is embedded in NSH.";
    reference
      "RFC XXXX: Network Service Header (NSH) Encapsulation
       for In-situ OAM (IOAM) Data";
  }

  identity node-action {
    description
      "Base identity to represent the node actions. It's used to
       indicate what action the node will take.";
  }

  identity action-encapsulate {
    base node-action;
    description
      "It indicates the node is to encapsulate the IOAM packet";
  }

  identity action-decapsulate {
    base node-action;
    description
      "It indicates the node is to decapsulate the IOAM packet";
  }

  identity trace-type {
    description
      "Base identity to represent trace types.";
  }

  identity trace-hop-lim-node-id {
    base trace-type;
    description
      "It indicates the presence of Hop_Lim and node_id in the
       node data.";
  }

  identity trace-if-id {
    base trace-type;
    description
      "It indicates presence of ingress_if_id and egress_if_id
       (short format) in the node data.";
  }

  identity trace-timestamp-seconds {
    base trace-type;
    description
      "It indicates presence of timestamp seconds in the node data.";
  }

  identity trace-timestamp-fraction  {
    base trace-type;
    description
      "It indicates presence of timestamp fraction in the node data.";
  }

  identity trace-transit-delay {
    base trace-type;
    description
      "It indicates presence of transit delay in the node data.";
  }

  identity trace-namespace-data {
    base trace-type;
    description
      "It indicates presence of name space specific data (short format)
       in the node data.";
  }

  identity trace-queue-depth {
    base trace-type;
    description
      "It indicates presence of queue depth in the node data.";
  }

  identity trace-checksum-complement {
    base trace-type;
    description
      "It indicates presence of the Checksum Complement node data.";
  }

  identity trace-hop-lim-node-id-wide {
    base trace-type;
    description
      "It indicates presence of Hop_Lim and node_id in wide format
       in the node data.";
  }

  identity trace-if-id-wide {
    base trace-type;
    description
      "It indicates presence of ingress_if_id and egress_if_id in
       wide format in the node data.";
  }

  identity trace-namespace-data-wide {
    base trace-type;
    description
      "It indicates presence of IOAM-Namespace specific data in wide
       format in the node data.";
  }

  identity trace-buffer-occupancy {
    base trace-type;
    description
      "It indicates presence of buffer occupancy in the node data.";
  }

  identity trace-opaque-state-snapshot {
    base trace-type;
    description
      "It indicates presence of variable length Opaque State Snapshot
       field.";
  }

  identity pot-type {
    description
      "Base identity to represent Proof of Transit (PoT) types.";
  }

  identity pot-type-0 {
    base pot-type;
    description
      "The IOAM POT Type field value is 0, and POT data is a 16
       Octet field to carry data associated to POT procedures.";
  }

  identity e2e-type {
    description
      "Base identity to represent e2e types";
  }

  identity e2e-seq-num-64 {
    base e2e-type;
    description
      "It indicates presence of a 64-bit sequence number.";
  }

  identity e2e-seq-num-32 {
    base e2e-type;
    description
      "It indicates the presence of a 32-bit sequence number.";
  }

  identity e2e-timestamp-seconds {
    base e2e-type;
    description
      "It indicates the presence of timestamp seconds representing
       the time at which the packet entered the IOAM-domain";
  }

  identity e2e-timestamp-fraction {
    base e2e-type;
    description
      "It indicates the presence of timestamp fraction representing
       the time at which the packet entered the IOAM-domain.";
  }

  identity namespace {
    description
      "Base identity to represent the Namespace-ID.";
  }

  identity default-namespace {
    base namespace;
    description
      "The Namespace-ID value of 0x0000 is defined as the
       Default-Namespace-ID and MUST be known to all the nodes
       implementing IOAM.";
  }

 /*
  * TYPE DEFINITIONS
  */
  typedef ioam-filter-type {
    type identityref {
      base filter;
    }
    description
      "It specifies a known type of filter.";
  }

  typedef ioam-protocol-type {
    type identityref {
      base protocol;
    }
    description
      "It specifies a known type of carrier protocol for the IOAM
       data.";
  }

  typedef ioam-node-action {
    type identityref {
      base node-action;
    }
    description
      "It specifies a known type of node action.";
  }

  typedef ioam-trace-type {
    type identityref {
      base trace-type;
    }
    description
      "It specifies a known trace type.";
  }
  typedef ioam-pot-type {
    type identityref {
      base pot-type;
    }
    description
      "It specifies a known pot type.";
  }

  typedef ioam-e2e-type {
    type identityref {
      base e2e-type;
    }
    description
      "It specifies a known e2e type.";
  }

  typedef ioam-namespace {
    type identityref {
      base namespace;
    }
    description
      "It specifies the supported namespace.";
  }

 /*
  * GROUP DEFINITIONS
  */

  grouping ioam-filter {
    description "A grouping for IOAM filter definition";

    leaf filter-type {
      type ioam-filter-type;
      description "filter type";
    }

    leaf ace-name {
      when "derived-from-or-self(../filter-type, 'ioam:acl-filter')";
      type leafref {
        path "/acl:acls/acl:acl/acl:aces/acl:ace/acl:name";
      }
      description "The Access Control Entry name is used to
      refer to an ACL specification.";
    }
  }

  grouping encap-tracing {
    description
      "A grouping for the generic configuration for
       tracing profile.";

    container trace-types {
      description
        "It indicates the list of trace types for encapsulation";

      leaf use-namespace {
        type ioam-namespace;
        description
          "It indicates the name space used for encapsulation";
      }

      leaf-list trace-type {
        type ioam-trace-type;
        description
          "The trace type is only defined at the encapsulation node.";
      }
    }

    leaf max-length {
      when "derived-from-or-self(../node-action,
            'ioam:action-encapsulate')";
      type uint32;
      units bytes;
      description
        "This field specifies the maximum length of the node data list
        in octets. The max-length is only defined at the
        encapsulation node.";
    }
  }

  grouping ioam-incremental-tracing-profile {
    description
      "A grouping for incremental tracing profile.";

    leaf node-action {
      type ioam-node-action;
      description
        "This object indicates the action the node need to
         take, e.g. encapsulation.";
    }

    uses encap-tracing {
      when "derived-from-or-self(node-action,
           'ioam:action-encapsulate')";
    }
  }
  grouping ioam-preallocated-tracing-profile {
    description
      "A grouping for incremental tracing profile.";

    leaf node-action {
      type ioam-node-action;
      description "This indicates what action the node will take,
      e.g. encapsulation.";
    }

    uses encap-tracing {
      when "derived-from-or-self(node-action,
           'ioam:action-encapsulate')";
    }
  }

  grouping ioam-e2e-profile {
    description
      "A grouping for edge-to-edge profile.";

    leaf node-action {
      type ioam-node-action;
      description
        "It indicates how the node acts for this profile";
    }

    container e2e-types {
      when "derived-from-or-self(../node-action,
           'ioam:action-encapsulate')";

      description
        "It indicates the list of e2e types for encapsulation";

      leaf use-namespace {
        type ioam-namespace;
        description
          "It indicates the name space used for encapsulation";
      }

      leaf-list e2e-type {
        type ioam-e2e-type;
        description
          "The e2e type is only defined at the encapsulation node.";
      }
    }
  }
  grouping ioam-admin-config {
    description
      "IOAM top-level administrative configuration.";

    leaf enabled {
      type boolean;
      default false;
      description
        "This object is to control the availability of configuration.
         It MUST be true before anything in the
         /ioam/ioam-profiles/ioam-profile subtree can be edited.
         If false, any configuration in place is not used.";
    }
  }

 /*
  * DATA NODES
  */

  container ioam {
    description "IOAM top level container";

    container ioam-info {
      config false;
      description
        "Describes assistant information such as units or timestamp
         format. So that monitoring systems can interpret the IOAM
         data.";

      leaf timestamp-type {
        type identityref {
          base lime:timestamp-type;
        }
        description
          "Type of timestamp, such as Truncated PTP or NTP.";
      }

      list available-interface {
        key "if-name";
        description
          "A list of available interfaces that support IOAM.";
        leaf if-name {
          type if:interface-ref;
          description "This is a reference to the Interface name.";
        }
      }
    }

    container ioam-profiles {
      description
        "Contains a list of IOAM profiles.";

      container admin-config {
        description
          "Contains all the administrative configurations related to
           the IOAM functionalities and all the IOAM profiles.";

        uses ioam-admin-config;
      }

      list ioam-profile {
        key "profile-name";
        description
          "A list of IOAM profiles that configured on the node.
           There is no mandatory type of profile (e.g.,
           incremental-trace, preallocated-trace.) in the list.
           But at least one profile should be added.";

        leaf profile-name {
          type string{
            length "1..300";
          }
          description
            "Unique identifier for each IOAM profile";
        }

        container filter {
          uses ioam-filter;
          description
            "The filter which is used to indicate the flow to apply
            IOAM.";
        }

        leaf protocol-type {
          type ioam-protocol-type;
          description
            "This item is used to indicate the carrier protocol where
            the IOAM is applied.";
        }

        container incremental-tracing-profile {
          if-feature incremental-trace;
          description
            "It describes the profile for incremental tracing option.";

          leaf enabled {
            type boolean;
            default false;
            description
              "When true, apply incremental tracing option to the
               specified flow identified by the filter.";
          }

          uses ioam-incremental-tracing-profile;
        }

        container preallocated-tracing-profile {
          if-feature preallocated-trace;
          description
            "It describes the profile for preallocated tracing option.";

          leaf enabled {
            type boolean;
            default false;
            description
              "When true, apply preallocated tracing option to the
               specified flow identified by the following filter.";
          }

          uses ioam-preallocated-tracing-profile;
        }

        container pot-profile {
          if-feature proof-of-transit;
          description
            "It describes the profile for PoT option.";

          leaf enabled {
            type boolean;
            default false;
            description
              "When true, apply Proof of Transit option to the
               specified flow identified by the following filter.";
          }

          leaf pot-type {
            type ioam-pot-type;
            description
              "The type of a particular POT variant that specifies
               the POT data that is included.";
          }
        }

        container e2e-profile {
          if-feature edge-to-edge;
          description
            "It describes the profile for e2e option";

          leaf enabled {
            type boolean;
            default false;
            description
              "When true, apply edge-to-edge option to the
               specified flow identified by the following filter.";
          }

          uses ioam-e2e-profile;
        }
      }
    }
  }
}
