module ietf-sfc-oam {
     namespace "urn:ietf:params:xml:ns:yang:ietf-sfc-oam";
     prefix sfcoam;
     import ietf-gen-oam {
       prefix goam;
     }
     import service-function  {
       prefix sfc-sf;
     }
     import service-function-path  {
       prefix sfc-sfp;
     }
     import service-function-forwarder  {
       prefix sfc-sff;
     }
      organization

       "IETF SFC Working Group";

      contact
          "TBD";
      description
          "The YANG module defines a SFC OAM configuration
          model.";

     revision "2015-12-10" {
       description
       "Initial revision";
           reference
           "foo";
     }

     identity sfc {
       base goam:technology-types;
       description
       "sfc type";
     }

     typedef SFC-layer {
       type enumeration {
       enum "Service function layer" {
         value 0;
                 description
                 "service function layer.";
       }
       enum "SFC forwarding layer" {
         value 1;
                 description
                 "SFC forwarding layer";
       }
       }
           description
           "SFC layer";
     }
    augment
    "/goam:domains/goam:domain/goam:MAs/goam:MA"
    +"/goam:connectivity-context" {
      description
          "augment the generic oam yang";
       case connectivity-context-sfc {
           description
           "connectivity context sfc.";
       leaf connectivity-context-sfp {
    type leafref {
      path "/sfc-sfp:service-function-paths/" +
        "sfc-sfp:service-function-path/sfc-sfp:name";
    }
         description
                 "connectivity context sfcp.";
       }
       }

    }
    augment
    "/goam:domains/goam:domain/goam:MAs"
   +"/goam:MA/goam:MEP/goam:mp-address" {
      description
          "augment the generic oam yang";
       case sf-mep-address {
       description

       "Service function (or service function forwarder) address plus
    service function path id to identify one SFC MEP. A SFC MP can be a
    service function or service function forwarder!";
       container sf-mep-addr{
                   description
           "container of sf-mep-addr";
       leaf sf-mep-ref {
         when "/goam:domains/goam:domain/goam:technology='sfc'"{
                 description
         "when technology = sfc.";
                 }
    type leafref {
      path "/sfc-sf:service-functions/sfc-sf:service-function/"
          + "sfc-sf:name";
    }
                 description
                 "sf mep reference.";
       }

       leaf sfp-mep-ref {
         when "/goam:domains/goam:domain/goam:technology='sfc'"{
                 description
         "when technology = sfc.";
                 }
    type leafref {
      path "/sfc-sfp:service-function-paths/" +
        "sfc-sfp:service-function-path/sfc-sfp:name";
    }
                 description
                 "sfp mep reference.";
       }
       }
           }

       case sff-mep-address {
       description

       "Service function address plus service function path id to
       identify one SFC MEP. A SFC MP can be a service function or service
       function forwarder!";

       leaf sff-mep-ref {
     type leafref {
       path "/sfc-sff:service-function-forwarders/sfc-sff:service-function-forwarder/"
           + "sfc-sff:name";
     }
                 description
                 "sff mep reference";
       }

       leaf sfp-mep-ref {
    type leafref {
      path "/sfc-sfp:service-function-paths/" +
        "sfc-sfp:service-function-path/sfc-sfp:name";
    }
                 description
                 "sfp mep reference.";
       }
       }
     }
     augment
    "/goam:domains/goam:domain/goam:MAs/goam:MA/goam:MEP/goam:session"
    +"/goam:destination-mep-address/goam:mp-address" {
      description
          "augment the generic oam yang";
       case sf-mep-address {

       leaf sf-mep-ref {
    type leafref {
      path "/sfc-sf:service-functions/sfc-sf:service-function/"
          + "sfc-sf:name";
    }
                 description
                 "sf mep reference";
       }

       leaf sfp-mep-ref {
    type leafref {
      path "/sfc-sfp:service-function-paths/" +
        "sfc-sfp:service-function-path/sfc-sfp:name";
    }
                 description
                 "sfp mep reference";
       }
       }

       case sff-mep-address {
       leaf sff-mep-ref {
     type leafref {
       path "/sfc-sff:service-function-forwarders/sfc-sff:service-function-forwarder/"
           + "sfc-sff:name";
     }
                 description
                 "sff mep reference";
       }

       leaf sfp-mep-ref {
    type leafref {
      path "/sfc-sfp:service-function-paths/" +
        "sfc-sfp:service-function-path/sfc-sfp:name";
    }
                 description
                 "sfp mep reference";
       }
           description
           "sff mep address";
       }
     }
     augment
    "/goam:domains/goam:domain/goam:MAs/goam:MA/goam:MEP"
   +"/goam:session/goam:connectivity-context" {
      description
          "augment the generic oam yang";
       case connectivity-context-sfc {
      leaf connectivity-context-sfp {
    type leafref {
      path "/sfc-sfp:service-function-paths/" +
        "sfc-sfp:service-function-path/sfc-sfp:name";
    }
                 description
                 "connectivity context sfc.";
       }
           description
           "connectivity context sfc.";
       }
     }

     //SFC extension of contiuity-check part

     /*
  augment "/goam:continuity-check/goam:input"
 +"/goam:source-mep/goam:mp-address" {
      description
          "augment the generic oam yang";
       case sf-mep-address {
       leaf sf-mep-ref {
    type leafref {
      path "/sfc-sf:service-functions/sfc-sf:service-function/"
          + "sfc-sf:name";
    }
       }

       leaf sfp-mep-ref {
      type leafref {
      path "/sfc-sfp:service-function-paths/" +
        "sfc-sfp:service-function-path/sfc-sfp:name";
    }
       }
       }

       case sff-mep-address {
       leaf sff-mep-ref {
     type leafref {
       path "/sfc-sff:service-function-forwarders/sfc-sff:service-function-forwarder/"
           + "sfc-sff:name";
     }
       }

       leaf sfp-mep-ref {
    type leafref {
      path "/sfc-sfp:service-function-paths/" +
        "sfc-sfp:service-function-path/sfc-sfp:name";
    }
       }
       }
     }*/

     augment "/goam:continuity-check/goam:input"
    +"/goam:destination-mp/goam:mp-address" {
      description
          "augment the generic oam yang";
       case sf-mep-address {
       leaf sf-mep-ref {
    type leafref {
      path "/sfc-sf:service-functions/sfc-sf:service-function/"
          + "sfc-sf:name";
    }
                 description
                 "sf mep reference";
       }

       leaf sfp-mep-ref {
    type leafref {
      path "/sfc-sfp:service-function-paths/" +
        "sfc-sfp:service-function-path/sfc-sfp:name";
    }
                 description
                 "sfp mep reference";
       }
           description
           "sf mep address";
       }
       case sff-mep-address {

       leaf sff-mep-ref {
     type leafref {
       path "/sfc-sff:service-function-forwarders/sfc-sff:service-function-forwarder/"
           + "sfc-sff:name";
     }
                 description
                 "sff mep reference";
       }
       leaf sfp-mep-ref {
    type leafref {
      path "/sfc-sfp:service-function-paths/" +
        "sfc-sfp:service-function-path/sfc-sfp:name";
    }
                 description
                 "sfp mep reference";
       }
           description
           "sff mep address";
       }
     }

     //SFC extension of connectity-verification part
/*
    augment "/goam:connectivity-verification"
    +"/goam:input/goam:source-mep/goam:mp-address" {
      description
          "augment the generic oam yang";
       case sf-mep-address {
       leaf sf-mep-ref {
    type leafref {
      path "/sfc-sf:service-functions/sfc-sf:service-function/"
          + "sfc-sf:name";
    }
       }

       leaf sfp-mep-ref {
    type leafref {
      path "/sfc-sfp:service-function-paths/" +
        "sfc-sfp:service-function-path/sfc-sfp:name";
    }
       }
       }

       case sff-mep-address {
       leaf sff-mep-ref {
     type leafref {
       path "/sfc-sff:service-function-forwarders/sfc-sff:service-function-forwarder/"
           + "sfc-sff:name";
     }
       }

       leaf sfp-mep-ref {
    type leafref {
      path "/sfc-sfp:service-function-paths/" +
        "sfc-sfp:service-function-path/sfc-sfp:name";
    }
       }
       }
     }*/

     augment "/goam:continuity-verification"
    +"/goam:input/goam:destination-mp/goam:mp-address" {
      description
          "augment the generic oam yang";
       case sf-mep-address {
       leaf sf-mep-ref {
    type leafref {
      path "/sfc-sf:service-functions/sfc-sf:service-function/"
          + "sfc-sf:name";
    }
                description
                "sf mep reference";
       }

       leaf sfp-mep-ref {
    type leafref {
      path "/sfc-sfp:service-function-paths/" +
        "sfc-sfp:service-function-path/sfc-sfp:name";
    }
                 description
                 "sfp mep reference";
       }
           description
           "sf mep address";
       }

       case sff-mep-address {
       leaf sff-mep-ref {
     type leafref {
       path "/sfc-sff:service-function-forwarders/sfc-sff:service-function-forwarder/"
           + "sfc-sff:name";
     }
                 description
                 "sff mep reference";
       }

       leaf sfp-mep-ref {
    type leafref {
      path "/sfc-sfp:service-function-paths/" +
        "sfc-sfp:service-function-path/sfc-sfp:name";
    }
                 description
                 "sfp mep reference";
       }
           description
           "sff mep address";
       }
     }

     //SFC extension of path-discovery part

    augment "/goam:path-discovery/goam:input" {
       description
       "adds SFC specific items on the input";
       leaf path-discovery-layer {
       type SFC-layer;

       description
         "Identifying which SFC layer to run path discovery";
       }

     }

     /*augment "/goam:path-discovery/goam:input"
     +"/goam:source-mep/goam:mp-address" {
      description
          "augment the generic oam yang";
       case sf-mep-address {
       leaf sf-mep-ref {
    type leafref {
      path "/sfc-sf:service-functions/sfc-sf:service-function/"
          + "sfc-sf:name";
    }
       }

       leaf sfp-mep-ref {
    type leafref {
      path "/sfc-sfp:service-function-paths/" +
        "sfc-sfp:service-function-path/sfc-sfp:name";
    }
       }
       }

       case sff-mep-address {
       leaf sff-mep-ref {
     type leafref {
       path "/sfc-sff:service-function-forwarders/sfc-sff:service-function-forwarder/"
           + "sfc-sff:name";
     }
       }

       leaf sfp-mep-ref {
    type leafref {
      path "/sfc-sfp:service-function-paths/" +
        "sfc-sfp:service-function-path/sfc-sfp:name";
    }
       }
       }
     }*/

     augment "/goam:path-discovery/goam:input"
     +"/goam:destination-mp/goam:mp-address" {
      description
          "augment the generic oam yang";
       case sf-mep-address {
       leaf sf-mep-ref {
    type leafref {
      path "/sfc-sf:service-functions/sfc-sf:service-function/"
          + "sfc-sf:name";
    }
                 description
                 "sf mep reference";
       }

       leaf sfp-mep-ref {
    type leafref {
      path "/sfc-sfp:service-function-paths/" +
        "sfc-sfp:service-function-path/sfc-sfp:name";
    }
                 description
                 "sfp mep reference";
       }
           description
           "sf mep address";
       }
       case sff-mep-address {
       leaf sff-mep-ref {
     type leafref {
       path "/sfc-sff:service-function-forwarders/sfc-sff:service-function-forwarder/"
           + "sfc-sff:name";
     }
                 description
                 "sff mep reference";
       }

       leaf sfp-mep-ref {
    type leafref {
      path "/sfc-sfp:service-function-paths/" +
        "sfc-sfp:service-function-path/sfc-sfp:name";
    }
                 description
                 "sfp mep reference";
       }
       description
           "sff mep address";
       }
     }

    augment "/goam:path-discovery/goam:output"
    +"/goam:response/goam:destination-mp/goam:mp-address" {
      description
          "augment the generic oam yang";
       case sf-mep-address {
       leaf sf-mep-ref {
    type leafref {
      path "/sfc-sf:service-functions/sfc-sf:service-function/"
          + "sfc-sf:name";
    }
                 description
                 "sf mep reference";
       }

       leaf sfp-mep-ref {
    type leafref {
      path "/sfc-sfp:service-function-paths/" +
        "sfc-sfp:service-function-path/sfc-sfp:name";
    }
       description
           "sfp mep reference";
           }
           description
           "sf mep address";
       }
       case sff-mep-address {
       leaf sff-mep-ref {
     type leafref {
       path "/sfc-sff:service-function-forwarders/sfc-sff:service-function-forwarder/"
           + "sfc-sff:name";
     }
                 description
                 "sff mep reference";
       }

       leaf sfp-mep-ref {
    type leafref {
      path "/sfc-sfp:service-function-paths/" +
        "sfc-sfp:service-function-path/sfc-sfp:name";
    }
                 description
                 "sfp mep reference";
       }
           description
           "sff mep address";
       }
     }

     //SFC extension of performance-measurement part
    /*
    augment "/goam-rpc:initiated-performance-measurement/goam-
    rpc:input/goam-rpc:source-mep/goam-rpc:mp-address" {
      description
          "augment the generic oam yang";
       case sf-mep-address {
       leaf sf-mep-ref {
    type leafref {
      path "/sfc-sf:service-functions/sfc-sf:service-function/"
          + "sfc-sf:name";
    }
       }

       leaf sfp-mep-ref {
    type leafref {
      path "/sfc-sfp:service-function-paths/" +
        "sfc-sfp:service-function-path/sfc-sfp:name";
    }
       }
       }

       case sff-mep-address {
       leaf sff-mep-ref {
     type leafref {
       path "/sfc-sff:service-function-forwarders/sfc-sff:service-function-forwarder/"
           + "sfc-sff:name";
     }
       }
       leaf sfp-mep-ref {
    type leafref {
      path "/sfc-sfp:service-function-paths/" +
        "sfc-sfp:service-function-path/sfc-sfp:name";
    }
       }

       }
     }*/
     }
