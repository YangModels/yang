module ietf-i2rs-service-topology{
namespace "urn:ietf:params:xml:ns:yang:ietf-i2rs-service-topology";
prefix i2rs-st;

import ietf-inet-types {
   prefix inet;
}

import ietf-network {
   prefix nw;
}
import ietf-network-topology {
  prefix "nt";
}

organization "IETF";
  contact
   "email: shares@ndzh.com;
    email: linda.dunbar@huawei.com;
        ";

  description
    "This module defines a model
         for the service topology.";

 revision 2016-01-03{
   description
     "Version 1 - initial version;
          Version 2 - yang format fixed";

  reference "draft-hares-i2rs-service-topo-dm-01.txt";
 }

     identity svc-topo-flag-identity {
       description "Base type for svc flags";
       }
     identity l3vpn-svc-topo {
       base svc-topo-flag-identity;
       description "L3VPN service type";
      }
     identity l2vpn-svc-topo {
       base svc-topo-flag-identity;
       description "L2VPN service type";
      }
      identity EVPN-svc-topo {
       base svc-topo-flag-identity;
       description "EVPN service type";
      }
       identity Seamless-MPLS-svc-topo {
       base svc-topo-flag-identity;
       description "Seamless MPLS service type";
      }
       identity Etree-svc-topo {
       base svc-topo-flag-identity;
       description "Seamless MPLS service type";
      }
       identity I2rs-svc-topo {
       base svc-topo-flag-identity;
       description "I2RS create service topo";
      }

     identity svc-tp-type {
       description "Base type for service
         termination-point type flags";
       }
     identity svc-tp-type-service {
       base svc-tp-type;
       description "service type";
      }
     identity svc-tp-type-ip {
       base svc-tp-type;
       description "service IP";
      }
     identity svc-tp-type-unnum {
               base svc-tp-type;
       description "service unnumbered link";
      }

          identity service-topology-types{
           description
               "service topology type";
          }

     grouping service-topology-types {
      leaf service-type {
           type identityref {
           base svc-topo-flag-identity;
          }
          description "list of service
                    topology type supported";
        }
                description
                "service topology types";
     }

     grouping service-topology-attributes {
             leaf name {
                           type string;
               description "name of service
                     topology";
                         }
             leaf composite-flag {
               type identityref {
                  base service-topology-types;
                                }
                description "other topologies
                this topology is configured to
                be a composite of
                (L3VPN, L2VPN, I2RS only)";
             }
             leaf service-topo-id {
                 type nw:network-id;
                                 description  "service topology id
                 to a service topology instance.";
              }
              leaf service-id-number {
                 type uint32;
                 description "ID for topology";
             }
             leaf node-count {
                type uint32;
                description "count of service level nodes
                 in the network.";
               }
             leaf composite-flag-status {
               type identityref {
                  base svc-topo-flag-identity;}
                description "other topologies
                this topology is currently a
                 composite of
                (L3VPN, L2VPN, I2RS only)";
             }
               description  "Group of attributes for
             service topology";
     }

     grouping node-svc-attribute {
       leaf domain-name{
          type inet:domain-name;
          description "Domain name for node";
       }
       leaf composite-flag {
         type identityref {
            base svc-topo-flag-identity;
                 }
         description "virtual network
          node can be composite of the
          topologies list
          (L3VPN, L2VPN, I2RS only)";
          }
       leaf service-node-id {
          type uint32;
          description "ID for node at
            service level";
       }
       leaf node-svc_status {
          type identityref {
            base service-topology-types;
                  }
          description "other topologies
            this topology is currewntly
            be composed of
                        (L3VPN, L2VPN, I2RS only)";
       }
          description
          "grouping of composite flag";
     }

       grouping service-link-attributes {
       leaf name {
                 type string;
         description "name of
           service link";
               }
       leaf link-id {
                 type uint32;
                 description "link id";
               }
       leaf svc-link-type {
         type identityref {
            base service-topology-types;
                 }
         description "other topologies
           this link is current a
                       composite of
           (L3VPN, L2VPN, I2RS only)";
       }
       leaf metric {
         type uint32;
         description "link metric
                   which may need to expand or
                        link to TE topologies.";
       }
           description "grouping of
                service link attribute";
     }

 grouping service-termination-point-attributes {
       leaf svc-tp-id {
           type uint32;
           description "termination point id";
        }
       container supporting-termination-point {
         leaf svc-tp-type {
           type identityref {
             base svc-tp-type;
                       }
         description "other topologies
           this link termination point is
           part of (L3VPN, L2VPN,
                   or I2RS only)";
                 }
         choice svc-tp-support-type{
           case svc-tp-type-service {

             leaf service-network-id {
               type uint32;
               description "service network id";
                      }
             leaf service-node-id {
               type uint32;
                               description "service node id";
                         }
             leaf service-link-id {
               type uint32;
                               description "service link id";
                         }
                         description "network, node,
                tp that supports this
                termination point";
                       }
           case svc-tp-type-inet {
             leaf ip-address{
                           type inet:ip-address;
                           description "ip address";
                         }
                         description "inet svc tp";
           }

                       case svc-tp-type-unnum {
             leaf unnumbered-id {
               type uint32;
                           description "unnumbered id";
                         }
                        description "unnumber svc tp";
                       }
                  description "service termination
                      point type cases";
         }
       description "container of
              supporting termination point";
       }
               description
               "grouping of service-termination-point-attributes";
     }

     /*
      * Data nodes
      */
           augment "/nw:networks/nw:network/nw:network-types"{
       uses service-topology-types;
               description
               "augment the network-tpyes with
               the service-topology-types grouping";
               }
     augment "/nw:networks/nw:network/nw:node" {
          leaf name {
          type inet:domain-name;
           description "service name.";
          }
          list composite_fag {
            key "service-node-id";
            leaf service-node-id{
              type uint32;
              description "service node id.";
            }
            leaf node-svc-type{
              type string;
              description "node service type.";
             }
          leaf-list next-hop{
            type uint32;
            description "next hop id.";
          }
          description
            "the list of composite flag.";
         }

        description "augments node list";
        }

 augment "/nw:networks/nw:network"{
      uses service-topology-attributes;
          description
          "augment the network with
          the servcie-topolgoy-attributes";
          }
 augment "/nw:networks/nw:network/nw:node"{
     uses node-svc-attribute;
         description
         "augment the node with the node-svc-attribute";
         }
 augment "/nw:networks/nw:network/nt:link" {
   uses service-link-attributes;
       description
       "augment the link with
       service-link-attributes";
       }
augment "/nw:networks/nw:network/nw:node/nt:termination-point"{
   uses service-termination-point-attributes;
       description
       "augment the termination-point with
       service-termination-point-attributes";
       }
} // module i2rs-service-topology
