module ietf-collected-data-manifest {
  yang-version 1.1;
  namespace
    "urn:ietf:params:xml:ns:yang:ietf-collected-data-manifest";
  prefix data-manifest;

  import ietf-datastores {
    prefix ds;
    reference
      "RFC 8342: Network Management Datastore Architecture.";
  }
  import ietf-yang-types {
    prefix yang;
    reference
      "RFC 6991: Common YANG Data Types";
  }

  organization
    "IETF OPSAWG (Network Configuration) Working Group";
  contact
    "WG Web:   <https://datatracker.ietf.org/wg/opsawg/>
     WG List:  <mailto:opsawg@ietf.org>
     Author:   Benoit Claise  <mailto:benoit.claise@huawei.com>
     Author:   Jean Quilbeuf   <mailto:jean.quilbeuf@huawei.com>";
  description
    "This module describes the context of data collection from a
     given network element. The contents of this model must be
     streamed along with the data streamed from the network
     element so that the context of the data collection can
     be retrieved later.

     This module must be completed with
     ietf-collected-data-platform-manifest
     to capture the whole context of a data collection session.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";

  revision 2021-10-15 {
    description
      "Initial revision";
    reference
      "RFC xxxx: Title to be completed";
  }

  container data-collection {
    config false;
    description
      "Defines the information for each collected object";
    list mdt-subscriptions {
      key "subscription-id";
      description
        "Contains the list of current subscriptions on the
         local device. Enables the collector to select its own
         subscriptions in the list.";
      leaf subscription-id {
        type uint64;
        description
          "Id of the subscription generated by the telemetry emitter.
           The collector can use this id to retrieve information
           about the collection status for the corresponding paths.

           The type is inspired by openconfig-telemetry. TODO check if
           ietf has telemetry modules that we could leafref to.

           path to subscription id in openconfig:
           openconfig-telemetry:telemetry-system/subscriptions/
            persistent-subscriptions/persistent-subscription/state/oid";
      }
      leaf datastore {
        type ds:datastore-ref;
        description
          "The datastore from which the data for this subscription has
           been collected.";
      }
      list mdt-path-data-manifest {
        key "path";
        description
          "Status of the collection for the given path";
        leaf path {
          type yang:xpath1.0;
          description
            "The XPath context in which this XPath expression is
             evaluated is the datastore selected for the containing
             subscription object. If the datastore is not specified
             then the context is the operational datastore context.";
        }
        leaf requested-period {
          when "../on-change = 'false'";
          type uint64;
          description
            "Requested period, in millisecond, between two successive
             updates.";
        }
        leaf actual-period {
          when "../on-change = 'false'";
          type uint64;
          description
            "Period in milisecond between two successive updates
             actually applied by the plaftorm at configuration time.
             This period can be larger than the requested period as the
             platform might adjust it for performance reasons.";
        }
        leaf on-change {
          type boolean;
          description
            "Whether the path is collected only when there is a
             change, i.e. Event-Driven Telemetry is enabled.";
        }
        leaf suppress-redundancy {
          type boolean;
          description
            "Whether the information is sent at every period or only
             when there is a change between two successive pollings.";
        }
      }
      // we could augment here with other kind of collection items
    }
  }
}
