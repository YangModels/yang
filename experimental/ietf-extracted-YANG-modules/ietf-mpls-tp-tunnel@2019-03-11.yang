module ietf-mpls-tp-tunnel {
  //yang-version 1.1;

  namespace "urn:ietf:params:xml:ns:yang:ietf-mpls-tp-tunnel";
  prefix "mpls-tp-tunnel";

  import ietf-te {
    prefix "te";
  }

  import ietf-mpls-tp-types {
    prefix "mpls-tp-types";
  }
  organization
    "Internet Engineering Task Force (IETF) TEAS WG";
  contact
    "
      WG List: <mailto:teas@ietf.org>

      ID-draft editor:
        Italo Busi (italo.busi@huawei.com);
        Haomian Zheng (zhenghaomian@huawei.com);
    ";
  description
    "This module defines technology-specific MPLS-TP tunnel
     data model.";
  revision 2019-03-11 {
    description
      "version -00 as an I-D";
    reference
      "draft-busizheng-teas-mpls-tp-yang";
  }
  augment "/te:te/te:tunnels/te:tunnel/"
        + "te:te-bandwidth/te:technology" {
    description "MPLS-TP bandwidth.";
    case mpls-tp {
      uses mpls-tp-types:mpls-tp-path-bandwidth;
    }
  }

  augment "/te:te/te:tunnels/te:tunnel/"
        + "te:p2p-primary-paths/te:p2p-primary-path/"
        + "te:computed-paths-properties/"
        + "te:computed-path-properties/"
        + "te:path-properties/te:path-route-objects/"
        + "te:path-computed-route-object/te:type/te:label/"
        + "te:label-hop/te:te-label/te:technology" {
    description "MPLS-TP label.";
    case mpls-tp {
      uses mpls-tp-types:mpls-tp-path-label;
    }
  }

  augment "/te:te/te:tunnels/te:tunnel/"
        + "te:p2p-primary-paths/te:p2p-primary-path/"
        + "te:lsps/te:lsp/"
        + "te:path-properties/te:path-route-objects/"
        + "te:path-computed-route-object/te:type/te:label/"
        + "te:label-hop/te:te-label/te:technology" {
    description "MPLS-TP label.";
    case mpls-tp {
      uses mpls-tp-types:mpls-tp-path-label;
    }
  }

  augment "/te:te/te:tunnels/te:tunnel/"
        + "te:p2p-secondary-paths/te:p2p-secondary-path/"
        + "te:computed-paths-properties/"
        + "te:computed-path-properties/"
        + "te:path-properties/te:path-route-objects/"
        + "te:path-computed-route-object/te:type/te:label/"
        + "te:label-hop/te:te-label/te:technology" {
    description "MPLS-TP label.";
    case mpls-tp {
      uses mpls-tp-types:mpls-tp-path-label;
    }
  }

  augment "/te:te/te:tunnels/te:tunnel/"
        + "te:p2p-secondary-paths/te:p2p-secondary-path/"
        + "te:lsps/te:lsp/"
        + "te:path-properties/te:path-route-objects/"
        + "te:path-computed-route-object/te:type/te:label/"
        + "te:label-hop/te:te-label/te:technology" {
    description "MPLS-TP label.";
    case mpls-tp {
      uses mpls-tp-types:mpls-tp-path-label;
    }
  }
}
