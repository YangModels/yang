module ietf-https-notif-transport {
  yang-version 1.1;
  namespace "urn:ietf:params:xml:ns:yang:ietf-https-notif-transport";
  prefix "hnt";

  import ietf-x509-cert-to-name {
    prefix x509c2n;
    reference
      "RFC 7407: YANG Data Model for SNMP Configuration.";
  }

  import ietf-subscribed-notifications {
    prefix sn;
    reference
      "RFC 8639: Subscription to YANG Notifications";
  }

  import ietf-subscribed-notif-receivers {
    prefix snr;
    reference
      "RFC XXXX: An HTTPS-based Transport for
                 Configured Subscriptions";
  }

  import ietf-http-client {
    prefix httpc;
    reference
      "RFC YYYY: YANG Groupings for HTTP Clients and HTTP Servers";
  }

  organization
    "IETF NETCONF Working Group";

  contact
    "WG Web:   <http://tools.ietf.org/wg/netconf>
     WG List:  <netconf@ietf.org>

     Authors: Mahesh Jethanandani (mjethanandani at gmail dot com)
              Kent Watsen (kent plus ietf at watsen dot net)";

  description
    "This YANG module is implemented by Publishers that implement
     the 'ietf-subscribed-notifications' module defined in RFC 8639.

     This module augments a 'case' statement called 'https' into
     the 'choice' statement called 'transport-type' defined
     by the 'ietf-https-notif-transport' module defined in RFC XXXX.

     Copyright (c) 2022 IETF Trust and the persons identified as
     the document authors.  All rights reserved.
     Redistribution and use in source and binary forms, with or
     without modification, is permitted pursuant to, and subject
     to the license terms contained in, the Revised BSD
     License set forth in Section 4.c of the IETF Trust's Legal
     Provisions Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "2022-07-18" {
    description
      "Initial Version.";
    reference
      "RFC XXXX: An HTTPS-based Transport for YANG Notifications.";
  }

  feature receiver-identity {
    description
      "Indicates that the server supports filtering notifications
       based on the receiver's identity derived from its TLS
       certificate.";
  }

  identity https {
    base sn:transport;
    description
      "HTTPS transport for notifications.";
  }

  grouping https-receiver-grouping {
    description
      "A grouping that may be used by other modules wishing to
       configure HTTPS-based notifications without using RFC 8639.";
    uses httpc:http-client-stack-grouping {
      refine "transport/tcp" {
        // create the logical impossibility of enabling the
        // "tcp" transport (i.e., "HTTP" without the 'S').
        if-feature "not httpc:tcp-supported";
      }
      augment "transport/tls/tls/http-client-parameters" {
        leaf path {
          type string;
          mandatory true;
          description
            "A path to the target resources.  Under this
             path the receiver must support both the 'capabilities'
             and 'relay-notification' resource targets, as described
             in RFC XXXX.";
        }
        description
          "Augmentation to add a receiver-specific path for the
           'capabilities' and 'relay-notification' resources.";
      }
    }
    container receiver-identity {
      if-feature receiver-identity;
      description
        "Maps the receiver's TLS certificate to a local identity
         enabling access control to be applied to filter out
         notifications that the receiver may not be authorized
         to view.";
      container cert-maps {
        uses x509c2n:cert-to-name;
        description
          "The cert-maps container is used by a TLS-based HTTP
           server to map the HTTPS client's presented X.509
           certificate to a 'local' username. If no matching and
           valid cert-to-name list entry is found, the publisher
           MUST close the connection, and MUST NOT not send any
           notifications over it.";
        reference
          "RFC 7407: A YANG Data Model for SNMP Configuration.";
      }
    }
  }

  augment "/sn:subscriptions/snr:receiver-instances/" +
          "snr:receiver-instance/snr:transport-type" {
    case https {
      container https-receiver {
        description
          "The HTTPS receiver to send notifications to.";
        uses https-receiver-grouping;
      }
    }
    description
      "Augment the transport-type choice to include the 'https'
       transport.";
  }
}
