module ietf-i2nsf-monitor {
    yang-version 1.1;
    namespace
      "urn:ietf:params:xml:ns:yang:ietf-i2nsf-monitor";
    prefix
      iim;
    import ietf-inet-types{
      prefix inet;
      reference
        "Section 4 of RFC 6991";
    }
    import ietf-yang-types {
      prefix yang;
      reference
        "Section 3 of RFC 6991";
    }
    organization
      "IETF I2NSF (Interface to Network Security Functions)
       Working Group";
    contact
      "WG Web: <http://tools.ietf.org/wg/i2nsf>
       WG List: <mailto:i2nsf@ietf.org>

       WG Chair: Linda Dunbar
       <mailto:Linda.duhbar@huawei.com>

       Editor: Jaehoon Paul Jeong
       <mailto:pauljeong@skku.edu>

       Editor: Chaehong Chung
       <mailto:darkhong@skku.edu>";

    description
      "This module is a YANG module for monitoring NSFs.

      Copyright (c) 2018 IETF Trust and the persons identified as
      authors of the code. All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC 6087; see
      the RFC itself for full legal notices.";

    revision "2019-07-23" {
      description "First revision";
      reference
        "RFC XXXX: I2NSF NSF Monitoring YANG Data Model";
    }

    typedef severity {
      type enumeration {
        enum high {
          description
            "high-level";
        }
        enum middle {
          description
            "middle-level";
        }
        enum low {
          description
            "low-level";
        }
      }
      description
        "An indicator representing severity";
    }
    typedef log-action {
      type enumeration {
        enum allow {
          description
            "If action is allowed";
        }
        enum alert {
          description
            "If action is alert";
        }
        enum block {
          description
            "If action is block";
        }
        enum discard {
          description
            "If action is discarded";
        }
        enum declare {
          description
            "If action is declared";
        }
        enum block-ip {
          description
            "If action is block-ip";
        }
        enum block-service{
          description
            "If action is block-service";
        }
      }
      description
        "This is used for protocol";
    }
    typedef dpi-type{
      type enumeration {
        enum file-blocking{
          description
            "DPI for blocking file";
        }
        enum data-filtering{
          description
            "DPI for filtering data";
        }
        enum application-behavior-control{
          description
            "DPI for controlling application behavior";
        }
      }
      description
        "This is used for dpi type";
    }
    typedef operation-type{
      type enumeration {
        enum login{
          description
            "Login operation";
        }
        enum logout{
          description
            "Logout operation";
        }
        enum configuration{
          description
            "Configuration operation";
        }
      }
      description
        "An indicator representing operation-type";
    }
    typedef login-mode{
      type enumeration {
        enum root{
          description
            "Root login-mode";
        }
        enum user{
          description
            "User login-mode";
        }
        enum guest{
          description
            "Guest login-mode";
        }
      }
      description
        "An indicator representing login-mode";
    }

    identity characteristics {
      description
      "Base identity for monitoring information
      characteristics";
    }
    identity acquisition-method {
      base characteristics;
      description
      "The type of acquisition-method. Can be multiple
      types at once.";
    }
    identity subscription {
      base acquisition-method;
      description
      "The acquisition-method type is subscription";
    }
    identity query {
      base acquisition-method;
      description
      "The acquisition-method type is query";
    }
    identity emission-type {
      base characteristics;
      description
      "The type of emission-type.";
    }
    identity periodical {
      base emission-type;
      description
      "The emission-type type is periodical.";
    }
    identity on-change {
      base emission-type;
      description
      "The emission-type type is on-change.";
    }
    identity dampening-type {
      base characteristics;
      description
      "The type of dampening-type.";
    }
    identity no-dampening {
      base dampening-type;
      description
      "The dampening-type is no-dampening.";
    }
    identity on-repetition {
      base dampening-type;
      description
      "The dampening-type is on-repetition.";
    }
    identity none {
      base dampening-type;
      description
      "The dampening-type is none.";
    }

    identity authentication-mode {
      description
        "User authentication mode types:
         e.g., Local Authentication,
         Third-Party Server Authentication,
         Authentication Exemption, or Single Sign-On (SSO)
         Authentication.";
    }
    identity local-authentication {
      base authentication-mode;
      description
        "Authentication-mode : local authentication.";
    }
    identity third-party-server-authentication {
      base authentication-mode;
      description
        "If authentication-mode is
        third-part-server-authentication";
    }
    identity exemption-authentication {
      base authentication-mode;
      description
      "If authentication-mode is
      exemption-authentication";
    }
    identity sso-authentication {
      base authentication-mode;
      description
      "If authentication-mode is
      sso-authentication";
    }

    identity alarm-type {
      description
        "Base identity for detectable alarm types";
    }
    identity MEM-USAGE-ALARM {
      base alarm-type;
      description
      "A memory alarm is alerted";
    }
    identity CPU-USAGE-ALARM {
      base alarm-type;
      description
      "A CPU alarm is alerted";
    }
    identity DISK-USAGE-ALARM {
      base alarm-type;
      description
      "A disk alarm is alerted";
    }
    identity HW-FAILURE-ALARM {
      base alarm-type;
      description
      "A hardware alarm is alerted";
    }
    identity IFNET-STATE-ALARM {
      base alarm-type;
      description
      "An interface alarm is alerted";
    }
    identity event-type {
      description
        "Base identity for detectable event types";
    }
    identity ACCESS-DENIED {
      base event-type;
      description
      "The system event is access-denied.";
    }
    identity CONFIG-CHANGE {
      base event-type;
      description
      "The system event is config-change.";
    }

    identity flood-type {
      description
        "Base identity for detectable flood types";
    }
    identity syn-flood {
      base flood-type;
      description
        "A SYN flood is detected";
    }
    identity ack-flood {
      base flood-type;
      description
        "An ACK flood is detected";
    }
    identity syn-ack-flood {
      base flood-type;
      description
        "An SYN-ACK flood is detected";
    }
    identity fin-rst-flood {
      base flood-type;
      description
        "A FIN-RST flood is detected";
    }
    identity tcp-con-flood {
      base flood-type;
      description
        "A TCP connection flood is detected";
    }
    identity udp-flood {
      base flood-type;
      description
        "A UDP flood is detected";
    }
    identity icmp-flood {
      base flood-type;
      description
        "An ICMP flood is detected";
    }
    identity https-flood {
      base flood-type;
      description
        "A HTTPS flood is detected";
    }
    identity http-flood {
      base flood-type;
      description
        "A HTTP flood is detected";
    }
    identity dns-reply-flood {
      base flood-type;
      description
        "A DNS reply flood is detected";
    }
    identity dns-query-flood {
      base flood-type;
      description
        "A DNS query flood is detected";
    }
    identity sip-flood {
      base flood-type;
      description
        "A SIP flood is detected";
    }

    identity nsf-event-name {
      description
      "Base identity for detectable nsf event types";
    }
    identity SEC-EVENT-DDOS {
      base nsf-event-name;
      description
      "The nsf event is sec-event-ddos.";
    }
    identity SESSION-USAGE-HIGH {
      base nsf-event-name;
      description
      "The nsf event is session-usage-high";
    }
    identity SEC-EVENT-VIRUS {
      base nsf-event-name;
      description
      "The nsf event is sec-event-virus";
    }
    identity SEC-EVENT-INTRUSION {
      base nsf-event-name;
      description
      "The nsf event is sec-event-intrusion";
    }
    identity SEC-EVENT-BOTNET {
      base nsf-event-name;
      description
      "The nsf event is sec-event-botnet";
    }
    identity SEC-EVENT-WEBATTACK {
      base nsf-event-name;
      description
      "The nsf event is sec-event-webattack";
    }
    identity attack-type {
      description
        "The root ID of attack-based notification
        in the notification taxonomy";
    }
    identity system-attack-type {
      base attack-type;
      description
        "This ID is intended to be used
        in the context of system events";
    }
    identity nsf-attack-type {
      base attack-type;
      description
        "This ID is intended to be used
         in the context of nsf event";
    }
    identity botnet-attack-type {
      base nsf-attack-type;
      description
        "This is an ID stub limited to indicating
        that this attack type is botnet.
        The usual semantic and taxonomy is missing
        and name is used.";
    }
    identity virus-type {
      base nsf-attack-type;
      description
        "The type of virus. Can be multiple types at once.
         This attack type is associated with a detected
         system-log virus-attack";
    }
    identity trojan {
      base virus-type;
      description
        "The detected virus type is trojan";
    }
    identity worm {
      base virus-type;
      description
        "The detected virus type is worm";
    }
    identity macro {
      base virus-type;
      description
        "The detected virus type is macro";
    }
    identity intrusion-attack-type {
      base nsf-attack-type;
      description
        "The attack type is associated with
        a detected system-log intrusion";
    }
    identity brute-force {
      base intrusion-attack-type;
      description
        "The intrusion type is brute-force";
    }
    identity buffer-overflow {
      base intrusion-attack-type;
      description
        "The intrusion type is buffer-overflow";
    }
    identity web-attack-type {
      base nsf-attack-type;
      description
        "The attack type associated with
        a detected system-log web-attack";
    }
    identity command-injection {
      base web-attack-type;
      description
        "The detected web attack type is command injection";
    }
    identity xss {
      base web-attack-type;
      description
        "The detected web attack type is XSS";
    }
    identity csrf {
      base web-attack-type;
      description
        "The detected web attack type is CSRF";
    }
    identity ddos-attack-type {
      base nsf-attack-type;
      description
        "The attack type is associated with a detected
        nsf-log event";
    }

    identity req-method {
      description
        "A set of request types (if applicable).
         For instance, PUT or GET in HTTP";
    }
    identity put-req {
      base req-method;
      description
        "The detected request type is PUT";
    }
    identity get-req {
      base req-method;
      description
        "The detected request type is GET";
    }

    identity filter-type {
      description
        "The type of filter used to detect, for example,
         a web-attack. Can be applicable to more than
         web-attacks. Can be more than one type.";
    }
    identity whitelist {
      base filter-type;
      description
        "The applied filter type is whitelist";
    }
    identity blacklist {
      base filter-type;
      description
        "The applied filter type is blacklist";
    }
    identity user-defined {
      base filter-type;
      description
        "The applied filter type is user-defined";
    }
    identity balicious-category {
      base filter-type;
      description
        "The applied filter is balicious category";
    }
    identity unknown-filter {
      base filter-type;
      description
        "The applied filter is unknown";
    }

    identity access-mode {
      description
        "Base identity for detectable access mode.";
    }
    identity ppp {
      base access-mode;
      description
        "Access-mode : ppp";
    }
    identity svn {
      base access-mode;
      description
        "Access-mode : svn";
    }
    identity local {
      base access-mode;
      description
        "Access-mode : local";
    }

    identity protocol-type {
      description
        "An identity used to enable type choices in leaves
         and leaflists wrt protocol metadata.";
    }
    identity tcp {
      base ipv4;
      base ipv6;
      description
        "TCP protocol type.";
        reference
          "RFC 793: Transmission Control Protocol";
    }
    identity udp {
      base ipv4;
      base ipv6;
      description
      "UDP protocol type.";
      reference
        "RFC 768: User Datagram Protocol";
    }
    identity icmp {
      base ipv4;
      base ipv6;
      description
        "General ICMP protocol type.";
        reference
          "RFC 792: Internet Control Message Protocol";
    }
    identity icmpv4 {
      base ipv4;
      description
        "ICMPv4 protocol type.";
    }
    identity icmpv6 {
      base ipv6;
      description
        "ICMPv6 protocol type.";
    }
    identity ip {
      base protocol-type;
      description
        "General IP protocol type.";
        reference
          "RFC 791: Internet Protocol
          RFC 2460: Internet Protocol, Version 6 (IPv6)";
    }
    identity ipv4 {
      base ip;
      description
        "IPv4 protocol type.";
        reference
          "RFC 791: Internet Protocol";
    }
    identity ipv6 {
      base ip;
      description
        "IPv6 protocol type.";
        reference
          "RFC 2460: Internet Protocol, Version 6 (IPv6)";
    }
    identity http {
      base tcp;
      description
        "HTPP protocol type.";
        reference
          "RFC 2616: Hypertext Transfer Protocol";
    }
    identity ftp {
      base tcp;
      description
       "FTP protocol type.";
       reference
         "RFC 959: File Transfer Protocol";
    }
    grouping common-monitoring-data {
      description
      "The data set of common monitoring";
      leaf message {
        type string;
        description
          "This is a freetext annotation of
          monitoring notification content";
      }
      leaf time-stamp {
        type yang:date-and-time;
        description
          "Indicates the time of message generation";
      }
      leaf vendor-name {
        type string;
        description
          "The name of the NSF vendor";
      }
      leaf nsf-name {
        type string;
        description
          "The name (or IP) of the NSF
          generating the message";
      }
      leaf module-name {
        type string;
        description
          "The module name outputting the message";
      }
      leaf severity {
        type severity;
        description
          "The severity of the alarm such
          as critical, high, middle, low.";
      }
    }
    grouping characteristics{
      description
        "A set of monitoring information characteristics";
      leaf acquisition-method {
        type identityref {
          base acquisition-method;
        }
        description
          "The acquisition-method for characteristics";
      }
      leaf emission-type {
        type identityref {
          base emission-type;
        }
        description
          "The emission-type for characteristics";
      }
      leaf dampening-type {
        type identityref {
          base dampening-type;
        }
        description
          "The dampening-type for characteristics";
      }
    }
    grouping i2nsf-system-alarm-type-content {
      description
        "A set of system alarm type contents";
      leaf usage {
        type uint8;
        description
          "specifies the amount of usage";
      }
      leaf threshold {
        type uint8;
        description
          "The threshold triggering the alarm or the event";
      }
    }
    grouping i2nsf-system-event-type-content {
      description
        "System event metadata associated
         with system events caused by user activity.";
      leaf user {
        type string;
        mandatory true;
        description
          "Name of a user";
      }
      leaf group {
        type string;
        mandatory true;
        description
          "Group to which a user belongs.";
      }
      leaf login-ip-addr {
        type inet:ipv4-address;
        mandatory true;
        description
          "Login IP address of a user.";
      }
      leaf authentication {
        type identityref {
          base authentication-mode;
        }
        description
          "The authentication-mode for authentication";
      }
    }
    grouping i2nsf-nsf-event-type-content-extend {
      description
        "A set of common IPv4-related NSF event
        content elements";
      leaf src-ip {
        type inet:ipv4-address;
        description
          "The source IP address of the packet";
      }
      leaf dst-ip {
        type inet:ipv4-address;
        description
          "The destination IP address of the packet";
      }
      leaf src-port {
        type inet:port-number;
        description
          "The source port of the packet";
      }
      leaf dst-port {
        type inet:port-number;
        description
          "The destination port of the packet";
      }
      leaf src-zone {
        type string;
        description
          "The source security zone of the packet";
      }
      leaf dst-zone {
        type string;
        description
          "The destination security zone of the packet";
      }
      leaf rule-id {
        type uint8;
        mandatory true;
        description
          "The ID of the rule being triggered";
      }
      leaf rule-name {
        type string;
        mandatory true;
        description
          "The name of the rule being triggered";
      }
      leaf profile {
        type string;
        description
          "Security profile that traffic matches.";
      }
      leaf raw-info {
        type string;
        description
          "The information describing the packet
          triggering the event.";
      }
    }
    grouping i2nsf-nsf-event-type-content {
      description
        "A set of common IPv4-related NSF event
        content elements";
      leaf dst-ip {
        type inet:ipv4-address;
        description
          "The destination IP address of the packet";
      }
      leaf dst-port {
        type inet:port-number;
        description
          "The destination port of the packet";
      }
      leaf rule-id {
        type uint8;
        mandatory true;
        description
          "The ID of the rule being triggered";
      }
      leaf rule-name {
        type string;
        mandatory true;
        description
          "The name of the rule being triggered";
      }
      leaf profile {
        type string;
        description
          "Security profile that traffic matches.";
      }
      leaf raw-info {
        type string;
        description
          "The information describing the packet
          triggering the event.";
      }
    }
    grouping traffic-rates {
      description
        "A set of traffic rates
        for statistics data";
      leaf total-traffic {
        type uint32;
        description
          "Total traffic";
      }
      leaf in-traffic-ave-rate {
        type uint32;
        description
          "Inbound traffic average rate in pps";
      }
      leaf in-traffic-peak-rate {
        type uint32;
        description
          "Inbound traffic peak rate in pps";
      }
      leaf in-traffic-ave-speed {
        type uint32;
        description
          "Inbound traffic average speed in bps";
      }
      leaf in-traffic-peak-speed {
        type uint32;
        description
          "Inbound traffic peak speed in bps";
      }
      leaf out-traffic-ave-rate {
        type uint32;
        description
          "Outbound traffic average rate in pps";
      }
      leaf out-traffic-peak-rate {
        type uint32;
        description
          "Outbound traffic peak rate in pps";
      }
      leaf out-traffic-ave-speed {
        type uint32;
        description
          "Outbound traffic average speed in bps";
      }
      leaf out-traffic-peak-speed {
        type uint32;
        description
          "Outbound traffic peak speed in bps";
      }
    }
    grouping i2nsf-system-counter-type-content{
      description
        "A set of system counter type contents";
      leaf interface-name {
        type string;
        description
          "Network interface name configured in NSF";
      }
      leaf in-total-traffic-pkts {
        type uint32;
        description
          "Total inbound packets";
      }
      leaf out-total-traffic-pkts {
        type uint32;
        description
          "Total outbound packets";
      }
      leaf in-total-traffic-bytes {
        type uint32;
        description
          "Total inbound bytes";
      }
      leaf out-total-traffic-bytes {
        type uint32;
        description
          "Total outbound bytes";
      }
      leaf in-drop-traffic-pkts {
        type uint32;
        description
          "Total inbound drop packets";
      }
      leaf out-drop-traffic-pkts {
        type uint32;
        description
          "Total outbound drop packets";
      }
      leaf in-drop-traffic-bytes {
        type uint32;
        description
          "Total inbound drop bytes";
      }
      leaf out-drop-traffic-bytes {
        type uint32;
        description
          "Total outbound drop bytes";
      }
      uses traffic-rates;
    }
    grouping i2nsf-nsf-counters-type-content{
      description
        "A set of nsf counters type contents";
      leaf src-ip {
        type inet:ipv4-address;
        description
          "The source IP address of the packet";
      }
      leaf dst-ip {
        type inet:ipv4-address;
        description
          "The destination IP address of the packet";
      }
      leaf src-port {
        type inet:port-number;
        description
          "The source port of the packet";
      }
      leaf dst-port {
        type inet:port-number;
        description
          "The destination port of the packet";
      }
      leaf src-zone {
        type string;
        description
          "The source security zone of the packet";
      }
      leaf dst-zone {
        type string;
        description
          "The destination security zone of the packet";
      }
      leaf src-region {
        type string;
        description
          "Source region of the traffic";
      }
      leaf dst-region{
        type string;
        description
          "Destination region of the traffic";
      }
      leaf policy-id {
        type uint8;
        description
          "The ID of the policy being triggered";
      }
      leaf policy-name {
        type string;
        description
          "The name of the policy being triggered";
      }
      leaf src-user{
        type string;
        description
          "User who generates traffic";
      }
      leaf protocol {
        type identityref {
          base protocol-type;
        }
        description
          "Protocol type of traffic";
      }
      leaf app {
        type string;
        description
          "Application type of traffic";
      }
    }

    notification system-detection-alarm {
      description
        "This notification is sent, when a system alarm
        is detected.";
      leaf alarm-category {
        type identityref {
          base alarm-type;
        }
        description
          "The alarm category for
          system-detection-alarm notification";
      }
      uses characteristics;
      uses i2nsf-system-alarm-type-content;
      uses common-monitoring-data;
    }
    notification system-detection-event {
      description
        "This notification is sent, when a security-sensitive
         authentication action fails.";
      leaf event-category {
        type identityref {
          base event-type;
        }
        description
          "The event category for system-detection-event";
      }
      uses characteristics;
      uses i2nsf-system-event-type-content;
      uses common-monitoring-data;
    }
    notification nsf-detection-flood {
      description
        "This notification is sent,
        when a specific flood type is detected";
      leaf event-name {
        type identityref {
         base SEC-EVENT-DDOS;
        }
        description
        "The event name for nsf-detection-flood";
      }
      uses i2nsf-nsf-event-type-content;
      leaf sub-attack-type {
        type identityref {
          base flood-type;
        }
        description
          "Any one of Syn flood, ACK flood, SYN-ACK flood,
           FIN/RST flood, TCP Connection flood, UDP flood,
           Icmp flood, HTTPS flood, HTTP flood, DNS query flood,
           DNS reply flood, SIP flood, etc.";
      }
      leaf start-time {
        type yang:date-and-time;
        mandatory true;
        description
          "The time stamp indicating when the attack started";
      }
      leaf end-time {
        type yang:date-and-time;
        mandatory true;
        description
          "The time stamp indicating when the attack ended";
      }
      leaf attack-rate {
        type uint32;
        description
          "The PPS rate of attack traffic";
      }
      leaf attack-speed {
        type uint32;
        description
          "The BPS speed of attack traffic";
      }
      uses common-monitoring-data;
    }
    notification nsf-detection-session-table {
      description
        "This notification is sent, when a session table
        event is detected";
      leaf current-session {
        type uint8;
        description
          "The number of concurrent sessions";
      }
      leaf maximum-session {
        type uint8;
        description
          "The maximum number of sessions that the session
           table can support";
      }
      leaf threshold {
        type uint8;
        description
          "The threshold triggering the event";
      }
      uses common-monitoring-data;
    }
    notification nsf-detection-virus {
      description
        "This notification is sent, when a virus is detected";
      uses i2nsf-nsf-event-type-content-extend;
      leaf virus {
        type identityref {
          base virus-type;
        }
        description
          "The virus type for nsf-detection-virus notification";
      }
      leaf virus-name {
        type string;
        description
        "The name of the detected virus";
      }

      leaf file-type {
        type string;
        description
          "The type of file virus code
          is found in (if applicable).";
      }
      leaf file-name {
        type string;
        description
           "The name of file virus code
           is found in (if applicable).";
      }
      uses common-monitoring-data;
    }
    notification nsf-detection-intrusion {
      description
        "This notification is sent, when an intrusion event
         is detected.";
      uses i2nsf-nsf-event-type-content-extend;
      leaf protocol {
        type identityref {
          base protocol-type;
        }
        description
          "The protocol type for
          nsf-detection-intrusion notification";
      }
      leaf app {
        type string;
        description
          "The employed application layer protocol";
      }
      leaf sub-attack-type {
        type identityref {
          base intrusion-attack-type;
        }
        description
          "The sub attack type for intrusion attack";
      }
      uses common-monitoring-data;
    }
    notification nsf-detection-botnet {
      description
        "This notification is sent, when a botnet event is
         detected";
      uses i2nsf-nsf-event-type-content-extend;
      leaf attack-type {
        type identityref {
          base botnet-attack-type;
        }
        description
          "The attack type for botnet attack";
      }
      leaf protocol {
        type identityref {
          base protocol-type;
        }
        description
          "The protocol type for nsf-detection-botnet notification";
      }
      leaf botnet-name {
        type string;
        description
          "The name of the detected botnet";
      }
      leaf role {
        type string;
        description
          "The role of the communicating
           parties within the botnet";
      }
      uses common-monitoring-data;
    }
    notification nsf-detection-web-attack {
      description
        "This notification is sent, when an attack event is
         detected";
      uses i2nsf-nsf-event-type-content-extend;
      leaf sub-attack-type {
        type identityref {
          base web-attack-type;
        }
        description
          "Concrete web attack type, e.g., sql injection,
           command injection, XSS, CSRF";
      }
      leaf request-method {
        type identityref {
          base req-method;
        }
        description
          "The method of requirement. For instance, PUT or
          GET in HTTP";
      }
      leaf req-uri {
        type string;
        description
        "Requested URI";
      }
      leaf uri-category {
        type string;
        description
        "Matched URI category";
      }
      leaf-list filtering-type {
        type identityref {
          base filter-type;
        }
        description
          "URL filtering type, e.g., Blacklist, Whitelist,
           User-Defined, Predefined, Malicious Category,
           Unknown";
      }
      uses common-monitoring-data;
    }
    notification system-access-log {
      description
        "The notification is sent, if there is
        a new system log entry about
         a system access event";
      leaf login-ip {
        type inet:ipv4-address;
        mandatory true;
        description
          "Login IP address of a user";
      }
      leaf administrator {
        type string;
        description
          "Administrator that maintains the device";
      }
      leaf login-mode {
        type login-mode;
        description
          "Specifies the administrator log-in mode";
      }
      leaf operation-type {
        type operation-type;
        description
          "The operation type that the administrator executes";
      }
      leaf result {
        type string;
        description
          "Command execution result";
      }
      leaf content {
        type string;
        description
          "The Operation performed by an administrator
          after login";
      }
      uses characteristics;
    }
    notification system-res-util-log {
      description
        "This notification is sent, if there is
        a new log entry representing resource
         utilization updates.";
      leaf system-status {
         type string;
         description
           "The current systems
           running status";
      }
      leaf cpu-usage {
        type uint8;
        description
          "Specifies the relative amount of
          cpu usage wrt platform resources";
      }
      leaf memory-usage {
         type uint8;
         description
           "Specifies the amount of memory usage";
      }
      leaf disk-usage {
        type uint8;
        description
          "Specifies the amount of disk usage";
      }
      leaf disk-left {
         type uint8;
         description
           "Specifies the amount of disk left";
      }
      leaf session-num {
        type uint8;
        description
          "The total number of sessions";
      }
      leaf process-num {
        type uint8;
        description
          "The total number of process";
      }
      leaf in-traffic-rate {
        type uint32;
        description
          "The total inbound traffic rate in pps";
      }
      leaf out-traffic-rate {
        type uint32;
        description
           "The total outbound traffic rate in pps";
      }
      leaf in-traffic-speed {
        type uint32;
        description
          "The total inbound traffic speed in bps";
      }
      leaf out-traffic-speed {
        type uint32;
        description
          "The total outbound traffic speed in bps";
      }
      uses characteristics;
    }
    notification system-user-activity-log {
      description
        "This notification is sent, if there is
        a new user activity log entry";
      uses characteristics;
      uses i2nsf-system-event-type-content;
      leaf access {
        type identityref {
          base access-mode;
        }
        description
          "The access type for
          system-user-activity-log notification";
      }
      leaf online-duration {
        type string;
        description
          "Online duration";
      }
      leaf logout-duration {
        type string;
        description
          "Lockout duration";
      }
      leaf additional-info {
        type string;
        description
          "User activities. e.g., Successful
          User Login, Failed Login attempts,
          User Logout, Successful User
          Password Change, Failed User
          Password Change, User Lockout,
          User Unlocking, Unknown";
      }
    }
    notification nsf-log-ddos {
      description
        "This notification is sent, if there is
        a new DDoS event log entry in the nsf log";
      leaf attack-type {
        type identityref {
          base ddos-attack-type;
        }
        description
          "The ddos attack type for
          nsf-log-ddos notification";
      }
      leaf attack-ave-rate {
        type uint32;
        description
          "The ave PPS of attack traffic";
      }
      leaf attack-ave-speed {
        type uint32;
        description
          "the ave bps of attack traffic";
      }
      leaf attack-pkt-num {
        type uint32;
        description
          "the number of attack packets";
      }
      leaf attack-src-ip {
        type inet:ipv4-address;
        description
          "The source IP addresses of attack
           traffics. If there are a large
           amount of IP addresses, then
           pick a certain number of resources
           according to different rules.";
      }
      leaf action {
        type log-action;
        description
          "Action type: allow, alert,
          block, discard, declare,
          block-ip, block-service";
      }
      uses characteristics;
      uses common-monitoring-data;
    }
    notification nsf-log-virus {
      description
        "This notification is sent, if there is
        a new virus event log entry in the nsf log";
      leaf attack-type {
        type identityref {
          base virus-type;
        }
        description
          "The virus type for nsf-log-virus notification";
      }
      leaf action {
        type log-action;
        description
          "Action type: allow, alert,
          block, discard, declare,
          block-ip, block-service";
      }
      leaf os{
        type string;
        description
          "simple os information";
      }
      leaf time {
        type yang:date-and-time;
        mandatory true;
        description
          "Indicate the time when the message
          is generated";
      }
      uses characteristics;
      uses common-monitoring-data;
    }
    notification nsf-log-intrusion {
      description
        "This notification is sent, if there is
        a new intrusion event log entry in the nsf log";
      leaf attack-type {
        type identityref {
          base intrusion-attack-type;
        }
        description
          "The intrusion attack type for
          nsf-log-intrusion notification";
      }
      leaf action {
        type log-action;
        description
          "Action type: allow, alert,
          block, discard, declare,
          block-ip, block-service";
      }
      leaf time {
        type yang:date-and-time;
        mandatory true;
        description
          "Indicate the time when the message
          is generated";
      }
      leaf attack-rate {
        type uint32;
        description
          "The PPS of attack traffic";
      }
      leaf attack-speed {
        type uint32;
        description
          "The bps of attack traffic";
      }
      uses characteristics;
      uses common-monitoring-data;
    }
    notification nsf-log-botnet {
      description
        "This notification is sent, if there is
        a new botnet event log in the nsf log";
      leaf attack-type {
        type identityref {
          base botnet-attack-type;
        }
        description
          "The botnet attack type for
          nsf-log-botnet notification";
      }
      leaf action {
        type log-action;
        description
          "Action type: allow, alert,
          block, discard, declare,
          block-ip, block-service";
      }
      leaf botnet-pkt-num{
        type uint8;
        description
          "The number of the packets sent to
          or from the detected botnet";
      }
      leaf os{
        type string;
        description
          "simple os information";
      }
      uses characteristics;
      uses common-monitoring-data;
    }
    notification nsf-log-dpi {
      description
        "This notification is sent, if there is
        a new dpi event in the nsf log";
      leaf attack-type {
        type dpi-type;
        description
          "The type of the dpi";
      }
      uses characteristics;
      uses i2nsf-nsf-counters-type-content;
      uses common-monitoring-data;
    }
    notification nsf-log-vuln-scan {
      description
        "This notification is sent, if there is
        a new vulnerability-scan report in the nsf log";
      leaf vulnerability-id {
        type uint8;
        description
          "The vulnerability id";
      }
      leaf victim-ip {
        type inet:ipv4-address;
        description
          "IP address of the victim host
          which has vulnerabilities";
      }
      leaf protocol {
        type identityref {
          base protocol-type;
        }
        description
          "The protocol type for
          nsf-log-vuln-scan notification";
      }
      leaf port-num {
        type inet:port-number;
          description
            "The port number";
      }
      leaf level {
        type severity;
        description
          "The vulnerability severity";
      }
      leaf os {
        type string;
        description
          "simple os information";
      }
      leaf vulnerability-info {
        type string;
        description
          "The information about the vulnerability";
      }
      leaf fix-suggestion {
        type string;
        description
          "The fix suggestion to the vulnerability";
      }
      leaf service {
        type string;
        description
          "The service which has vulnerability in the victim host";
      }
      uses characteristics;
      uses common-monitoring-data;
    }
    notification nsf-log-web-attack {
      description
        "This notification is sent, if there is
        a new web-attack event in the nsf log";
      leaf attack-type {
        type identityref {
          base web-attack-type;
        }
        description
          "The web attack type for
          nsf-log-web-attack notification";
      }
      leaf rsp-code {
        type string;
        description
          "Response code";
      }
      leaf req-clientapp {
        type string;
        description
          "The client application";
      }
      leaf req-cookies {
        type string;
        description
          "Cookies";
      }
      leaf req-host {
        type string;
        description
          "The domain name of the requested host";
      }
      leaf raw-info {
        type string;
        description
          "The information describing
          the packet triggering the event.";
      }
      uses characteristics;
      uses common-monitoring-data;
    }
    container counters {
      description
        "This is probably better covered by an import
        as this will not be notifications.
        Counter are not very suitable as telemetry, maybe
        via periodic subscriptions, which would still
        violate principle of least surprise.";
      container system-interface {
        description
          "The system counter type is interface counter";
        uses characteristics;
        uses i2nsf-system-counter-type-content;
        uses common-monitoring-data;
      }
      container nsf-firewall {
        description
          "The nsf counter type is firewall counter";
        uses characteristics;
        uses i2nsf-nsf-counters-type-content;
        uses traffic-rates;
      }
      container nsf-policy-hits {
        description
          "The counters of policy hit";
        uses characteristics;
        uses i2nsf-nsf-counters-type-content;
        uses common-monitoring-data;
        leaf hit-times {
          type uint32;
          description
            "The hit times for policy";
        }
      }
    }
  }
