module example-rip {

  namespace "http://example.com/rip";

  prefix "rip";

  import ietf-routing {
    prefix "rt";
  }

  import ietf-interfaces {
    prefix "if";
  }

  identity rip {
    base rt:routing-protocol;
    description
      "Identity for the RIP routing protocol.";
  }

  typedef rip-metric {
    type uint8 {
      range "0..16";
    }
  }

  grouping route-content {
    description
      "RIP-specific route content.";
    leaf metric {
      type rip-metric;
    }
    leaf tag {
      type uint16;
      default "0";
      description
        "This leaf may be used to carry additional info, e.g. AS
         number.";
    }
  }

  augment "/rt:get-route/rt:output/rt:route" {
    description
      "Add RIP-specific route content.";
    uses route-content;
  }

  augment "/rt:routing/rt:router/rt:routing-protocols/"
        + "rt:routing-protocol" {
    when "rt:type = 'rip:rip'";
    container rip-configuration {
      container rip-interfaces {
        list rip-interface {
          key "name";
          leaf name {
            type if:interface-ref;
          }
          leaf enabled {
            type boolean;
            default "true";
          }
          leaf metric {
            type rip-metric;
            default "1";
          }
        }
      }
      leaf update-interval {
        type uint8 {
          range "10..60";
        }
        units "seconds";
        default "30";
        description
          "Time interval between periodic updates.";
      }
    }
  }
  augment "/rt:routing/rt:router/rt:routing-tables/rt:routing-table/"
        + "rt:routes/rt:route" {
    when "../../../../rt:routing-protocols/"
       + "rt:routing-protocol[rt:name=current()/rt:source-protocol]/"
       + "rt:type='rip:rip'" {
      description
        "This augment is only valid if the source protocol from which
         the route originated is RIP.";
    }
    description
      "RIP-specific route components.";
    uses route-content;
  }
}
