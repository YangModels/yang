module ietf-opt-if-g698-2 {
     namespace "urn:ietf:params:xml:ns:yang:ietf-opt-if";
     prefix ietf-opt-if-g698-2;

     import ietf-interfaces {
       prefix if;
     }

     organization
       "IETF NETMOD (NETCONF Data Modelling Language) Working Group";

     contact
       "WG Web:   <http://tools.ietf.org/wg/netmod/>
        WG List:  <mailto:netmod@ietf.org>

        WG Chair: Thomas Nadeau
                  <mailto:tnadeau@lucidvision.com>

        WG Chair: Juergen Schoenwaelder
                  <mailto:j.schoenwaelder@jacobs-university.de>

        Editor:   Dharini Hiremagalur
                  <mailto:dharinih@juniper.net>";

     description
       "This module contains a collection of YANG definitions for
        configuring Optical interfaces.

        Copyright (c) 2013 IETF Trust and the persons identified as
                authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).";

        revision 2014-5-10 {
           description
               "Initial revision.";
           reference
               "RFC XXXX: A YANG Data Model for Optical Management of
                 an Interface for g.698.2 support";
        }
        revision 2014-10-14 {
           description
              "Revision 1.0";
        }
        revision 2014-11-10{
           description
              "Revision 2.0";
        }
        revision 2015-02-24{
           description
              "Revision 3.0";
        }

   grouping optIfOChApplicationCode  {
          description "Application code entity.";
          leaf applicationCodeId {
               description
                   "Id for the Application code";
               type uint8 {
                   range "1..255";
               }
          }
          leaf applicationCodeType {
               description
                   "Type for the Application code
                     0 - Standard, 1 - Proprietory
                     When the Type is Proprietory, then the
                     first 6 octets of the applicationCode
                     will be the OUI (organizationally unique
                     identifier)";
               type uint8 {
                   range "0..1";
               }
          }
          leaf applicationCodeLength {
               description
                   "Number of octets in the Application code";
               type uint8 {
                   range "1..255";
               }
          }
           leaf applicationCode {
               description "This parameter indicates the transceiver
                  application code at Ss and Rs as defined in
                  [ITU.G698.2] Chapter 5.3, that is/should be used by
                  this interface.
                  The optIfOChApplicationsCodeList has all the
                  application codes supported by this interface.";
               type string {
                   length "1..255";
               }
           }
   }

   grouping optIfOChApplicationCodeList {
       description "List of Application codes group.";
       leaf numberApplicationCodesSupported {
           type uint32;
           description "Number of Application codes supported by
                        this interface";
       }
       list applicationCodeList {
           key "applicationCodeId";
           uses optIfOChApplicationCode;
       }
   }

  grouping optIfOChPower {
      leaf outputPower {
         type int32;
                 units ".01dbm";
         description "The output power for this interface in .01
                       dbm.";
      }

              leaf inputPower {
                  type int32;
                  config false;
                      units ".01dbm";
          description "The current input power of this interface";
               }
      }

      grouping optIfOChWavelength {
       leaf wavelengthn {
                       type uint32;
           description "This parameter indicate minimum wavelength
           spectrum - n, in a definite wavelength Band (L, C and S)
                       as represented in[RFC6205] by the formula -
                       Wavelength (nm ) = 1471nm + n* Channel Spacing
                                             (converted to nm)
           Eg - Channel Spacing in nm
           'Wavelength (nm ) = 1471nm + n* 20nm  (20nm is the
            spacing for CWDM)' ";

                     }
      }

   notification optIfOChWavelengthChange {
      description "A change of wavelength has been detected.";
      leaf "if-name" {
          type leafref {
              path "/if:interfaces/if:interface/if:name";
          }
      }
      container wavelength {
          uses optIfOChWavelength;
      }
   }

   notification optIfOChApplicationCodeChange {
      description "A change of Application code has been detected.";
      leaf "if-name" {
          type leafref {
              path "/if:interfaces/if:interface/if:name";
          }
      }
      container newApplicationCode {
          uses optIfOChApplicationCode;
      }
   }

   augment "/if:interfaces/if:interface" {

      container optIfOChRsSs {
        description "RsSs path configuration for an interface";

         container ifCurrentApplicationCode {
            uses optIfOChApplicationCode;
         }

         container ifSupportedApplicationCodes {
             config false;
             uses optIfOChApplicationCodeList;
         }

         uses optIfOChPower;

         uses optIfOChWavelength;
      }
   }
}
