module ietf-nvo3-base {
  namespace "urn:ietf:params:xml:ns:yang:ietf-nvo3-base";
  //namespace need to be assigned by IANA
  prefix "nvo3";
  import ietf-inet-types {
    prefix "inet";
  }
  import ietf-yang-types {
    prefix yang;
  }

  organization "IETF NVO3 Working Group";
  contact "zhangmingui@huawei.com
    sean.gao@huawei.com";  
  description "nvo3 yang module";
  revision "2019-03-01" {
    description
      "Initial version";
    reference "RFC 7348 RFC 7637";
  }
  typedef vrfName {
    type string {
      length "1..31";
    }
    description
      "vrfName is a string type with length constraints";
  }
  typedef ifName {
    type string {
      length "1..63";
    }
    description
      "ifName is a string type with length constraints";
  }
  typedef vniStatus {
    type enumeration {
      enum up {
        description 
	         "The VNI is up";  
      }
      enum down {
        description 
          "The VNI is down";  
      }
    }  
    description
      "The status of a VNI can be either up or down";
  } 
  typedef protocolType {
    type enumeration {
      enum null {
        description
          "No specific protocol is used";
      }
      enum evpn {
        description
	         "EVPN is used as the control plane protocol";
      }
    }
    description
      "The protocol type being used as control plane";
  }
  typedef peerType {
    type enumeration {
      enum static {
        description 
	         "Static peer NVE";     
      }
      enum dynamic {
        description 
	         "Dynamic peer NVE";  
      }
    }
    description
      "The type of the peer NVE";
  }
  typedef tunnelStatus {
    type enumeration {
      enum up {
        description
          "The tunnel is up";
	  }
	  enum down {
        description
          "The tunnel is down";
      }
    }
    description
      "The status of a tunnel can be either up or down";
  }
  typedef vniStatisticsEnable {
    type enumeration {
      enum enable {
        description
          "The statistics is enabled";
	  }
	  enum disable {
        description
          "The statistics is disabled";
	  }
    }
    description
	     "The statistics of a VNI can be enabled or disabled";
  }
  typedef tunnelType {
    type enumeration {
      enum dynamic {
        description
          "The tunnel is built in a dynamic way";
	  }
	  enum static {
        description
          "The tunnel is built by static configuration";
	  }
    }
    description
      "The type of a tunnel";
  }
  container nvo3{
    description
      "NVO3 base YANG main part";
    container common {
      description
        "Common part";
      leaf nvo3-enable {
        type boolean;
        default "false";
        description
          "Enable/Disable NVO3 featrues";
    }
  }
    container nves {
      description
        "Parameters of NVEs";
      list nve {
        key "if-name source-interface";
        description
	         "The list of NVEs";
        leaf if-name {
          type ifName;
          description
            "nve interface name";
        }
        leaf vtep-ip {
          type inet:ipv4-address-no-zone;
          description
            "NVO3 tunnel source address";
        }
        leaf ipv6-vtep-ip {
          type inet:ipv6-address-no-zone;
          description
            "ipv6 NVO3 tunnel source address";
        }
        leaf source-interface {
          type ifName;
          description
            "source interface";
        }
        leaf mac-address {
          type yang:mac-address;
          description
            "mac address";
        }
        leaf bypass-vtep-ip {
          type inet:ipv4-address-no-zone;
          description
            "bypass NVO3 tunnel source address";
        }
        container vni-members {
	         description
	           "The VNI members on the NVE";
          list vni-member {
            key "vni-id";
            description
              "nve vni member";
            leaf vni-id {
              type uint32 {
                range "1..16777215";
              }
              description
                "Associate NVO3 VNIs (Virtual Network Identifiers) with the NVE interface.";
            }
            leaf protocol-bgp {
              type protocolType;
              default "null";
              description
                "Enables BGP EVPN with ingress replication for the VNI.";
            }
            container peers {
              description
	               "The peers in this VNI";
              list peer {
                key "peer-ip";
                description
		             "A peer NVE in this VNI";
                leaf peer-ip {
                  type inet:ipv4-address-no-zone;
                  description
                    "peer ip address";
                }
                leaf out-vni-id {
                  type uint32 {
                    range "1..16777215";
                  }
                  description
                    "out vni id";
                }
                leaf split-horizon-group {
                  type string {
                    length "1..31";
                  }
                  description
                    "split group name";
                }
              }
            }
            container ipv6-peers {
              description
                "The IPv6 peers in this VNI";
              list ipv6-peer {
                key "ipv6-peer-ip";
	             description
		           "An IPv6 peer NVE in this VNI";
                leaf ipv6-peer-ip {
                  type inet:ipv6-address-no-zone;
                  description
                    "peer ipv6 address";
                }
              }
            }
            container flood-proxys {
	             description
	               "The flood proxys for this VNI";
              list flood-proxy {
                key "peer-ip";
                leaf peer-ip {
                  type inet:ipv4-address-no-zone;
                  description
                    "peer ip address";
                }
		           description
		             "List of the flood proxys";
              }
            }
            list mcast-group {
              key "mcast-group";
	             description
	               "The multicast groups in this VNI";
              leaf mcast-group {
                type inet:ipv4-address-no-zone;
                description
                  "mcast ip address";
              }
            }
          }
        }
	      container vni-map-l2vpns {
         description
           "Mapping VNIs to L2VPNs";
	      list vni-map-l2vpn {
	        key "vni-id";
	        description
	          "L2VPN";
	        leaf l2vpn-id {
	          type uint32 {
	            range "1..16777215";
	          }
	          mandatory true;
	          description
	            "l2vpn id";
	        }
	        leaf l2vpn-name {
	          type string {
	            length "1..31";
	          }
	          description
	            "l2vpn name";
	        }
	        leaf vni-id {
	          type uint32 {
	            range "1..16777215";
	          }
	          description
	            "vni id";
	        }
	        leaf split-horizon-group {
	          type string {
	            length "1..31";
	          }
	          description
	            "split group name";
	        }
	      }
	    }
	    container vni-map-l3vpns {
	      description
         "Mapping VNIs to L3VPNs";
	      list vni-map-l3vpn {
	        key "l3vpn-name";
	        description
           "L3VPN";
	        leaf l3vpn-name {
	          type vrfName;
	          description
	            "l3vpn name";
	        }
	        leaf vni-id {
	          type uint32 {
	            range "1..16777215";
	          }
	          description
	            "vni id";
	        }
	      }
	    }
      container vni-statistics-infos {
          config false;
 	     description
            "The statistics information for VNIs";
          list vni-statistic-info {
            key "vni-id";
            config false;
            description
              "The statistics information for a VNI";
            leaf vni-id {
              type uint32 {
                range "1..16777215";
              }
              config false;
              description
                "vni id";
            }
            container vni-statistics {
              config false;
 	         description
                "The statistics information items for a VNI";
              leaf rx-bits-persec {
                type uint64;
                config false;
	               description
                  "Received bits per second";
              }
              leaf rx-pkts-persec {
                type uint64;
                config false;
	               description
                  "Received packets per second";
              }
              leaf tx-bits-persec {
                type uint64;
                config false;
	               description
                  "Transmitted bits per second";
              }
              leaf tx-pkts-persec {
                type uint64;
                config false;
	               description
                  "Transmitted packets per second";
              }
              leaf rx-pkts {
                type uint64;
                config false;
	               description
                  "Received packets";
              }
              leaf rx-bytes {
                type uint64;
                config false;
	               description
                  "Received bytes";
              }
              leaf tx-pkts {
                type uint64;
                config false;
				   description
                  "Transmitted packets";
              }
              leaf tx-bytes {
                type uint64;
                config false;
				   description
                  "Transmitted bytes";
              }
              leaf rx-unicast-pkts {
                type uint64;
                config false;
				   description
                  "Received unicast packets";
              }
              leaf rx-multicast-pkts {
                type uint64;
                config false;
				   description
                  "Received multicast packets";
              }
              leaf rx-broadcast-pkts {
                type uint64;
                config false;
				   description
                  "Received broadcast packets";
              }
              leaf drop-unicast-pkts {
                type uint64;
                config false;
				   description
                  "Dropped unicast packets";
              }
              leaf drop-multicast-pkts {
                type uint64;
                config false;	
				   description
                  "Dropped multicast packets";
              }
              leaf drop-broadcast-pkts {
                type uint64;
                config false;
				   description
                  "Dropped broadcast packets";
              }
              leaf tx-unicast-pkts {
                type uint64;
                config false;
				   description
                  "Transmitted unicast packets";
              }
              leaf tx-multicast-pkts {
                type uint64;
                config false;
				   description
                  "Transmitted multicast packets";
              }
              leaf tx-broadcast-pkts {
                type uint64;
                config false;
				   description
                  "Transmitted broadcast packets";
              }
            }
          }
        }
        container vnipeer-statistics-cfgs {
          description
            "Statistics configuration of peers in the VNI.";
			 list vnipeer-satistics-cfg {
            key "vni-id peer-ip";
			   description
              "Statistics configuration of a peer in the VNI.";
            leaf vni-id {
              type uint32 {
                range "1..16777215";
              }
              description
                "vni id";
            }
            leaf peer-ip {
              type inet:ipv4-address-no-zone;
			     description
              	"The Ipv4 address of the peer";
            }
          }
        }
        container vnipeer-statistics-infos {
          config false;
		     description
            "Statistics configuration of the peers in a VNI";
          list vnipeer-satistics-info {
            key "vni-id source-ip peer-ip";
            config false;
			   description
              "Statistics information of a peer in the VNI.";
            leaf vni-id {
              type uint32 {
                range "0..16777215";
              }
              config false;
              description
                "vni id";
            }
            leaf source-ip {
              type inet:ipv4-address-no-zone;
              config false;
		         description
                "Source address";
            }
            leaf peer-ip {
              type inet:ipv4-address-no-zone;
              config false;
		         description
                "Address of the peer";
            }
            container vnipeer_statistics {
              config false;
			     description
				   "Statistics information items of a peer in the VNI";
              leaf rx-bits-persec {
                type uint64;
                config false;
			       description
                  "Received bits per second";
              }
              leaf rx-pkts-persec {
                type uint64;
                config false;
				   description
                  "Received packets per second";
              }
              leaf tx-bits-persec {
                type uint64;
                config false;
				   description
                  "Transmitted bits per second";
              }
              leaf tx-pkts-persec {
                type uint64;
                config false;
			  	   description
                  "Transmitted packets per second";
              }
              leaf rx-pkts {
                type uint64;
                config false;
				   description
                  "Received packets";
              }
              leaf rx-bytes {
                type uint64;
                config false;
				   description
                  "Received bytes";
              }
              leaf tx-pkts {
                type uint64;
                config false;
				   description
                  "Transmitted packets";
              }
              leaf tx-bytes {
                type uint64;
                config false;
				   description
                  "Transmitted bytes";
              }
              leaf rx-unicast-pkts {
                type uint64;
                config false;
				   description
                  "Received unicast packets";
              }
              leaf rx-multicast-pkts {
                type uint64;
                config false;
				   description
                  "Received multicast packets";
              }
              leaf rx-broadcast-pkts {
                type uint64;
                config false;
				   description
                  "Received broadcast packets";
              }
              leaf drop-unicast-pkts {
                type uint64;
                config false;
				   description
                  "Dropped unicast packets";
              }
              leaf drop-multicast-pkts {
                type uint64;
                config false;	
				   description
                  "Dropped multicast packets";
              }
              leaf drop-broadcast-pkts {
                type uint64;
                config false;
				   description
                  "Dropped broadcast packets";
              }
              leaf tx-unicast-pkts {
                type uint64;
                config false;
				   description
                  "Transmitted unicast packets";
              }
              leaf tx-multicast-pkts {
                type uint64;
                config false;
				   description
                  "Transmitted multicast packets";
              }
              leaf tx-broadcast-pkts {
                type uint64;
                config false;
				   description
                  "Transmitted broadcast packets";
              }
            }
          }
        }
        container ipv6-vnipeer-statistics-cfgs {
		     description
            "Statistics configuration of IPv6 peers in the VNI.";
          list ipv6-vnipeer-statistics-cfg {
            key "vni-id ipv6-source-ip ipv6-peer-ip";
			   description
              "Statistics configuration of an IPv6 peer in the VNI.";
            leaf vni-id {
              type uint32 {
                range "1..16777215";
              }
              description
                "vni id";
            }
            leaf ipv6-source-ip {
              type inet:ipv6-address-no-zone;
			     description
                "Source IPv6 address";
            }
            leaf ipv6-peer-ip {
              type inet:ipv6-address-no-zone;
 			 description
                "IPv6 address of the peer";
            }
          }
        }
        container ipv6-vnipeer-statistics-infos {
          config false;
          description
            "Statistics information of IPv6 peers in the VNI.";
          list ipv6-vnipeer-statistics-info {
            key "vniId ipv6-source-ip ipv6-peer-ip";
            config false;
			   description
              "Statistics information of an IPv6 peer in the VNI.";
            leaf vniId {
              type uint32 {
                range "1..16777215";
              }
              config false;
              description
                "vni id";
            }
            leaf ipv6-source-ip {
              type inet:ipv6-address-no-zone;
              config false;
			     description
                "Source IPv6 address";
            }
            leaf ipv6-peer-ip {
              type inet:ipv6-address-no-zone;
              config false;
			     description
                "IPv6 address of the peer";
            }
            container ipv6_vnipeer_statistics {
              config false;
			     description
                "Statistics information items of an IPv6 peer in the VNI.";
              leaf rx-bits-persec {
                type uint64;
                config false;
			       description
                  "Received bits per second";
              }
              leaf rx-pkts-persec {
                type uint64;
                config false;
				   description
                  "Received packets per second";
              }
              leaf tx-bits-persec {
                type uint64;
                config false;
				   description
                  "Transmitted bits per second";
              }
              leaf tx-pkts-persec {
                type uint64;
                config false;
			  	   description
                  "Transmitted packets per second";
              }
              leaf rx-pkts {
                type uint64;
                config false;
				   description
                  "Received packets";
              }
              leaf rx-bytes {
                type uint64;
                config false;
				   description
                  "Received bytes";
              }
              leaf tx-pkts {
                type uint64;
                config false;
				   description
                  "Transmitted packets";
              }
              leaf tx-bytes {
                type uint64;
                config false;
				   description
                  "Transmitted bytes";
              }
              leaf rx-unicast-pkts {
                type uint64;
                config false;
				   description
                  "Received unicast packets";
              }
              leaf rx-multicast-pkts {
                type uint64;
                config false;
				   description
                  "Received multicast packets";
              }
              leaf rx-broadcast-pkts {
                type uint64;
                config false;
				   description
                  "Received broadcast packets";
              }
              leaf drop-unicast-pkts {
                type uint64;
                config false;
				   description
                  "Dropped unicast packets";
              }
              leaf drop-multicast-pkts {
                type uint64;
                config false;	
				   description
                  "Dropped multicast packets";
              }
              leaf drop-broadcast-pkts {
                type uint64;
                config false;
				   description
                  "Dropped broadcast packets";
              }
              leaf tx-unicast-pkts {
                type uint64;
                config false;
				   description
                  "Transmitted unicast packets";
              }
              leaf tx-multicast-pkts {
                type uint64;
                config false;
				   description
                  "Transmitted multicast packets";
              }
              leaf tx-broadcast-pkts {
                type uint64;
                config false;
				   description
                  "Transmitted broadcast packets";
              }
            }
          }
        }
      }
    }
    container vnipeer-infos {
      config false;
	     description
        "Information of the peers";
      list vnipeer-info {
        key "vni-id source-ip peer-ip";
        config false;
		   description
          "Information of a peer";
        leaf vni-id {
          type uint32 {
            range "1..16777215";
          }
          config false;
          description
            "vni-id";
        }
        leaf source-ip {
          type inet:ip-address-no-zone;
          config false;
          description
            "source ip";
        }
        leaf peer-ip {
          type inet:ip-address-no-zone;
          config false;
          description
            "peer ip";
        }
        leaf type {
          type peerType;
          config false;
          description
            "peer type";
        }
        leaf out-vni-id {
          type uint32 {
            range "1..16777215";
          }
          config false;
          description
            "out vni id";
        }
      }
    }
    container vni-infos {
	     description
        "Information of the VNIs";
      list vni_info {
        key "vni-id";
		   description
		     "Information of a VNI";
        leaf vni-id {
          type uint32 {
            range "1..16777215";
          }
          description
            "vni id";
        }
        leaf statistics-enable {
          type vniStatisticsEnable;
          default "disable";
		     description
		  	   "Statistics is enabled or not";
        }
        leaf status {
          type vniStatus;
          config false;
		     description
		  	   "The status of the VNI";
        }
      }
    }
    container tunnel-infos {
      config false;
	     description
		   "Information of tunnels";
      list tunnel-infos {
        key "tunnel-id";
        config false;
		   description
		     "Information of a tunnel";
        leaf tunnel-id {
          type uint32 {
            range "1..4294967295";
          }
          config false;
          description
            "tunnel id";
        }
        leaf source-ip {
          type inet:ip-address-no-zone;
          config false;
          description
            "source";
        }
        leaf peer-ip {
          type inet:ip-address-no-zone;
          config false;
          description
            "peer ip";
        }
        leaf status {
          type tunnelStatus;
          config false;
          description
            "tunnel status";
        }
        leaf type {
          type tunnelType;
          config false;
          description
            "tunnel type";
        }
        leaf up-time {
          type string {
            length "1..10";
          }
          config false;
          description
            "tunnel up time";
        }
        leaf vrf-name {
          type vrfName;
          default "_public_";
          config false;
          description
            "vrf";
        }
      }
    }
  }
}
