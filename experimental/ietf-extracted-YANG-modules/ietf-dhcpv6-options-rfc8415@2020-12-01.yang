module ietf-dhcpv6-options-rfc8415 {
  yang-version 1.1;
  namespace "urn:ietf:params:xml:ns:yang:ietf-dhcpv6-options-8415-cli
ent";
  prefix "rfc8415-cli";

  import ietf-inet-types {
    prefix inet;
    reference
      "RFC 6991: Common YANG Data Types";
  }

  import ietf-dhcpv6-common {
    prefix dhcpv6-common;
    reference
      "To be updated on publication";
  }

  import ietf-dhcpv6-client {
    prefix dhcpv6-client;
    reference
      "To be updated on publication";
  }

  organization "DHC WG";
  contact
    "cuiyong@tsinghua.edu.cn
    wangh13@mails.tsinghua.edu.cn
    lh.sunlinh@gmail.com
    ian.farrer@telekom.de
    sladjana.zechlin@telekom.de
    hezihao9512@gmail.com";

  description "This YANG module contains DHCPv6 options defined
    in RFC8415 that can be used by DHCPv6 clients.";

  revision 2020-12-01 {
    description "Version update for draft -12 publication.";
    reference "I-D: draft-ietf-dhc-dhcpv6-yang-12";
  }

  revision 2020-11-19 {
    description "Separated into a client specific set of options.";
    reference "I-D: draft-ietf-dhc-dhcpv6-yang-12";
  }

  revision 2020-05-26 {
    description "Version update for draft -11 publication and
      to align revisions across the different modules.";
    reference "I-D: draft-ietf-dhc-dhcpv6-yang-11";
  }

  revision 2019-06-07 {
    description "Major reworking to only contain RFC8415 options.
      if-feature for each option removed. Removed groupings
        of features by device or combination of devices. Added ";
    reference "I-D: draft-ietf-dhc-dhcpv6-yang";
  }

  revision 2018-09-04 {
    description "";
    reference "I-D: draft-ietf-dhc-dhcpv6-yang";
  }

  revision 2018-03-04 {
    description "Resolved most issues on the DHC official
      github";
    reference "I-D: draft-ietf-dhc-dhcpv6-yang";
  }

  revision 2017-12-22 {
    description "Resolve most issues on Ian's github.";
    reference "I-D: draft-ietf-dhc-dhcpv6-yang";
  }

  revision 2017-11-24 {
    description "First version of the separated DHCPv6 options
      YANG model.";
    reference "I-D:draft-ietf-dhc-dhcpv6-yang";
  }

  /*
   * Groupings
   */

  grouping option-request-option-group {
    container option-request-option {
      description "OPTION_ORO (6) Option Request Option. A client
        MUST include an Option Request option in a Solicit, Request,
             Renew, Rebind, or Information-request message to inform
               the server about options the client wants the server t
o send
               to the client.";
      reference "RFC8415: Dynamic Host Configuration Protocol for
        IPv6 (DHCPv6)";
      leaf-list oro-option {
        description "List of options that the client is requesting,
                    identified by option code";
        type uint16;
      }
    }
  }

  grouping status-code-option-group {
    container status-code-option {
      description "OPTION_STATUS_CODE (13) Status Code Option.";
      reference "RFC8415: Dynamic Host Configuration Protocol
        for IPv6 (DHCPv6)";
      leaf status-code {
        type uint16;
        description "The numeric code for the status encoded
          in this option. See the Status Codes registry at
          <https://www.iana.org/assignments/dhcpv6-parameters>
          for the current list of status codes.";
      }
      leaf status-message {
        type string;
        description "A UTF-8 encoded text string suitable for
          display to an end user. MUST NOT be null-terminated.";
      }
    }
  }

  grouping rapid-commit-option-group {
    container rapid-commit-option {
      presence "Enable sending of this option";
      description "OPTION_RAPID_COMMIT (14) Rapid Commit Option.
        The presence node is used to enable the option.";
      reference "RFC8415: Dynamic Host Configuration Protocol for
        IPv6 (DHCPv6)";
    }
  }

  grouping user-class-option-group {
    container user-class-option {
      description "OPTION_USER_CLASS (15) User Class Option";
      reference "RFC8415: Dynamic Host Configuration Protocol
        for IPv6 (DHCPv6)";
      list user-class-data {
        key user-class-datum-id;
        min-elements 1;
        description "The user classes of which the client
          is a member.";
        leaf user-class-datum-id {
          type uint8;
          description "User class datum ID";
        }
        leaf user-class-datum {
          type string;
          description "Opaque field representing a User Class
            of which the client is a member.";
        }
      }
    }
  }

  grouping vendor-class-option-group {
    container vendor-class-option {
      description "OPTION_VENDOR_CLASS (16) Vendor Class Option";
      reference "RFC8415: Dynamic Host Configuration Protocol
        for IPv6 (DHCPv6)";
      list vendor-class-option-instances {
        key enterprise-number;
        description "The vendor class option allows for multiple
          instances in a single message. Each list entry defines
          the contents of an instance of the option.";
        leaf enterprise-number {
          type uint32;
          description "The vendor's registered Enterprise Number
            as maintained by IANA.";
        }
        list vendor-class {
          key vendor-class-datum-id;
          description "The vendor classes of which the client is
            a member.";
          leaf vendor-class-datum-id {
            type uint8;
            description "Vendor class datum ID";
          }
          leaf vendor-class-datum {
            type string;
            description "Opaque field representing a vendor class
              of which the client is a member.";
          }
        }
      }
    }
  }

  grouping vendor-specific-information-option-group {
    container vendor-specific-information-option {
      description "OPTION_VENDOR_OPTS (17) Vendor-specific
        Information Option";
      reference "RFC8415: Dynamic Host Configuration Protocol
        for IPv6 (DHCPv6)";
      list vendor-specific-information-option-instances {
        key enterprise-number;
        description "The vendor specific information option allows
          for multiple instances in a single message. Each list entry
            defines the contents of an instance of the option.";
        leaf enterprise-number {
          type uint32;
          description "The vendor's registered Enterprise Number,
                      as maintained by IANA.";
        }
        list vendor-option-data {
          key sub-option-code;
          description "Vendor options, interpreted by vendor-specific
            client/server functions.";
          leaf sub-option-code {
            type uint16;
            description "The code for the sub-option.";
          }
          leaf sub-option-data {
            type string;
            description "The data area for the sub-option.";
          }
        }
      }
    }
  }

  grouping reconfigure-accept-option-group {
    container reconfigure-accept-option {
      presence "Enable sending of this option";
      description "OPTION_RECONF_ACCEPT (20)  Reconfigure Accept
        Option.
        A client uses the Reconfigure Accept option to announce to
        the server whether the client is willing to accept
        Reconfigure messages, and a server uses this option to tell
        the client whether or not to accept Reconfigure messages.
        In the absence of this option, the default behavior is that
        the client is unwilling to accept Reconfigure messages.
        The presence node is used to enable the option.";
      reference "RFC8415: Dynamic Host Configuration Protocol
        for IPv6 (DHCPv6)";
    }
  }

  /*
   * Augmentations
   */

  augment "/dhcpv6-client:dhcpv6-client/dhcpv6-client:client-if/dhcpv
6-client:client-configured-options" {
    when "../../../dhcpv6-client:dhcpv6-node-type='dhcpv6-client:clie
nt'";
    uses option-request-option-group;
    uses status-code-option-group;
    uses rapid-commit-option-group;
    uses user-class-option-group;
    uses vendor-class-option-group;
    uses vendor-specific-information-option-group;
    uses reconfigure-accept-option-group;
  }
}
