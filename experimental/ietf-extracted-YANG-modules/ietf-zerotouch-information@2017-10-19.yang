module ietf-zerotouch-information {
  yang-version 1.1;
  namespace "urn:ietf:params:xml:ns:yang:ietf-zerotouch-information";
  prefix zti;

  import ietf-yang-types {
    prefix yang;
    reference "RFC 6991: Common YANG Data Types";
  }
  import ietf-inet-types {
    prefix inet;
    reference "RFC 6991: Common YANG Data Types";
  }
  import ietf-restconf {
    prefix rc;
    description
      "This import statement is only present to access
       the yang-data extension defined in RFC 8040.";
    reference "RFC 8040: RESTCONF Protocol";
  }

  organization
    "IETF NETCONF (Network Configuration) Working Group";

  contact
    "WG Web:   http://tools.ietf.org/wg/netconf
     WG List:  <mailto:netconf@ietf.org>
     Author:   Kent Watsen <mailto:kwatsen@juniper.net>";

  description
    "This module defines the data model for the Zero Touch Information
     artifact defined by RFC XXXX: Zero Touch Provisioning for NETCONF
     or RESTCONF based Management.

     The key words 'MUST', 'MUST NOT', 'REQUIRED', 'SHALL',
     'SHALL NOT', 'SHOULD', 'SHOULD NOT', 'RECOMMENDED', 'MAY',
     and 'OPTIONAL' in the module text are to be interpreted as
     described in RFC 2119.

     Copyright (c) 2017 IETF Trust and the persons identified as
     authors of the code. All rights reserved.

     Redistribution and use in source and binary forms, with or
     without modification, is permitted pursuant to, and subject
     to the license terms contained in, the Simplified BSD License
     set forth in Section 4.c of the IETF Trust's Legal Provisions
     Relating to IETF Documents (http://trustee.ietf.org/license-info)

     This version of this YANG module is part of RFC XXXX; see the
     RFC itself for full legal notices.";

  revision 2017-10-19 {
    description
      "Initial version";
    reference
      "RFC XXXX: Zero Touch Provisioning for NETCONF or RESTCONF based
       Management";
  }

  identity hash-algorithm {
    description
      "A base identity for hash algorith verification";
  }

  identity sha-256 {
    base "hash-algorithm";
    description "The SHA-256 algorithm.";
    reference "RFC 6234: US Secure Hash Algorithms.";
  }

  rc:yang-data "zerotouch-information" {
    choice information-type {
      mandatory true;
      description
        "This choice statement ensures the response contains
         redirect-information or onboarding-information.";
      container redirect-information {
        description
          "Redirect information is described in Section 2.1 in
           RFC XXXX.  Its purpose is to redirect a device to
           another bootstrap server.";
        reference
          "RFC XXXX: Zero Touch Provisioning for NETCONF or RESTCONF
           based Management";
        list bootstrap-server {
          key "address";
          min-elements 1;
          description
            "A bootstrap server entry.";
          leaf address {
            type inet:host;
            mandatory true;
            description
              "The IP address or hostname of the bootstrap server the
               device should redirect to.";
          }
          leaf port {
            type inet:port-number;
            default "443";
            description
              "The port number the bootstrap server listens on.  If no
               port is specified, the IANA-assigned port for 'https'
               (443) is used.";
          }
          leaf trust-anchor {
            type binary;
            description
              "An X.509 v3 certificate structure as specified by RFC
               5280, Section 4, encoded using ASN.1 distinguished
               encoding rules (DER), as specified in ITU-T X.690.  A
               certificate that the device can use as the trust anchor
               to authenticate the bootstrap server the device is
               being redirected to.  If not specified, the device may
               establish a provisional connection to the bootstrap
               server, as described in RFC XXXX.";
            reference
              "RFC 5280:
                 Internet X.509 Public Key Infrastructure Certificate
                 and Certificate Revocation List (CRL) Profile.
               ITU-T X.690:
                  Information technology - ASN.1 encoding rules:
                  Specification of Basic Encoding Rules (BER),
                  Canonical Encoding Rules (CER) and Distinguished
                  Encoding Rules (DER).
               RFC XXXX:
                  Zero Touch Provisioning for NETCONF or RESTCONF
                  based Management.";
          }
        }
      }
      container onboarding-information {
        description
          "Onboarding information is described in Section 2.2 in
           RFC XXXX.  Its purpose is to provide the device everything
           it needs to bootstrap itself.";
        reference
          "RFC XXXX: Zero Touch Provisioning for NETCONF or RESTCONF
           based Management";
        container boot-image {
          description
            "Specifies criteria for the boot image the device MUST
             be running.";
          leaf os-name {
            type string;
            mandatory true;
            description
              "The name of the operating system software the device
               MUST be running in order to not require a software
               image upgrade (ex. VendorOS).";
          }
          leaf os-version {
            type string;
            mandatory true;
            description
              "The version of the operating system software the device
               MUST be running in order to not require a software
               image upgrade (ex. 17.3R2.1).";
          }
          leaf-list download-uri {
            type inet:uri;
            must '../image-verification' {
              description
                "Image verification information must be provided if
                 the device is going to download an image.";
            }
            ordered-by user;
            description
              "An ordered list of URIs to where the necessary
               boot-image file MAY be obtained.  Deployments must
               know through out-of-band means which URI schemes
               (http, ftp, etc.) the bootstrapping device supports.
               If a secure scheme (e.g., https) is provided, a
               device MAY establish an untrusted connection to the
               remote server to obtain the boot-image.";
          }
          list image-verification {
            key hash-algorithm;
            description
              "A list of hash values that a device can use to verify
               boot image files with.";
            leaf hash-algorithm {
              type identityref {
                base "hash-algorithm";
              }
              mandatory true;
              description
                "Identifies the hash algorithm used.";
            }
            leaf hash-value {
              type yang:hex-string;
              description
                "The hex-encoded value of the specified hash algorithm
                 over the contents of the boot image file.";
            }
          }
        }
        leaf configuration-handling {
          type enumeration {
            enum "merge" {
              description
                "Merge configuration into the running datastore.";
            }
            enum "replace" {
              description
                "Replace the existing running datastore with the
                 passed configuration.";
            }
          }
          must '../configuration';
          description
            "This enumeration indicates how the server should process
             the provided configuration.";
        }
        leaf pre-configuration-script {
          type script;
          description
            "A script that, when present, is executed before the
             configuration has been processed.";
        }
        anydata configuration {
          must '../configuration-handling';
          description
            "Any configuration data model known to the device.  It may
             contain manufacturer-specific and/or standards-based data
             models.";
        }
        leaf post-configuration-script {
          type script;
          description
            "A script that, when present, is executed after the
             configuration has been processed.";
        }
      }
    }
  }

  typedef script {
    type binary;
    description
      "A device specific script that enables the execution of
       commands to perform actions not possible thru configuration
       alone.

       No attempt is made to standardize the contents, running
       context, or programming language of the script, other than
       that it can emit an exit status code and stderr/sdtout.  The
       contents of the script are considered specific to the vendor,
       product line, and/or model of the device.

       If a script is erroneously provided to a device that does not
       support the execution of scripts, the device SHOULD send a
       'script-warning' progress report, but otherwise continue
       processing the bootstrapping data as if the script had not
       been present.

       The script returns exit status code '0' on success and non-zero
       on error, with accompanying stderr/stdout for logging purposes.
       In the case of an error, the exit status code will specify what
       the device should do as follows.

       If the exit status code is greater than zero, then the device
       should assume that the script had a soft error, which the
       script believes does not affect manageability.  If the device
       obtained the bootstrap information from a bootstrap server,
       it SHOULD send a 'script-warning' progress report.

       If the exit status code is less than zero, the device should
       assume the script had a hard error, which the script believes
       will affect manageability.  In this case, the device SHOULD
       send a 'script-error' progress report followed by a reset that
       will wipe out anything the script may have done and restart
       the entire bootstrapping process again.";
  }
}
