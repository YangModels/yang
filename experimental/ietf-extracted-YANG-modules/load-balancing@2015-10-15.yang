submodule load-balancing {
  belongs-to sfc-control-planes{
    prefix sfc-lb;
  }
  organization "ETRI.";
  contact
  "M-K. Shin mkshin@etri.re.kr
   M-J Choi mjchoi@kangwon.ac.kr";
  description
  "This module constructs and maintains SFPs to localize the
   traffic in the network considering load and administrative
   domain of SFIs.";
  revision 2015-10-15 {
 reference
 "draft-shin-sfc-control-plane-yang-00 -
  Yang Data Model for Service Function Chaining Control Plane";
  }
  container load-balancing {
    description
    "This container constructs and maintains SFPs
     to localize the traffic in the network considering load
     and administrative domain of SFIs.";
    leaf load-type {
      type enumeration {
        enum traffic{
           description
           "Traffic";
        }
        enum cpu{
           description
           "CPU";
        }
        enum memory{
           description
           "Memory";
        }
      }
      description
      "A resource type for load balancing.";
    }
    leaf source-sfp-name {
      type string;
      description
      "The name of service function path with heavy load.";
    }
    leaf target-sfp-name {
      type string;
      description
      "Another name of service function path for load
       distribution.";
    }
  }
  rpc perform-load-balance {
    description
    "Perform a load balancing.";
    input {
      leaf load-type {
        type enumeration {
          enum traffic{
             description
             "Traffic";
          }

          enum cpu{
             description
             "CPU";
          }

          enum memory{
             description
             "Memory";
          }
        }
        description
        "A resource type for load balancing.";
      }
      leaf source-sfp-name {
        type string;
        description
        "The name of service function path with heavy load.";
      }
    }
    output  {
      leaf target-sfp-name {
        type string;
        description
        "Another name of service function path for load
         distribution.";
      }
   }
}
}
