module iana-bfd-types {

  yang-version 1.1;

  namespace "urn:ietf:params:xml:ns:yang:iana-bfd-types";

  prefix "iana-bfd-types";

  organization "IANA";

  contact
    "        Internet Assigned Numbers Authority

    Postal: ICANN
            4676 Admiralty Way, Suite 330
            Marina del Rey, CA 90292

    Tel:    +1 310 823 9358
    <mailto:iana@iana.org>";

  description
    "This module contains a collection of YANG data types
     considered defined by IANA and used for BFD.

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove
  // this note

  reference "RFC XXXX";

  revision 2018-01-22 {
    description "Initial revision.";
    reference "RFC XXXX: IANA BFD YANG Data Types.";
  }

  /*
   * Type Definitions
   */
  typedef diagnostic {
    type enumeration {
      enum none {
        value 0;
        description "None";
      }
      enum control-expiry {
        value 1;
        description "Control timer expiry";
      }
      enum echo-failed {
        value 2;
        description "Echo failure";
      }
      enum neighbor-down {
        value 3;
        description "Neighbor down";
      }
      enum forwarding-reset {
        value 4;
        description "Forwarding reset";
      }
      enum path-down {
        value 5;
        description "Path down";
      }
      enum concatenated-path-down {
        value 6;
        description "Concatenated path down";
      }
      enum admin-down {
        value 7;
        description "Admin down";
      }
      enum reverse-concatenated-path-down {
        value 8;
        description "Reverse concatenated path down";
      }
      enum mis-connectivity-defect {
        value 9;
        description "Mis-connectivity defect as specified in RFC6428";
      }
    }
    description
      "BFD diagnostic as defined in RFC 5880. Range is 0 to 31.";
  }

  typedef auth-type {
    type enumeration {
      enum reserved {
        value 0;
        description "Reserved";
      }
      enum simple-password {
        value 1;
        description "Simple password";
      }
      enum keyed-md5 {
        value 2;
        description "Keyed MD5";
      }
      enum meticulous-keyed-md5 {
        value 3;
        description "Meticulous keyed MD5";
      }
      enum keyed-sha1 {
        value 4;
        description "Keyed SHA1";
      }
      enum meticulous-keyed-sha1 {
        value 5;
        description "Meticulous keyed SHA1";
      }
    }
    description
      "BFD authentication type as defined in RFC 5880. Range is 0 to
       255.";
  }
}
