module ietf-flexi-grid-topology {
  yang-version 1.1;
  namespace "urn:ietf:params:xml:ns:yang:ietf-flexi-grid-topology";

prefix "flexi-grid-topology";

import ietf-network {
  prefix "nw";
  reference
    "RFC 8345: A YANG Data Model for Network Topologies";
}

import ietf-network-topology {
  prefix "nt";
  reference
    "RFC 8345: A YANG Data Model for Network Topologies";
}

import ietf-te-topology {
  prefix "tet";
  reference
    "RFC YYYY: YANG Data Model for
     Traffic Engineering (TE) Topologies";
}

import ietf-layer0-types {
  prefix "layer0-types";
  reference
    "RFC ZZZZ: A YANG Data Model for WSON
     (Wavelength Switched Optical Networks)";
}

  organization
     "IETF CCAMP Working Group";
   contact
     "WG Web: <http://tools.ietf.org/wg/ccamp/>
      WG List: <mailto:ccamp@ietf.org>

      Editor: Jorge E. Lopez de Vergara  
        <mailtojorge.lopez_vergara@uam.es>

      Editor: Daniel Perdices 
        <mailto:daniel.perdices@naudit.es>

      Editor: Haomian Zheng
        <mailto:zhenghaomian@huawei.com>

      Editor: Daniel King
        <mailto:d.king@lancaster.ac.uk>";

      Editor: Young Lee
        <mailto:younglee.tx@gmail.com>

   description
     "This module defines a model for flexi-grid topology

   Copyright (c) 2020 IETF Trust and the persons identified
   as authors of the code.  All rights reserved.

   Redistribution and use in source and binary forms, with
   or without modification, is permitted pursuant to, and
   subject to the license terms contained in, the Simplified BSD
   License set forth in Section 4.c of the IETF Trust's Legal
   Provisions Relating to IETF Documents
   (http://trustee.ietf.org/license-info).";

revision 2020-07-12 {
  description
    "Initial Version";

  reference
    "RFC ZZZZ: A Yang Data Model for flexi-grid Optical Networks ";
}

/*
 * Groupings
 */
grouping flexi-grid-node-attributes {
  description "flexi-grid node attributes.";

  container flexi-grid-node {
    description "flexi-grid node attrtibutes.";
    leaf node-type {
      type identityref {
        base l0-types:layer0-node-type;
      }
      description "flexi-grid node type.";
    }
  }
}

grouping flexi-grid-link-attributes {
  description
   "Future flexi-grid link attributes extensions";
}
grouping flexi-grid-tp-attributes {
  description "flexi-grid-tp-attributes";

  list supported-payload-types {
    key "index";
    description
      "Supported payload types of a TP. The payload type is defined
       as the generalized PIDs in GMPLS.";
    leaf index {
      type uint16;
      description "payload type index";
    }
    leaf payload-type {
      type string;
      description "the payload type supported by this client tp";
      reference
        "http://www.iana.org/assignments/gmpls-sig-parameters
         /gmpls-sig-parameters.xhtml";
    }
  }
  leaf client-facing {
    type boolean;
    default 'false';
    description
      "Indicating if it is a client-facing TP.";
  }
}

grouping flexi-grid-ttp-attributes {
  description
   "flexi-grid tunnel termination point (e.g.tranponder)
     attributes";
  leaf-list supported-operational-modes {
    type l0-types:operational-mode;
    description
      "List of all supported vendor-specific
       mode identifiers";
  }
  leaf configured-operational-modes {
    type l0-types:operational-mode;
    description
     "Vendor-specific mode identifier configured
       on the TTP.";
  }

  leaf-list supported-fec-types {
    type identityref {
      base l0-types:fec-type;
    }
     description
      "List of all supported FEC types by this TTP.";
  }

  leaf-list supported-termination-types {
    type identityref {
      base l0-types:term-type;
    }
      description
       "List of all supported termination types by this TTP.";
  }

  leaf supports-bit-stuffing {
     type boolean;
     description
       "Indicate whether bit stuffing is supported by this TTP.";
  }

  leaf is-tunable {
    type boolean;
    description 
      "Indicates if the TTP, or transponder, is tunable. Tunable
       transponders are assumed to be fully tunable to any of the 
       96 channels within DWDM C-band.";
  }

  leaf max-subcarrier-channel-num {
    type uint8 {
   range "1..max";
    }
    default 1;
    description
      "Indicate the maximum number of subcarrier channels for 
        super-channel transponders. When the value equals 1 it
        represents regular single-channel transponder.";
  }
  leaf supports-flexi-grid {
    type boolean;
    description 
      "Indicates if the TTP, or transponder, supports flex grid.";
  }
}

/*
 * Data nodes
 */

augment "/nw:networks/nw:network/nw:network-types"
 + "/tet:te-topology" {
    description "flexi-grid-topology augmented";
    container flexi-grid-topology {
      presence "indicates a topology of Flex Grid";
      description
        "Container to identify flexi-grid topology type";
    }
}

augment "/nw:networks/nw:network/nt:link/tet:te"
      + "/tet:te-link-attributes"   {
  when "/nw:networks/nw:network/nw:network-types"
      +"/tet:te-topology/flexi-grid:flexi-grid-topology" {
     description "This augment is only valid for flexi-grid.";
  }
  description "flexi-grid Link augmentation.";
  uses flexi-grid-link-attributes;
}

augment "/nw:networks/nw:network/nw:node/nt:termination-point/"
      + "tet:te" {
  when "/nw:networks/nw:network/nw:network-types"
      +"/tet:te-topology/flexi-grid:flexi-grid-topology" {
     description "This augment is only valid for flexi-grid.";
  }
  description "flexi-grid TP attributes.";
  uses flexi-grid-tp-attributes;
}

augment "/nw:networks/nw:network/nw:node/tet:te"
      + "/tet:te-node-attributes" {
  when "/nw:networks/nw:network/nw:network-types"
     +"/tet:te-topology/flexi-grid:flexi-grid-topology" {
     description "This augment is only valid for flexi-grid.";
  }
  description "flexi-grid Node augmentation.";
  uses flexi-grid-node-attributes;
}
augment "/nw:networks/nw:network/nw:node/tet:te"
      + "/tet:tunnel-termination-point" {
  when "/nw:networks/nw:network/nw:network-types"
     +"/tet:te-topology/flexi-grid:flexi-grid-topology" {
    description "This augment is only valid for flexi-grid.";
  }
  description "flexi-grid tunnel termination point augmentation.";
  uses flexi-grid-ttp-attributes;
}

/*
 * Augment TE bandwidth
 */

/* Augment maximum LSP bandwidth of link terminationpoint (LTP) */
augment "/nw:networks/nw:network/nw:node/nt:termination-point/"
      + "tet:te/"
      + "tet:interface-switching-capability/tet:max-lsp-bandwidth/"
      + "tet:te-bandwidth/tet:technology" {
  when "../../../../../../nw:network-types/tet:te-topology/"
     + "flexi-grid:flexi-grid-topology" {
    description "Augment flexi-grid TE bandwidth";
  }
  description "flexi-grid bandwidth.";
  case flexi-grid {
    uses l0-types:flexi-grid-path-bandwidth;
  }
}

/* Augment bandwidth path constraints of connectivity-matrices */
augment "/nw:networks/nw:network/nw:node/tet:te/"
      + "tet:te-node-attributes/tet:connectivity-matrices/"
      + "tet:path-constraints/tet:te-bandwidth/tet:technology" {
  when "../../../../../../nw:network-types/tet:te-topology/"
     + "flexi-grid:flexi-grid-topology" {
    description "Augment flexi-grid TE bandwidth";
  }
  description "flexi-grid bandwidth.";
  case flexi-grid {
    uses l0-types:flexi-grid-link-bandwidth;
  }
}
/* Augment bandwidth path constraints of connectivity-matrix */
augment "/nw:networks/nw:network/nw:node/tet:te/"
      + "tet:te-node-attributes/tet:connectivity-matrices/"
      + "tet:connectivity-matrix/"
      + "tet:path-constraints/tet:te-bandwidth/tet:technology" {
  when "../../../../../../../nw:network-types/tet:te-topology/"
     + "flexi-grid:flexi-grid-topology" {
    description "Augment flexi-grid TE bandwidth";
  }
  description "flexi-grid bandwidth.";
  case flexi-grid {
    uses l0-types:flexi-grid-link-bandwidth;
  }
}

/* Augment bandwidth path constraints of connectivity-matrices
   information-source */
augment "/nw:networks/nw:network/nw:node/tet:te/"
      + "tet:information-source-entry/tet:connectivity-matrices/"
      + "tet:path-constraints/tet:te-bandwidth/tet:technology" {
  when "../../../../../../nw:network-types/tet:te-topology/"
     + "flexi-grid:flexi-grid-topology" {
    description "Augment flexi-grid TE bandwidth";
  }
  description "flexi-grid bandwidth.";
  case flexi-grid {
    uses l0-types:flexi-grid-link-bandwidth;
  }
}

/* Augment bandwidth path constraints of connectivity-matrix 
   information-source */
augment "/nw:networks/nw:network/nw:node/tet:te/"
      + "tet:information-source-entry/tet:connectivity-matrices/"
      + "tet:connectivity-matrix/"
      + "tet:path-constraints/tet:te-bandwidth/tet:technology" {
  when "../../../../../../../nw:network-types/tet:te-topology/"
     + "flexi-grid:flexi-grid-topology" {
    description "Augment flexi-grid TE bandwidth";
  }
  description "flexi-grid bandwidth.";
  case flexi-grid {
    uses l0-types:flexi-grid-link-bandwidth;
  }
}
/* Augment client bandwidth of tunnel termination point (TTP) */
augment "/nw:networks/nw:network/nw:node/tet:te/"
      + "tet:tunnel-termination-point/"
      + "tet:client-layer-adaptation/tet:switching-capability/"
      + "tet:te-bandwidth/tet:technology" {
  when "../../../../../../nw:network-types/tet:te-topology/"
     + "flexi-grid:flexi-grid-topology" {
    description "Augment flexi-grid TE bandwidth";
  }
  description "flexi-grid bandwidth.";
  case flexi-grid {
    uses l0-types:flexi-grid-link-bandwidth;
  }
}

/* Augment bandwidth path constraints of local-link-connectivities */
augment "/nw:networks/nw:network/nw:node/tet:te/"
      + "tet:tunnel-termination-point/"
      + "tet:local-link-connectivities/tet:path-constraints/"
      + "tet:te-bandwidth/tet:technology" {
  when "../../../../../../nw:network-types/tet:te-topology/"
     + "flexi-grid:flexi-grid-topology" {
    description "Augment flexi-grid TE bandwidth";
  }
  description "flexi-grid bandwidth.";
  case flexi-grid {
    uses l0-types:flexi-grid-link-bandwidth;
  }
}

/* Augment bandwidth path constraints of local-link-connectivity
   (LLC) */
augment "/nw:networks/nw:network/nw:node/tet:te/"
      + "tet:tunnel-termination-point/"
      + "tet:local-link-connectivities/"
      + "tet:local-link-connectivity/tet:path-constraints/"
      + "tet:te-bandwidth/tet:technology" {
  when "../../../../../../../nw:network-types/tet:te-topology/"
     + "flexi-grid:flexi-grid-topology" {
    description "Augment flexi-grid TE bandwidth";
  }
  description "flexi-grid bandwidth.";
  case flexi-grid {
    uses l0-types:flexi-grid-link-bandwidth;
  }
}
/* Augment maximum LSP bandwidth of TE link */
augment "/nw:networks/nw:network/nt:link/tet:te/"
      + "tet:te-link-attributes/"
      + "tet:interface-switching-capability/tet:max-lsp-bandwidth/"
      + "tet:te-bandwidth/tet:technology" {
  when "../../../../../../nw:network-types/tet:te-topology/"
     + "flexi-grid:flexi-grid-topology" {
    description "flexi-grid TE bandwidth.";
  }
  description "flexi-grid bandwidth.";
  case flexi-grid {
    uses l0-types:flexi-grid-path-bandwidth;
  }
}

/* Augment maximum bandwidth of TE link */
augment "/nw:networks/nw:network/nt:link/tet:te/"
      + "tet:te-link-attributes/"
      + "tet:max-link-bandwidth/"
      + "tet:te-bandwidth/tet:technology" {
  when "../../../../../nw:network-types/tet:te-topology/"
     + "flexi-grid:flexi-grid-topology" {
    description "flexi-grid TE bandwidth.";
  }
  description "flexi-grid bandwidth.";
  case flexi-grid {
    uses l0-types:flexi-grid-link-bandwidth;
  }
}

/* Augment maximum reservable bandwidth of TE link */
augment "/nw:networks/nw:network/nt:link/tet:te/"
      + "tet:te-link-attributes/"
      + "tet:max-resv-link-bandwidth/"
      + "tet:te-bandwidth/tet:technology" {
  when "../../../../../nw:network-types/tet:te-topology/"
     + "flexi-grid:flexi-grid-topology" {
    description "flexi-grid TE bandwidth.";
  }
  description "flexi-grid bandwidth.";
  case flexi-grid {
    uses l0-types:flexi-grid-link-bandwidth;
  }
}
/* Augment unreserved bandwidth of TE Link */
augment "/nw:networks/nw:network/nt:link/tet:te/"
      + "tet:te-link-attributes/"
      + "tet:unreserved-bandwidth/"
      + "tet:te-bandwidth/tet:technology" {
  when "../../../../../nw:network-types/tet:te-topology/"
     + "flexi-grid:flexi-grid-topology" {
    description "flexi-grid TE bandwidth.";
  }
  description "flexi-grid bandwidth.";
  case flexi-grid {
    uses l0-types:flexi-grid-link-bandwidth;
  }
}
/* Augment maximum LSP bandwidth of TE link information-source */
augment "/nw:networks/nw:network/nt:link/tet:te/"
      + "tet:information-source-entry/"
      + "tet:interface-switching-capability/"
      + "tet:max-lsp-bandwidth/"
      + "tet:te-bandwidth/tet:technology" {
  when "../../../../../../nw:network-types/tet:te-topology/"
     + "flexi-grid:flexi-grid-topology" {
    description "flexi-grid TE bandwidth.";
  }
  description "flexi-grid bandwidth.";
  case flexi-grid {
    uses l0-types:flexi-grid-path-bandwidth;
  }
}

/* Augment maximum bandwidth of TE link information-source */
augment "/nw:networks/nw:network/nt:link/tet:te/"
      + "tet:information-source-entry/"
      + "tet:max-link-bandwidth/"
      + "tet:te-bandwidth/tet:technology" {
  when "../../../../../nw:network-types/tet:te-topology/"
     + "flexi-grid:flexi-grid-topology" {
    description "flexi-grid TE bandwidth.";
  }
  description "flexi-grid bandwidth.";
  case flexi-grid {
    uses l0-types:flexi-grid-link-bandwidth;
  }
}
/* Augment maximum reservable bandwidth of TE link information-source
 */
augment "/nw:networks/nw:network/nt:link/tet:te/"
      + "tet:information-source-entry/"
      + "tet:max-resv-link-bandwidth/"
      + "tet:te-bandwidth/tet:technology" {
  when "../../../../../nw:network-types/tet:te-topology/"
     + "flexi-grid:flexi-grid-topology" {
    description "flexi-grid TE bandwidth.";
  }
  description "flexi-grid bandwidth.";
  case flexi-grid {
    uses l0-types:flexi-grid-link-bandwidth;
  }
}

/* Augment unreserved bandwidth of TE link information-source */
augment "/nw:networks/nw:network/nt:link/tet:te/"
      + "tet:information-source-entry/"
      + "tet:unreserved-bandwidth/"
      + "tet:te-bandwidth/tet:technology" {
  when "../../../../../nw:network-types/tet:te-topology/"
     + "flexi-grid:flexi-grid-topology" {
    description "flexi-grid TE bandwidth.";
  }
  description "flexi-grid bandwidth.";
  case flexi-grid {
    uses l0-types:flexi-grid-link-bandwidth;
  }
}

/* Augment maximum LSP bandwidth of TE link template */
augment "/nw:networks/tet:te/tet:templates/"
      + "tet:link-template/tet:te-link-attributes/"
      + "tet:interface-switching-capability/"
      + "tet:max-lsp-bandwidth/"
      + "tet:te-bandwidth/tet:technology" {
/*
    when "../../../../../../nw:network-types/tet:te-topology/"
       + "flexi-grid:flexi-grid-topology" {
      description "flexi-grid TE bandwidth.";
    }
*/
    description "flexi-grid bandwidth.";
    case flexi-grid {
      uses l0-types:flexi-grid-path-bandwidth;
    }
  }
  /* Augment maximum bandwidth of TE link template */
  augment "/nw:networks/tet:te/tet:templates/"
        + "tet:link-template/tet:te-link-attributes/"
        + "tet:max-link-bandwidth/"
        + "tet:te-bandwidth/tet:technology" {
/*
    when "../../../../../nw:network-types/tet:te-topology/"
        + "flexi-grid:flexi-grid-topology" {
      description "flexi-grid TE bandwidth.";
    }
*/
    description "flexi-grid bandwidth.";
    case flexi-grid {
      uses l0-types:flexi-grid-link-bandwidth;
    }
  }
  /* Augment maximum reservable bandwidth of TE link template */
  augment "/nw:networks/tet:te/tet:templates/"
        + "tet:link-template/tet:te-link-attributes/"
        + "tet:max-resv-link-bandwidth/"
        + "tet:te-bandwidth/tet:technology" {
/*
    when "../../../../../nw:network-types/tet:te-topology/"
        + "flexi-grid:flexi-grid-topology" {
      description "flexi-grid TE bandwidth.";
    }
*/
    description "flexi-grid bandwidth.";
    case flexi-grid {
      uses l0-types:flexi-grid-link-bandwidth;
    }
  }

  /* Augment unreserved bandwidth of TE link template */
  augment "/nw:networks/tet:te/tet:templates/"
        + "tet:link-template/tet:te-link-attributes/"
        + "tet:unreserved-bandwidth/"
        + "tet:te-bandwidth/tet:technology" {
/*
    when "../../../../../../nw:network-types/tet:te-topology/"
        + "flexi-grid:flexi-grid-topology" {
      description "flexi-grid TE bandwidth.";
    }
*/
    description "flexi-grid bandwidth.";
    case flexi-grid {
      uses l0-types:flexi-grid-link-bandwidth;
    }
  }

  /*
   * Augment TE label.
   */

  /* Augment label restrictions of connectivity-matrices */
  augment "/nw:networks/nw:network/nw:node/tet:te/"
        + "tet:te-node-attributes/tet:connectivity-matrices/"
        + "tet:label-restrictions/tet:label-restriction" {
    when "../../../../../../nw:network-types/tet:te-topology/"
       + "flexi-grid:flexi-grid-topology" {
      description "Augment flexi-grid TE label";
    }
    description "flexi-grid label.";
    uses l0-types:flexi-grid-label-restriction;
  }
  /* Augment label restrictions start of connectivity-matrices */
  augment "/nw:networks/nw:network/nw:node/tet:te/"
        + "tet:te-node-attributes/tet:connectivity-matrices/"
        + "tet:label-restrictions/tet:label-restriction/"    
        + "tet:label-start/"
        + "tet:te-label/tet:technology" {
    when "../../../../../../../../nw:network-types/tet:te-topology/"
       + "flexi-grid:flexi-grid-topology" {
      description "Augment flexi-grid TE label";
    }
    description "flexi-grid label.";
    case flexi-grid {
      uses l0-types:flexi-grid-link-label;
    }
  }
  /* Augment label restrictions end of connectivity-matrices */
  augment "/nw:networks/nw:network/nw:node/tet:te/"
        + "tet:te-node-attributes/tet:connectivity-matrices/"
        + "tet:label-restrictions/" 
        + "tet:label-restriction/tet:label-end/"
        + "tet:te-label/tet:technology" {
    when "../../../../../../../../"
       + "nw:network-types/tet:te-topology/"
       + "flexi-grid:flexi-grid-topology" {
      description "Augment flexi-grid TE label";
    }
    description "flexi-grid label.";
    case flexi-grid {
      uses l0-types:flexi-grid-link-label;
    }
  }

  /* Augment label restrictions step of connectivity-matrices */
  augment "/nw:networks/nw:network/nw:node/tet:te/"
        + "tet:te-node-attributes/tet:connectivity-matrices/"
        + "tet:label-restrictions/" 
        + "tet:label-restriction/tet:label-step/"
        + "tet:technology" {
    when "../../../../../../../"
       + "nw:network-types/tet:te-topology/"
       + "flexi-grid:flexi-grid-topology" {
      description "Augment flexi-grid TE label";
    }
    description "flexi-grid label step.";
    case flexi-grid {
      uses l0-types:flexi-grid-label-step;
    }
  }
  /* Augment label hop of underlay primary path of connectivity-matrices
   */
  augment "/nw:networks/nw:network/nw:node/tet:te/"
        + "tet:te-node-attributes/tet:connectivity-matrices/"
        + "tet:underlay/tet:primary-path/tet:path-element/"
        + "tet:type/tet:label/tet:label-hop/"
        + "tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of underlay backup path of connectivity-matrices
   */
  augment "/nw:networks/nw:network/nw:node/tet:te/"
        + "tet:te-node-attributes/tet:connectivity-matrices/"
        + "tet:underlay/tet:backup-path/tet:path-element/"
        + "tet:type/tet:label/tet:label-hop/"
        + "tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of route-exclude of connectivity-matrices */
  augment "/nw:networks/nw:network/nw:node/tet:te/"
        + "tet:te-node-attributes/tet:connectivity-matrices/"
        + "tet:optimizations/tet:algorithm/tet:metric/"
        + "tet:optimization-metric/"
        + "tet:explicit-route-exclude-objects/"
        + "tet:route-object-exclude-object/"
        + "tet:type/tet:label/tet:label-hop/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of route-include of connectivity-matrices (added)
   */
  augment "/nw:networks/nw:network/nw:node/tet:te/"
        + "tet:te-node-attributes/tet:connectivity-matrices/"
        + "tet:optimizations/tet:algorithm/tet:metric/"
        + "tet:optimization-metric/"
        + "tet:explicit-route-include-objects/"
        + "tet:route-object-include-object/"
        + "tet:type/tet:label/tet:label-hop/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of path-route of connectivity-matrices */
  augment "/nw:networks/nw:network/nw:node/tet:te/"
        + "tet:te-node-attributes/tet:connectivity-matrices/"
        + "tet:path-properties/tet:path-route-objects/"
        + "tet:path-route-object/tet:type/tet:label/tet:label-hop/"
        + "tet:te-label/tet:technology"{
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment ingress label restrictions of connectivity-matrix */
  augment "/nw:networks/nw:network/nw:node/tet:te/"
        + "tet:te-node-attributes/tet:connectivity-matrices/"
        + "tet:connectivity-matrix/tet:from/"
        + "tet:label-restrictions/tet:label-restriction" {
    when "../../../../../../../../"
       + "nw:network-types/tet:te-topology/"
       + "flexi-grid:flexi-grid-topology" {
      description "Augment flexi-grid TE label";
    }
    description "flexi-grid label.";
    uses l0-types:flexi-grid-label-restriction;
  }

  /* Augment ingress label restrictions start of connectivity-matrix */
  augment "/nw:networks/nw:network/nw:node/tet:te/"
        + "tet:te-node-attributes/tet:connectivity-matrices/"
        + "tet:connectivity-matrix/tet:from/"
        + "tet:label-restrictions/tet:label-restriction/" 
        + "tet:label-start/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment ingress label restrictions end of connectivity-matrix */
  augment "/nw:networks/nw:network/nw:node/tet:te/"
        + "tet:te-node-attributes/tet:connectivity-matrices/"
        + "tet:connectivity-matrix/tet:from/"
        + "tet:label-restrictions/tet:label-restriction/" 
        + "tet:label-end/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment ingress label restrictions step of connectivity-matrix */
  augment "/nw:networks/nw:network/nw:node/tet:te/"
        + "tet:te-node-attributes/tet:connectivity-matrices/"
        + "tet:connectivity-matrix/tet:from/"
        + "tet:label-restrictions/tet:label-restriction/" 
        + "tet:label-step/"
        + "tet:technology" {
    when "../../../../../../../../../"
       + "nw:network-types/tet:te-topology/"
       + "flexi-grid:flexi-grid-topology" {
      description "Augment flexi-grid TE label";
    }
    description "flexi-grid label.";
    case flexi-grid {
      uses l0-types:flexi-grid-label-step;
    }
  }

  /* Augment egress label restrictions of connectivity-matrix */
  augment "/nw:networks/nw:network/nw:node/tet:te/"
        + "tet:te-node-attributes/tet:connectivity-matrices/"
        + "tet:connectivity-matrix/tet:to/"
        + "tet:label-restrictions/tet:label-restriction" {
    when "../../../../../../../../"
       + "nw:network-types/tet:te-topology/"
       + "flexi-grid:flexi-grid-topology" {
      description "Augment flexi-grid TE label";
    }
    description "flexi-grid label.";
    uses l0-types:flexi-grid-label-restriction;
  }

  /* Augment egress label restrictions start of connectivity-matrix */
  augment "/nw:networks/nw:network/nw:node/tet:te/"
        + "tet:te-node-attributes/tet:connectivity-matrices/"
        + "tet:connectivity-matrix/tet:to/"
        + "tet:label-restrictions/tet:label-restriction/" 
        + "tet:label-start/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment egress label restrictions end of connectivity-matrix */
  augment "/nw:networks/nw:network/nw:node/tet:te/"
        + "tet:te-node-attributes/tet:connectivity-matrices/"
        + "tet:connectivity-matrix/tet:to/"
        + "tet:label-restrictions/tet:label-restriction/" 
        + "tet:label-end/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }

  /* Augment egress label restrictions step of connectivity-matrix */
  augment "/nw:networks/nw:network/nw:node/tet:te/"
        + "tet:te-node-attributes/tet:connectivity-matrices/"
        + "tet:connectivity-matrix/tet:to/"
        + "tet:label-restrictions/tet:label-restriction/" 
        + "tet:label-step/"
        + "tet:technology" {
    when "../../../../../../../../../"
       + "nw:network-types/tet:te-topology/"
       + "flexi-grid:flexi-grid-topology" {
      description "Augment flexi-grid TE label";
    }
    description "flexi-grid label.";
    case flexi-grid {
      uses l0-types:flexi-grid-label-step;
    }
  }
  /* Augment label hop of underlay primary path of connectivity-matrix 
   */
  augment "/nw:networks/nw:network/nw:node/tet:te/"
        + "tet:te-node-attributes/tet:connectivity-matrices/"
        + "tet:connectivity-matrix/"
        + "tet:underlay/tet:primary-path/tet:path-element/"
        + "tet:type/tet:label/tet:label-hop/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of underlay backup path of connectivity-matrix */
  augment "/nw:networks/nw:network/nw:node/tet:te/"
        + "tet:te-node-attributes/tet:connectivity-matrices/"
        + "tet:connectivity-matrix/"
        + "tet:underlay/tet:backup-path/tet:path-element/"
        + "tet:type/tet:label/tet:label-hop/"
        + "tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of route-exclude of connectivity-matrix */
  augment "/nw:networks/nw:network/nw:node/tet:te/"
        + "tet:te-node-attributes/tet:connectivity-matrices/"
        + "tet:connectivity-matrix/tet:optimizations/"
        + "tet:algorithm/tet:metric/tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of route-include of connectivity-matrix */
  augment "/nw:networks/nw:network/nw:node/tet:te/"
        + "tet:te-node-attributes/tet:connectivity-matrices/"
        + "tet:connectivity-matrix/tet:optimizations/"
        + "tet:algorithm/tet:metric/tet:optimization-metric/"
        + "tet:explicit-route-include-objects/"
        + "tet:route-object-include-object/tet:type/"
        + "tet:label/tet:label-hop/tet:te-label/tet:technology" {
    when "../../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of path-route of connectivity-matrix */
  augment "/nw:networks/nw:network/nw:node/tet:te/"
        + "tet:te-node-attributes/tet:connectivity-matrices/"
        + "tet:connectivity-matrix/"
        + "tet:path-properties/tet:path-route-objects/"
        + "tet:path-route-object/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label restrictions of connectivity-matrices 
     information-source */
  augment "/nw:networks/nw:network/nw:node/tet:te/"
        + "tet:information-source-entry/"
        + "tet:connectivity-matrices/tet:label-restrictions/"
        + "tet:label-restriction" {
    when "../../../../../../nw:network-types/tet:te-topology/"
       + "flexi-grid:flexi-grid-topology" {
      description "Augment flexi-grid TE label";
    }
    description "flexi-grid label.";
    uses l0-types:flexi-grid-label-restriction;
  }

  /* Augment label restrictions start of connectivity-matrices 
     information-source */
  augment "/nw:networks/nw:network/nw:node/tet:te/"
        + "tet:information-source-entry/"
        + "tet:connectivity-matrices/tet:label-restrictions/"
        + "tet:label-restriction/"
        + "tet:label-start/tet:te-label/tet:technology" {
    when "../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment label restrictions end of connectivity-matrices 
     information-source */
  augment "/nw:networks/nw:network/nw:node/tet:te/"
        + "tet:information-source-entry/"
        + "tet:connectivity-matrices/tet:label-restrictions/"
        + "tet:label-restriction/"
        + "tet:label-end/tet:te-label/tet:technology" {
    when "../../../../../../../../"
       + "nw:network-types/tet:te-topology/"
       + "flexi-grid:flexi-grid-topology" {
      description "Augment flexi-grid TE label";
    }
    description "flexi-grid label.";
    case flexi-grid {
      uses l0-types:flexi-grid-link-label;
    }
  }

  /* Augment label restrictions step of connectivity-matrices 
     information-source */
  augment "/nw:networks/nw:network/nw:node/tet:te/"
        + "tet:information-source-entry/"
        + "tet:connectivity-matrices/tet:label-restrictions/"
        + "tet:label-restriction/"
        + "tet:label-step/tet:technology" {
    when "../../../../../../../"
       + "nw:network-types/tet:te-topology/"
       + "flexi-grid:flexi-grid-topology" {
      description "Augment flexi-grid TE label";
    }
    description "flexi-grid label.";
    case flexi-grid {
      uses l0-types:flexi-grid-label-step;
    }
  }

  /* Augment label hop of underlay primary path of connectivity-matrices
information-source */
  augment "/nw:networks/nw:network/nw:node/tet:te/"
        + "tet:information-source-entry/tet:connectivity-matrices/"
        + "tet:underlay/tet:primary-path/tet:path-element/tet:type/"
        + "tet:label/tet:label-hop/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of underlay backup path of connectivity-matrices
information-source */
  augment "/nw:networks/nw:network/nw:node/tet:te/"
        + "tet:information-source-entry/tet:connectivity-matrices/"
        + "tet:underlay/tet:backup-path/tet:path-element/tet:type/"
        + "tet:label/tet:label-hop/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of route-exclude of connectivity-matrices 
     information-source */
  augment "/nw:networks/nw:network/nw:node/tet:te/"
        + "tet:information-source-entry/tet:connectivity-matrices/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of route-include of connectivity-matrices 
     information-source */
  augment "/nw:networks/nw:network/nw:node/tet:te/"
        + "tet:information-source-entry/tet:connectivity-matrices/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of path-route of connectivity-matrices
     information-source */
  augment "/nw:networks/nw:network/nw:node/tet:te/"
        + "tet:information-source-entry/tet:connectivity-matrices/"
        + "tet:path-properties/tet:path-route-objects/"
        + "tet:path-route-object/tet:type/"
        + "tet:label/tet:label-hop/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment ingress label restrictions of connectivity-matrix
     information-source */
  augment "/nw:networks/nw:network/nw:node/tet:te/"
        + "tet:information-source-entry/tet:connectivity-matrices/"
        + "tet:connectivity-matrix/"
        + "tet:from/tet:label-restrictions/tet:label-restriction" {
    when "../../../../../../../../"
       + "nw:network-types/tet:te-topology/"
       + "flexi-grid:flexi-grid-topology" {
      description "Augment flexi-grid TE label";
    }
    description "flexi-grid label.";
    uses l0-types:flexi-grid-label-restriction;
  }

  /* Augment ingress label restrictions start of connectivity-matrix
information-source */
  augment "/nw:networks/nw:network/nw:node/tet:te/"
        + "tet:information-source-entry/tet:connectivity-matrices/"
        + "tet:connectivity-matrix/"
        + "tet:from/tet:label-restrictions/" 
        + "tet:label-restriction/"
        + "tet:label-start/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }

  /* Augment ingress label restrictions end of connectivity-matrix
information-source */
  augment "/nw:networks/nw:network/nw:node/tet:te/"
        + "tet:information-source-entry/tet:connectivity-matrices/"
        + "tet:connectivity-matrix/"
        + "tet:from/tet:label-restrictions/" 
        + "tet:label-restriction/"
        + "tet:label-end/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment ingress label restrictions step of connectivity-matrix
information-source */
  augment "/nw:networks/nw:network/nw:node/tet:te/"
        + "tet:information-source-entry/tet:connectivity-matrices/"
        + "tet:connectivity-matrix/"
        + "tet:from/tet:label-restrictions/" 
        + "tet:label-restriction/"
        + "tet:label-step/tet:technology" {
    when "../../../../../../../../../"
       + "nw:network-types/tet:te-topology/"
       + "flexi-grid:flexi-grid-topology" {
      description "Augment flexi-grid TE label";
    }
    description "flexi-grid label.";
    case flexi-grid {
      uses l0-types:flexi-grid-label-step;
    }
  }
  /* Augment egress label restrictions of connectivity-matrix
     information-source */
  augment "/nw:networks/nw:network/nw:node/tet:te/"
        + "tet:information-source-entry/tet:connectivity-matrices/"
        + "tet:connectivity-matrix/"
        + "tet:to/tet:label-restrictions/tet:label-restriction" {
    when "../../../../../../../../"
       + "nw:network-types/tet:te-topology/"
       + "flexi-grid:flexi-grid-topology" {
      description "Augment flexi-grid TE label";
    }
    description "flexi-grid label.";
    uses l0-types:flexi-grid-label-restriction;
  }

  /* Augment egress label restrictions start of connectivity-matrix
information-source */
  augment "/nw:networks/nw:network/nw:node/tet:te/"
        + "tet:information-source-entry/tet:connectivity-matrices/"
        + "tet:connectivity-matrix/"
        + "tet:to/tet:label-restrictions/tet:label-restriction/"
        + "tet:label-start/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment egress label restrictions end of connectivity-matrix
     information-source */
  augment "/nw:networks/nw:network/nw:node/tet:te/"
        + "tet:information-source-entry/tet:connectivity-matrices/"
        + "tet:connectivity-matrix/"
        + "tet:to/tet:label-restrictions/tet:label-restriction/"
        + "tet:label-end/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-link-label;
    }
  }

  /* Augment egress label restrictions step of connectivity-matrix
     information-source */
  augment "/nw:networks/nw:network/nw:node/tet:te/"
        + "tet:information-source-entry/tet:connectivity-matrices/"
        + "tet:connectivity-matrix/"
        + "tet:to/tet:label-restrictions/tet:label-restriction/"
        + "tet:label-step/tet:technology" {
    when "../../../../../../../../../"
       + "nw:network-types/tet:te-topology/"
       + "flexi-grid:flexi-grid-topology" {
      description "Augment flexi-grid TE label";
    }
    description "flexi-grid label.";
    case flexi-grid {
      uses l0-types:flexi-grid-label-step;
    }
  }

  /* Augment label hop of underlay primary path of connectivity-matrix
     information-source */
  augment "/nw:networks/nw:network/nw:node/tet:te/"
        + "tet:information-source-entry/tet:connectivity-matrices/"
        + "tet:connectivity-matrix/"
        + "tet:underlay/tet:primary-path/tet:path-element/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of underlay backup path of connectivity-matrix
     information-source */
  augment "/nw:networks/nw:network/nw:node/tet:te/"
        + "tet:information-source-entry/tet:connectivity-matrices/"
        + "tet:connectivity-matrix/"
        + "tet:underlay/tet:backup-path/tet:path-element/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of route-exclude of connectivity-matrix
     information-source */
  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of route-include of connectivity-matrix
     information-source */
  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of path-route of connectivity-matrix
     information-source */
  augment "/nw:networks/nw:network/nw:node/tet:te/"
        + "tet:information-source-entry/tet:connectivity-matrices/"
        + "tet:connectivity-matrix/"
        + "tet:path-properties/tet:path-route-objects/"
        + "tet:path-route-object/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label restrictions of local-link-connectivities */
  augment "/nw:networks/nw:network/nw:node/tet:te/"
        + "tet:tunnel-termination-point/"
        + "tet:local-link-connectivities/"
        + "tet:label-restrictions/tet:label-restriction" {
    when "../../../../../../nw:network-types/tet:te-topology/"
       + "flexi-grid:flexi-grid-topology" {
      description "Augment flexi-grid TE label";
    }
    description "flexi-grid label.";
    uses l0-types:flexi-grid-label-restriction;
  }

  /* Augment label restrictions start of local-link-connectivities */
  augment "/nw:networks/nw:network/nw:node/tet:te/"
      + "tet:tunnel-termination-point/"
      + "tet:local-link-connectivities/"
      + "tet:label-restrictions/tet:label-restriction/"
      + "tet:label-start/"
      + "tet:te-label/tet:technology" {
    when "../../../../../../../../"
       + "nw:network-types/tet:te-topology/"
       + "flexi-grid:flexi-grid-topology" {
      description "Augment flexi-grid TE label";
    }
    description "flexi-grid label.";
    case flexi-grid {
      uses l0-types:flexi-grid-link-label;
    }
  }

  /* Augment label restrictions end of local-link-connectivities */
  augment "/nw:networks/nw:network/nw:node/tet:te/"
        + "tet:tunnel-termination-point/"
        + "tet:local-link-connectivities/"
        + "tet:label-restrictions/tet:label-restriction/"  
        + "tet:label-end/"
        + "tet:te-label/tet:technology"{
    when "../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment label restrictions step of local-link-connectivities */
  augment "/nw:networks/nw:network/nw:node/tet:te/"
        + "tet:tunnel-termination-point/"
        + "tet:local-link-connectivities/"
        + "tet:label-restrictions/tet:label-restriction/"  
        + "tet:label-step/"
        + "tet:technology"{
    when "../../../../../../../"
       + "nw:network-types/tet:te-topology/"
       + "flexi-grid:flexi-grid-topology" {
      description "Augment flexi-grid TE label";
    }
    description "flexi-grid label.";
    case flexi-grid {
      uses l0-types:flexi-grid-label-step;
    }
  }
  /* Augment label hop of underlay primary path of
     local-link-connectivities */
  augment "/nw:networks/nw:network/nw:node/tet:te/"
        + "tet:tunnel-termination-point/"
        + "tet:local-link-connectivities/"
        + "tet:underlay/tet:primary-path/tet:path-element/tet:type/"
        + "tet:label/tet:label-hop/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of underlay backup path of
     local-link-connectivities */
  augment "/nw:networks/nw:network/nw:node/tet:te/"
        + "tet:tunnel-termination-point/"
        + "tet:local-link-connectivities/"
        + "tet:underlay/tet:backup-path/tet:path-element/tet:type/"
        + "tet:label/tet:label-hop/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of route-exclude of local-link-connectivities */
  augment "/nw:networks/nw:network/nw:node/tet:te/"
        + "tet:tunnel-termination-point/"
        + "tet:local-link-connectivities/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of route-include of local-link-connectivities */
  augment "/nw:networks/nw:network/nw:node/tet:te/"
        + "tet:tunnel-termination-point/"
        + "tet:local-link-connectivities/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of path-route of local-link-connectivities */
  augment "/nw:networks/nw:network/nw:node/tet:te/"
        + "tet:tunnel-termination-point/"
        + "tet:local-link-connectivities/"
        + "tet:path-properties/tet:path-route-objects/"
        + "tet:path-route-object/tet:type/"
        + "tet:label/tet:label-hop/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label restrictions of local-link-connectivity (LLC) */
  augment "/nw:networks/nw:network/nw:node/tet:te/"
        + "tet:tunnel-termination-point/"
        + "tet:local-link-connectivities/"
        + "tet:local-link-connectivity/"
        + "tet:label-restrictions/tet:label-restriction" {
    when "../../../../../../../nw:network-types/tet:te-topology/"
       + "flexi-grid:flexi-grid-topology" {
      description "Augment flexi-grid TE label";
    }
    description "flexi-grid label.";
    uses l0-types:flexi-grid-label-restriction;
  }

 /* Augment label restrictions start of local-link-connectivity (LLC) 
   */
  augment "/nw:networks/nw:network/nw:node/tet:te/"
        + "tet:tunnel-termination-point/"
        + "tet:local-link-connectivities/"
        + "tet:local-link-connectivity/"
        + "tet:label-restrictions/tet:label-restriction/"
        + "tet:label-start/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-link-label;
    }
  }
 /* Augment label restrictions end of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-end/tet:te-label/tet:technology" {
    when "../../../../../../../../../"
       + "nw:network-types/tet:te-topology/"
       + "flexi-grid:flexi-grid-topology" {
      description "Augment flexi-grid TE label";
    }
    description "flexi-grid label.";
    case flexi-grid {
      uses l0-types:flexi-grid-link-label;
    }
  }
  /* Augment label restrictions step of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-step/tet:technology" {
    when "../../../../../../../../"
       + "nw:network-types/tet:te-topology/"
       + "flexi-grid:flexi-grid-topology" {
      description "Augment flexi-grid TE label";
    }
    description "flexi-grid label.";
    case flexi-grid {
      uses l0-types:flexi-grid-label-step;
    }
  }

  /* Augment label hop of underlay primary path of 
     local-link-connectivity (LLC) */
  augment "/nw:networks/nw:network/nw:node/tet:te/"
        + "tet:tunnel-termination-point/"
        + "tet:local-link-connectivities/"
        + "tet:local-link-connectivity/"
        + "tet:underlay/tet:primary-path/tet:path-element/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of underlay backup path of
     local-link-connectivity (LLC) */
  augment "/nw:networks/nw:network/nw:node/tet:te/"
        + "tet:tunnel-termination-point/"
        + "tet:local-link-connectivities/"
        + "tet:local-link-connectivity/"
        + "tet:underlay/tet:backup-path/tet:path-element/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of route-exclude of local-link-connectivity (LLC)
   */
  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of route-include of local-link-connectivity (LLC)
   */
  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../../"
       + "nw:network-types/tet:te-topology/"
       + "flexi-grid:flexi-grid-topology" {
      description "Augment flexi-grid TE label";
    }
    description "flexi-grid label.";
    case flexi-grid {
      uses l0-types:flexi-grid-path-label;
    }
  }

  /* Augment label hop of path-route of local-link-connectivity (LLC)
   */
  augment "/nw:networks/nw:network/nw:node/tet:te/"
        + "tet:tunnel-termination-point/"
        + "tet:local-link-connectivities/"
        + "tet:local-link-connectivity/"
        + "tet:path-properties/tet:path-route-objects/"
        + "tet:path-route-object/tet:type/"
        + "tet:label/tet:label-hop/tet:te-label/tet:technology" {
    when "../../../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of underlay primary path of TE link */
  augment "/nw:networks/nw:network/nt:link/tet:te/"
        + "tet:te-link-attributes/"
        + "tet:underlay/tet:primary-path/tet:path-element/tet:type/"
        + "tet:label/tet:label-hop/tet:te-label/tet:technology" {
    when "../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label hop of underlay backup path of TE link */
  augment "/nw:networks/nw:network/nt:link/tet:te/"
        + "tet:te-link-attributes/"
        + "tet:underlay/tet:backup-path/tet:path-element/tet:type/"
        + "tet:label/tet:label-hop/tet:te-label/tet:technology" {
    when "../../../../../../../../"
       + "nw:network-types/tet:te-topology/"
       + "flexi-grid:flexi-grid-topology" {
      description "Augment flexi-grid TE label";
    }
    description "flexi-grid label.";
    case flexi-grid {
      uses l0-types:flexi-grid-path-label;
    }
  }
  /* Augment label restrictions of TE link */
  augment "/nw:networks/nw:network/nt:link/tet:te/"
        + "tet:te-link-attributes/"
        + "tet:label-restrictions/tet:label-restriction" {
    when "../../../../../nw:network-types/tet:te-topology/"
       + "flexi-grid:flexi-grid-topology" {
      description "Augment flexi-grid TE label";
    }
    description "flexi-grid label.";
    uses l0-types:flexi-grid-label-restriction;
  }
  /* Augment label restrictions start of TE link */
  augment "/nw:networks/nw:network/nt:link/tet:te/"
        + "tet:te-link-attributes/"
        + "tet:label-restrictions/tet:label-restriction/"
        + "tet:label-start/tet:te-label/tet:technology" {
    when "../../../../../../../nw:network-types/tet:te-topology/"
       + "flexi-grid:flexi-grid-topology" {
      description "Augment flexi-grid TE label";
    }
    description "flexi-grid label.";
    case flexi-grid {
      uses l0-types:flexi-grid-link-label;
    }
  }
  /* Augment label restrictions end of TE link */
  augment "/nw:networks/nw:network/nt:link/tet:te/"
        + "tet:te-link-attributes/"
        + "tet:label-restrictions/tet:label-restriction/"
        + "tet:label-end/tet:te-label/tet:technology" {
    when "../../../../../../../nw:network-types/tet:te-topology/"
       + "flexi-grid:flexi-grid-topology" {
      description "Augment flexi-grid TE label";
    }
    description "flexi-grid label.";
    case flexi-grid {
      uses l0-types:flexi-grid-link-label;
    }
  }
  /* Augment label restrictions step of TE link */
  augment "/nw:networks/nw:network/nt:link/tet:te/"
        + "tet:te-link-attributes/"
        + "tet:label-restrictions/tet:label-restriction/"
        + "tet:label-step/tet:technology" {
    when "../../../../../../nw:network-types/tet:te-topology/"
       + "flexi-grid:flexi-grid-topology" {
      description "Augment flexi-grid TE label";
    }
    description "flexi-grid label.";
    case flexi-grid {
      uses l0-types:flexi-grid-label-step;
    }
  }

  /* Augment label restrictions of TE link information-source */
  augment "/nw:networks/nw:network/nt:link/tet:te/"
        + "tet:information-source-entry/"
        + "tet:label-restrictions/tet:label-restriction" {
    when "../../../../../nw:network-types/tet:te-topology/"
       + "flexi-grid:flexi-grid-topology" {
      description "Augment flexi-grid TE label";
    }
    description "flexi-grid label.";
    uses l0-types:flexi-grid-label-restriction;
  }
  /* Augment label restrictions start of TE link information-source */
  augment "/nw:networks/nw:network/nt:link/tet:te/"
        + "tet:information-source-entry/"
        + "tet:label-restrictions/tet:label-restriction/"
        + "tet:label-start/tet:te-label/tet:technology" {
    when "../../../../../../../nw:network-types/tet:te-topology/"
       + "flexi-grid:flexi-grid-topology" {
      description "Augment flexi-grid TE label";
    }
    description "flexi-grid label.";
    case flexi-grid {
      uses l0-types:flexi-grid-link-label;
    }
  }
  /* Augment label restrictions end of TE link information-source */
  augment "/nw:networks/nw:network/nt:link/tet:te/"
        + "tet:information-source-entry/"
        + "tet:label-restrictions/tet:label-restriction/"
        + "tet:label-end/tet:te-label/tet:technology" {
    when "../../../../../../../nw:network-types/tet:te-topology/"
       + "flexi-grid:flexi-grid-topology" {
      description "Augment flexi-grid TE label";
    }
    description "flexi-grid label.";
    case flexi-grid {
      uses l0-types:flexi-grid-link-label;
    }
  }
  /* Augment label restrictions step of TE link information-source */
  augment "/nw:networks/nw:network/nt:link/tet:te/"
        + "tet:information-source-entry/"
        + "tet:label-restrictions/tet:label-restriction/"
        + "tet:label-step/tet:technology" {
    when "../../../../../../nw:network-types/tet:te-topology/"
       + "flexi-grid:flexi-grid-topology" {
      description "Augment flexi-grid TE label";
    }
    description "flexi-grid label.";
    case flexi-grid {
      uses l0-types:flexi-grid-label-step;
    }
  }

  /* Augment label hop of underlay primary path of TE link template */
  augment "/nw:networks/tet:te/tet:templates/"
        + "tet:link-template/tet:te-link-attributes/"
        + "tet:underlay/tet:primary-path/tet:path-element/tet:type/"
        + "tet:label/tet:label-hop/tet:te-label/tet:technology" {
/*
    when "../../../../../../../../../"
       + "nw:network-types/tet:te-topology/"
       + "flexi-grid:flexi-grid-topology" {
          description "Augment flexi-grid TE label";
    }
*/
    description "flexi-grid label.";
    case flexi-grid {
      uses l0-types:flexi-grid-path-label;
    }
  }
  /* Augment label hop of underlay backup path of TE link template */
  augment "/nw:networks/tet:te/tet:templates/"
        + "tet:link-template/tet:te-link-attributes/"
        + "tet:underlay/tet:backup-path/tet:path-element/tet:type/"
        + "tet:label/tet:label-hop/tet:te-label/tet:technology" {
/*
    when "../../../../../../../../../"
       + "nw:network-types/tet:te-topology/"
       + "flexi-grid:flexi-grid-topology" {
      description "Augment flexi-grid TE label";
    }
*/
    description "flexi-grid label.";
    case flexi-grid {
      uses l0-types:flexi-grid-path-label;
    }
  }
  /* Augment label restrictions of TE link template */
  augment "/nw:networks/tet:te/tet:templates/"
        + "tet:link-template/tet:te-link-attributes/"
        + "tet:label-restrictions/tet:label-restriction" {
/*
    when "../../../../../nw:network-types/tet:te-topology/"
        + "flexi-grid:flexi-grid-topology" {
      description "Augment flexi-grid TE label";
    }
*/
    description "flexi-grid label.";
    uses l0-types:flexi-grid-label-restriction;
  }

  /* Augment label restrictions start of TE link template */
  augment "/nw:networks/tet:te/tet:templates/"
        + "tet:link-template/tet:te-link-attributes/"
        + "tet:label-restrictions/tet:label-restriction/"
        + "tet:label-start/tet:te-label/tet:technology" {
/*
    when "../../../../../../../nw:network-types/tet:te-topology/"
        + "flexi-grid:flexi-grid-topology" {
      description "Augment flexi-grid TE label";
    }
*/
    description "flexi-grid label.";
    case flexi-grid {
      uses l0-types:flexi-grid-link-label;
    }
  }
  /* Augment label restrictions end of TE link template */
  augment "/nw:networks/tet:te/tet:templates/"
        + "tet:link-template/tet:te-link-attributes/"
        + "tet:label-restrictions/tet:label-restriction/"
        + "tet:label-end/tet:te-label/tet:technology" {
/*
    when "../../../../../../../nw:network-types/tet:te-topology/"
        + "flexi-grid:flexi-grid-topology" {
      description "Augment flexi-grid TE label";
    }
*/
    description "flexi-grid label.";
    case flexi-grid {
      uses l0-types:flexi-grid-link-label;
    }
  }

  /* Augment label restrictions step of TE link template */
  augment "/nw:networks/tet:te/tet:templates/"
        + "tet:link-template/tet:te-link-attributes/"
        + "tet:label-restrictions/tet:label-restriction/"
        + "tet:label-step/tet:technology" {
/*
    when "../../../../../../nw:network-types/tet:te-topology/"
        + "flexi-grid:flexi-grid-topology" {
      description "Augment flexi-grid TE label";
    }
*/
    description "flexi-grid label.";
    case flexi-grid {
      uses l0-types:flexi-grid-label-step;
    }
  }
}
