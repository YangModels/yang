module ietf-qos-action {
  yang-version 1.1;
  namespace "urn:ietf:params:xml:ns:yang:ietf-qos-action";
  prefix action;

  import ietf-inet-types {
    prefix inet;
    reference
      "RFC 6991: Common YANG Data Types";
  }
  import iana-qos-types {
    prefix qos-types;
    reference
      "RFC XXXX: YANG Model for QoS";
  }

  organization
    "IETF Routing Area Working Group";

  contact
    "WG Web:   <https://datatracker.ietf.org/wg/rtgwg/>
     WG List:  <mailto:rtgwg@ietf.org>

     Editor:   Aseem Choudhary
               <mailto:achoudhary@aviatrix.com>
     Editor:   Mahesh Jethanandani
               <mailto:mjethanandani@gmail.com>";

  description
    "This module contains a collection of YANG definitions for
     configuring qos specification implementations.

     Copyright (c) 2021 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2023-03-10 {
    description
      "Initial version";
    reference
      "RFC XXXX: YANG Models for Quality of Service (QoS).";
  }

  grouping rate-value-unit {
    leaf value {
      type uint64;
      description
        "rate value";
    }
    leaf unit {
      type identityref {
        base qos-types:rate-unit-type;
      }
      description
        "rate unit";
    }
    description
      "rate value and unit grouping";
  }

  grouping meter-action-params {
    description
      "meter action parameters";

    list action {
      key "action-type";
      ordered-by user;
      description
        "Configuration of basic-meter & associated actions";

      leaf action-type {
        type identityref {
          base qos-types:meter-action-type;
        }
        description
          "meter action type";
      }

      choice action-val {
        description
          "Meter action based on choice of meter action type";
      }
    }
  }

  grouping single-rate-two-color-meter {
    container single-rate-two-color-meter {
      description
        "A container for Basic Single Rate Two Color Marker.";

      leaf committed-information-rate {
        type uint64;
        units "bytes-per-second";
        description
          "The value for Committed Information Rate (CIR).";
      }

      leaf committed-burst-size {
        type uint64;
        units "bytes";
        description
          "The value for Committed Burst Size (CBS).";
      }

      container conform-action {
        uses meter-action-params;
        description
          "A packet is marked conforming, or green if it does not
           exceed CIR.";
      }

      container exceed-action {
        uses meter-action-params;
        description
          "A packet is marked exceeding, or yellow if it does
           exceed CIR.";
      }
    }
    description
      "A grouping for Single Rate Two Color Meter attributes.";
  }

  grouping single-rate-three-color-meter {
    container single-rate-three-color-meter {
      description
        "Grouping that defines the Single Rate Three Color Meter
        (srTCM).";

      leaf committed-information-rate {
        type uint64;
        units "bytes-per-second";
        description
          "The value for Committed Information Rate (CIR).";
        reference
          "RFC 2697: A Single Rate Three Color Marker.";
      }

      leaf committed-burst-size {
        type uint64;
        units "bytes";
        description
          "The value for Committed Burst Size (CBS).";
        reference
          "RFC 2697: A Single Rate Three Color Marker.";
      }

      leaf excess-burst-size {
        type uint64;
        units "bytes";
        description
          "The value for Excess Burst Size (EBS).";
        reference
          "RFC 2697: A Single Rate Three Color Marker.";
      }

      container conform-action {
        uses meter-action-params;
        description
          "A packet is marked conforming, or green if it does not
           exceed CBS.";
        reference
          "RFC 2697: A Single Rate Three Color Marker.";
      }

      container exceed-action {
        uses meter-action-params;
        description
          "A packet is marked exceeding, or yellow if it does exceed
           CBS, but not the EBS.";
        reference
          "RFC 2697: A Single Rate Three Color Marker.";
      }

      container violate-action {
        uses meter-action-params;
        description
          "A packet is marked violating, or red if it is exceeds
           both CBS and EBS.";
        reference
          "RFC 2697: A Single Rate Three Color Marker.";
      }
    }
    description
      "Single Rate Three Color Marker attributes";
  }

  grouping two-rate-three-color-meter {
    description
      "A grouping that defines A Two Rate Three Color Meter
       (trTCM).";
    container two-rate-three-color-meter {
      description
        "A container that defines A Two Rate Three Color Meter
         (trTCM).";

      leaf committed-information-rate {
        type uint64;
        units "bytes-per-second";
        description
          "The value for Committed Information Rate (CIR).";
        reference
          "RFC 2698: A Two Rate Three Color Marker.";
      }

      leaf committed-burst-size {
      type uint64;
        units "bytes";
        description
          "The value for Commited Burst Size (CBS).";
        reference
          "RFC 2698: A Two Rate Three Color Marker.";
      }

      leaf peak-information-rate {
        type uint64;
        units "bytes-per-second";
        description
          "The value for Peak Information Rate (PIR).";
        reference
          "RFC 2698: A Two Rate Three Color Marker.";
      }

      leaf peak-burst-size {
        type uint64;
        units "bytes";
        description
          "The value for Peak Burst Size (PBS).";
        reference
          "RFC 2698: A Two Rate Three Color Marker.";
      }

      container conform-action {
        uses meter-action-params;
        description
          "A packet is marked conforming, or green, if it does not
           exceed CIR.";
        reference
          "RFC 2698: A Two Rate Three Color Marker.";
      }

      container exceed-action {
        uses meter-action-params;
        description
          "A packet is marked exceeding, or yellow, if it exceeds
           CIR but not PIR.";
        reference
          "RFC 2698: A Two Rate Three Color Marker.";
      }

      container violate-action {
        uses meter-action-params;
        description
          "A packet is marked as violating, or red, if it exceeds
           both CIR and PIR.";
        reference
          "RFC 2698: A Two Rate Three Color Marker.";
      }
    }
  }

  grouping meter {
    choice meter-types {
      case single-rate-two-color-meter-type {
        uses single-rate-two-color-meter;
        description
          "A Basic Single Rate Two Color Meter.";
      }

      case single-rate-three-color-meter-type {
        uses single-rate-three-color-meter;
        description
          "Singe Rate Three Color Meter (srTCM).";
        reference
          "RFC 2697: A Single Rate Three Color Marker.";
      }

      case two-rate-three-color-meter-type {
        uses two-rate-three-color-meter;
        description
          "A Two Rate Three Color Marker.";
      }
      description
        "A meter action based on choice of meter action type.";
    }
    description
      "Meter attributes.";
  }

  container meters {
    description
      "list of meter templates";

    list meter {
      key "name";
      description
        "meter entry template";

      leaf name {
        type string;
        description
          "meter identifier";
      }
      uses meter;
    }
  }

  grouping meter-reference {
    container meter {
      leaf name {
        type string ;
        mandatory true;
        description
          "This leaf defines name of the meter referenced";
      }
      leaf type {
        type identityref {
          base qos-types:meter-type;
        }
        mandatory true;
        description
          "This leaf defines type of the meter";
      }
      description
        "meter reference name";
    }
    description
      "meter reference";
  }

  grouping count {
    container count {
    if-feature qos-types:count;
      leaf count-action {
        type empty;
        description
          "count action";
      }
      description
        "the count action";
    }
    description
      "the count action grouping";
  }

  grouping named-counter {
    container named-counter {
    if-feature qos-types:named-counter;
      leaf count-name-action {
        type string;
        description
          "count action";
      }
      description
        "the count action";
    }
    description
      "the count action grouping";
  }

  grouping discard {
    container discard {
      leaf discard {
        type empty;
        description
          "discard action";
      }
      description
        "discard action";
    }
    description
      "discard grouping";
  }

  grouping priority {
    container priority {
      leaf level {
        type uint8;
        description
          "priority level";
      }
      description
        "priority attributes";
    }
    description
      "priority attributes grouping";
  }
  grouping min-rate {
    container min-rate {
      uses rate-value-unit;
      description
        "min guaranteed bandwidth";
    }
    description
      "minimum rate grouping";
  }
  grouping dscp-marking {
    container dscp {
      leaf dscp {
        type inet:dscp;
        description
          "dscp marking";
      }
      description
        "dscp marking container";
    }
    description
      "dscp marking grouping";
  }
  grouping traffic-group-marking {
    container traffic-group {
      leaf traffic-group {
        type string;
        description
          "traffic group marking";
      }
      description
        "traffic group marking container";
    }
    description
      "traffic group marking grouping";
  }
  grouping child-policy {
    container child-policy {
      if-feature qos-types:child-policy;
      leaf name {
        type string;
        description
          "Hierarchical Policy";
      }
      description
        "Hierarchical Policy configuration container";
    }
    description
      "Grouping of Hierarchical Policy configuration";
  }

  grouping max-rate {
    container max-rate {
      uses rate-value-unit;

      leaf burst-value {
        type uint64;
        description
          "Burst value in bytes.";
      }

      leaf burst-unit {
        type identityref {
          base qos-types:burst-unit-type;
        }
        description
          "Unit specification for the burst value.";
      }
      description
        "Maximum rate attributes container";
    }
    description
      "Grouping for maximum rate attributes";
  }

  grouping red-config-parameters {
    leaf min-threshold-val {
      type uint64;
      description
       "minimum value of red threshold";
    }
    leaf min-threshold-unit {
      type identityref {
        base qos-types:red-threshold-unit;
      }
      description
       "unit of minimum red threshold";
    }
    leaf max-threshold-val {
      type uint64;
      description
       "maximum value of red threshold";
    }
    leaf max-threshold-unit {
      type identityref {
        base qos-types:red-threshold-unit;
      }
      description
       "unit of maximum red threshold";
    }
    leaf weight {
      type uint8;
      description
       "the decay factor for the average queue size
        calculation. the numbers are 2's exponent";
    }
    leaf max-probability-val {
      type uint64;
      description
       "value of maximum probability value. this value need
        be interpreted along with max-probability-unit";
    }
    leaf max-probability-unit {
      type identityref {
        base qos-types:probability-unit;
      }
      description
       "probability unit type as defined
        by probability-unit";
    }
    description
      "Random Early Detect Configuration Parameters";
  }
  grouping queue {
    container queue {
      uses priority;
      uses min-rate;
      uses max-rate;
      container algorithmic-drop {
        choice drop-algorithm {
          case tail-drop {
            container tail-drop {
              leaf tail-drop {
                type empty;
                description
                 "tail drop algorithm";
              }
              description
                "Tail Drop configuration container";
            }
            description
              "Tail Drop choice";
          }
          case red {
            container red {
              uses red-config-parameters;
              leaf ecn-enabled {
                type boolean;
                default "false";
                description
                  "ecn is enabled on the queue";
              }
              description
                "Random Early Detect configuration";
            }
          }
          case wred {
            container wred {
              list wred {
                key "profile";
                leaf profile {
                  type uint8;
                  description
                    "profile id of each wred profile";
                }
                leaf color-type {
                  type identityref {
                    base qos-types:wred-color-type;
                  }
                  description
                    "wred color-type of each profile";
                }
                list color-val {
                  key "min max";
                  leaf min {
                    type uint8;
                    description
                      "minimum value of color types";
                  }
                  leaf max {
                    type uint8;
                    description
                      "maximum value of color types";
                  }
                  description
                    "list of color markings which constitute
                     a traffic profile";
                }
                uses red-config-parameters;
                description
                  "list of RED profiles each with its own
                   threshold values";
              }
              leaf ecn-enabled {
                type boolean;
                default "false";
                description
                  "ecn is enabled on the queue";
              }
              description
                "Weighted Random Early Detect configuration";
            }
          }
          description
            "Choice of Drop Algorithm";
        }
        description
          "Algorithmic Drop configuration container";
      }
      description
        "Queue configuration container";
    }
    description
      "Queue grouping";
  }

  container queues {
    description
      "List of queue templates";

    list queue {
      key "name";
      description
        "Queue entry template";

      leaf name {
        type string;
        description
          "A unique name identifying this queue template";
      }
      uses queue;
    }
  }

  grouping queue-reference {
    container queue-reference {
      leaf queue-name {
        type string;
        mandatory true;
        description
          "This leaf defines name of the  queue template referenced";
      }
      description
        "Queue template reference";
    }
    description
      "Queue template reference grouping";
  }

  grouping scheduler {
    container scheduler {
      uses min-rate;
      uses max-rate;
      description
        "Schedular configuration container";
    }
    description
      "Schedular configuration grouping";
  }
}
