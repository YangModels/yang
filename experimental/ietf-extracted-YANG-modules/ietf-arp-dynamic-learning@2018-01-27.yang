submodule ietf-arp-dynamic-learning {
 yang-version 1.1;
 belongs-to ietf-arp {
   prefix arp;
 }

 import ietf-interfaces {
   prefix if;
   description
     "A Network Management Datastore Architecture (NMDA)
      compatible version of the ietf-interfaces module
      is required.";
 }
 import ietf-ip {
   prefix ip;
   description
     "A Network Management Datastore Architecture (NMDA)
      compatible version of the ietf-ip module is
      required.";
 }

 organization
   "IETF Routing Area Working Group (rtgwg)";
 contact
   "WG Web: <http://tools.ietf.org/wg/rtgwg/>
    WG List: <mailto: rtgwg@ietf.org>
    Editor: Xiaojian Ding
        dingxiaojian1@huawei.com
    Editor: Feng Zheng
        habby.zheng@huawei.com
    Editor: Robert Wilton
        rwilton@cisco.com";
 description
   "This YANG module augments 'ietf-if' and  'ietf-ip'
    modules with parameters for ARP configuration on interfaces.
    The model fully conforms to the Network Management
    Datastore Architecture (NMDA).

    Copyright (c) 2017 IETF Trust and the persons
    identified as authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX; see
    the RFC itself for full legal notices.";

 revision 2018-01-27 {
   description
     "Initial revision.";
   reference "RFC XXX: ARP (Address Resolution Protocol) YANG data model";
 }

 augment "/if:interfaces/if:interface" {
   description
     "Augment interface configuration with parameters of ARP.";
   container arp-dynamic-learning {
     description
       "Support for ARP configuration on interfaces.";
     leaf expire-time {
       type uint32 {
         range "60..86400";
       }
       units "second";
       description
         "Aging time of a dynamic ARP entry.";
     }
     leaf learn-disable {
       type boolean;
       default "false";
       description
         "Whether dynamic ARP learning is disabled. If the value
          is True, dynamic ARP learning is disabled. If the value
          is False, dynamic ARP learning is enabled.";
     }
     leaf proxy-enable {
       type boolean;
       default "false";
       description
         "Enable proxy ARP.";
     }
     list if-limit {
       key "vlan-id";
       description
         "Maximum number of dynamic ARP entries that an
          interface can learn. If the number of ARP entries that
          an interface can learn changes and the number of the
          learned ARP entries exceeds the changed value, the
          interface cannot learn additional ARP entries. The
          system prompts you to delete the excess ARP entries.";
       leaf vlan-id {
         type uint16 {
           range "0..4094";
         }
         description
           "ID of the VLAN where ARP learning is restricted.
            This parameter can be set only on Layer 2 interfaces
            and sub-interfaces. Ethernet, GE, VE, and Eth-Trunk
            interfaces can be both Layer 3 and Layer 2
            interfaces. When they work in Layer 3 mode, they
            cannot have VLANs configured. When they work in Layer
            2 mode, they must have VLANs configured. Ethernet,
            GE, and Eth-Trunk sub-interfaces can be both common
            and QinQ sub-interfaces. ";
       }
       leaf limit-number {
         type uint32 {
           range "1..65536";
         }
         mandatory true;
         description
           "Maximum number of dynamic ARP entries that an
            interface can learn.";
       }
       leaf threshold-value {
         type uint32 {
           range "60..100";
         }
         must "not(not(../limit-number))" {
           description
             "Upper boundary must be higher than lower boundary.";
         }
         description
           "Alarm-Threshold for Maximum number of ARP entries
            that an interface can learn.";
       }
     }
     container probe {
       description
         "Common configuration parameters for all ARP probe.";
       leaf interval {
         type uint8 {
           range "1..5";
         }
         units "second";
         description
           "Interval for detecting dynamic ARP entries.";
       }
       leaf times {
         type uint8 {
           range "0..10";
         }
         description
           "Number of aging probe attempts for a dynamic ARP entry.
            If a device does not receive an ARP reply message after
            the number of aging probe attempts reaches a specified
            number,thedynamic ARP entry is deleted.";
       }
       leaf unicast {
         type boolean;
         default "false";
         description
           "Send unicast ARP aging probe messages for a dynamic ARP
            entry.";
       }
     }
     container gratuitous {
       description
         "Configure gratuitous ARP.";
       leaf gratuitous-enable {
         type boolean;
         default "false";
         description
           "Enable or disable sending gratuitous-arp packet on
            interface.";
       }
       leaf interval {
         type uint32 {
           range "1..86400";
         }
         units "second";
         description
           "The interval of sending gratuitous-arp packet on the
            interface.";
       }
       leaf drop {
         type boolean;
         default "false";
         description
           "Drop the receipt of gratuitous ARP packets on the interface.";
       }
     }
     container statistics {
       config false;
       description
         "IP ARP Statistics information on interfaces";
       leaf in-requests-pkts {
         type uint64;
         description
           "Total ARP requests received";
       }
       leaf in-replies-pkts {
         type uint64;
         description
           "Total ARP replies received";
       }
       leaf in-gratuitous-pkts {
         type uint64;
         description
           "Total gratuitous ARP received";
       }
       leaf out-requests-pkts {
         type uint64;
         description
           "Total ARP requests sent";
       }
       leaf out-replies-pkts {
         type uint64;
         description
           "Total ARP replies sent";
       }
       leaf out-gratuitous-pkts {
         type uint64;
         description
           "Total gratuitous ARP sent";
       }
     }
   }
 }
 augment "/if:interfaces/if:interface/ip:ipv4/ip:neighbor" {
   description
     "Augment neighbor list with parameters of ARP,
      eg., support for remaining expire time query on interfaces.";
   leaf remaining-expire-time {
     type uint32;
     config false;
     description
       "Remaining expire time of a dynamic ARP entry. ";
   }
 }
}
