module ietf-cmis-control {
  yang-version 1.1;
  namespace "urn:ietf:params:xml:ns:yang:ietf-cmis-control";
  prefix cmis-ctrl;

  import ietf-interfaces {
    prefix if;
  }

  organization
    "IETF CCAMP Working Group";
  contact
    "WG Web:   <https://datatracker.ietf.org/wg/ccamp/>
    WG List:  <mailto:ccamp@ietf.org>

    Editor:   Shunsuke Homma
      <mailto:shunsuke.homma.ietf@gmail.com>

    Editor:   Hitoshi Irino
      <mailto:hitoshi.irino.ntt@gmail.com>";

  description
    "This YANG module defines a data model for the management
    of CMIS (Common Management Interface Specification) pages
    as specified by OIF. It enables configuration and retrieval
    of CMIS page data, including access types and value fields,
    to support the management of pluggable optical modules via
    NETCONF or RESTCONF.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.

    Copyright (c) 2026 IETF Trust and the persons identified
    as authors of the code.  All rights reserved.

    Redistribution and use in source and binary forms, with or
    without modification, is permitted pursuant to, and
    subject to the license terms contained in, the Revised
    BSD License set forth in Section 4.c of the IETF Trust's
    Legal Provisions Relating to IETF Documents
    (http://trustee.ietf.org/license-info).

    This version of this YANG module is part of RFC XXXX
    (https://www.rfc-editor.org/info/rfcXXXX); see the RFC itself
    for full legal notices.";

// RFC Ed.: replace XXXX with actual RFC number and remove this note

  revision "2026-05-12" {
    description
      "Revised control model to use whitelist approach.
       Added remote-read-allowed-pages for granular access control.";
    reference
      "RFC XXXX: A YANG Data Model for CMIS Access and Control";
  }

  revision "2025-04-21" {
    description
      "Initial revision.";
    reference
      "I-D.hi-ccamp-cmis-control-yang-00";
  }

  /*
   * CMIS control data nodes
   */

  typedef access-type {
      type enumeration {
        enum rw {
          description "A readable and writable element.";
        }
        enum rww {
          description "A readable and writable element that can be
          modified by the module.";
        }
        enum ro {
          description "A read-only element.";
        }
        enum wo {
          description "A write-only element.";
        }
        enum wo/sc {
          description "A write-only element with self-clearing side
          effect.";
        }
        enum ro/cor {
          description "A read-only element with clear-on-read side
          effect.";
        }
      }
      description
        "Defines access types for CMIS elements as defined in
        OIF-CMIS.";
  }

  grouping cmis-page {
    description
      "Parameters stored in the CMIS page";

    leaf page-num{
      type uint8 {
        range "0 .. 255";
      }
      mandatory true;
      description
        "The number of the CMIS page.";
    }

    leaf bank {
      type uint8;
      mandatory true;
      description
        "The banks corresponding to the CMIS page.";
    }

    leaf page-access-type {
      type access-type;
      config false;
      description "Access type of the CMIS page.";
    }

    leaf description {
      type string;
      description
        "The description of the CMIS page.";
    }

    list value {
      key "offset";
      description
      "The value contained in the CMIS page.";

      leaf offset {
        type uint8;
        mandatory true;
        description
          "The memory address of the value.";
      }

      leaf size {
        type uint8 {
          range "1 .. 128";
        }
        mandatory true;
        description
          "The memory size of the value.";
      }

      leaf value-access-type {
        type access-type;
        config false;
        description "Access type of the target value.";
      }

      leaf value-data {
        type binary;
        mandatory true;
        description
          "The data contained in the value. It is writable only
          when the access-type is not Read-Only or Read-Only with
          clear-on-read side effect.";
      }

      leaf description {
        type string;
        description
          "The description of the value.";
      }
    }
  }

  grouping cmis-pages {
    description
      "The list of the accessible CMIS pages supported by the
      pluggable device accommodated into the interface.";

    list cmis-page {
      key "page-num";
      description "A CMIS page supported by the device.";
      uses cmis-page;
      }
  }

  grouping cmis-control {
    description
      "Parameters for CMIS control and governance.";

    leaf cmis-enabled {
      type boolean;
      default "false";
      config false;
      description
        "The availability of the CMIS for control the pluggable
        device equipped in the interface. If the device does not
        support CMIS, this value is false.";
    }

    leaf cmis-version {
      type string;
      config false;
      description
        "The version of the CMIS by the pluggable device.";
    }

    leaf default-policy {
      type enumeration {
        enum disabled {
          description
            "Remote access is completely disabled for pages not
             listed in the whitelists.";
        }
        enum read-only {
          description
            "Remote access is restricted to monitoring only for pages
             not listed in 'remote-write-allowed-pages'.";
        }
      }
      default "read-only";
      description
        "Defines the default access policy for CMIS pages.";
    }

    list remote-read-allowed-pages {
      key "page-num";
      description
        "A whitelist of pages that are allowed to be READ
         by a remote controller, even if the default-policy
         is 'disabled'. This list is useful when
         'default-policy' is set to 'disabled' but specific
         pages need to be monitored.

         Note: Lower Memory (Address 0-127) SHOULD NOT be included in
         this list if it contains Clear-on-Read (CoR) registers that
         are managed by the Host NOS.";

      leaf page-num {
        type uint8;
        description "The CMIS page number allowed for remote read.";
      }
    }

    list remote-write-allowed-pages {
      key "page-num";
      description
        "A whitelist of pages that are allowed to be modified by
         a remote controller (Read/Write).
         If a page is listed in both this list and
         'remote-read-allowed-pages', this list takes precedence,
         granting Read/Write access.

         Note: Lower Memory (Address 0-127) MUST NOT be included in
         this list as it contains critical Host management flags.

         When a page is removed from this list, or when the
         default-policy changes to 'disabled' (and the page is
         not in the read-whitelist),
         the Host NOS MUST strictly enforce its local configuration
         (running-config) on the target CMIS pages.
         Values modified by a remote controller MUST be
         overwritten by the Host's local configuration or reset
         to default values to maintain configuration
         consistency.";

      leaf page-num {
        type uint8;
        description "The CMIS page number allowed for remote write.";
      }
    }

    uses cmis-pages;

  }

  /*
   * Augment Interface
   */

  augment "/if:interfaces/if:interface" {
    description "Augments interface with CMIS control parameters.";
    container cmis-control {
      description "Container for CMIS control.";
      uses cmis-control;
    }
  }
}
