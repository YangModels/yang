module iana-opsawg-mud-tls-profile {
   yang-version 1.1;
   namespace "urn:ietf:params:xml:ns:yang:iana-opsawg-mud-tls-profile";
   prefix mud-tls-profile;

   import ietf-crypto-types {
     prefix ct;
     reference "draft-ietf-netconf-crypto-types-01:
                Common YANG Data Types for Cryptography";
   }

   import iana-hash-algs {
     prefix iha;
     reference
          "RFC XXXX: Common YANG Data Types for Hash algorithms";
   }

   import ietf-access-control-list {
     prefix acl;
     reference
       "RFC 8519: YANG Data Model for Network Access
                  Control Lists (ACLs)";
   }

   organization
     "IETF Operations and Management Area Working Group Working Group";
   contact
      "Editor:  Konda, Tirumaleswar Reddy
               <mailto:TirumaleswarReddy_Konda@McAfee.com>";

   description
     "This module contains YANG definition for the IoT device
      (D)TLS profile.

      Copyright (c) 2019 IETF Trust and the persons identified as
      authors of the code.  All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC XXXX; see
      the RFC itself for full legal notices.";

   revision 2019-06-12 {
     description
       "Initial revision";
   }

   typedef extension-type {
     type uint16;
     description "Extension type";
   }

    typedef supported-group {
     type uint16;
     description "Named group (DHE or ECDHE)";
   }

   typedef SPKI-pin-set {
     type binary;
     description "Subject Public Key Info pin set";
   }

   typedef signature-algorithm {
     type uint16;
     description "Signature algorithm";
   }

   typedef psk-key-exchange-mode {
     type uint8;
     description "pre-shared key exchange mode";
   }

   typedef client-public-key-length {
     type uint8;
     description "client public key length";
   }

   typedef application-protocol {
     type string;
     description "application protocol";
   }

   typedef cert-compression-algorithm {
     type uint16;
     description "certificate compression algorithm";
   }

   typedef certificate_authority {
     type binary;
     description "Distinguished Name of Certificate authority";
   }

   typedef cipher-algorithm {
     type uint8;
     description "Cipher Algorithm";
   }

   typedef aead-algorithm {
     type uint8;
     description "AEAD Algorithm";
   }

   typedef tls-version {
       type enumeration {
         enum tls-1.2 {
           value 1;
           description
               "TLS Protocol Version 1.2.";
           reference
              "RFC 5246: The Transport Layer Security (TLS) Protocol
                                   Version 1.2";
         }
         enum tls-1.3 {
           value 2;
           description
               "TLS Protocol Version 1.3.";
           reference
              "RFC 8446: The Transport Layer Security (TLS) Protocol
                                   Version 1.3";
         }
      }
      description
           "Indicates the TLS version.";
   }

   typedef dtls-version {
     type enumeration {
         enum dtls-1.2 {
           value 1;
           description
               "DTLS Protocol Version 1.2.";
           reference
              "RFC 6346: Datagram Transport Layer Security 1.2";
         }
         enum dtls-1.3 {
           value 2;
           description
               "DTLS Protocol Version 1.3.";
           reference
               "draft-ietf-tls-dtls13: Datagram Transport Layer Security 1.3";
         }
     }
     description
       "Indicates the DTLS version.";
   }

   feature tls-1_2 {
     description
       "TLS Protocol Version 1.2 is supported.";
       reference
         "RFC 5246: The Transport Layer Security (TLS) Protocol
                    Version 1.2";
   }

   feature tls-1_3 {
     description
       "TLS Protocol Version 1.3 is supported.";
       reference
         "RFC 8446: The Transport Layer Security (TLS) Protocol
                    Version 1.3";
   }

   feature dtls-1_2 {
       description
          "DTLS Protocol Version 1.2 is supported.";
       reference
          "RFC 6346: Datagram Transport Layer Security Version 1.2";
   }

   feature dtls-1_3 {
       description
         "DTLS Protocol Version 1.3 is supported.";
       reference
         "draft-ietf-tls-dtls13: Datagram Transport Layer Security 1.3";
   }

   grouping client-profile {
     description
       "A grouping for (D)TLS profiles.";
     container client-profile {
       list tls-dtls-profiles {
         key "profile-name";
         description
          "A list of (D)TLS version profiles supported by the client.";
        leaf profile-name {
          type string {
            length "1..64";
          }
          description
            "The name of (D)TLS profile; space and special
            characters are not allowed.";
         }
         leaf-list supported_versions {
           type uint16;
           description
             "(D)TLS versions supported by the client";
         }
         list cipher-suites {
            key "cipher aead";
            leaf cipher {
               type cipher-algorithm;
               description "Cipher";
            }
            leaf aead {
               type aead-algorithm;
               description "AEAD";
           }
          description "Cipher Suites";
         }
         leaf-list extension-types {
           type extension-type;
           description "Extension Types";
         }
         leaf-list acceptlist-ta-certs {
           type ct:trust-anchor-cert-cms;
           description
             "A list of trust anchor certificates used by the client.";
         }
         container SPKI {
            leaf-list SPKI-pin-sets {
                type SPKI-pin-set;
                description
                  "A list of SPKI pin sets pre-configured on the client
                  to validate self-signed server certificate or
                  raw public key.";
            }
            leaf SPKI-hash-algorithm {
               type iha:hash-algorithm-type;
              description
                "cryptographic hash algorithm used to generate the
                SPKI pinset.";
            }
         }
         leaf-list psk-key-exchange-modes {
           if-feature "tls-1_3 or dtls-1_3";
           type psk-key-exchange-mode;
           description
             "pre-shared key exchange modes";
         }
         leaf-list supported-groups {
            type supported-group;
            description
             "A list of named groups supported by the client.";
         }
         leaf-list signature-algorithms-cert {
            if-feature "tls-1_3 or dtls-1_3";
            type signature-algorithm;
            description
             "A list signature algorithms the client can validate
              in X.509 certificates.";
         }
         leaf-list signature-algorithms {
            type signature-algorithm;
            description
             "A list signature algorithms the client can validate
              in the CertificateVerify message.";
         }
         leaf-list application-protocols {
            type application-protocol;
            description
             "A list application protocols supported by the client";
         }
         leaf-list cert-compression-algorithms {
            if-feature "tls-1_3 or dtls-1_3";
            type cert-compression-algorithm;
            description
             "A list certificate compression algorithms
              supported by the client";
         }
         leaf-list certificate_authorities {
            if-feature "tls-1_3 or dtls-1_3";
            type certificate_authority;
            description
             "A list of the distinguished names of certificate authorities
              acceptable to the client";
         }
   }
  }
 }
 augment "/acl:acls/acl:acl/acl:aces/acl:ace/acl:matches" {
   description
     "MUD (D)TLS specific matches.";
   uses client-profile;
 }
}
