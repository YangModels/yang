module ietf-netconf-txid {
  yang-version 1.1;
  namespace "urn:ietf:params:xml:ns:yang:ietf-netconf-txid";
  prefix ietf-netconf-txid;

  import ietf-netconf {
    prefix nc;
    reference
      "RFC 6241: Network Configuration Protocol (NETCONF)";
  }
  import ietf-netconf-nmda {
    prefix ncds;
    reference
      "RFC 8342: Network Management Datastore Architecture (NMDA)";
  }
  import ietf-yang-structure-ext {
    prefix sx;
    reference
      "RFC 8791: YANG Data Structure Extensions.";
  }
  import ietf-yang-types {
    prefix yang;
    reference
      "RFC 6991: Common YANG Data Types";
  }

  organization
    "IETF NETCONF (Network Configuration) Working Group";
  contact
    "WG Web:   <https://datatracker.ietf.org/wg/netconf/>
     WG List:  <netconf@ietf.org>

     Author:   Jan Lindblad
               <mailto:jlindbla@cisco.com>";
  description
    "NETCONF Transaction ID aware operations for NMDA.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
    ";

  revision 2023-03-01 {
    description
      "Initial revision";
    reference
      "RFC XXXX: Transaction ID Mechanism for NETCONF";
  }

  feature last-modified {
    description
      "Servers implementing this module MUST support the
       etag txid mechanism.  Servers MAY also support the
       last-modified txid mechanism.  Support is shown by announcing
       this feature.";
  }

  extension versioned-node {
    description
      "This statement is used by servers to declare that a
       the server is maintaining a Txid for the YANG node with this
       statement.  Which YANG nodes are versioned nodes may be useful
       information for clients (especially during development).

       Servers are not required to use this statement to declare
       which nodes are versioned nodes.

       Example of use:

       container interfaces {
       ietf-netconf-txid:versioned-node;
       ...
       }
      ";
  }

  typedef etag-t {
    type string {
      pattern '.* .*' {
        modifier "invert-match";
      }
      pattern '.*".*' {
        modifier "invert-match";
      }
      pattern '.*\.*' {
        modifier "invert-match";
      }
    }
    description
      "Unique Entity-tag txid value representing a specific
       transaction.  Could be any string that does not contain
       spaces, double quotes or backslash.

       The txid values '?', '!' and '=' have special meaning:

       '?' This txid value is used by clients and is
          guaranteed not to match any txid on the server.

       '!' This txid value used by servers to indicate
          the node in the candidate datastore has changed
          relative to the running datastore, but not yet received
          a new txid value on the server.

       '=' This txid value used by servers to indicate
          that contents has been pruned due to txid match
          between client and server.
      ";
  }

  typedef last-modified-t {
    type union {
      type yang:date-and-time;
      type enumeration {
        enum ? {
          description
            "Txid value used by clients that is
             guaranteed not to match any txid on the server.";
        }
        enum ! {
          description
            "Txid value used by servers to indicate
             the node in the candidate datastore has changed
             relative to the running datastore, but not yet received
             a new txid value on the server.";
        }
        enum = {
          description
            "Txid value used by servers to indicate
             that contents has been pruned due to txid match
             between client and server.";
        }
      }
    }
    description
      "Last-modified txid value representing a specific transaction.
       The txid values '?', '!' and '=' have special meaning.";
  }

  grouping txid-grouping {
    leaf with-etag {
      type boolean;
      description
        "Indicates whether the client requests the server to include
         a txid:etag txid attribute when the configuration has
         changed.";
    }
    leaf with-last-modified {
      if-feature "last-modified";
      type boolean;
      description
        "Indicates whether the client requests the server to include
         a txid:last-modified attribute when the configuration has
         changed.";
    }
    description
      "Grouping for txid mechanisms, to be augmented into
       RPCs that modify configuration data stores.";
  }

  grouping txid-value-grouping {
    leaf etag-value {
      type etag-t;
      description
        "Indicates server's txid value for a YANG node.";
    }
    leaf last-modified-value {
      if-feature "last-modified";
      type last-modified-t;
      description
        "Indicates server's txid value for a YANG node.";
    }
    description
      "Grouping for txid mechanisms, to be augmented into
       output of RPCs that return txid metadata for configuration
       data stores.";
  }

  augment "/nc:edit-config/nc:input" {
    uses txid-grouping;
    description
      "Injects the txid mechanisms into the
       edit-config operation";
  }

  augment "/nc:commit/nc:input" {
    uses txid-grouping;
    description
      "Injects the txid mechanisms into the
       commit operation";
  }

  augment "/ncds:edit-data/ncds:input" {
    uses txid-grouping;
    description
      "Injects the txid mechanisms into the
       edit-data operation";
  }

  sx:structure txid-value-mismatch-error-info {
    container txid-value-mismatch-error-info {
      description
        "This error is returned by a NETCONF server when a client
         sends a configuration change request, with the additional
         condition that the server aborts the transaction if the
         server's configuration has changed from what the client
         expects, and the configuration is found not to actually
         not match the client's expectation.";
      leaf mismatch-path {
        type instance-identifier;
        description
          "Indicates the YANG path to the element with a mismatching
           etag txid value.";
      }
      leaf mismatch-etag-value {
        type etag-t;
        description
          "Indicates server's txid value of the etag
           attribute for one mismatching element.";
      }
      leaf mismatch-last-modified-value {
        if-feature "last-modified";
        type last-modified-t;
        description
          "Indicates server's txid value of the last-modified
           attribute for one mismatching element.";
      }
    }
  }
}
