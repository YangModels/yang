module ietf-l1-mef-service-types {
  namespace "urn:ietf:params:xml:ns:yang:ietf-l1-mef-service-types";
  prefix "l1-st";

  organization
      "IETF CCAMP Working Group";
  contact
      "WG Web: <http://tools.ietf.org/wg/ccamp/>
      WG List: <mailto:ccamp@ietf.org>
      Editor: G. Fioccolla(giuseppe.fioccola@telecomitalia.it)
      Editor: K. Lee (kwangkoog.lee@kt.com)
      Editor: Y. Lee (leeyoung@huawei.com)
      Editor: D. Dhody (dhruv.ietf@gmail.com)
      Editor: O. G. de-Dios(oscar.gonzalezdedios@telefonica.com)
      Editor: D. Ceccarelli(daniele.ceccarelli@ericsson.com)";

  description
     "This module defines L1 service types based on MEF
     subscriber Layer 1 Connectivity Service Attribute. Refer to
     'MEF x.y.x Technical Specification Working Draft v0.09 5,
     December 13, 2017' for all terms and the original references
     used in the module.

     Copyright (c) 2018 IETF Trust and the persons identified as
     authors of the code.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).

     This version of this YANG module is part of RFC XXXX; see
     the RFC itself for full legal notices.";

  revision "2018-07-05" {
       description "Initial revision.";
       reference "RFC XXXX: A Yang Data Model for L1 Connectivity
                 Service Model (L1CSM)";
  // Note: The RFC Editor will replace XXXX with the number
  // assigned to the RFC once this draft becomes an RFC.
  }

  identity protocol-type {
     description
     "base identity from which client protocol type is derived.";
     }

     identity aGigE {
          base "protocol-type";
          description
              "GigE protocol type";
     }

     identity a10GigE_WAN {
          base "protocol-type";
          description
               "10GigE-WAN protocol type";
     }

     identity a10GigE_LAN {
          base "protocol-type";
          description
               "10GigE-LAN protocol type";
     }

     identity a40GigE {
          base "protocol-type";
          description
               "40GigE protocol type";
     }

     identity a100GigE {
          base "protocol-type";
          description
               "100GigE protocol type";
     }

     identity FC-100 {
          base "protocol-type";
          description
               "Fiber Channel - 100 protocol type";
     }

     identity FC-200 {
          base "protocol-type";
          description
               "Fiber Channel - 200 protocol type";
     }

     identity FC-400 {
          base "protocol-type";
          description
               "Fiber Channel - 400 protocol type";
     }

     identity FC-800 {
          base "protocol-type";
          description
               "Fiber Channel - 800 protocol type";
     }

     identity FC-1200 {
          base "protocol-type";
          description
               "Fiber Channel - 1200 protocol type";
     }

     identity FC-1600 {
          base "protocol-type";
          description
               "Fiber Channel - 1600 protocol type";
     }

     identity FC-3200 {
          base "protocol-type";
          description
               "Fiber Channel - 3200 protocol type";
     }

     identity STM-1 {
          base "protocol-type";
          description
               "SDH STM-1 protocol type";
     }

     identity STM-4 {
          base "protocol-type";
          description
               "SDH STM-4 protocol type";
     }

     identity STM-16 {
          base "protocol-type";
          description
               "SDH STM-16 protocol type";
     }

     identity STM-64 {
          base "protocol-type";
          description
               "SDH STM-64 protocol type";
     }

     identity STM-256 {
          base "protocol-type";
          description
               "SDH STM-256 protocol type";
     }

     identity OC-3 {
          base "protocol-type";
          description
               "SONET OC-3 protocol type";
     }
     identity OC-12 {
          base "protocol-type";
          description
               "SONET OC-12 protocol type";
     }

     identity OC-48 {
          base "protocol-type";
          description
               "SONET OC-48 protocol type";
     }

     identity OC-192 {
          base "protocol-type";
          description
               "SONET OC-192 protocol type";
     }

     identity OC-768 {
          base "protocol-type";
          description
               "SONET OC-768 protocol type";
     }

  identity coding-func {
     description
     "base identity from which coding func is derived.";
  }

     identity a1000X-PCS-36 {
          base "coding-func";
          description
               "PCS clause 36 coding function that corresponds to 1000BASE-X";
     }

     identity a10GW-PCS-49-WIS-50 {
          base "coding-func";
          description
               "PCS clause 49 and WIS clause 50 coding func that corresponds to
10GBASE-W (WAN PHY)";
     }

     identity a10GR-PCS-49 {
          base "coding-func";
          description
               "PCS clause 49 coding function that corresponds to 10GBASE-R (LAN
PHY)";
     }
     identity a40GR-PCS-82 {
          base "coding-func";
          description
               "PCS clause 82 coding function that corresponds to 40GBASE-R";
     }

     identity a100GR-PCS-82 {
          base "coding-func";
          description
               "PCS clause 82 coding function that corresponds to 100GBASE-R";
     }

     /* coding func needs to expand for Fiber Channel, SONET, SDH  */

  identity optical-interface-func {
     description
     "base identity from which optical-interface-function is derived.";
  }

     identity SX-PMD-clause-38 {
          base "optical-interface-func";
          description
               "SX-PMD-clause-38 Optical Interface function for 1000BASE-X PCS-36";
     }

     identity LX-PMD-clause-38 {
          base "optical-interface-func";
          description
               "LX-PMD-clause-38 Optical Interface function for 1000BASE-X PCS-36";
     }

     identity LX10-PMD-clause-59 {
          base "optical-interface-func";
          description
               "LX10-PMD-clause-59 Optical Interface function for 1000BASE-X PCS-
36";
     }

     identity BX10-PMD-clause-59 {
          base "optical-interface-func";
          description
               "BX10-PMD-clause-59 Optical Interface function for 1000BASE-X PCS-
36";
     }

     identity LW-PMD-clause-52 {
          base "optical-interface-func";
          description
               "LW-PMD-clause-52 Optical Interface function for 10GBASE-W PCS-49-
WIS-50";
     }

     identity EW-PMD-clause-52 {
          base "optical-interface-func";
          description
               "EW-PMD-clause-52 Optical Interface function for 10GBASE-W PCS-49-
WIS-50";
     }

     identity LR-PMD-clause-52 {
          base "optical-interface-func";
          description
               "LR-PMD-clause-52 Optical Interface function for 10GBASE-R PCS-49";
     }

     identity ER-PMD-clause-52 {
          base "optical-interface-func";
          description
               "ER-PMD-clause-52 Optical Interface function for 10GBASE-R PCS-49";
     }

     identity LR4-PMD-clause-87 {
          base "optical-interface-func";
          description
               "LR4-PMD-clause-87 Optical Interface function for 40GBASE-R PCS-82";
     }

     identity ER4-PMD-clause-87 {
          base "optical-interface-func";
          description
               "ER4-PMD-clause-87 Optical Interface function for 40GBASE-R PCS-82";
     }

     identity FR-PMD-clause-89 {
          base "optical-interface-func";
          description
               "FR-PMD-clause-89 Optical Interface function for 40GBASE-R PCS-82";
     }

     identity LR4-PMD-clause-88 {
          base "optical-interface-func";
          description
               "LR4-PMD-clause-88 Optical Interface function for 100GBASE-R PCS-
82";
     }

     identity ER4-PMD-clause-88 {
          base "optical-interface-func";
          description
               "ER4-PMD-clause-88 Optical Interface function for 100GBASE-R PCS-
82";
     }

     /* optical interface func needs to expand for Fiber Channel, SONET and SDH */

  identity performance-metriclist {
     description "list of performance metric";
  }

     identity One-way-Delay {
          base "performance-metriclist";
          description "one-way-delay";
     }

     identity One-way-Errored-Second {
          base "performance-metriclist";
          description "one-way-errored-second";
     }

     identity One-way-Severely-Errored-Second {
          base "performance-metriclist";
          description "one-way-severely-errored-second";
     }

     identity One-way-Unavailable-Second {
          base "performance-metriclist";
          description "one-way-unavailable-second";
     }

     identity One-way-Availability {
          base "performance-metriclist";
          description "one-way-availability";
     }

}
