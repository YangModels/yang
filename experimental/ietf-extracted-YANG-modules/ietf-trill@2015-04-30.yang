module ietf-trill {
  yang-version 1;
  namespace "urn:ietf:params:xml:ns:yang:ietf-trill";
  prefix ietf-trill;
  revision 2015-04-30{
    description "creating trill base model";
  }

  container trillSites {
    list trillSite {
     key "instanceId";

     leaf instanceId {
       config "true";
       type uint32 {
        range "0..4294967295";
       }
     }
     leaf name {
       config "true";
       type string;
     }
     container trillNetEntitys {
       list trillNetEntity {
         key "netEntity";

         leaf netEntity {
          config "true";
          type string;
         }
       }
     }
     container lspTimer {
       leaf lspLife {
         description "LSP aging timer.Unit:Second";
         config "true";
         default "1200";
         type uint16 {
           range "2..65535";
         }
       }
          leaf lspRefresh {
         description "LSP refresh timer.Unit:Second";
           config "true";
           default "900";
           type uint16 {
             range "1..65534";
           }
       }
       leaf lspGeneration {
         description "LSP generate timer.Unit:Second";
         config "true";
         default "2";
         type uint8 {
           range "1..120";
         }
         }
       }
       leaf nickNumber {
         config "true";
         default "1";
         type uint16 {
           range "1..256";
         }
       }
       leaf treeNumber {
         config "true";
         default "1";
         type uint16 {
           range "1..65535";
         }
       }
       leaf referenceBandwidth {
         config "true";
         default "20000000";
         type uint32 {
           range "1..2147483648";
         }
       }
       leaf nativeConfidence {
         description "The confidence in { MAC, VLAN, local port }
triples learned from locally received native frames";
         config "true";
         default "32";
         type uint8 {
           range "0..255";
         }
       }
       leaf remoteConfidence {
         description "The confidence in { MAC, VLAN, remote
RBridge } triples learned from decapsulating frames";
         config "true";
         default "32";
         type uint8 {
           range "0..255";
         }
       }
       leaf minLinkMTU {
         config "true";
         default "1470";
         type uint16 {
           range "1..65535";
         }
       }
       leaf MTUProbes {
         description "The number of failed MTU-probes";
         config "true";
         default "3";
         type uint8 {
           range "1..255";
         }
       }
       container Nicknames {
         list Nickname {
           key "nickName";
           leaf nickName {
             config "true";
             mandatory "true";
             type uint16 {
                 range "1..65471";
             }
           }
           leaf priority {
             config "true";
             default "192";
             type uint8 {
                 range "128..255";
             }
           }
           leaf rootPriority {
             config "true";
             default "32768";
             type uint16 {
                 range "1..65535";
             }
           }
         }
       }
     container trillPorts {
       list trillPort {
         key "ifName";
         leaf ifName {
           description "trill interface";
           type string;
         }
         leaf portMode {
           config "true";
           default "p2p";
           type enumeration {
             enum "access" {
               value "0";
               description "access:only process native frame";
             }
             enum "p2p" {
               value "1";
               description "p2p:use IS-IS P2P Hellos";
             }
             enum "trunk" {
               value "2";
               description "trunk:only process TRILL frames";
             }
             enum "hybrid" {
               value "3";
               description "hybrid: both trunk and access port";
             }
           }
         }
         container timer {
           leaf csnp {
           config "true";
           default "10";
           type uint16 {
             range "1..65535";
           }
         }
         leaf hello {
           config "true";
           default "10";
           type uint8 {
             range "3..255";
           }
         }
         leaf holdingMultiplier {
           config "true";
           default "3";
           type uint16 {
             range "3..1000";
           }
         }
         leaf lspRetransmit {
           config "true";
           default "5";
           type uint16 {
             range "1..300";
           }
         }
         container lspThrottle {
           leaf throttleInterval {
             description "The interval timer between two LSP
messages.Unit:ms";
             config "true";
             default "50";
             type uint16 {
               range "1..10000";
             }
           }
           leaf countNumber {
             description "The max messages number being sent each
time.Unit:ms";
               config "true";
               default "10";
               type uint16 {
                 range "1..1000";
               }
             }
         }
            leaf inhibitionTimer {
              description "The inhibition time for the port when
root bridge changes.Unit:Second";
           config "true";
           default "30";
           type uint8 {
             range "0..30";
           }
         }
            }
            container drbConfig {
              leaf drbPriority {
           config "true";
           default "64";
           type uint8 {
             range "0..127";
           }
           }
           leaf holdingTimer {
             config "true";
             default "10";
             type uint8 {
               range "3..255";
             }
           }
         }
         leaf macLearningFlag {
           description "if learning MAC address from locally
received native frames";
           config "true";
           default "true";
           type boolean;
         }
         leaf trillFrameReceiveFlag {
           description "if receiving of TRILL frames from non IS-IS
adjacency";
           config "true";
           default "false";
           type boolean;
         }
         leaf cost {
           config "true";
           default "0";
           type uint32 {
             range "0..16777215";
           }
         }
         leaf enabledVlans {
           config "true";
           type binary{
             length "1..4096";
           }
         }
         leaf announcingVlans {
           config "true";
           type binary{
             length "1..4096";
           }
         }
         leaf forwardingVlans {
           config "true";
           type binary{
             length "1..4096";
           }
         }
         leaf circuitId {
           config "false";
           type uint8;
         }
         leaf circuitMTU {
           config "false";
           type uint32;
         }
         leaf designatedVlan {
           config "true";
           type uint16{
             range "1..4096";
           }
         }
         leaf drbStatus {
           config "false";
           type enumeration {
             enum "Non-DRB" {
               value "0";
               description "Non-DRB:";
             }
             enum "DRB" {
               value "1";
               description "DRB:";
             }
             enum "Down" {
               value "2";
               description "Down:";
             }
             enum "Suspended" {
               value "3";
               description "Suspended:";
             }
           }
         }
       }
     }
        container vlanConfigs {
          list  vlanConfig{
          key "vlanID";
       config "true";

          leaf vlanID {
       config "true";
       type uint16 {
         range "1..4096";
       }
       }
          leaf participationFlag {
         config "true";
         default "false";
         type boolean;
       }
          leaf priority {
         config "true";
         default "64";
         type uint8 {
           range "0..127";
         }
       }
       leaf holdingTimer {
         config "true";
         default "10";
         type uint8 {
           range "3..255";
         }
       }
          }
        }
     container trillRouteInfos {
       list  trillRouteInfo {
         key "nickName nextHop";
         config "false";

         leaf nickName {
           config "false";
           type uint32;
         }
         leaf cost {
           config "false";
           type uint32;
         }
         leaf outInterface {
           config "false";
           type string;
         }
         leaf outVlan {
           config "false";
           type uint32;
         }
         leaf nextHop {
           config "false";
           type string;
         }
         leaf hopCount {
           config "false";
           type uint32;
         }
       }
     }

     container trillMRouteInfos {
       list trillMRouteInfo {
         description "Distribution pruning tree route table; For
non-pruning tree, VLAN is set to be 0XFFFF";
         key "vlan rootNickname";
         config "false";

         leaf vlan {
           config "false";
           type uint16;
         }
         leaf rootNickname {
           config "false";
           type uint16;
         }
         leaf hopCount {
           config "false";
           type uint16;
         }
         container outInterfaceinfo {

           list trillMRouteOutInterfaceInfo {

             key "outInterface outVlan";
             config "false";

             leaf outInterface {
               config "false";
               type "string";
             }
             leaf outVlan {
               config "false";
               type "uint32";
             }
           }
         }
       }
     }

     container trillRpfCheckInfos {
       list trillRpfCheckInfo {
         key "ingressNickname treeNickname";
         config "false";
         leaf ingressNickname {
           config "false";
           type "uint16";
         }
         leaf treeNickname {
           config "false";
           type "uint16";
         }
         leaf interfaceName {
           config "false";
           type "string";
         }
         leaf neighborMac {
           config "false";
           type "string";
         }
         leaf outVlan {
           config "false";
           type "uint16";
         }
       }
     }

     container trillPeerInfos {
       list trillPeerInfo {
         key "hostName circuitId";
         config "false";

         leaf hostName {
           description "Peer RBridge name";
           config "false";
           type "string";
         }
         leaf interfaceName {
           config "false";
           type "string";
         }
         leaf circuitId {
           config "false";
           type "string";
         }
         leaf status {
           config "false";
           type enumeration {
           enum "report" {
             value "0";
             description "report:";
           }
           enum "detect" {
             value "1";
             description "detect:";
           }
           enum "down" {
             value "2";
             description "down:";
           }
           enum "2way" {
             value "3";
             description "2way:";
           }
           }
         }
         leaf holdTime {
           config "false";
           type "uint32";
         }
         leaf priority {
           config "false";
           type "string";
         }
       }
     }

     container trillLsdbInfos {
       list trillLsdbInfo {
         key "lspId";
         config "false";

         leaf lspId {
           config "false";
           type "string";
         }
         leaf seqenceNumber {
           config "false";
           type "string";
         }
         leaf checkSum {
           config "false";
           type "string";
         }
         leaf lspLength {
           config "false";
           type uint32 {
             range "0..2000";
           }
         }
         leaf attBit {
           config "false";
           type uint8 {
             range "0..1";
           }
         }
         leaf partitionBit {
           config "false";
           type uint8 {
             range "0..1";
           }
         }
         leaf overloadBit {
           config "false";
           type uint8 {
             range "0..1";
           }
         }
         leaf holdTime {
           config "false";
           type "string";
         }
         leaf localLsp {
           config "false";
           type "boolean";
         }
       }
     }
     container trillNicknameInfos {
       list trillNicknameInfo {

         key "nickName systemId";
         config "false";

         leaf nickName {
           config "false";
           type uint32;
         }
         leaf priority {
           config "false";
           type uint32;
         }
         leaf rootPriority {
           config "false";
           type uint32;
         }
         leaf systemId {
           config "false";
           type string;
         }
         leaf conflictState {
           config "false";
           type enumeration {
           enum "S" {
             value "0";
             description "S:";
           }
           enum "A" {
             value "1";
             description "A:";
           }
           }
         }
         leaf staticFlag {
           config "false";
           type enumeration {
           enum "S" {
             value "0";
             description "S:";
           }
           enum "D" {
             value "1";
             description "D:";
           }
           }
         }
         leaf isLocal {
           config "false";
           type boolean;
         }
       }
     }
     container trillStatistics {

          container interfaceStat {
            leaf upNum {
               config "false";
               type uint32;
            }
            leaf downNum {
               config "false";
               type uint32;
            }
          }
          container pktstatistics {
            leaf reportNum {
              config "false";
              type uint32;
            }
            leaf detectNum {
               config "false";
               type uint32;
            }
            leaf twoWayNum {
              config "false";
              type uint32;
            }
          }
          leaf unicastRoutesNum {
            config "false";
            type uint32;
          }
          leaf multicastRoutesNum {
            config "false";
            type uint32;
          }
          leaf rpfEntrysNum {
            config "false";
            type uint32;
          }
          leaf remoteNicknamesNum {
            config "false";
            type uint32;
          }
          leaf lsdbLSPsNum {
            config "false";
            type uint32;
          }
          leaf selfLSPsNum {
            config "false";
            type uint32;
          }
          leaf multicastTreesNum {
            config "false";
            type uint32;
          }
          leaf unicastNodesNum {
            config "false";
            type uint32;
          }
          leaf multicastNodesNum {
            config "false";
            type uint32;
          }
        }

        container pktStatistics {
          list pktStatistic {
            key "interfaceName";
            config "false";

            leaf interfaceName {
              config "false";
              type string;
            }
            leaf sentHellosNum {
              config "false";
              type uint32;
            }
            leaf recvedHellosNum {
              config "false";
              type uint32;
            }
            leaf sentLSPsNum {
              config "false";
              type uint32;
            }
            leaf recvedLSPsNum {
              config "false";
              type uint32;
            }
            leaf sentCSNPsNum {
              config "false";
              type uint32;
            }
            leaf recvedCSNPsNum {
              config "false";
              type uint32;
            }
            leaf sentPSNPsNum {
              config "false";
              type uint32;
            }
            leaf recvedPSNPsNum {
              config "false";
              type uint32;
            }
            leaf lspRetransmissionsNum {
              config "false";
              type uint32;
            }
            leaf drbElectionsNum {
              config "false";
              type uint32;
            }
          }
        }
      }
   }
