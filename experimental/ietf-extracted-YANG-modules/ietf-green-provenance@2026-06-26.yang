module ietf-green-provenance {
  yang-version 1.1;
  namespace
    "urn:ietf:params:xml:ns:yang:ietf-green-provenance";
  prefix igp;

  import ietf-power-and-energy {
    prefix eo;
    reference
      "I-D.ietf-green-power-and-energy-yang: Power and Energy
       YANG Module";
  }

  import ietf-yang-types {
    prefix yang;
    reference
      "RFC 9911: Common YANG Data Types";
  }

  organization
    "IETF GREEN Working Group";

  contact
    "WG Web:  <https://datatracker.ietf.org/wg/green/>
     WG List: <mailto:green@ietf.org>";

  description
    "This module augments the GREEN Power and Energy YANG module
     (ietf-power-and-energy) with provenance traceability leaves
     for each Energy Object, exposing the outcome of COSE
     signature verification performed by the controller.

     The key words 'MUST', 'MUST NOT', 'REQUIRED', 'SHALL',
     'SHALL NOT', 'SHOULD', 'SHOULD NOT', 'RECOMMENDED', 'NOT
     RECOMMENDED', 'MAY', and 'OPTIONAL' in this document are
     to be interpreted as described in BCP 14 (RFC 2119)
     (RFC 8174) when, and only when, they appear in all
     capitals, as shown here.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://www.rfc-editor.org/info/rfcXXXX); see the RFC
     itself for full legal notices.";

  revision 2026-06-26 {
    description
      "Initial revision.";
    reference
      "RFC XXXX: Provenance Traceability Augmentation for the
       GREEN Power and Energy YANG Module";
  }

  /* Identities */

  identity key-owner-type {
    description
      "Base identity for the entity that provisioned and manages
       the COSE signing key used to sign data associated with an
       Energy Object.";
  }

  identity key-owner-device {
    base key-owner-type;
    description
      "The Energy Object generated and manages its own key pair
       and self-attests its own telemetry.";
  }

  identity key-owner-controller {
    base key-owner-type;
    description
      "The controller generated and manages the key pair on
       behalf of the Energy Object, typically because the Energy
       Object lacks native signing capability.  The controller
       signs data it collected on the Energy Object's behalf.";
  }

  identity key-owner-external-ca {
    base key-owner-type;
    description
      "The key belongs to a certificate authority or data
       authority outside the operator's administrative domain,
       such as a grid energy provider or carbon intensity
       service.";
  }

  /* Augmentation */

  augment "/eo:energy-objects/eo:energy-entry" {
    description
      "Adds provenance traceability metadata to each Energy
       Object entry.  All leaves are set by the controller after
       verifying a COSE provenance signature associated with this
       Energy Object's telemetry, per
       I-D.ietf-opsawg-yang-provenance.  The provenance-signature
       value itself is not stored here; see Section 3.2 of this
       document.";

    leaf provenance-key-id {
      type string {
        length "1..256";
      }
      config false;
      description
        "The Key Identifier (kid) from the COSE_Sign1 protected
         header of the most recently verified provenance
         signature associated with this Energy Object.  Absent if
         no provenance signature has been received and verified.";
      reference
        "RFC 9052: CBOR Object Signing and Encryption (COSE),
         Section 3.1;
         I-D.ietf-opsawg-yang-provenance, Section 3.1";
    }

    leaf provenance-key-owner {
      type identityref {
        base key-owner-type;
      }
      config false;
      description
        "Identifies the entity that provisioned and manages the
         signing key whose kid is recorded in provenance-key-id.
         Absent if no provenance signature has been received and
         verified.";
    }

    leaf traceability-verified {
      type boolean;
      config false;
      description
        "Whether the most recently received provenance signature
         for this Energy Object passed COSE verification.  A
         controller SHOULD NOT use this Energy Object's data in
         any reporting or control pipeline while this leaf is
         false.  Absent if no verification has been attempted.";
    }

    leaf traceability-last-verified {
      type yang:date-and-time;
      config false;
      description
        "The date and time at which the controller last
         successfully verified a provenance signature for this
         Energy Object.  Absent if no successful verification has
         occurred.";
    }

    leaf traceability-failure-reason {
      type string {
        length "0..512";
      }
      config false;
      description
        "A human-readable explanation of the most recent
         provenance verification failure.  Present only when
         traceability-verified is false.";
    }
  }
}
