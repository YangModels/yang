module softwire {
  namespace "urn:ietf:params:xml:ns:yang:softwire";
  prefix "softwire";

  import ietf-inet-types { prefix inet; }

  organization "softwire";

  contact
    "
    Qi Sun sunqi@csnet1.cs.tsinghua.edu.cn
    Hao Wang wangh13@mails.tsinghua.edu.cn
    Yong Cui yong@csnet1.cs.tsinghua.edu.cn
    Ian Farrer ian.farrer@telekom.de
    ";

  description
    "This document defines a YANG data model that can be used to
    configure and manage softwire concentrators.
    Copyright (c) 2014 IETF Trust and the persons identified
    as authors of the code. All rights reserved.
    This version of this YANG module is part of RFC XXX; see the RFC
    itself for full legal notices.";

  revision 2014-10-20 {
    description
      "Initial revision.";
  }

/*
 * Typedef
 */

/*
 * Features
 */

  feature lw4over6 {
    description
      "Lightweight 4over6 moves the Network Address and Port
      Translation (NAPT) function from the centralized DS-Lite tunnel
      concentrator to the tunnel client located in the Customer
      Premises Equipment (CPE).  This removes the requirement for a
      Carrier Grade NAT function in the tunnel concentrator and
      reduces the amount of centralized state that must be held to a
      per-subscriber level.  In order to delegate the NAPT function
      and make IPv4 Address sharing possible, port-restricted IPv4
      addresses are allocated to the CPEs.";
    reference
      "I-D.ietf-softwire-lw4over6";
  }

  feature map-e {
    description
      "MAP-E is a mechanism for transporting IPv4 packets across an
      IPv6 network using IP encapsulation, and a generic mechanism
      for mapping between IPv6 addresses and IPv4 addresses and
      transport layer ports.";
    reference
      "I-D.ietf-softwire-map";
  }

/*
 * Grouping
 */

  grouping port-set {
    description
      "A range of transport layer ports.";
    leaf offset {
      type uint8;
      default "0";
      description
        "The number of offset bits.";
    }
    leaf psid-len {
      type uint8;
      description
        "The length of Port Set Identifier (PSID).";
    }
    leaf psid {
      type inet:port-number;
      description
        "Algorithmically identifies a set of ports.";
    }
  }

  grouping binding-table {
    description
      "The lwAFTR maintains an address binding table containing the
      binding between the lwB4's IPv6 address, the allocated IPv4
      address and restricted port-set.";
    list binding-entry {
      key "id";
      leaf id {
        type uint32;
      }
      leaf binding-ipv4-addr {
        type inet:ipv4-address;
        description
          "The IPv4 address assigned to a lwB4, which is used as the
          IPv4 External Address for lwB4 local NAPT44. One of three
          elemnts constructing a binding entry.";
      }
      container port-set {
        uses port-set;
      }
      leaf binding-ipv6-addr {
        type inet:ipv6-address;
        description
          "The IPv6 address of the lwB4, which is used to bind the
          IPv4 address and port-set.";
      }
      leaf active {
        type boolean;
        description
          "Used to delete the inactive binding-entries.";
      }
    }
  }

  grouping map-rule-table {
    description
      "The (conceptual) table containing rule Information for
      a specific mapping rule. It can also be used for row creation.";
    list map-rule-entry {
      key "id";
      leaf id {
        type uint8;
      }
      leaf IPv6-prefix {
        type inet:ipv6-address;
        description
          "The IPv6 prefix defined in the mapping rule which will be
          assigned to CE.";
      }
      leaf IPv6-prefix-len {
        type uint8;
        description
          "The length of the IPv6 prefix defined in the mapping rule.
          As a parameter for the mapping rule, it will be also assigned
          to CE.";
      }
      leaf IPv4-prefix {
        type inet:ipv4-address;
        description
          "The IPv4 prefix defined in the mapping rule which will be
          assigned to CE.";
      }
      leaf IPv4-prefix-len {
        type uint8;
        description
          "The length of the IPv4 prefix defined in the mapping
          rule. As a parameter for the mapping rule, it will be also
          assigned to CE.";
      }
      container port-set {
        uses port-set;
      }
      leaf ea-len {
        type uint8;
        description
          "The length of the Embedded-Address (EA) defined in
          mapping rule which will be assigned to CE.";
      }
      leaf active {
        type boolean;
        description
            "Used to delete inactive map-rule-entries.";
      }
    }
  }

/*
 * Configuration Data Nodes
 */

  container softwire-config {
    description
      "The configuration data for concentrators in softwire. ";
    leaf enabled {
      type boolean;
      default "true";
      description
        "Enable/disable the Softwire concentrator function.";
    }
    leaf name {
      type string;
      description
        "The name of the softwire concentrator.";
    }
    leaf description {
      type string;
      description
        "A textual description of the softwire concentrator.";
    }
    leaf softwire-num-threshold {
      type uint32;
      description
        "The maximum number of tunnels that can be created on
        the concentrator.";
    }
    leaf tunnel-mtu {
      type uint32;
      description
        "The MTU of tunnel payload on the softwire concentrator.";
    }
    container lw4over6 {
      if-feature lw4over6;
      description
        "Indicate this device supports the Lightweight 4over6 function.
        Devices advertise the lw4over6 feature through the capability
        exchange mechanism when a NETCONF session is established.";
      container lwaftrs {
        description
          "An AFTR element (Address Family Transition Router element
          [RFC6333]), which supports Lightweight 4over6 extension.
          An lwAFTR is an IPv4-in-IPv6 tunnel endpoint which maintains
          per-subscriber address binding only and does not perform a
          NAPT44 function.";
        list lwaftr {
          key "id";
          leaf id {
            type uint32;
          }
          leaf lwaftr-ipv6-addr {
            type inet:ipv6-address;
            description
              "The IPv6 address of the lwAFTR.";
          }
          container binding-table {
            uses binding-table;
          }
        }
      }
    }
    container map-e {
      if-feature map-e;
      description
        "Indicate the devices support the MAP-E function. Devices
        advertise the map-e feature through the capability exchange
        mechanism when a NETCONF session is established.";
      container map-brs {
        description
          "A MAP enabled router managed by the service provider at
          the edge of a MAP domain.
          A Border Relay router has at least an IPv6-enabled interface
          and an IPv4 interface connected to the native IPv4 network.
          A MAP BR may also be referred to simply as a "BR" within the
          context of MAP.";
        list map-br {
          key "id";
          leaf id {
            type uint32;
          }
          leaf br-ipv6-addr {
            type inet:ipv6-address;
            description
              "The IPv6 address of the Border Router.";
          }
          container map-rule-table {
            uses map-rule-table;
          }
        }
      }
    }
  }
