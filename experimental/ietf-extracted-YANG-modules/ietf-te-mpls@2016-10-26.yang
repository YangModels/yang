module ietf-te-mpls {

  namespace "urn:ietf:params:xml:ns:yang:ietf-te-mpls";

  /* Replace with IANA when assigned */
  prefix "te-mpls";

  /* Import TE generic types */
  import ietf-te {
    prefix te;
  }

  /* Import MPLS TE specific types */
  import ietf-te-mpls-types {
    prefix te-mpls-type;
  }

  organization
    "IETF Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editor:   Tarek Saad
               <mailto:tsaad@cisco.com>

     Editor:   Rakesh Gandhi
               <mailto:rgandhi@cisco.com>

     Editor:   Vishnu Pavan Beeram
               <mailto:vbeeram@juniper.net>

     Editor:   Himanshu Shah
               <mailto:hshah@ciena.com>

     Editor:   Xufeng Liu
               <mailto:xufeng.liu@ericsson.com>

     Editor:   Xia Chen
               <mailto:jescia.chenxia@huawei.com>

     Editor:   Raqib Jones
               <mailto:raqib@Brocade.com>

     Editor:   Bin Wen
               <mailto:Bin_Wen@cable.comcast.com>";

  description
    "YANG data module for MPLS TE configurations,
    state, RPC and notifications.";

  revision "2016-10-26" {
    description "Latest update to MPLS TE YANG module.";
    reference "TBD";
  }

  /* MPLS TE tunnel properties*/
  grouping tunnel-mpls-properties_config {
    description "MPLS TE tunnel properties";
    uses te-mpls-type:tunnel-routing-properties;
    uses te-mpls-type:tunnel-forwarding-properties;
  }

  /*** End of MPLS TE tunnel configuration/state */

  /**
   * MPLS TE augmentations
   */

  /* MPLS TE tunnel augmentations */
  augment "/te:te/te:tunnels/te:tunnel/te:config" {
    description "MPLS TE tunnel config augmentations";
    uses tunnel-mpls-properties_config;
  }
  augment "/te:te/te:tunnels/te:tunnel/te:state" {
    description "MPLS TE tunnel state augmentations";
    uses tunnel-mpls-properties_config;
  }

  /* MPLS TE LSPs augmentations */
}
