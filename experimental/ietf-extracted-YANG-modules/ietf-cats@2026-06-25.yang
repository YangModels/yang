module ietf-cats {
  yang-version 1.1;
  namespace "urn:ietf:params:xml:ns:yang:ietf-cats";
  prefix cats;

  import ietf-routing {
    prefix rt;
    reference
      "RFC 8349: A YANG Data Model for Routing
                 Management (NMDA Version)";
  }

  import ietf-inet-types {
    prefix inet;
    reference
      "RFC 9911: Common YANG Data Types, Section 4";
  }

  import ietf-yang-types {
    prefix yang;
    reference
      "RFC 9911: Common YANG Data Types, Section 3";
  }

  organization
    "IETF Computing-Aware Traffic Steering (CATS) Working Group";

  contact
    "WG Web:  https://datatracker.ietf.org/group/cats
     WG List: CATS <mailto:cats@ietf.org>

     Editor:  Huijuan Yao
              <mailto:yaohuijuan@chinamobile.com>
     Editor:  Changwang Lin
              <mailto:linchangwang.04414@h3c.com>
     Editor:  Zhenqiang Li
              <mailto:lizhenqiang@chinamobile.com>
     Editor:  Quan Xiong
              <mailto:xiong.quan@zte.com.cn>
     Editor:  Luis M. Contreras
              <mailto:luismiguel.contrerasmurillo@telefonica.com>";

  description
    "This module describes a YANG model for managing the CATS
     system.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see the
     RFC itself for full legal notices.";

  revision 2026-06-25 {
    description
      "Initial Version";
    reference
      "RFC XXXX: YANG Data Model for CATS";
   }

  typedef cs-id {
    type union {
      type uint32;
      type inet:ipv4-address;
      type inet:ipv6-address;
    }
    description
      "This type defines the CATS Service ID (CS-ID),
       which uniquely identifies a service.";
    reference
      "draft-ietf-cats-framework: A Framework for Computing-Aware
                                  Traffic Steering (CATS)";
  }

  typedef csci-id {
    type union {
      type uint32;
      type inet:ipv4-address;
      type inet:ipv6-address;
    }
    description
      "This type defines the CATS Service Contact Instance ID
       (CSCI-ID), which uniquely identifies a service contact
       instance.";
    reference
      "draft-ietf-cats-framework: A Framework for Computing-Aware
                                  Traffic Steering (CATS)";
  }

  /*
   * Identities for source-type
   */
  identity source-type-base {
    description
      "Base identity for source types of service computing metrics.";
  }

  identity source-type-static {
    base source-type-base;
    description
      "Static configuration. This identity is used when the
       service metric information is configured statically
       (not learned from a dynamic protocol).";
  }

  /*
   * Identities for metric-type
   */
  identity metric-type-base {
    description
      "Base identity for service metric types.";
  }

  identity metric-delay {
    base metric-type-base;
    description
      "Transmission delay metric. The metric value is the delay
       time in milliseconds.";
  }

  identity metric-service-ratio {
    base metric-type-base;
    description
      "Service capacity ratio metric. The metric value is the
       current capacity percentage.";
  }

  identity metric-memory-ratio {
    base metric-type-base;
    description
      "Memory utilization metric. The metric value is the current
       memory utilization percentage.";
  }

  grouping service-policy-type {
    description
      "Service policy type";
    leaf policy-type {
      type enumeration {
        enum base-on-affinity {
          value 0;
          description "Base on affinity";
        }
        enum base-on-sm-only {
          value 1;
          description "Base on service metric only";
        }
        enum base-on-nm-only {
          value 2;
          description "Base on network metric only";
        }
        enum base-on-sm-nm {
          value 3;
          description 
            "Base on the combination of service metric and network
             metric";
        } 
      }
      description "Service policy type";
    }
  }

  augment "/rt:routing" {
    description
      "This augments the CATS configuration.";
    container cats {
      description
        "Support for the CATS configuration.";
      container base {
        description
          "CATS base configuration.";
        leaf enable {
          type boolean;
          description
            "Enable CATS";
        }
        leaf update-interval {
          type uint32;
          units "seconds";
          default "30";
          description
            "Update interval of CATS metric. A value of 0
             indicates that metrics are sent only when a
             significant change occurs and not on a periodic
             basis.";
        }
        leaf metric-limits {
          type uint32;
          description
            "The maximum number of metric table entries that
             can be maintained by the device. This limit prevents
             resource exhaustion. The actual maximum value is
             implementation-dependent and should be documented by the
             vendor. A value of 0 indicates no configured limit
             (subject to device capacity).";
        }
        leaf flow-limits {
          type uint32;
          description
            "The maximum number of flow table entries that
             can be maintained by the device. This limit prevents
             resource exhaustion. The actual maximum value is
             implementation-dependent and should be documented by the
             vendor. A value of 0 indicates no configured limit
             (subject to device capacity).";
        }
        leaf flow-timeout {
          type uint32;
          units "seconds";
          default "120";
          description
            "CATS flow timeout when no flow. A value of 0 means
             that the flow does not time out due to inactivity
             (i.e., infinite timeout), and must be terminated
             explicitly (e.g., via signaling or administrative
             action).";
        }
        leaf notify-interval {
          type uint32;
          units "seconds";
          default "10";
          description
            "The minimum interval between consecutive notifications.
             This is used to prevent notification flooding when
             limits are reached and unreached in quick succession
             (flapping). A value of 0 means notifications are
             sent immediately without rate limiting.";
        }
        list service-policy {
          key "cs-id";
          description
            "CATS service policy configuration for traffic steering.
             Each entry defines the policy type for a specific
             service identified by cs-id.";
          leaf cs-id {
            type cs-id;
            description
              "The CATS Service ID (CS-ID) that uniquely
               identifies a service. This identifier is used
               by clients to access the service.";
            reference
              "draft-ietf-cats-framework: A Framework for
                                          Computing-Aware Traffic
                                          Steering (CATS)";
          }
          uses service-policy-type;
        }
      }

      container traffic-classifiers {
        description
          "CATS traffic-classifier entries for classifying
           traffic by service. Each entry defines the matching
           criteria for a specific service identified by cs-id.";
        list traffic-classifier {
          key "cs-id";
          description
            "A traffic classifier entry for a specific service.
             The cs-id uniquely identifies the service to be
             classified.";
          leaf cs-id {
            type cs-id;
            description
              "The CATS Service ID (CS-ID) that uniquely
               identifies a service.";
            reference
              "draft-ietf-cats-framework: A Framework for
                                          Computing-Aware Traffic
                                          Steering (CATS)";
          }
          leaf description {
            type string {
              length "0..255";
            }
            description
              "A human-readable description of this service
               (e.g., 'http', 'video-streaming'). The length
               constraint provides a reasonable upper bound
               for short descriptive text and avoids
               unbounded-string risks. The value 255 follows
               the historical SNMP SnmpAdminString convention
               for management text. Note that length counts
               Unicode characters, not UTF-8 octets.
               Zero-length is permitted for empty descriptions.";
          }
          leaf server-port {
            type uint16;
            description
              "Server-port of the service, matches the
               destination port in the IP packets of data
               flows destined for the service.";
          }
          leaf protocol {
            type uint8;
            description
              "The IP protocol number of the service. This value
               matches the protocol field in the IP header of data
               flows destined for the service. Common values include:
               6 (Transmission Control Protocol), 17 (User Datagram
               Protocol), and 132 (Stream Control Transmission
               Protocol).";
            reference
              "IANA: Protocol Numbers Registry
                     <https://www.iana.org/assignments/
                     protocol-numbers/>";
          }
          leaf matched-packets {
            type yang:zero-based-counter64;
            config false;
            description
              "The number of packets matching the specified
               service.";
          }
          leaf matched-bytes {
            type yang:zero-based-counter64;
            config false;
            description
              "The number of bytes in packets matching the specified
               service.";
          }
        }
      }

      container service-metrics {
        description
          "CATS service metric entries for controlling
           delivery of service metrics from the control plane
           to the forwarding plane.";
        list service-metric {
          key "cs-id csci-id source-type";
          description
            "A service metric entry for a specific service
             instance. The combination of cs-id, csci-id,
             and source-type uniquely identifies a service
             metric entry.";
          leaf cs-id {
            type cs-id;
            description
              "The CATS Service ID (CS-ID) that uniquely
               identifies a service.";
            reference
              "draft-ietf-cats-framework: A Framework for
                                          Computing-Aware Traffic
                                          Steering (CATS)";
          }
          leaf csci-id {
            type csci-id;
            description
              "The CATS Service Contact Instance ID (CSCI-ID)
               that uniquely identifies a specific service contact
               instance.";
            reference
              "draft-ietf-cats-framework: A Framework for
                                          Computing-Aware Traffic
                                          Steering (CATS)";
          }
          leaf source-type {
            type identityref {
              base source-type-base;
            }
            description
              "The source type of the service computing metric.
               Indicates how the metric information was learned.
               The base identity 'source-type-base' can be extended
               by other modules to define additional source types.";
          }
          leaf priority {
            type uint8;
            description
              "The server priority. The smaller the value,
               the higher the priority (i.e., 0 is the highest
               priority). This convention follows common practice
               in networking protocols (e.g., IP precedence,
               administrative distance).";
          }
          leaf affinity {
            type uint8;
            description
              "The server affinity. The higher the value,
               the higher the affinity (i.e., 0 is the lowest
               affinity). This convention follows common practice
               for affinity or weight metrics in load balancing.";
          }
          leaf location {
            type inet:ip-address;
            description
              "The IPv4 or IPv6 address of the service site where
               this service contact instance resides. This address
               represents the logical location of the service in
               the network topology. CATS-enabled routers use this
               location information to compute network distances
               and make steering decisions based on proximity to
               the service instance.";
          }
          container metrics {
            description
              "Service metrics for the service contact instance.
               Each metric entry carries a metric type and its
               associated value.";
            list metric {
              key "metric-type";
              description "A service metric of a specific type.";
              leaf metric-type {
                type identityref {
                  base metric-type-base;
                }
                description
                  "The type of the service metric. The base identity
                   'metric-type-base' can be extended by other
                   modules to define additional metric types.";
                reference
                  "draft-ietf-cats-metric-definition: CATS Metrics
                                                      Definition";
              }
              leaf metric-value {
                type uint32;
                description "The value of the service metric.";
              }
            }
          }
          leaf forwarded-packets {
            type yang:zero-based-counter64;
            config false;
            description
              "The number of packets forwarded by the specified
               service";
          }
          leaf forwarded-bytes {
            type yang:zero-based-counter64;
            config false;
            description
              "The number of bytes in packets forwarded by the
               specified service";
          }
        }
      }
      notification metric-limit-exceeded {
        description
          "Event notification sent when the number of metric
           entries exceeds the configured maximum limit.";
        leaf timestamp {
          type yang:date-and-time;
          mandatory true;
          description
            "The time when the metric limit was exceeded.";
        }
        leaf message {
          type string {
            length "1..255";
          }
          mandatory true;
          description
            "A human-readable message describing the event,
             including the configured maximum limit.
             The length constraint provides a reasonable upper
             bound for short event messages and avoids
             unbounded-string risks. The value 255 follows the
             historical SNMP SnmpAdminString convention for
             management text. Note that length counts Unicode
             characters, not UTF-8 octets. Zero-length is
             disallowed since this notification always carries
             content.";
        }
      }
      notification metric-limit-recovered {
        description
          "Event notification sent when the number of metric
           entries returns to or falls below the configured
           maximum limit after having exceeded it.";
        leaf timestamp {
          type yang:date-and-time;
          mandatory true;
          description
            "The time when the metric limit was recovered.";
        }
        leaf message {
          type string {
            length "1..255";
          }
          mandatory true;
          description
            "A human-readable message describing the event,
             including the configured maximum limit.
             The length constraint provides a reasonable upper
             bound for short event messages and avoids
             unbounded-string risks. The value 255 follows the
             historical SNMP SnmpAdminString convention for
             management text. Note that length counts Unicode
             characters, not UTF-8 octets. Zero-length is
             disallowed since this notification always carries
             content.";
        }
      }
      notification flow-limit-exceeded {
        description
          "Event notification sent when the number of flow
           entries exceeds the configured maximum limit.";
        leaf timestamp {
          type yang:date-and-time;
          mandatory true;
          description
            "The time when the flow limit was exceeded.";
        }
        leaf message {
          type string {
            length "1..255";
          }
          mandatory true;
          description
            "A human-readable message describing the event,
             including the configured maximum limit.
             The length constraint provides a reasonable upper
             bound for short event messages and avoids
             unbounded-string risks. The value 255 follows the
             historical SNMP SnmpAdminString convention for
             management text. Note that length counts Unicode
             characters, not UTF-8 octets. Zero-length is
             disallowed since this notification always carries
             content.";
        }
      }
      notification flow-limit-recovered {
        description
          "Event notification sent when the number of flow
           entries returns to or falls below the configured
           maximum limit after having exceeded it.";
        leaf timestamp {
          type yang:date-and-time;
          mandatory true;
          description
            "The time when the flow limit was recovered.";
        }
        leaf message {
          type string {
            length "1..255";
          }
          mandatory true;
          description
            "A human-readable message describing the event,
             including the configured maximum limit.
             The length constraint provides a reasonable upper
             bound for short event messages and avoids
             unbounded-string risks. The value 255 follows the
             historical SNMP SnmpAdminString convention for
             management text. Note that length counts Unicode
             characters, not UTF-8 octets. Zero-length is
             disallowed since this notification always carries
             content.";
        }
      }
    }
  }
}
