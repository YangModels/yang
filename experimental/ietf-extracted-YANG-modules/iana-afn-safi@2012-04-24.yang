module iana-afn-safi {
  namespace "urn:ietf:params:xml:ns:yang:iana-afn-safi";
  prefix "ianaaf";

  organization
    "IANA";
  contact
    "        Internet Assigned Numbers Authority

     Postal: ICANN
             4676 Admiralty Way, Suite 330
             Marina del Rey, CA 90292

     Tel:    +1 310 823 9358
     E-Mail: iana&iana.org";
  description
    "This YANG module provides two typedefs containing YANG
     definitions for the following IANA-registered enumerations:

     - Address Family Numbers (AFN)

     - Subsequent Address Family Identifiers (SAFI)

     The latest revision of this YANG module can be obtained from the
     IANA web site.

     Copyright (c) 2012 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";
  // RFC Ed.: replace XXXX with actual RFC number and remove this
  // note.

  // RFC Ed.: update the date below with the date of RFC publication
  // and remove this note.
  revision 2012-04-24 {
    description
      "Initial revision.";
    reference
      "RFC XXXX: TITLE";
  }

  typedef address-family {
    type enumeration {
      enum other {
        value "0";
        description
          "none of the following";
      }
      enum ipV4 {
        value "1";
        description
          "IP Version 4";
      }
      enum ipV6 {
        value "2";
        description
          "IP Version 6";
      }
      enum nsap {
        value "3";
        description
          "NSAP";
      }
      enum hdlc {
        value "4";
        description
          "(8-bit multidrop)";
      }
      enum bbn1822 {
        value "5";
        description
          "BBN Report 1822";
      }
      enum all802 {
        value "6";
        description
          "(includes all 802 media plus Ethernet 'canonical
           format')";
      }
      enum e163 {
        value "7";
        description
          "E.163";
      }
      enum e164 {
        value "8";
        description
          "(SMDS, FrameRelay, ATM)";
      }
      enum f69 {
        value "9";
        description
          "(Telex)";
      }
      enum x121 {
        value "10";
        description
          "(X.25, Frame Relay)";
      }
      enum ipx {
        value "11";
        description
          "IPX (Internet Protocol Exchange)";
      }
      enum appleTalk {
        value "12";
        description
          "Apple Talk";
      }
      enum decnetIV {
        value "13";
        description
          "DEC Net Phase IV";
      }
      enum banyanVines {
        value "14";
        description
          "Banyan Vines";
      }
      enum e164withNsap {
        value "15";
        description
          "(E.164 with NSAP format subaddress)";
      }
      enum dns {
        value "16";
        description
          "(Domain Name System)";
      }
      enum distinguishedName {
        value "17";
        description
          "(Distinguished Name, per X.500)";
      }
      enum asNumber {
        value "18";
        description
          "(16-bit quantity, per the AS number space)";
      }
      enum xtpOverIPv4 {
        value "19";
        description
          "XTP over IP version 4";
      }
      enum xtpOverIpv6 {
        value "20";
        description
          "XTP over IP version 6";
      }
      enum xtpNativeModeXTP {
        value "21";
        description
          "XTP native mode XTP";
      }
      enum fibreChannelWWPN {
        value "22";
        description
          "Fibre Channel World-Wide Port Name";
      }
      enum fibreChannelWWNN {
        value "23";
        description
          "Fibre Channel World-Wide Node Name";
      }
      enum gwid {
        value "24";
        description
          "Gateway Identifier";
      }
      enum afi {
        value "25";
        description
          "AFI for L2VPN";
      }
    }
    description
      "This typedef is a YANG enumeration of IANA-registered address
       family numbers (AFN).";
    reference
      "Address Family Numbers. IANA, 2011-01-20.
       <http://www.iana.org/assignments/address-family-numbers/
       address-family-numbers.xml>

       IANA-ADDRESS-FAMILY-NUMBERS-MIB DEFINITIONS
       <http://www.iana.org/assignments/ianaaddressfamilynumbers-mib>
      ";
  }

  typedef subsequent-address-family {
    type enumeration {
      enum nlri-unicast {
        value "1";
        description
          "Network Layer Reachability Information used for unicast
           forwarding";
        reference
          "RFC4760";
      }
      enum nlri-multicast {
        value "2";
        description
          "Network Layer Reachability Information used for multicast
           forwarding";
        reference
          "RFC4760";
      }
      enum nlri-mpls {
        value "4";
        description
          "Network Layer Reachability Information (NLRI) with MPLS
           Labels";
        reference
          "RFC3107";
      }
      enum mcast-vpn {
        value "5";
        description
          "MCAST-VPN";
        reference
          "draft-ietf-l3vpn-2547bis-mcast-bgp-08";
      }
      enum nlri-dynamic-ms-pw {
        value "6";
        status "obsolete";
        description
          "Network Layer Reachability Information used for Dynamic
           Placement of Multi-Segment Pseudowires (TEMPORARY -
           Expires 2008-08-23)";
        reference
          "draft-ietf-pwe3-dynamic-ms-pw-13";
      }
      enum tunnel-safi {
        value "64";
        description
          "Tunnel SAFI";
        reference
          "draft-nalawade-kapoor-tunnel-safi-05";
      }
      enum vpls {
        value "65";
        description
          "Virtual Private LAN Service (VPLS)";
        reference
          "RFC4761, RFC6074";
      }
      enum bgp-mdt {
        value "66";
        description
          "BGP MDT SAFI";
        reference
          "RFC6037";
      }
      enum bgp-4over6 {
        value "67";
        description
          "BGP 4over6 SAFI";
        reference
          "RFC5747";
      }
      enum bgp-6over4 {
        value "68";
        description
          "BGP 6over4 SAFI";
        reference
          "mailto:cuiyong&tsinghua.edu.cn";
      }
      enum l1vpn-auto-discovery {
        value "69";
        description
          "Layer-1 VPN auto-discovery information";
        reference
          "draft-ietf-l1vpn-bgp-auto-discovery-05";
      }
      enum mpls-vpn {
        value "128";
        description
          "MPLS-labeled VPN address";
        reference
          "RFC4364";
      }
      enum multicast-bgp-mpls-vpn {
        value "129";
        description
          "Multicast for BGP/MPLS IP Virtual Private Networks
           (VPNs)";
        reference
          "draft-ietf-l3vpn-2547bis-mcast-10,
           draft-ietf-l3vpn-2547bis-mcast-10";
      }
      enum route-target-constraints {
        value "132";
        description
          "Route Target constraints";
        reference
          "RFC4684";
      }
      enum ipv4-diss-flow {
        value "133";
        description
          "IPv4 dissemination of flow specification rules";
        reference
          "RFC5575";
      }
      enum vpnv4-diss-flow {
        value "134";
        description
          "IPv4 dissemination of flow specification rules";
        reference
          "RFC5575";
      }
      enum vpn-auto-discovery {
        value "140";
        description
          "VPN auto-discovery";
        reference
          "draft-ietf-l3vpn-bgpvpn-auto-09";
      }
    }
    description
      "This typedef is a YANG enumeration of IANA-registered
       subsequent address family identifiers (SAFI).";
    reference
      "Subsequent Address Family Identifiers (SAFI) Parameters. IANA,
       2011-03-04. <http://www.iana.org/assignments/safi-namespace/
       safi-namespace.xml>
      ";
  }
}
