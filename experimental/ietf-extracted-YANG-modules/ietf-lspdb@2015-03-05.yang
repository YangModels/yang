module ietf-lspdb {

    namespace "urn:ietf:params:xml:ns:yang:ietf-lspdb";
    prefix lspdb;

    import ietf-inet-types {
        prefix "inet";
    }

    import ietf-yang-types {
        prefix "yang";
    }

    import ietf-interfaces {
        prefix "if";
    }

    organization
        "IETF XXX Working Group";

    contact
        "
        Editor:   Dhruv dhody
                  <dhruv.dhody@huawei.com>
        Editor:   Xian ZHANG
                  <zhang.xian@huawei.com>";
    description
        "This module contains a collection of YANG definitions for
        configuring LSP database. The intent of this module is to
        serve as a base model and it is kept protocol-independent.
        It is expected that it will be augmented depending on the
        targeted protocol.

        Copyright (c) 2015 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).";

    revision 2015-03-05 {
        description
            "Initial revision.";
        reference
            "RFC XXX: A YANG Data Model for Label Switched Path
                        (LSP) Database Management";
    }

    /*
     * Features:none.
     */

    /*
     * Typedefs
     */

    typedef lsp-signalingtypes {
        type enumeration {
            enum "rsvp" {
                value 1;
                description
                "Resource reSerVation Protocol.";
            }
            enum "ldp" {
                value 2;
                description
                "Label Distribution Protocol";
            }
            enum "bgp" {
                value 3;
                description
                "Border Gateway Protocol.";
            }
            enum "sr" {
                value 4;
                description
                "Segment Routing.";
            }
            enum "static" {
                value 5;
                description
                "Manually Configured.";
            }
        }
        description
            "The signalling type of a LSP.";
    }

    typedef status-types {
        type enumeration {
            enum "up" {
                value 1;
                description
                "UP";
            }
            enum "down" {
                value 2;
                description
                "Not working/failed";
            }
            enum "standby" {
                value 3;
                description
                "Idle state, created by not used";
            }
        }
        description
            "The status types of a LSP.";
    }

    typedef lsr-types {
        type enumeration {
            enum "ingress" {
                value 1;
                description
                "Ingress node";
            }
            enum "transit" {
                value 2;
                description
                "Transit node";
            }
            enum "egress" {
                value 3;
                description
                "Egress node";
            }
        }
        description
            "the role of the Label Switched Router (LSR) for a
            LSP entry.";
    }

    typedef lsp-ref {
        type leafref {
            path "/lspdb/lsp-entry/system-generated-id";
        }
        description
            "This type is used by data models that need to
            reference other LSP.";
    }

    /*
     * Operational data nodes
     */

    container lspdb {

        config false;

        description
            "This container defines the information of all the
            LSP a node has/stores";
        leaf lsp-num {
            type uint32;

            description
                "This stores the total number of LSPs, including
                working and backup.";
        }

        list lsp-entry {

            key "system-generated-id";

            description
                "This define each LSP entry.";

            leaf system-generated-id {
                type uint64;
                description
                    "This is generated by the local node and it is
                    unique within this node";
            }

            leaf lsp-signaling {
                type lsp-signalingtypes;
                mandatory true;
                description
                    "The signalling protocol/mechanism for the
                                        LSP.";
            }

            leaf is-primary {
                type boolean;
                description
                    "Whether a LSP is a primary or second LSP.
                     1-primary, 0-secondary";
            }

            leaf lsr-type {
                type lsr-types;
                description
                    "The role of this LSR with regard to the
                     current LSP";
            }

            leaf source {
                type inet:ip-address;
                mandatory true;
                description
                    "The Source node of this LSP";
            }

            leaf destination {
                type inet:ip-address;
                mandatory true;
                description
                    "The Destination node of this LSP";
            }

            leaf creation-time {
                type yang:date-and-time;
                description
                    "The time the LSP was created.";
            }

            leaf last-change {
                type yang:date-and-time;
                description
                    "The time the LSP entered its current state.";
            }

            leaf operation-status {
                type status-types;
                description
                    "The operational status of this LSP";
            }

            container incoming {
                description
                    "The incoming interface, label
                                        information.";
                leaf incoming-interface {
                    type if:interface-state-ref;
                    description
                        "The reference to the name of the incoming
                         interface.";
                }
                container incoming-label {
                    description
                        "Empty container, Label format to be
                        augmented depending on the  data plane
                        technology";
                }
            }

            container outgoing {
                description
                    "The outgoing interface, label
                                         information.";
                leaf outgoing-interface {
                    type if:interface-state-ref;
                    description
                        "The reference to the name of the outgoing
                         interface.";
                }

                container outgoing-label {
                    description
                        "Empty container, Label format to be
                        augmented depending on the data plane
                        technology";
                }
            }

            leaf-list primary-lsp {
                type lsp-ref;
                description
                    "A list of references to primary LSPs (if
                    exist) for this LSP.";
                reference
                    "xxx";
            }

            leaf-list backup-lsp {
                type lsp-ref;
                description
                    "A list of references to backup LSPs (if
                    exist) for this LSP.";
                reference
                    "xxx";
            }

            container statistics {
                description
                    "TBD";
            }
        }
    }
}//module
