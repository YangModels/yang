module ietf-tls-server {
  yang-version 1.1;
  namespace "urn:ietf:params:xml:ns:yang:ietf-tls-server";
  prefix tlss;

  import ietf-netconf-acm {
    prefix nacm;
    reference
      "RFC 8341: Network Configuration Access Control Model";
  }

  import ietf-crypto-types {
    prefix ct;
    reference
      "RFC AAAA: Common YANG Data Types for Cryptography";
  }

  import ietf-truststore {
    prefix ts;
    reference
      "RFC BBBB: A YANG Data Model for a Truststore";
  }

  import ietf-keystore {
    prefix ks;
    reference
      "RFC CCCC: A YANG Data Model for a Keystore";
  }

  import ietf-tls-common {
    prefix tlscmn;
    revision-date 2020-05-20; // stable grouping definitions
    reference
      "RFC FFFF: YANG Groupings for TLS Clients and TLS Servers";
  }

  organization
    "IETF NETCONF (Network Configuration) Working Group";

  contact
    "WG Web:   <http://datatracker.ietf.org/wg/netconf/>
     WG List:  <mailto:netconf@ietf.org>
     Author:   Kent Watsen <mailto:kent+ietf@watsen.net>
     Author:   Gary Wu <mailto:garywu@cisco.com>";

  description
    "This module defines reusable groupings for TLS servers that
     can be used as a basis for specific TLS server instances.

     Copyright (c) 2020 IETF Trust and the persons identified
     as authors of the code. All rights reserved.

     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC FFFF
     (https://www.rfc-editor.org/info/rfcFFFF); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2020-05-20 {
    description
      "Initial version";
    reference
      "RFC FFFF: YANG Groupings for TLS Clients and TLS Servers";
  }

  // Features

  feature tls-server-hello-params-config {
    description
      "TLS hello message parameters are configurable on a TLS
       server.";
  }

  feature tls-server-keepalives {
    description
      "Per socket TLS keepalive parameters are configurable for
       TLS servers on the server implementing this feature.";
  }

  feature client-auth-config-supported {
    description
      "Indicates that the configuration for how to authenticate
       clients can be configured herein, as opposed to in an
       application specific location.  That is, to support the
       consuming data models that prefer to place client
       authentication with client definitions, rather then
       in a data model principally concerned with configuring
       the transport.";
  }

  feature x509-certificate-auth {
    description
      "Indicates that the server supports authenticating clients
       using X.509 certificates.";
  }

  feature raw-public-key-auth {
    description
      "Indicates that the server supports authenticating clients
       using ray public keys.";
  }

  feature psk-auth {
    description
      "Indicates that the server supports authenticating clients
       using PSKs (pre-shared or pairwise-symmetric keys).";
  }

  // Groupings

  grouping tls-server-grouping {
    description
      "A reusable grouping for configuring a TLS server without
       any consideration for how underlying TCP sessions are
       established.

       Note that this grouping uses fairly typical descendent
       node names such that a stack of 'uses' statements will
       have name conflicts.  It is intended that the consuming
       data model will resolve the issue (e.g., by wrapping
       the 'uses' statement in a container called
       'tls-server-parameters').  This model purposely does
       not do this itself so as to provide maximum flexibility
       to consuming models.";

    container server-identity {
      nacm:default-deny-write;
      description
        "A locally-defined or referenced end-entity certificate,
         including any configured intermediate certificates, the
         TLS server will present when establishing a TLS connection
         in its Certificate message, as defined in Section 7.4.2
         in RFC 5246.";
      reference
        "RFC 5246: The Transport Layer Security (TLS) Protocol
                   Version 1.2
         RFC CCCC: A YANG Data Model for a Keystore";
      choice auth-type {
        mandatory true;
        description
          "A choice amongst authentication types.";
        case certificate {
          if-feature x509-certificate-auth;
          container certificate {
            description
              "Specifies the server identity using a certificate.";
            uses
              ks:local-or-keystore-end-entity-cert-with-key-grouping{
              refine "local-or-keystore/local/local-definition" {
                must 'public-key-format'
                     + ' = "ct:subject-public-key-info-format"';
              }
              refine "local-or-keystore/keystore/keystore-reference"
                     + "/asymmetric-key" {
                must 'deref(.)/../ks:public-key-format'
                     + ' = "ct:subject-public-key-info-format"';
              }
            }
          }
        }
        case raw-private-key {
          if-feature raw-public-key-auth;
          container raw-private-key {
            description
              "Specifies the server identity using a raw
               private key.";
            uses ks:local-or-keystore-asymmetric-key-grouping {
              refine "local-or-keystore/local/local-definition" {
                must 'public-key-format'
                     + ' = "ct:subject-public-key-info-format"';
              }
              refine "local-or-keystore/keystore/keystore-reference"{
                must 'deref(.)/../ks:public-key-format'
                     + ' = "ct:subject-public-key-info-format"';
              }
            }
          }
        }
        case psk {
          if-feature psk-auth;
          container psk {
            description
              "Specifies the server identity using a PSK (pre-shared
              or pairwise-symmetric key).  Note that, when the PSK is
              configured as a Keystore reference, the key's 'name'
              node MAY be used as the PSK's ID when used by the TLS
              protocol.";
            uses ks:local-or-keystore-symmetric-key-grouping {
              augment "local-or-keystore/local/local-definition" {
                if-feature "ks:local-definitions-supported";
                description
                  "An 'id' value for when the PSK is used by TLS.";
                leaf id {
                  type string;  // FIXME: is this the right type?
                  description
                    "The key id used in the TLS protocol for PSKs.";
                }
              }
            }
          }
        }
      }
    } // container server-identity

    container client-authentication {
      if-feature "client-auth-config-supported";
      nacm:default-deny-write;
      presence
        "Indicates that client authentication is supported (i.e.,
         that the server will request clients send certificates).
         If not configured, the TLS server SHOULD NOT request the
         TLS clients provide authentication credentials.";
      description
        "Specifies how the TLS server can authenticate TLS clients.
         Any combination of credentials is additive and unordered.

         Note that no configuration is required for PSK (pre-shared
         or pairwise-symmetric key) based authentication as the key
         is necessarily the same as configured in the '../server-
         identity' node.";
      container ca-certs {
        if-feature "x509-certificate-auth";
        presence
          "Indicates that the TLS server can authenticate TLS clients
           using configured certificate authority certificates.";
        description
          "A set of certificate authority (CA) certificates used by
           the TLS server to authenticate TLS client certificates. A
           client certificate is authenticated if it has a valid
           chain of trust to a configured CA certificate.";
        reference
          "RFC BBBB: A YANG Data Model for a Truststore";
        uses ts:local-or-truststore-certs-grouping;
      }
      container ee-certs {   // FIXME: plural too much?
        if-feature "x509-certificate-auth";
        presence
          "Indicates that the TLS server can authenticate TLS
           clients using configured client certificates.";
        description
          "A set of client certificates (i.e., end entity
           certificates) used by the TLS server to authenticate
           certificates presented by TLS clients. A client
           certificate is authenticated if it is an exact
           match to a configured client certificate.";
        reference
          "RFC BBBB: A YANG Data Model for a Truststore";
        uses ts:local-or-truststore-certs-grouping;
      }
      container raw-public-keys {
        if-feature "raw-public-key-auth";
        presence
          "Indicates that the TLS server can authenticate TLS
           clients using raw public keys.";
        description
          "A set of raw public keys used by the TLS server to
           authenticate raw public keys presented by the TLS
           client.  A raw public key is authenticated if it
           is an exact match to a configured raw public key.";
        reference
          "RFC BBBB: A YANG Data Model for a Truststore";
        uses ts:local-or-truststore-public-keys-grouping {
          refine "local-or-truststore/local/local-definition"
                 + "/public-key" {
            must 'public-key-format'
                 + ' = "ct:subject-public-key-info-format"';
          }
          refine "local-or-truststore/truststore"
                 + "/truststore-reference" {
            must 'deref(.)/../*/ts:public-key-format'
                 + ' = "ct:subject-public-key-info-format"';
          }
        }
      }
      container psks {
        if-feature "psk-auth";
        presence
          "Indicates that the TLS server can authenticate the TLS
           client using its PSK (pre-shared or pairwise-symmetric
           key).";
        description
          "No configuration is required since the PSK value is the
           same as PSK value configured in the 'client-identity'
           node.";
      }
    } // container client-authentication

    container hello-params {
      nacm:default-deny-write;
      if-feature "tls-server-hello-params-config";
      uses tlscmn:hello-params-grouping;
      description
        "Configurable parameters for the TLS hello message.";
    } // container hello-params

    container keepalives {
      nacm:default-deny-write;
      if-feature "tls-server-keepalives";
      description
        "Configures the keepalive policy for the TLS server.";
      leaf peer-allowed-to-send {
        type empty;
        description
          "Indicates that the remote TLS client is allowed to send
           HeartbeatRequest messages, as defined by RFC 6520
           to this TLS server.";
        reference
          "RFC 6520: Transport Layer Security (TLS) and Datagram
           Transport Layer Security (DTLS) Heartbeat Extension";
      }
      container test-peer-aliveness {
        presence
          "Indicates that the TLS server proactively tests the
           aliveness of the remote TLS client.";
        description
          "Configures the keep-alive policy to proactively test
           the aliveness of the TLS client.  An unresponsive
           TLS client is dropped after approximately max-wait
           * max-attempts seconds.";
        leaf max-wait {
          type uint16 {
            range "1..max";
          }
          units "seconds";
          default "30";
          description
            "Sets the amount of time in seconds after which if
             no data has been received from the TLS client, a
             TLS-level message will be sent to test the
             aliveness of the TLS client.";
        }
        leaf max-attempts {
          type uint8;
          default "3";
          description
            "Sets the maximum number of sequential keep-alive
             messages that can fail to obtain a response from
             the TLS client before assuming the TLS client is
             no longer alive.";
        }
      }
    } // container keepalives
  } // grouping tls-server-grouping
} // module ietf-tls-server
