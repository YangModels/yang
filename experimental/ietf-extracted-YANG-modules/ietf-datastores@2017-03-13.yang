module ietf-datastores {
  yang-version 1.1;
  namespace "urn:ietf:params:xml:ns:yang:ietf-datastores";
  prefix ds;

  organization
    "IETF NETMOD (NETCONF Data Modeling Language) Working Group";

  contact
    "WG Web:   <https://datatracker.ietf.org/wg/netmod/>

     WG List:  <mailto:netmod@ietf.org>

     Author:   Martin Bjorklund
               <mailto:mbj@tail-f.com>

     Author:   Juergen Schoenwaelder
               <mailto:j.schoenwaelder@jacobs-university.de>

     Author:   Phil Shafer
               <mailto:phil@juniper.net>

     Author:   Kent Watsen
               <mailto:kwatsen@juniper.net>

     Author:   Rob Wilton
               <rwilton@cisco.com>";

  description
    "This YANG module defines a set of identities for datastores.
     These identities can be used to identify datastores in protocol
     operations.

     Copyright (c) 2017 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX
     (http://www.rfc-editor.org/info/rfcxxxx); see the RFC itself
     for full legal notices.";

  revision 2017-03-13 {
    description
      "Initial revision.";
    reference
      "RFC XXXX: Network Management Datastore Architecture";
  }

  /*
   * Identities
   */

  identity datastore {
    description
     "Abstract base identity for datastore identities.";
  }

  identity static {
    description
     "Abstract base identity for static configuration datastores.";
  }

  identity dynamic {
    description
     "Abstract base identity for dynamic configuration datastores.";
  }

  identity running {
    base static;
    description
     "The 'running' datastore.";
  }

  identity candidate {
    base static;
    description
     "The 'candidate' datastore.";
  }

  identity startup {
    base static;
    description
     "The 'startup' datastore.";
  }

  identity intended {
    base static;
    description
     "The 'intended' datastore.";
  }

  identity operational {
    base datastore;
    description
     "The 'operational' state datastore.";
  }

}
