module ietf-rib-extension {
  namespace "urn:ietf:params:xml:ns:yang:ietf-rib-extension";

  prefix rib;

  import ietf-inet-types {
    prefix "inet";
  }

  import ietf-interfaces {
    prefix "if";
  }

  import ietf-routing {
    prefix "rt";
  }

  import ietf-ipv4-unicast-routing {
    prefix "v4ur";
  }

  import ietf-ipv6-unicast-routing {
    prefix "v6ur";
  }

  organization
    "Cisco Systems
     170 West Tasman Drive
     San Jose, CA 95134-1706
     USA";
  contact
    "Acee Lindem - acee@cisco.com
     Yingzhen QU - yiqu@cisco.com";

  description
    "This YANG module extends the generic data model for
     RIB by augmenting the ietf-netmod-routing-cfg
     model. It is intended that the module will be extended
     by vendors to define vendor-specific RIB parameters.
    ";

  revision 2016-06-29 {
    description
      "Initial RFC Version";
    reference
      "RFC XXXX: A YANG Data Model for RIB Extensions.";
  }

  /* Groupings */
  grouping next-hop {
    description
      "Next-hop grouping";
    leaf interface {
      type if:interface-ref;
      description
        "Outgoing interface";
    }
    leaf address {
      type inet:ip-address;
      description
        "IPv4 or IPv6 Address of the next-hop";
    }
  }

  grouping attributes {
    description
      "Common attributes applicable to all paths";
    leaf metric {
      type uint32;
      description "Route metric";
    }
    leaf tag {
      type uint32;
      description "Route tag";
    }
  }
  grouping path-attribute {
    description
      "Path attribute grouping";
    leaf repair-path {
      type leafref {
        path "/rt:routing-state/rt:ribs/rt:rib/"
             + "rt:routes/repair-route/id";
      }
      description
        "IP Fast ReRoute (IPFRR) repair path, use a path
         from repair-route list";
    }
  }

  augment "/rt:routing/rt:control-plane-protocols/"
        + "rt:control-plane-protocol/rt:static-routes/v4ur:ipv4/"
        + "v4ur:route/v4ur:next-hop/v4ur:next-hop-options/"
        + "v4ur:simple-next-hop"
  {
    description
      "Augment 'simple-next-hop' case in IPv4 unicast route.";
    leaf preference {
      type uint32;
      default "1";
      description "Route preference - Used to select among multiple
                  static routes with a lower preference next-hop
                  preferred and equal preference paths yielding
                  Equal Cost Multi-Path (ECMP).";
    }
    leaf tag {
      type uint32;
      default "0";
      description "Route tag";
    }
  }

  augment "/rt:routing/rt:control-plane-protocols/"
        + "rt:control-plane-protocol/rt:static-routes/v4ur:ipv4/"
        + "v4ur:route/v4ur:next-hop/v4ur:next-hop-options/"
        + "v4ur:next-hop-list/v4ur:next-hop-list/v4ur:next-hop"
  {
    description
      "Augment static route configuration 'next-hop-list'.";

    leaf preference {
      type uint32;
      default "1";
      description "Route preference - Used to select among multiple
                  static routes with a lower preference next-hop
                  preferred and equal preference paths yielding
                  Equal Cost Multi-Path (ECMP).";
    }
    leaf tag {
      type uint32;
      default "0";
      description "Route tag";
    }
  }

  augment "/rt:routing/rt:control-plane-protocols/"
        + "rt:control-plane-protocol/rt:static-routes/v6ur:ipv6/"
        + "v6ur:route/v6ur:next-hop/v6ur:next-hop-options/"
        + "v6ur:simple-next-hop"
  {
    description
      "Augment 'simple-next-hop' case in IPv6 unicast route.";
    leaf preference {
      type uint32;
      default "1";
      description "Route preference - Used to select among multiple
                  static routes with a lower preference next-hop
                  preferred and equal preference paths yielding
                  Equal Cost Multi-Path (ECMP).";
    }
    leaf tag {
      type uint32;
      default "0";
      description "Route tag";
    }
  }

  augment "/rt:routing/rt:control-plane-protocols/"
        + "rt:control-plane-protocol/rt:static-routes/v6ur:ipv6/"
        + "v6ur:route/v6ur:next-hop/v6ur:next-hop-options/"
        + "v6ur:next-hop-list/v6ur:next-hop-list/v6ur:next-hop"
  {
    description
      "Augment static route configuration 'next-hop-list'.";

    leaf preference {
      type uint32;
      default "1";
      description "Route preference - Used to select among multiple
                  static routes with a lower preference next-hop
                  preferred and equal preference paths yielding
                  Equal Cost Multi-Path (ECMP).";
    }
    leaf tag {
      type uint32;
      default "0";
      description "Route tag";
    }
  }

  augment "/rt:routing-state/rt:ribs/rt:rib/"
        + "rt:routes/rt:route"
  {
    description
      "Augment a route in RIB with tag.";
    uses attributes;
  }

  augment "/rt:routing-state/rt:ribs/rt:rib/"
        + "rt:routes"
  {
    description
      "Augment a route with a list of repair-paths.";
    list repair-route {
      key "id";
      description
        "A repair-path entry, which can be referenced
         by a repair-path.";
      leaf id {
        type string;
        description
          "A unique identifier.";
      }

      container next-hop {
              description
                "Route's next-hop attribute.";
        leaf outgoing-interface {
          type if:interface-state-ref;
          description
            "Name of the outgoing interface.";
        }
        leaf next-hop-address {
          type inet:ip-address;
          description
            "IP address of the next hop.";
        }
      }
      leaf metric {
        type uint32;
        description "Route metric";
      }
    }
  }

  augment "/rt:routing-state/rt:ribs/rt:rib/"
        + "rt:routes/rt:route/rt:next-hop/rt:next-hop-options/"
        + "rt:simple-next-hop"
  {
     description
       "Add more parameters to a path.";
     uses path-attribute;
  }

  augment "/rt:routing-state/rt:ribs/rt:rib/"
        + "rt:routes/rt:route/rt:next-hop/rt:next-hop-options/"
        + "rt:special-next-hop"
  {
    description
      "Add more parameters to a path.";
    uses path-attribute;
  }

  augment "/rt:routing-state/rt:ribs/rt:rib/"
        + "rt:routes/rt:route/rt:next-hop/rt:next-hop-options/"
        + "rt:next-hop-list/rt:next-hop-list/rt:next-hop"
  {
    description
      "This case augments the 'next-hop-options' in the routing
       model.";
    uses path-attribute;
  }
}
