module ietf-sav {
  yang-version "1.1";
  namespace "urn:ietf:params:xml:ns:yang:ietf-sav";
  prefix "sav";

  import ietf-yang-types {
    prefix "yang";
  }

  import ietf-interfaces {
    prefix "if";
  }

  import ietf-inet-types {
    prefix "inet";
  }

  organization
    "IETF SAVNET Working Group";

  contact
    "TBD";

  description
    "This YANG module defines the essential elements for the
     management of Source address validation (SAV). The model
     fully conforms to the Network Management Datastore
     Architecture (NMDA).

     The key words 'MUST', 'MUST NOT', 'REQUIRED', 'SHALL', 'SHALL
     NOT', 'SHOULD', 'SHOULD NOT', 'RECOMMENDED', 'NOT
     RECOMMENDED', 'MAY', and 'OPTIONAL' in this document are to be
     interpreted as described in BCP 14 (RFC 2119) (RFC 8174) when,
     and only when, they appear in all capitals, as shown here.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).
     This version of this YANG module is part of RFC XXXX
     (https://www.rfc-editor.org/info/rfcXXXX); see the RFC itself
     for full legal notices.";

  reference
    "RFC XXXX: A YANG Data Model For SAV Management.";

  revision 2023-05-20 {
    description
      "Initial revision.";
    reference
      "RFC XXXX: A YANG Data Model for SAV Management.";
  }

  /* Features */

  feature router-id {
    description
      "This feature indicates that the server supports an explicit
       32-bit router ID that is used by some control-plane
       protocols.

       Servers that do not advertise this feature set a router ID
       algorithmically, usually to one of the configured IPv4
       addresses. However, this algorithm is implementation
       specific.";
  }

  /* Identities */

  identity address-family {
    description
      "Base identity from which identities describing address
       families are derived.";
  }

  identity ipv4 {
    base address-family;
    description
      "This identity represents an IPv4 address family.";
  }

  identity ipv6 {
    base address-family;
    description
      "This identity represents an IPv6 address family.";
  }

  identity source-protocol {
    description
      "Base identity from which source protocol
       identities are derived.";
  }

  identity static {
    base source-protocol;
    description
      "'Static' pseudo-protocol.";
  }

  identity sav-mode {
    description
      "Base identity from which identities describing SAV
       modes of the specified interface are derived.";
  }

  identity sav-im {
    base sav-mode;
    description
      "This identity represents an SAV incomplete mode, this is,
       interface-based mode.";
  }

  identity sav-cm {
    base sav-mode;
    description
      "This identity represents an SAV complete mode, this is,
       prefix-based mode.";
  }

  identity sav-check-type {
    description
      "Base identity from which identities describing SAV
       check types of the specified interface are derived.";
  }

  identity sav-allow-list {
    base sav-check-type;
    description
      "This identity represents an SAV allow list type.";
  }

  identity sav-block-list {
    base sav-check-type;
    description
      "This identity represents an SAV block list type.";
  }

  /* Type Definitions */

  typedef rule-preference {
    type uint32;
    description
      "This type is used for SAV-rule preferences.";
  }

  /* Groupings */

  grouping address-family {
    description
      "This grouping provides a leaf identifying an address
       family.";
    leaf address-family {
      type identityref {
        base address-family;
      }
      mandatory true;
      description
        "Address family.";
    }
  }

  grouping router-id {
    description
      "This grouping provides a router ID.";
    leaf router-id {
      type yang:dotted-quad;
      description
        "A 32-bit number in the form of a dotted quad that is used
         by some control-plane protocols identifying a router.";
      reference
        "RFC 2328: OSPF Version 2";
    }
  }

  grouping rule-metadata {
    description
      "Common SAV-rule metadata.";
    leaf source-protocol {
      type identityref {
        base source-protocol;
      }
      mandatory true;
      description
        "Type of the source protocol from which the
         SAV-rule originated.";
    }
    leaf active {
      type empty;
      description
        "The presence of this leaf indicates that the rule is
         preferred among all rules in the same SAV table that
         have the same source prefix.";
    }
    leaf last-updated {
      type yang:date-and-time;
      description
        "Timestamp of the last modification of the rule. If the
         rule was never modified, it is the time when the SAV
         rule was inserted into the SAV table.";
    }
    leaf total-packets {
      type uint64;
      description
        "Number of the total packets checked by a SAV rule.";
    }
    leaf total-bytes {
      type uint64;
      description
        "Number of the total bytes checked by a SAV rule.";
    }
    leaf drop-packets {
      type uint64;
      description
        "Number of the drop packets by a SAV rule.";
    }
    leaf drop-bytes {
      type uint64;
      description
        "Number of the drop bytes by a SAV rule.";
    }
    leaf sav-invalid-packets {
      type uint64;
      description
        "Number of the packets with invalid SAV result.";
    }
    leaf sav-invalid-bytes {
      type uint64;
      description
        "Number of the packet bytes with invalid SAV result.";
    }
    leaf sav-valid-packets {
      type uint64;
      description
        "Number of the packets with valid SAV result.";
    }
    leaf sav-valid-bytes {
      type uint64;
      description
        "Number of the packet bytes with valid SAV result.";
    }
  }

  grouping limit-metadata {
    description
      "Common SAV-rule limit metadata.";
    leaf number {
      type uint32;
      description
        "This attribute allows for controlling number limit.";
    }
    leaf threshold-percent {
      type uint8 {
        range "0..100";
      }
      description
        "This attribute allows for controlling threshold percentage
         limit.";
    }
    leaf threshold-number {
      type uint32;
      description
        "This attribute allows for controlling threshold number
         limit.";
    }
  }

  /* Augments */

  augment "/if:interfaces/if:interface" {
    description
      "SAV configuration of incoming interfaces.";
    container sav-control {
      description
        "Support for SAV interface configuration.";
      leaf sav-enabled {
        type boolean;
        description
          "This attribute allows for controlling the SAV function
           of the incoming interface.";
      }
      leaf sav-mode {
        type identityref {
          base sav-mode;
        }
        description
          "This attribute allows for controlling the SAV mode
           of the incoming interface.";
      }
      action sav-reset {
        description
          "Reset action of a SAV incoming interface";
        input {
          leaf reset-statistics {
            type boolean;
            description
              "This attribute allows for clearing the SAV
               statistics of the incoming interface.";
          }
        }
      }
      container sav-spoof-top {
        description
          "Support for reporting the top few SAV rules with the
           highest number of filtered counterfeit packets under
           specified interface.";
        leaf enabled {
          type boolean;
          description
            "This attribute allows for controlling the function of
             reporting the top few SAV rules with the highest
             number of filtered counterfeit packets under specified
             interface.";
        }
        leaf top-number {
          type uint32;
          description
            "This attribute allows for setting the top number of
             the SAV rules with the highest number of filtered
             counterfeit packets under specified interface.";
        }
      }
      container sav-block-flow-report {
        description
          "Support for viewing the information of data flow blocked
           by SAVNET under specified interface.";
        leaf enabled {
          type boolean;
          description
            "This attribute allows for controlling the function of
             viewing the information of data flow blocked by
             SAVNET under specified interface.";
        }
      }
    }
  }

  /* Data nodes */

  container sav {
    description
      "Configuration parameters for the SAV subsystem.";
    uses router-id {
      if-feature "router-id";
      description
        "Support for the global router ID. Control-plane protocols
         that use a router ID can use this parameter or override it
         with another value.";
    }
    container interfaces {
      config false;
      description
        "Network-layer interfaces used for SAV.";
      list interface {
        key "name";
        description
          "Each entry contains the SAV statistics of a interface";
        leaf name {
          type if:interface-ref;
          description
            "The name of an interface.";
        }
        leaf total-packets {
          type uint64;
          description
            "The number of total packets for specified interface.";
        }
        leaf total-bytes {
          type uint64;
          description
            "The byte number of total packets for specified
             interface.";
        }
        leaf drop-packets {
          type uint64;
          description
            "The number of drop packets for SAV function.";
        }
        leaf drop-bytes {
          type uint64;
          description
            "The byte number of drop packets for SAV function.";
        }
        leaf sav-invalid-packets {
          type uint64;
          description
            "The number of the packets with invalid SAV result.";
        }
        leaf sav-invalid-bytes {
          type uint64;
          description
            "The byte number of the packets with invalid SAV
             result.";
        }
        leaf sav-valid-packets {
          type uint64;
          description
            "The number of the packets with valid SAV result";
        }
        leaf sav-valid-bytes {
          type uint64;
          description
            "The byte number of the packets with valid SAV
             result.";
        }
      }
    }
    container v4sav-entry-limits {
      description
        "Specification limit of ipv4 SAV table.";
      uses limit-metadata;
    }
    container v6sav-entry-limits {
      description
        "Specification limit of ipv6 SAV table.";
      uses limit-metadata;
    }
    container source-protocol-priorities {
      description
        "Support for SAV source protocol priorities.";
      list source-protocol-priority {
        key "type";
        description
          "Each entry contains a SAV source protocol
           priority.";
        leaf type {
          type identityref {
            base source-protocol;
          }
          description
            "Type of the source protocol -- an identity
             derived from the 'source-protocol' base
             identity.";
        }
        leaf preference {
          type rule-preference;
          description
            "This attribute allows for selecting the preferred
             SAV-rule among SAV-rules from the different source
             protocol. A smaller value indicates a SAV-rule that is
             more preferred.";
        }
      }
    }
    container sav-controls {
      description
        "Support for SAV global configuration.";
      leaf sav-enabled {
        type boolean;
        description
          "This attribute allows for controlling the SAV
           function.";
      }
      leaf sav-mode {
        type identityref {
          base sav-mode;
        }
        description
          "This attribute allows for controlling the SAV mode.";
      }
      action sav-interface-reset {
        description
          "Global reset action of SAV interface";
        input {
          leaf reset-statistics {
            type boolean;
            description
              "This attribute allows for clearing the SAV
               statistics of all interfaces.";
          }
        }
      }
      container sav-spoof-top {
        description
          "Support for reporting the top few SAV rules with the
           highest number of filtered counterfeit packets.";
        leaf enabled {
          type boolean;
          description
            "This attribute allows for globally controlling the
             function of reporting the top few SAV rules with the
             highest number of filtered counterfeit packets.";
        }
        leaf top-number {
          type uint32;
          description
            "This attribute allows for globally setting the top
             number of the SAV rules with the highest number of
             filtered counterfeit packets.";
        }
      }
      container sav-block-flow-report {
        description
          "Support for viewing the information of data flow blocked
           by SAVNET.";
        leaf enabled {
          type boolean;
          description
            "This attribute allows for globally controlling the
             function of viewing the information of data flow
             blocked by SAVNET.";
        }
      }
    }
    container static-savs {
      description
        "Support for the 'static' pseudo-protocol.
         Address-family-specific modules augment this node with
         their lists of SAV rules.";
    }
    container sav-tables {
      description
        "Support for SAV tables.";
      list sav-table {
        key "name";
        description
          "Each entry contains a configuration for a SAV
           table identified by the 'name' key.";
        leaf name {
          type string;
          description
            "The name of the SAV table.";
        }
        uses address-family {
          description
            "The address family of the SAV table.";
        }
        leaf description {
          type string;
          description
            "Textual description of the SAV table.";
        }
        container sav-rules {
          config false;
          description
            "Current contents of the SAV table.";
          list sav-rule {
            description
              "A SAV table rule entry. This data node
               MUST be augmented with information specific to
               SAV-rule of each address family.";
            leaf rule-preference {
              type rule-preference;
              description
                "This attribute allows for selecting the
                 preferred SAV-rule among SAV-rules with the same
                 source prefix. A smaller value indicates a
                 SAV-rule that is more preferred.";
            }
            container incoming-interfaces {
              description
                "Network-layer incoming interfaces of a SAV rule.";
              leaf-list incoming-interface {
                type if:interface-ref;
                description
                  "Each entry is the name of a SAV incoming
                   interface";
              }
            }
            uses rule-metadata;
          }
        }
        action active-sav-rule {
          description
            "Return the active SAV rule that is used for the
             source address.

             Address-family-specific modules MUST augment input
             parameters with a leaf named 'source-address'.";
          output {
            container sav-rule {
              description
                "The active SAV rule for the specified source.

                 If no rule exists in the SAV table for the source
                 address, no output is returned.

                 Address-family-specific modules MUST augment this
                 container with appropriate contents.";
              container incoming-interfaces {
                description
                  "Network-layer incoming interfaces of a SAV
                   rule.";
                leaf-list incoming-interface {
                  type if:interface-ref;
                  description
                    "Each entry is the name of a SAV incoming
                     interface";
                }
              }
              uses rule-metadata;
            }
          }
        }
      }
    }
    container sav-block-flow-infos {
      config false;
      description
        "The information of data flow blocked by SAVNET.";
      list sav-block-flow-info {
        description
          "The information of a data stream blocked by SAVNET.";
        leaf source-ip-address {
          type inet:ip-address;
          description
            "Source address of the data stream blocked by SAVNET.";
        }
        leaf source-port {
          type uint16;
          description
            "Source port of the data stream blocked by SAVNET.";
        }
        leaf destination-ip-address {
          type inet:ip-address;
          description
            "Destination address of the data stream blocked by
             SAVNET.";
        }
        leaf destination-port {
          type uint16;
          description
            "Destination port of the data stream blocked by
             SAVNET.";
        }
        leaf arrival-time {
          type yang:date-and-time;
          description
            "Arrival time of the data stream blocked by SAVNET.";
        }
      }
    }
  }
  notification sav-event {
    description
      "This notification is sent when there is an abnormality in
       SAV table.";
    uses router-id {
      if-feature "router-id";
      description
        "the router ID of the server corresponding to the SAV
         table.";
    }
    uses address-family {
      description
        "The address family of the SAV table.";
    }
    leaf sav-limit-reached {
      type boolean;
      description
        "Indicates that the number of SAV table entries reached
         the upper limit.";
    }
    container top-spoof-sav-rules {
      description
        "The top few SAV rules with the highest number of filtered
         counterfeit packets.";
      list sav-rule {
        description
          "A SAV rule entry. This data node MUST be augmented with
           information specific to SAV-rule of each address
           family.";
        leaf rule-preference {
          type rule-preference;
          description
            "This attribute allows for selecting the preferred
             SAV-rule among SAV-rules with the same source prefix.
             A smaller value indicates a SAV-rule that is more
             preferred.";
        }
        container incoming-interfaces {
          description
            "Network-layer incoming interfaces of a SAV rule.";
          leaf-list incoming-interface {
            type if:interface-ref;
            description
              "Each entry is the name of a SAV incoming interface";
          }
        }
        uses rule-metadata;
      }
    }
  }
}
