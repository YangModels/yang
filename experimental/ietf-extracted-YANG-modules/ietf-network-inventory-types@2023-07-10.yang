module ietf-network-inventory-types {
  yang-version 1.1;
  namespace
    "urn:ietf:params:xml:ns:yang:ietf-network-inventory-types";
  prefix nw-inv-types;

  import ietf-inet-types {
    prefix inet;
    reference
      "RFC 6991: Common YANG Data Types";
  }
  import ietf-yang-types {
    prefix yang;
    reference
      "RFC 6991: Common YANG Data Types";
  }
  import iana-hardware {
    prefix ianahw;
    reference
      "RFC 8348: A YANG Data Model for Hardware Management";
  }
  import ietf-hardware {
    prefix hw;
    reference
      "RFC 8348: A YANG Data Model for Hardware Management";
  }

  organization
    "IETF OPSAWG (Operations and Management Area Working Group)";
  contact
    "WG Web:   <https://datatracker.ietf.org/wg/opsawg/>
     WG List:  <mailto:opsawg@ietf.org>

     Editor: Bo Wu
          <lana.wubo@huawei.com>
     Editor: Cheng Zhou
          <zhouchengyjy@chinamobile.com>
     Editor: Qin Wu
          <bill.wu@huawei.com>
     Editor: Mohamed Boucadair
          <mohamed.boucadair@orange.com>";
  description
    "This YANG module contains a collection of network inventory
        specific YANG data type defintions.

     Copyright (c) 2023 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.";

  revision 2023-07-10 {
    description
      "Initial revision.";
    reference
      "RFC XXXX: A Network Inventory Management Model for
       Enterprise Networks ";
  }

  identity software-component {
    description
      "Base identity for software components in a managed device.";
  }

  identity operating-system {
    base software-component;
    description
      "OS software type.";
  }

  identity operating-system-patch {
    base software-component;
    description
      "An operating system update - which should be a subcomponent
       of the `operating-system` running on a component. A patch is
       defined to be a set of software changes that are atomically
       installed (and uninstalled) together. ";
  }

  identity bios {
    base software-component;
    description
      "Legacy BIOS or UEFI firmware interface responsible for
       initializing hardware components and first stage boot
       loader.";
  }

  identity boot-loader {
    base software-component;
    description
      "Software layer responsible for loading and booting the
       device OS or network OS.";
  }

  identity software-module {
    base software-component;
    description
      "A base identity for software modules installed and/or
       running on the device.  Modules include user-space programs
       and kernel modules that provide specific functionality.
       A component with type SOFTWARE_MODULE should also have a
       module type that indicates the specific type of software
       module";
  }

  identity operating-software-patch {
    base software-component;
    description
      "An software update - which should be a subcomponent
       of the `software-module` running on a component. A patch is
       defined to be a set of software changes that are atomically
       installed (and uninstalled) together. ";
  }

  /* Groupings */

  grouping component-info {
    description
      "Grouping for common component information.";
    leaf hardware-rev {
      type string;
      config false;
      description
        "The vendor-specific hardware revision string for the
         component.  The preferred value is the hardware revision
         identifier actually printed on the component itself (if
         present).";
      reference
        "RFC 6933: Entity MIB (Version 4) -
                   entPhysicalHardwareRev";
    }
    leaf firmware-rev {
      type string;
      config false;
      description
        "The vendor-specific firmware revision string for the
         component.";
      reference
        "RFC 6933: Entity MIB (Version 4) -
                   entPhysicalFirmwareRev";
    }
    leaf software-rev {
      type string;
      config false;
      description
        "The vendor-specific software revision string for the
         component.";
      reference
        "RFC 6933: Entity MIB (Version 4) -
                   entPhysicalSoftwareRev";
    }
    leaf serial-num {
      type string;
      config false;
      description
        "The vendor-specific serial number string for the
         component.  The preferred value is the serial number
         string actually printed on the component itself (if
         present).";
      reference
        "RFC 6933: Entity MIB (Version 4) - entPhysicalSerialNum";
    }
    leaf mfg-name {
      type string;
      config false;
      description
        "The name of the manufacturer of this physical component.
         The preferred value is the manufacturer name string
         actually printed on the component itself (if present).

         Note that comparisons between instances of the
         'model-name', 'firmware-rev', 'software-rev', and
         'serial-num' nodes are only meaningful amongst
         components with the same value of 'mfg-name'.

         If the manufacturer name string associated with the
         physical component is unknown to the server, then this
         node is not instantiated.";
      reference
        "RFC 6933: Entity MIB (Version 4) - entPhysicalMfgName";
    }
    leaf model-name {
      type string;
      config false;
      description
        "The vendor-specific model name identifier string
         associated with this physical component.  The preferred
         value is the customer-visible part number, which may be
         printed on the component itself.
         If the model name string associated with the physical
         component is unknown to the server, then this node is not
         instantiated.";
      reference
        "RFC 6933: Entity MIB (Version 4) - entPhysicalModelName";
    }
    leaf alias {
      type string;
      config false;
      description
        "An 'alias' name for the component, as specified by a
         network manager, that provides a non-volatile 'handle' for
         the component.

         If no configured value exists, the server MAY set the
         value of this node to a locally unique value in the
         operational state.

         A server implementation MAY map this leaf to the
         entPhysicalAlias MIB object.  Such an implementation needs
         to use some mechanism to handle the differences in size
         and characters allowed between this leaf and
         entPhysicalAlias.  The definition of such a mechanism is
         outside the scope of this document.";
      reference
        "RFC 6933: Entity MIB (Version 4) - entPhysicalAlias";
    }
    leaf asset-id {
      type string;
      config false;
      description
        "This node is a user-assigned asset tracking identifier for
         the component.

         A server implementation MAY map this leaf to the
         entPhysicalAssetID MIB object.  Such an implementation
         needs to use some mechanism to handle the differences in
         size and characters allowed between this leaf and
         entPhysicalAssetID.  The definition of such a mechanism is
         outside the scope of this document.";
      reference
        "RFC 6933: Entity MIB (Version 4) - entPhysicalAssetID";
    }
    leaf mfg-date {
      type yang:date-and-time;
      config false;
      description
        "The date of manufacturing of the managed component.";
      reference
        "RFC 6933: Entity MIB (Version 4) - entPhysicalMfgDate";
    }
    leaf-list uri {
      type inet:uri;
      config false;
      description
        "This node contains identification information about the
         component.";
      reference
        "RFC 6933: Entity MIB (Version 4) - entPhysicalUris";
    }
    leaf uuid {
      type yang:uuid;
      config false;
      description
        "A Universally Unique Identifier of the component.";
      reference
        "RFC 6933: Entity MIB (Version 4) - entPhysicalUUID";
    }
    leaf oper-state {
      type hw:oper-state;
      config false;
      description
        "The operational state for this component.
         Note that this node does not follow the administrative
         state.  An administrative state of 'down' does not
         predict an operational state of 'disabled'.
         Note that some implementations may not be able to
         accurately report oper-state while the admin-state node
         has a value other than 'unlocked'.  In these cases, this
         node MUST have a value of 'unknown'.";
      reference
        "RFC 4268: Entity State MIB - entStateOper";
    }
  }

  grouping components {
    description
      "Grouping for software and hardware components.";
    container components {
      description
        "The components within the device.";
      list component {
        key "name";
        description
          "The list of software instances contained within the
           device.";
        leaf name {
          type string;
          description
            "The name of the component.";
        }
        leaf class {
          type union {
            type identityref {
              base ianahw:hardware-class;
            }
            type identityref {
              base software-component;
            }
          }
          config false;
          description
            "Type of component as identified by the system";
        }
        leaf parent {
          type leafref {
            path "../../component/name";
          }
          config false;
          description
            "The name of the component that physically contains this
             component.

             If this leaf is not instantiated, it indicates that this
             component is not contained in any other component.

             In the event that a physical component is contained by
             more than one physical component (e.g., double-wide
             modules), this node contains the name of one of these
             components.  An implementation MUST use the same name
             every time this node is instantiated.";
          reference
            "RFC 6933: Entity MIB (Version 4) -
                       entPhysicalContainedIn";
        }
        leaf parent-rel-pos {
          type int32 {
            range "0 .. 2147483647";
          }
          config false;
          description
            "An indication of the relative position of this child
             component among all its sibling components.  Sibling
             components are defined as components that:

               o share the same value of the 'parent' node and

               o share a common base identity for the 'class' node.";
          reference
            "RFC 6933: Entity MIB (Version 4) -
                       entPhysicalParentRelPos";
        }
        leaf is-fru {
          type boolean;
          config false;
          description
            "This node indicates whether or not this component is
             considered a 'field-replaceable unit' by the vendor.
             If this node contains the value 'true', then this
             component identifies a field-replaceable unit.";
          reference
            "RFC 6933: Entity MIB (Version 4) - entPhysicalIsFRU";
        }
        uses component-info;
        leaf usage-state {
          type hw:usage-state;
          config false;
          description
            "The usage state for this component.

             This node refers to a component's ability to service
             more components in a containment hierarchy.

             Some components will exhibit only a subset of the usage
             state values.  Components that are unable to ever
             service any components within a containment hierarchy
             will always have a usage state of 'busy'.  In some
             cases, a component will be able to support only one
             other component within its containment hierarchy and
             will therefore only exhibit values of 'idle' and
             'busy'.";
          reference
            "RFC 4268: Entity State MIB - entStateUsage";
        }
        leaf alarm-state {
          type hw:alarm-state;
          config false;
          description
            "The alarm state for this component.  It does not
             include the alarms raised on child components within
             its containment hierarchy.";
          reference
            "RFC 4268: Entity State MIB - entStateAlarm";
        }
        leaf standby-state {
          type hw:standby-state;
          config false;
          description
            "The standby state for this component.

             Some components will exhibit only a subset of the
             remaining standby state values.  If this component
             cannot operate in a standby role, the value of this
             node will always be 'providing-service'.";
          reference
            "RFC 4268: Entity State MIB - entStateStandby";
        }
      }
    }
  }

  grouping licenses {
    description
      "Grouping for licenses.";
    container licenses {
      config false;
      description
        "Container for list of licenses";
      list license {
        key "license-id";
        description
          "List of licenses.";
        leaf license-id {
          type string;
          description
            "License ID. A string that uniquelly identifies the
             license. ";
        }
        leaf description {
          type string;
          description
            "The license description.";
        }
        leaf license-data {
          type union {
            type binary;
            type string;
          }
          description
            "The contents of the licence (if required) .";
        }
        leaf active {
          type boolean;
          default "false";
          description
            "The activation state of the license.";
        }
        leaf issue-date {
          type uint64;
          description
            "The date and time at which the license was issued.";
        }
        leaf expiration-date {
          type uint64;
          description
            "The date and time at which the license will expire.";
        }
        leaf in-use {
          type boolean;
          description
            "The license is in use.";
        }
        leaf expired {
          type boolean;
          description
            "The license has expired.";
        }
        leaf valid {
          type boolean;
          description
            "The license is valid. Can be activated in the system
             or platform.";
        }
      }
    }
  }
}
