module sfc-control-planes {
    namespace "urn:etri:params:xml:ns:yang:sfc-cp";
    prefix sfc-cp;
    include path-maintenance {
        revision-date 2015-10-15;
    }
    include path-optimization {
        revision-date 2015-10-15;
    }
    include load-balancing {
        revision-date 2015-10-15;
    }
    include sfc-topology {
        revision-date 2015-10-15;
    }
    include policy {
        revision-date 2015-10-15;
    }
    include history {
        revision-date 2015-10-15;
    }
    include fault-handling {
        revision-date 2015-10-15;
    }
    include event {
        revision-date 2015-10-15;
    }
    organization "ETRI.";
    contact
    "M-K. Shin mkshin@etri.re.kr
     M-J Choi mjchoi@kangwon.ac.kr";
    description
     "This Module define the management information of
      the control plane as a total of nine modules.";

    revision 2015-10-15{
        reference
         "draft-shin-sfc-control-plane-yang-00 -
          Yang Data Model for Service Function Chaining Control Plane";
    }
}
