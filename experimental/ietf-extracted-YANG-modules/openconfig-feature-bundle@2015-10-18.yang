module openconfig-feature-bundle {

  // namespace
  // TODO: change to an ietf or other more generic namespace
  namespace "http://openconfig.net/yang/feature-bundle";

  prefix bundle;

  import openconfig-module-catalog { prefix cat; }

  // meta
  organization "OpenConfig working group";

  contact
    "OpenConfig working group
    netopenconfig@googlegroups.com";

  description
    "This module can be used to build network features using
    published YANG Models.";

  revision "2015-10-18" {
    description
      "Initial Revision";
    reference "TBD";
  }

  grouping bundle-information {

    description
      "Template defining the bundle";

    leaf name {
        type string;
        description "Published name of bundle, for example:
          l3vpn, l2vpn, internet-access";
    }

    leaf version {
        type string;
        description "bundle version number";
    }

    leaf description {
        type string;
        description "User defined information about bundle";
    }

    leaf category {
      type string;
      description
       "Categorization of bundle such as:
        network, service, oam, experimental, other";
    }

    leaf subcategory {
      type string;
      description
         "Sub-Categorization of bundle such as:
          protocol, operational, other";
    }
  } //bundle-template

  grouping bundle-ingredients {

    description "Module ingredients used in bundle";

    container modules {

      description
        "Modules that comprise the bundle";

      list module {

        key "module-type";

        description
          "List of modules from yang-module-catalog comprising
           the bundle";

        leaf module-type {
            type string;
          description
            "A user-define type of the module";
        }

        leaf catalog-reference {
          type leafref {
           path "/cat:organizations"
                 + "/cat:organization"
                 + "/cat:modules"
                 + "/cat:module"
                 + "/cat:name";
          }
          description
            "Link to a module defined by a standards body";
        }

        leaf application-sequence {
           type uint8;
           description
             "Sequence number indicating order of application of
              module";
        }
      } //module-info
    } //bundle-modules
  } //bundle-ingredients

  container bundle {

    description
      "Build the bundle";

    uses bundle-information;
    uses bundle-ingredients;

  } //bundle

}
