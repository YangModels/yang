module ietf-ppr {
  yang-version 1.1;
  namespace "urn:ietf:params:xml:ns:yang:ietf-ppr";

  prefix ppr;

  import ietf-inet-types {
    prefix inet;
  }

  import ietf-yang-types {
    prefix "yang";
  }

  import ietf-routing-types {
    prefix "rt-types";
  }

  import ietf-routing {
    prefix rt;
  }

  organization
      "IETF LSR - Link State Routing Working Group";

  contact
    "WG Web:   <http://datatracker.ietf.org/group/lsr/>
     WG List:  <mailto:lsr@ietf.org>

     Author:   Yingzhen Qu
               <mailto:yingzhen.qu@huawei.com>
               Uma Chunduri
               <mailto:uma.chunduri@huawei.com>";
  description
    "This Yang module defines the configuration and operational
     state for Preferred Path Routing common to all vendor
     implementations.

     This YANG model conforms to the Network Management
     Datastore Architecture (NDMA) as described in RFC XXXX.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";

  reference "RFC XXXX";

  revision 2018-06-20 {
    description
      "Initial revision.";
    reference
      "RFC XXXX: A YANG Data Model for PPR.";
  }

  augment "/rt:routing" {
    description
      "This module augments routing-instace configuration
       with preferred path routing.";
    container preferred-path-routing {
      description
        "preferred path routing configuration.";

      list preferred-path-mpls {
        key "ppr-id";
        description
          "List of preferred path using MPLS data plane.";
        leaf ppr-id {
          type uint32;
          description
            "PPR ID, A 20 bit label or 32 bit SID.";
        }
        leaf-list pde-id {
          type uint32;
          description
            "List of PPR Path Description Element (PDE).";
        }
      }

      list preferred-path-ipv4 {
        key "ppr-id";
        description
          "List of preferred path using IPv4 data plane.";
        leaf ppr-id {
          type inet:ipv4-prefix;
          description
            "PPR ID, IPv4 address format.";
        }
        leaf-list pde-id {
          type inet:ipv4-prefix;
          description
            "List of PPR Path Description Element (PDE).";
        }
      }

      list preferred-path-ipv6 {
        key "ppr-id";
        description
          "List of preferred path using IPv6 data plane.";
        leaf ppr-id {
          type inet:ipv6-prefix;
          description
            "PPR ID, IPv6 address format.";
        }
        leaf-list pde-id {
          type inet:ipv6-prefix;
          description
            "List of PPR Path Description Element (PDE).";
        }
      }

      list preferred-path-srv6 {
        key "ppr-id";
        description
          "List of preferred path using SRv6 data plane.";
        leaf ppr-id {
          type inet:ipv6-prefix;
          description
            "PPR ID, SRv6 SID format.";
        }
        leaf-list pde-id {
          type inet:ipv6-prefix;
          description
            "List of PPR Path Description Element (PDE).";
        }
      }
    }
  }
}
