module iana-tunnel-type {
  yang-version 1.1;
  namespace "urn:ietf:params:xml:ns:yang:iana-tunnel-type";
  prefix iana-tunnel-type;

  import iana-if-type  {
    prefix ift;
    reference
      "RFC 7224: IANA Interface Type YANG Module";
  }

  organization
    "IANA";
  contact
    "Internet Assigned Numbers Authority

  Postal: ICANN
          12025 Waterfront Drive, Suite 300
          Los Angeles, CA  90094-2536
          United States of America
  Tel:    +1 310 301 5800
  <mailto:iana@iana.org>";

  description
    "This module contains a collection of YANG identities defined
    by IANA and used as interface types for tunnel interfaces.

    Copyright (c) 2019 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX; see
    the RFC itself for full legal notices.";

  revision 2019-01-10 {
    description
      "Initial revision.";
    reference
      "RFC XXXX: Tunnel Interface Types YANG Module";
  }
  identity other {
    base ift:tunnel;
    description
      "None of the following values.";
    reference
     "RFC 4087: IP Tunnel MIB";
  }
  identity direct {
    base ift:tunnel;
    description
      "No intermediate header.";
    reference
      "RFC 2003: IP Encapsulation within IP
       RFC 4213: Basic Transition Mechanisms for IPv6 Hosts
                 and Routers";
   }
   identity gre {
     base ift:tunnel;
     description
       "GRE encapsulation.";
     reference
      "RFC 1701: Generic Routing Encapsulation (GRE)
       RFC 1702: Generic Routing Encapsulation over IPv4 networks
       RFC 7676: IPv6 Support for Generic Routing Encapsulation
                 (GRE)";
  }
  identity minimal {
    base ift:tunnel;
    description
      "Minimal encapsulation.";
    reference
      "RFC 2004: Minimal Encapsulation within IP";
  }
  identity l2tp {
    base ift:tunnel;
    description
      "L2TP encapsulation.";
   reference
     "RFC 2661: Layer Two Tunneling Protocol (L2TP)";
  }
  identity pptp {
    base ift:tunnel;
    description
      "PPTP encapsulation.";
    reference
      "RFC 2637: Point-to-Point Tunneling Protocol (PPTP)";
  }
  identity l2f {
    base ift:tunnel;
    description
      "L2F encapsulation.";
    reference
      "RFC 2341: Cisco Layer Two Forwarding (Protocol) (L2F)";
  }
  identity udp {
    base ift:tunnel;
    description
      "UDP encapsulation.";
    reference
      "Section 3.1.11 of RFC 8085";
  }
  identity atmp {
    base ift:tunnel;
    description
     "ATMP encapsulation.";
    reference
      "RFC 2107: Ascend Tunnel Management Protocol - ATMP";
  }
  identity msdp {
    base ift:tunnel;
    description
      "MSDP encapsulation.";
    reference
      "RFC 3618: Multicast Source Discovery Protocol (MSDP)";
  }
  identity sixtofour {
    base ift:tunnel;
    description
      "6to4 encapsulation.";
    reference
      "RFC 3056: Connection of IPv6 Domains via IPv4 Clouds";
  }
  identity sixoverfour {
    base ift:tunnel;
    description
      "6over4 encapsulation.";
    reference
      "RFC 2529: Transmission of IPv6 over IPv4 Domains without
                 Explicit Tunnels";
  }
  identity isatap {
    base ift:tunnel;
    description
      "ISATAP encapsulation.";
    reference
      "RFC 5214:  Intra-Site Automatic Tunnel Addressing Protocol
                 (ISATAP)";
  }
  identity teredo {
    base ift:tunnel;
    description
      "Teredo encapsulation.";
    reference
      "RFC 4380: Teredo- Tunneling IPv6 over UDP through
                 Network Address Translations (NATs)";
  }
  identity iphttps {
    base ift:tunnel;
    description
      "IP over HTTPS (IP-HTTPS) Tunneling Protocol.";
    reference
      "Microsoft Corporation, IP over HTTPS (IP-HTTPS) Tunneling
       Protocol Specification,
       https://msdn.microsoft.com/en-us/library/dd358571.aspx";
  }
  identity softwiremesh {
    base ift:tunnel;
    description
      "softwire mesh tunnel.";
    reference
      "RFC 5565: Softwire Mesh Framework";
  }
  identity dslite {
    base ift:tunnel;
    description
      "DS-Lite tunnel.";
    reference
      "RFC 6333: Dual-Stack Lite Broadband Deployments Following
                 IPv4 Exhaustion";
  }
  identity  aplusp {
    base ift:tunnel;
    description
      "A+P encapsulation.";
    reference
      "RFC 6346: The Address plus Port (A+P) Approach to the IPv4
                 Address Shortage";
  }
}
