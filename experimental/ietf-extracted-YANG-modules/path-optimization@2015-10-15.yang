submodule path-optimization {
  belongs-to sfc-control-planes {
    prefix sfc-po;
  }
  organization "ETRI.";
  contact
  "M-K. Shin mkshin@etri.re.kr
   M-J Choi mjchoi@kangwon.ac.kr";
  description
  "This module constructs and maintains a SFP with a low stretch
   considering the topological locations and properties (e.g.,
   latency, bandwidth) of SF.";
  revision 2015-10-15 {
 reference
 "draft-shin-sfc-control-plane-yang-00 -
  Yang Data Model for Service Function Chaining Control Plane";
  }
  container path-optimization {
    description
    "This container constructs and maintains a SFP with
     a low stretch considering the topological locations and
     properties (e.g., latency, bandwidth) of SF.";
    leaf sfp-name {
      type string;
      description
      "The name of service function path to be changed for
       optimization.";
    }
    leaf optimized-sfp {
      type string;
      description
      "The name of optimized service function path.";
    }
    leaf sfp-availability {
      type boolean;
      description
      "The availability of the optimized service function path:
       true or false.";
    }
    leaf load-status {
      type uint8;
      description
      "A percentage value of load status.";
    }
  }
  rpc find-optimized-sfp {
    description
    "Find an optimized service function path.";
    input  {
      leaf sfp-name {
        type string;
        description
        "The name of service function path to be changed for
         optimization.";
      }
    }
    output {
      leaf optimized-sfp {
        type string;
        description
        "The name of optimized service function path.";
      }
      leaf sfp-availability {
        type string;
        description
        "The availability of the optimized service function path:
         true or false.";
      }
   }
}
}
