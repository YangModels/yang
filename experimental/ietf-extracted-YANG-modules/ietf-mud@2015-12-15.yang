module ietf-mud {
  yang-version 1;
  namespace "urn:ietf:params:xml:ns:yang:ietf-mud";
  prefix "ietf-mud";

  import ietf-access-control-list {
    prefix "acl";
  }

  import ietf-yang-types
  {
    prefix "yang";
  }

  import ietf-inet-types
  {
    prefix "inet";
  }

  organization
    "Cisco Systems, Inc.";

  contact
    "Eliot Lear
     lear@cisco.com
    ";

  description
    "This YANG module defines a component that augments the
     IETF description of an access list.  This specific module
     focuses on additional filters that include local, model,
     and same-manufacturer.
    Copyright (c) 2015 IETF Trust and the persons identified as
    the document authors.  All rights reserved.
    Redistribution and use in source and binary forms, with or
    without modification, is permitted pursuant to, and subject
    to the license terms contained in, the Simplified BSD
    License set forth in Section 4.c of the IETF Trust's Legal
    Provisions Relating to IETF Documents
    (http://trustee.ietf.org/license-info).
    This version of this YANG module is part of RFC XXXX; see
    the RFC itself for full legal notices.";

  revision "2015-12-15"  {
    description "A policy container for manufacturer-driven policy";
    reference "RFC XXXX";
  }

  container support-information
  {

    description "Information about when support end(ed), and
                 when to refresh";

    leaf last-update
    {
      type yang:date-and-time;
      description "This is intended to be the time and date that
                   the MUD file was generated.";
    }

    leaf cache-validity
    {
      type uint32;
      description "The information retrieved from the MUD server is
                 valid for these many hours, after which it should
                 be refreshed.";
    }

    leaf masa-server {
      type inet:uri;
      description "The URI of the MASA server that network
      elements should forward requests to for this device.";
    }

    leaf is-supported
    {
      type boolean;
      description "The element is currently supported
                   by the manufacturer.";
    }
  }

  augment "/acl:access-lists/acl:acl/" +
     "acl:access-list-entries/acl:ace/" +
     "acl:matches" {
    description "adding manufacturer-driven policy";

    leaf manufacturer
    {
      type inet:host;
      description "authority component of the manufacturer URI";
    }

    leaf same-manufacturer
    {
      type boolean;
      description "expand to ACEs for each device
               with the same origin";
    }

    leaf model
      {
    type string;
    description "specific model for a given manufacturer";
      }

    leaf local-networks {
      type empty;
      description "this string is used to indicate networks
                   considered local in a given environment.";
    }
    leaf controller {
      type inet:uri;
      description "expands to one or more controllers for a
                   given service that is codified by inet:uri.";
    }
  }
}
