module example-adm {
  yang-version 1.1;
  namespace "ari:/example-adm";
  prefix example-adm;

  import ietf-amm {
    prefix amm;
  }

  organization "Example Org.";
  description "Example module.";
  amm:enum "4294967296";
}
