module ietf-yang-full-embed {
  yang-version 1.1;
  namespace "urn:ietf:params:xml:ns:yang:ietf-yang-full-embed";
  prefix full;

  organization
    "IETF NETMOD (NETCONF Data Modeling Language) Working Group";
  contact
    "WG Web:   <https://datatracker.ietf.org/wg/netmod/>
     WG List:  <mailto:netmod@ietf.org>

     Editor:   ";
  description
    "This module defines a YANG extension statement that can be used
     to incorporate data models defined in other YANG modules in a
     module.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.";

  revision 2023-11-05 {
    description
      "Initial revision.";
    reference
      "RFC XXXX: YANG Full Embed";
  }

  extension embed {
    argument prefix;
    description
      "The argument 'prefix' MUST be the prefix of a module imported
       by the calling module.

       The 'embed' statement MUST NOT be used in a YANG version 1
       module, neither explicitly nor via a 'uses' statement.

       The 'embed' statement MAY be present as a substatement of
       'anydata' and MUST NOT be present elsewhere.

       Whenever a sequence of 'embed' statements is used, the schema
       tree defined by the set of the included modules is inserted
       in the schema tree of the calling module, at the place where
       the sequence is declared";
  }
}
