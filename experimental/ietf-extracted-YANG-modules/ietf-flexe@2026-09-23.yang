module ietf-flexe {
  yang-version 1.1;
  namespace "urn:ietf:params:xml:ns:yang:ietf-flexe";
  prefix "flexe";

  import ietf-interfaces {
    prefix if;
    reference
    "RFC 8343: A YANG Data Model For Interface Management";
  }

  organization "IETF CCAMP Working Group";
  contact
   "WG Web:   http://datatracker.ietf.org/wg/ccamp/
    WG List:  <mailto:ccamp@ietf.org>
    Author:   Minxue Wang
              <mailto: wangminxue@chinamobile.com>
    Author:   Liuyan Han
              <mailto: hanliuyan@chinamobile.com>
    Author:   Xuesong Geng
              <mailto:gengxuesong@huawei.com>
    Author:   Jin Zhou
              <mailto: zhou.jin6@zte.com.cn>                     
    Author:   Luis M. Contreras 
              <mailto:luismiguel.contrerasmurillo@telefonica.com>";
  description
   "This YANG module defines a data model for the configuration
    of FlexE, which includes the configuration of FlexE group and 
    FlexE client.

    Copyright (c) 2022 IETF Trust and the persons identified as
    authors of the code. All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see the
    RFC itself for full legal notices.";

  revision "2026-09-23" {
    description "the eleventh version";
    reference
    "RFC XXXX: YANG Data Model for FlexE Management";
  }

  typedef negotiation-mode-type {
    type enumeration {
      enum "dynamic" {
        value 1;
        description
          "Dynamic mode.";
      }
      enum "static" {
        value 2;
        description
          "Static mode.";
      }
    }
    description
      "Negotiation mode of a FlexE group.";
  }

  container flexe {
    description
      "Specify FlexE group configuration information.";
    reference
      "Flex Ethernet 2.1 Implementation Agreement";
    container flexe-groups {
      description
        "List of FlexE groups.";
      list flexe-group {
        key "index";
        description
          "Configure FlexE group.";
        leaf index {
          type uint32 {
            range "1..65535";
          }
          description
            "FlexE group index.";
        }
        leaf group-num {
          type uint32 {
            range "1..1048574";
          }
          mandatory true;
          description
            "FlexE group number.";
          reference
            "OIF FlexE 2.1, Section 7.3.6";
        }
        leaf negotiation-mode {
          type negotiation-mode-type;
          mandatory true;
          description
            "FlexE group calendar negotiation mode, the default 
             value is 'dynamic'.";
        }
        leaf total-bandwidth {
          type string {
            length "1..9";
          }
          config false;
          description
            "FlexE group total bandwidth in Gbit/s, such as 10.";
        }
        leaf free-bandwidth {
          type string {
            length "1..9";
          }
          config false;
          description
            "FlexE group free bandwidth in Gbit/s, such as 100.";
        }
        leaf sync-phy-number {
          type uint32 {
            range "1..254";
          }
          config false;
          description
            "The FlexE PHY number used for synchronization
             management channel in a FlexE group, which is 
             one of the PHY number value in a FlexE group.";
          reference
            "OIF FlexE 2.1, Section 7.3.5";
        }
        container flexe-phys {
          description
            "List of physical port information in a FlexE Group.";
          list flexe-phy {
            key "port-name";
            description
              "FlexE PHY port name.";
            leaf port-name {
              type if:interface-ref;
              description
                "Physical port name. ";
            }
            leaf phy-number {
              type uint32 {
                range "1..254";
              }
              mandatory true;
              description
                "Number of a FlexE physical port. ";
              reference
                "OIF FlexE 2.1, Section 6.1";  
            }
            leaf free-timeslot-list {
              type string {
                length "1..199";
              }
              config false;
              description
               "Free timeslots of a FlexE PHY. The string 
               consists of one or more numbers separated by 
               commas (,) or hyphens (-), e.g.'1-5' indicates
               1,2,3,4,5 timeslots, '0,5,7-10' indicates
               0,5,7,8,9,10 timeslots.";
            }
            leaf used-timeslot-list {
              type string {
                length "1..199";
              }
              config false;
              description
               "Used timeslots of a FlexE PHY. The string 
               consists of one or more numbers separated by 
               commas (,) or hyphens (-), e.g.'1-5' indicates
               1,2,3,4,5 timeslots, '0,5,7-10' indicates
               0,5,7,8,9,10 timeslots.";
            }
          }
        }
      }
    }

   container flexe-clients {
     description
       "All the clients configured in the same FlexE group.";
     list flexe-client{
       key "client-index";
       description
          "Specify FlexE client configuration information.";
       reference
          "OIF FlexE 2.1, Section 6.7";
       leaf client-index {
         type uint32 {
           range "1..65535";
         }
         description
           "FlexE client index.";
       }
       leaf group-index {
         type leafref {
           path "/flexe:flexe/flexe:flexe-groups"
              + "/flexe:flexe-group/flexe:index";
         }
         mandatory true;
         description
           "A local FlexE group index configured
           for a client on one equipment for the
           sake of simplicity on configuration and
            management.";
        }
        leaf client-num {
          type uint32 {
            range "1..65534";
          }
          mandatory true;
          description
            "FlexE Client number.";
        }
        container timeslot-lists {
          description
            "List of binding timeslots.";
          list timeslot-list {
            key "port-name";
            description
              "Configure binding timeslots.";
            leaf port-name {
              type leafref{
               path "/flexe:flexe"
                  + "/flexe:flexe-groups"
                  + "/flexe:flexe-group"
                  + "/flexe:flexe-phys"
                  + "/flexe:flexe-phy/flexe:port-name";
              }
              description
                "FlexE physical port name.";
            }
            leaf time-slot {
              type string {
                length "1..199";
              }
              mandatory true;
              description            
                "Timeslot allocated for a FlexE client. The string 
                 consists of one or more numbers separated by 
                 commas (,) or hyphens (-), e.g.'1-5' indicates
                 1,2,3,4,5 timeslots, '0,5,7-10' indicates
                 0,5,7,8,9,10 timeslots.

                 Convention: The valid range of a timeslot number 
                 is determined by the flexe-phy:
                 - When the flexe-phy is 50GBASE-R, the timeslot  
                   number are in the range 0-9;          
                 - When the flexe-phy is 100GBASE-R, the timeslot 
                   number are in the range 0-19;
                 - When the flexe-phy is 200GBASE-R, the timeslot  
                   number are in the range 0-39;
                 - When the flexe-phy is 400GBASE-R, the timeslot  
                   number are in the range 0-79;
                ";
              reference
                "OIF FlexE 2.1, Section 6.8";             
              }
            }
          }
        }
      }
    }
  }
