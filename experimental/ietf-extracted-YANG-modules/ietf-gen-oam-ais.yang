module ietf-gen-oam-ais {
namespace "urn:ietf:params:xml:ns:yang:ietf-gen-oam-ais";
prefix goamais;
import ietf-gen-oam {
prefix goam;
}
import ietf-yang-types {
prefix yang;
}
organization

"IETF LIME (Layer Independent OAM Management in Multi-Layer
Environment) Working Group";
contact
"sudhin jacob sjacob@juniper.net.";
description
"This YANG module defines generic ais 
Expires December 25, 2016.";

revision 2016-06-25 {
description
"Initial revision.";
reference "draft-jacpra-lime-yang-ais";
}

container oam-ais {
description
"This set of data definitions covers the proactive OAM Fault
Management Alarm Indication Signal function.

leaf enabled {
type boolean;
default false;
description
"This attribute specifies whether transmission is enabled. The
value 'true' indicates AIS transmission is enabled. The
value 'false' indicates AIS transmission is disabled.";

leaf interval {
type int8;
default one-second;
description
"This attribute specifies the AIS transmission period 1s or 1m";

}
leaf priority {
type int8;
description
"This attribute specifies the priority of frames with AIS
information. If AIS is supported, the default value for
the CoS for AIS frame MUST be the value which yields the
lowest frame loss performance for this EVC.";

}
leaf client-meg-level {
type int8;
default 0;
description
"The MEG/Maintenance Domain Level of the Client AIS PDU (transmitted
level).";

}
leaf drop-eligible {
type boolean;
default false;

description

"This attribute specifies the eligibility of frames with ETH-AIS
information to be discarded when congestion conditions are
encountered.The value 'true' indicates frames are eligible to be
discarded.The value 'false' indicates frames are not eligible to be
discarded. This attribute may be constrained to read-only in
some implementations";

leaf transmit-status {
type boolean;
config false;

description

"This attribute specifies the current AIS transmission status of the
MEP.The value 'true' indicates AIS frames are currently being
transmitted by the MEP.The value 'false' indicates AIS frames are not currently
being transmitted by the MEP.";

}
leaf receive-status {
type boolean;
config false;

description

"This attribute specifies the current AIS receive status of the
MEP. The value 'true' indicates an AIS PDU has been received
and 3.5 times the interval defined in the PDU has not yet
passed, otherwise it is 'false'.";

}
leaf transmit-counter {
type yang:zero-based-counter32;
config false;
description
"This attribute contains the count of the total number of AIS messages
sent by the MEP. The count is incremented every time an AIS
PDU is transmitted by the MEP.";

}
leaf receive-counter {
type yang:counter32;
config false;
description
"This attribute contains the count of the total number of AIS messages
received by the MEP. The count is incremented every time an
AIS PDU is received by the MEP.";

}
leaf last-received-mac-address {
type yang:mac-address;
config false;
description
"The source MAC Address Field of last AIS received by the MEP.
If no AIS PDU has been received by the NE the MAC address is
set to all zeros.";

}

leaf ma-name {
type yang:ma-name;
config false;
description
"The ma name where the fault is detected";

}

leaf md-name {
type yang:md-name;
config false;
description
"The md name where the fault is detected.";

}

leaf  hostname {
type yang:hostname;
config false;
description
"The hostname of the device where fault is detected.";

}

leaf  fault-type {
type int8;
config false;
description
"The type of fault the value 1 means adjacency loss 2 means
errored ccm 3 means cross connect ccm";

}

leaf  mep-id {
type uint16;
config false;
description
"The mep id of the device where the fault was detected ";

}
}
}
