module ietf-lisp-mapserver {
  namespace "urn:ietf:params:xml:ns:yang:ietf-lisp-mapserver";
  prefix lisp-ms;
  import ietf-lisp {
    prefix lisp;
  }
  import ietf-lisp-address-types {
   prefix lcaf;
  }
  import ietf-inet-types {
    prefix inet;
  }
  organization
   "IETF LISP (Locator/ID Separation Protocol) Working Group";
  contact
    "lisp@ietf.org";
  description
    "This YANG module defines the generic configuration
     data for a LISP Map-Server. The module can be extended by
     vendors to define vendor-specific configuration parameters
     and policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";

  revision 2015-07-02 {
    description
      "Initial revision.";
    reference
      "https://tools.ietf.org/html/rfc6833";
  }
  identity ms {
    base lisp:lisp-device;
    description
      "LISP Map-Server.";
  }
  augment "/lisp:lisp/lisp:devices/lisp:device" {
    when "lisp:type = lisp-ms:ms" {
      description
        "Augment is valid when LISP device type is Map-Server.";
    }
    description
      "This augments LISP devices list with Map-Server specific
       parameters.";
    container map-server-cfg {
      presence "LISP Map-Server operation enabled";
      description
        "Map-Server configuration parameters.";
      container sites {
        description
          "Sites for which the Map-Server accepts registrations.";
        list site {
          key "site-id";
          description
            "List of sites for which the Map-Server acceptes
             registrations.";
          leaf site-id {
            type uint64;
            description
              "Site identifier.";
          }
    //Can be augmented to have below for per site auth-key
    //      leaf auth-key {
    //        description "clear text authentication key";
    //        type string;
    //      }
          container devices {
            description
              "Site devices registered with the Map-Server.";
            list device {
              key "device-id";
              description
                "List of site devices registered with the
                 Map-Server.";
              leaf device-id {
                type uint64;
                description
                  "Device identifier.";
              }
              container auth-key {
                description
                  "Device authentication key.";
                leaf auth-key-value {
                  type string;
                  description
                    "Clear text authentication key";
                }
                leaf auth-key-type {
                  type lisp:auth-key-type;
                  description
                    "Authentication key type.";
                }
              }

              container eids {
                description
                  "EIDs registered by device.";
                list eid {
                  key "id";
                  description
                    "List of EIDs registered by device.";
                  leaf id {
                    type lisp:eid-id;
                    description
                      "Id of the EID registered.";
                  }
                  container eid-address {
                    uses lcaf:lisp-address;
                    description
                      "EID in generic LISP address format registered
                       with the Map-Server.";
                  }
                  leaf more-specifics-accepted {
                      type boolean;
                      description
                        "Flag indicating if more specific prefixes
                         can be registered.";
                  }
                  leaf mapping-expiration-timeout {
                      type int16;
                      units "seconds";
                      default "180"; //3 times the mapregister int
                      description
                        "Time before mapping is expired if no new
                         registrations are received.";
                  }
        // Can be augmented to have below for per-eid auth-key
        //          leaf auth-key {
        //            description "clear text authentication key";
        //            type string;
        //          }
                }
              }
            }
          }
        }
      }
      container static-mappings {
        uses lisp:mappings;
        description
          "Datastore of statically registred mappings.";
      }
      choice mapping-system {
        mandatory true;
        description
          "Interface to Mapping System.";
        container ddt-mapping-system {
          presence "DDT Mapping System in use";
          description
            "DDT Mapping System interface.";
          leaf-list ddt-root {
            type inet:ip-address;
            description
              "List of DDT root address.";
          }
          container authoritative-eids {
            description
              "Authoritative EIDs";
            list authoritative-eid {
              key "id";
              description
                "List of authoritative EIDs.";
              leaf id {
                type lisp:eid-id;
                description
                  "EID id.";
              }
              container eid-address {
                uses lcaf:lisp-address;
                description
                  "EID in generic LISP address format.";
              }
            }
          }
        }
        container alt-mapping-system {
          presence "ALT Mapping System in use";
          description
            "ALT Mapping System interface.";
        // TBD
        }
      }
    }
  }
  augment "/lisp:lisp-state/lisp:devices/lisp:device" {
    when "lisp:type = lisp-ms:ms" {
      description
        "Augment is valid when LISP device type is Map-Server.";
    }
    description
      "This augments LISP devices list state with Map-Server
       specific parameters.";
    container ms-state {
      config false;
      description
        "Map-Server state.";
      container registered-mappings {
        uses lisp:mappings;
        description
          "Datastore of registred mappings.";
      }
    }
  }
}
