module ietf-te-kpi-telemetry {

    namespace "urn:ietf:params:xml:ns:yang:ietf-te-kpi-telemetry";

    prefix "te-tel";

    import ietf-te {
        prefix "te";
    }

    import ietf-te-types {
       prefix "te-types";
    }

    import ietf-routing-types {
       prefix "rt-types";
    }

    organization
        "IETF Traffic Engineering Architecture and Signaling (TEAS)
        Working Group";

    contact
        "Editor: Young Lee <leeyoung@huawei.com>
         Editor: Dhruv Dhody <dhruv.ietf@gmail.com>
         Editor: Ricard Vilalta <ricard.vilalta@cttc.es>
         Editor: Satish Karunanithi <satish.karunanithi@gmail.com>";

    description
        "This module describes telemetry for teas tunnel model";

    revision 2018-07-02 {
        description
            "Initial revision. This YANG file defines
            the reusable base types for TE telemetry.";
        reference
            "Derived from earlier versions of base YANG files";
    }

    /*
     * Identities
     */

    identity telemetry-param-type {
        description
            "Base identity for telemetry param types";
    }

    identity one-way-delay {
        base telemetry-param-type;
        description
            "To specify average Delay in one (forward)
             direction";
    }

    identity bidirectional-delay {
        base telemetry-param-type;
        description
            "To specify average Delay in both (forward and reverse)
             directions";
    }

    identity one-way-delay-variation {
        base telemetry-param-type;
        description
            "To specify average Delay Variation in one (forward) direction";
    }

    identity bidirectional-delay-variation {
        base telemetry-param-type;
        description
            "To specify average Delay Variation in both (forward and reverse)
             directions";
    }

    identity one-way-packet-loss {
        base telemetry-param-type;
        description
            "To specify packet loss in one (forward) direction.";
    }

    identity bidirectional-packet-loss {
        base telemetry-param-type;
        description
            "To specify packet loss in in both (forward and reverse)
             directions";
    }

    identity utilized-bandwidth {
        base telemetry-param-type;
        description
            "To specify utilized bandwidth over the specified source
             and destination.";
    }

     identity utilized-percentage {
          base telemetry-param-type;
          description
               "To specify utilization percentage of the entity
                (e.g., tunnel, link, etc.)";
     }
    /*
     * Enums
     */
    typedef scaling-criteria-operation {
        type enumeration {
            enum AND {
                description
                 "AND operation";
            }
            enum OR {
                 description
                  "OR operation";
            }
        }
        description
         "Operations to analize list of scaling criterias";
    }

    /*
     * Groupings
     */

    grouping bidirectional-telemetry-data {
     description
               "list all bidirectional telemetry data in this grouping";

         leaf bidirectional-delay {
            type uint32;
            units "microseconds";
               description
               "To specify average Delay in both (forward and reverse)
                  directions during the measurement interval";
         }

         leaf bidirectional-min-delay {
            type uint32;
            units "microseconds";
               description
               "To specify minimum Delay in both (forward and reverse)
                  directions during the measurement interval";
         }

         leaf bidirectional-max-delay {
            type uint32;
            units "microseconds";
               description
               "To specify maximum Delay in both (forward and reverse)
                  directions during the measurement interval";
         }

         leaf bidirectional-delay-variation {
            type uint32;
            units "microseconds";
               description
                "To specify average Delay Variation in both
                 (forward and reverse) directions during the
                  measurement interval";
         }

         leaf bidirectional-packet-loss {
            type decimal64 {
                fraction-digits 4;
                range "0.0000..100.0000";
            }
            units "percent";
               description
               "To specify packet loss in in both (forward and reverse)
                  directions";
         }

         leaf bidirectional-residual-bandwidth {
            type rt-types:bandwidth-ieee-float32;
               description
                    "To specify residual bandwidth over the specified source
                  and destination in bytes per seconds.";
            reference
                "RFC 3471";
         }
          leaf bidirectional-available-bandwidth {
            type rt-types:bandwidth-ieee-float32;
               description
                    "To specify available bandwidth over the specified source
                  and destination in bytes per seconds.";
            reference
                "RFC 3471";
         }
          leaf bidirectional-utilized-bandwidth {
            type rt-types:bandwidth-ieee-float32;
               description
                    "To specify utilized bandwidth over the specified source
                  and destination in bytes per seconds.";
            reference
                "RFC 3471";
          }
          leaf utilized-percentage {
               type uint8;
               units "percentage";
               description
                    "integer indicating a percentage value (0..100) for
utilization";
          }
     }

    grouping scaling-duration {
     description
         "Base scaling criteria durations";
     leaf threshold-time {
            type uint32;
            units "seconds";
            description
                "The duration for which the criteria must hold true";
        }

        leaf cooldown-time {
            type uint32;
            units "seconds";
            description
            "The duration after a scaling-in/scaling-out action has been
            triggered, for which there will be no further operation";
        }
    }

    grouping scaling-criteria {
        description
            "Grouping for scaling criteria";
     leaf performance-type {
                type identityref {
                base telemetry-param-type;
                }
                description
                    "Reference to the tunnel level telemetry type";
     }

     leaf te-telemetry-tunnel-ref {
            type leafref {
                path "/te:te/te:tunnels/te:tunnel/te:name";
            }
            description
                "Reference to tunnel";
        }
    }

    grouping scaling-intent {
     description
          "Basic sclaing intent";

     uses scaling-duration;

        leaf scale-in-operation-type {
            type scaling-criteria-operation;
            default AND;
            description
                "Operation to be applied to check between scaling criterias to
                check if the scale in threshold condition has been met.
                Defaults to AND";
        }

        leaf scale-out-operation-type {
            type scaling-criteria-operation;
            default OR;
            description
                "Operation to be applied to check between scaling criterias to
                check if the scale out threshold condition has been met.
                Defauls to OR";
        }

     list scaling-condition {
          key "performance-type";
          description
               "Scaling conditions";
          uses scaling-criteria;
     }

    }

    /*
     * Augments
     */

    augment "/te:te/te:tunnels/te:tunnel" {

        description
            "Augmentation parameters for config scaling-criteria
            TE tunnel topologies. Scale in/out criteria might be used
            for network autonomics in order the controller
            to react to a certain set of monitored params.";
        container te-scaling-intent {
           description
                "scaling intent";

           container scale-in-intent{
                description
                    "scale-in";
                uses scaling-intent;
            }
           container scale-out-intent{
                description
                    "scale-out";
                uses scaling-intent;
            }
         }
        container te-telemetry {
                config false;
                description
                    "telemetry params";
                    leaf id {
                         type string;
                         description "Id of telemetry param";
                    }

                    uses te-types:performance-metric-attributes;
                  /* all unidirectional PM data is defined in this grouping */

                    uses bidirectional-telemetry-data;
                    /* all bidirectional PM data is defined in this grouping */

                    leaf te-ref{
                         type leafref{ path
'/te:te/te:tunnels/te:tunnel/te:name'; }
                         description "Reference to measured te tunnel";
                    }
        }

    }

}
