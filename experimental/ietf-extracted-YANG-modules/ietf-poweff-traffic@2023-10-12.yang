module ietf-poweff-traffic {
  yang-version 1.1;
  namespace "urn:ietf:params:xml:ns:yang:ietf-poweff-traffic";
  prefix ietf-poweff-traffic;
  import ietf-yang-types {
    prefix yang;
  }
  import ietf-interfaces {
    prefix if;
  }
  import ietf-lmo-assets-inventory {
    prefix ietf-lmo-asset;
  }
  import ietf-lmo {
    prefix ietf-lmo;
  }
  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
    Editor:  Marisol Palmero
              <mailto:mpalmero@cisco.com>";
  description
    "This YANG module describes the live interface and traffic related
     metrics. It should be based on rfc7223,
     https://datatracker.ietf.org/doc/rfc7223/

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
     ";

  revision 2023-10-12 {
    description
      "Initial revision to document power traffic data";
    reference
      "RFC XXXX: ...";
  }
  augment /ietf-lmo:lmos/ietf-lmo:lmo/ietf-lmo:inst {
    when "derived-from-or-self(../ietf-lmo:lmo-class, "+
         " 'ietf-lmo-asset:asset')";
    description
      "Traffic attributes related to sustainability";
    container interfaces {
      description "Interface parameters";
      list interface {
        key "name";
        leaf name {
          type leafref {
            path "/if:interfaces/if:interface/if:name";
            require-instance false;
          }
          description
            "The name of the interface.";
        }
        leaf description {
          type string;
          description
            "A textual description of the interface.

             A server implementation MAY map this leaf to the ifAlias
             MIB object.  Such an implementation needs to use some
             mechanism to handle the differences in size and characters
             allowed between this leaf and ifAlias.  The definition of
             such a mechanism is outside the scope of this document.

             Since ifAlias is defined to be stored in non-volatile
             storage, the MIB implementation MUST map ifAlias to the
             value of 'description' in the persistently stored
             configuration.";
          reference
            "RFC 2863: The Interfaces Group MIB - ifAlias";
        }
        leaf if-index {
          type int32;
          description
            "The ifIndex value for the ifEntry represented by this
            interface";
          reference
            "RFC 2863: The Interfaces Group MIB - ifIndex";
        }
        leaf interface-type {
          type string;
          //TO_DO adjust type to identy interface-type or similar
          description
            "The type of the interface.

             When an interface entry is created, a server MAY
             initialize the type leaf with a valid value, e.g., if it
             is possible to derive the type from the name of the
             interface.

             If a client tries to set the type of an interface to a
             value that can never be used by the system, e.g., if the
             type is not supported or if the type does not match the
             name of the interface, the server MUST reject the request.
             A NETCONF server MUST reply with an rpc-error with the
             error-tag 'invalid-value' in this case.";
          reference
            "RFC 2863: The Interfaces Group MIB - ifType";
        }
        leaf bandwidth {
          type yang:gauge64;
          units "kbits/s";
          description
            "It is considered to be the Max bandwidth of the interface,
             in kbps, it could also be called capacity";
        }
        leaf speed {
          type yang:gauge64;
          units "kbits/s";
          description
            "It is considered to be current bandwidth of the interface,
             in kbps, it could also be called capacity";
        }
        leaf data-rate-frequency {
          type string;
          //TO_DO normalized to do not be string, as different devices
          //will provide different implementation
          description
            "The length of time for which data is used to compute load
            statistics, load-interval command in interface
            configuration. Default value is 5min";
        }
        container statistics {
          description "A collection of interface-related statistics
            objects.";
          leaf input-data-rate {
            type uint64;
            units "kbits/s";
            mandatory "true";
            description
              "Input data rate in 1000's of bps. Average number of bits
               received per second in the last load period
               (300 sec by default)";
          }
          leaf input-packet-rate {
            type uint64;
            units "packet/s";
            description
              "Input packets per second. Average number of packets
              received per second in the last load period
              (300 sec by default)";
          }
          leaf output-data-rate {
            type uint64;
            units "kbits/s";
            mandatory "true";
            description
              "Output data rate in 1000's of bps. Average number of bits
              sent per second in the last load period
              (300 sec by default)";
          }
          leaf output-packet-rate {
            type uint64;
            units "packet/s";
            description
              "Output packets per second. Average number of packets
              sent per second in the last load period
              (300 sec by default)";
          }
        }
        description "Interface parameters for a specific interface";
      }
    }
  }
}
