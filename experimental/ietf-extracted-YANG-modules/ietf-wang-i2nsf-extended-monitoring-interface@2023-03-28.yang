module ietf-wang-i2nsf-extended-monitoring-interface{
 yang-version 1.1;
 namespace
   "urn:ietf:params:xml:ns:yang:wang-i2nsf-extended-
        monitoring-interface";
 prefix i2nsf-exmi;
 import ietf-inet-types{
   prefix inet;
   reference "Section 4 of RFC 6991";
 }
 import ietf-yang-types{
   prefix yang;
   reference "Section 3 of RFC 6991";
 }
 organization
   "IETF I2NSF (Interface to Network Security Functions)
    Working Group";
 contact
   "WG Web: <https://datatracker.ietf.org/wg/i2nsf>
    WG List: <mailto:i2nsf@ietf.org>
    Author:   Weilin Wang
              <mailto:21111026@bjtu.edu.cn>
    Author:   Huachun Zhou
              <mailto:hchzhou@bjtu.edu.cn>
    Author:   Man Li
              <mailto:20111018@bjtu.edu.cn>
    Author:   Qi Guo
              <mailto:20120044@bjtu.edu.cn>
    Author:   Shuangxing Deng
              <mailto:21120038@bjtu.edu.cn>";
 description
   "This module is a YANG module for the extension of I2NSF
    NSF Monitoring.
   The key words 'MUST', 'MUST NOT', 'REQUIRED', 'SHALL',
   'SHALL NOT', 'SHOULD', 'SHOULD NOT', 'RECOMMENDED',
   'NOT RECOMMENDED', 'MAY', and 'OPTIONAL' in this
   document are to be interpreted as described in BCP 14
   (RFC 2119) (RFC 8174) when, and only when, they appear
   in all capitals, as shown here.
   Copyright (c) 2022 IETF Trust and the persons identified as
   authors of the code. All rights reserved.
   Redistribution and use in source and binary forms, with or
   without modification, is permitted pursuant to, and subject
   to the license terms contained in, the Revised BSD License
   set forth in Section 4.c of the IETF Trust's
   Legal Provisions Relating to IETF Documents
   (https://trustee.ietf.org/license-info).
   This version of this YANG module is part of RFC XXXX
   (https://www.rfc-editor.org/info/rfcXXXX); see the RFC itself
   for full legal notices.";
 revision "2023-03-28" {
   description "Initial revision.";
   reference
     "RFC XXXX: Extension of I2NSF NSF Monitoring Interface
      YANG Data Model";
 }
/*
 * Identity
 */
   identity characteristics {
     description
       "Base identity for monitoring information
       characteristics.";
     reference
       "I-D: I2NSF NSF Monitoring Interface YANG Data Model";
   }
   identity acquisition-method {
     base characteristics;
     description
       "The type of acquisition-method. It can be multiple
       types at once.";
   }
   identity subscription {
     base acquisition-method;
     description
       "The acquisition-method type is subscription.";
   }
   identity query {
     base acquisition-method;
     description
       "The acquisition-method type is query.";
   }
  identity emission-type {
    base characteristics;
    description
      "The type of emission-type.";
  }
  identity periodic {
    base emission-type;
    description
      "The emission-type type is periodic.";
  }
  identity on-change {
    base emission-type;
    description
      "The emission-type type is on-change.";
  }
  identity dampening-type {
    base characteristics;
    description
      "The type of message dampening to stop the rapid
       transmission of messages, such as on-repetition
       and no-dampening.";
  }
  identity no-dampening {
    base dampening-type;
    description
      "The dampening-type is no-dampening. No-dampening
       type does not limit the transmission for the
       messages of the same type.";
  }
  identity on-repetition {
    base dampening-type;
    description
      "The dampening-type is on-repetition. On-repetition
       type limits the transmitted on-change message to one
       message at a certain interval.";
  }
  identity protocol {
    description
      "An identity used to enable type choices in leaves
       and leaf-lists with respect to protocol metadata.
       This is used to identify the type of protocol that
       goes through the NSF.";
  }
  identity ip {
    base protocol;
    description
      "General IP protocol type.";
    reference
      "RFC0791: Internet Protocol
       RFC8200: Internet Protocol, Version 6 (IPv6)";
  }
  identity ipv4 {
    base ip;
    description
      "IPv4 protocol type.";
    reference
      "RFC0791: Internet Protocol";
  }
  identity ipv6 {
    base ip;
    description
      "IPv6 protocol type.";
    reference
      "RFC8200: Internet Protocol, Version 6 (IPv6)";
  }
  identity icmp {
    base protocol;
    description
      "Base identity for ICMPv4 and ICMPv6 condition
       capability";
    reference
      "RFC0792: Internet Control Message Protocol
       RFC4443: Internet Control Message Protocol (ICMPv6)
       for the Internet Protocol Version 6 (IPv6)
       Specification- ICMPv6";
  }
  identity icmpv4 {
    base icmp;
    description
      "ICMPv4 protocol type.";
    reference
      "RFC0791: Internet Protocol
       RFC0792: Internet Control Message Protocol";
  }
  identity icmpv6 {
    base icmp;
    description
      "ICMPv6 protocol type.";
    reference
      "RFC8200: Internet Protocol, Version 6 (IPv6)
       RFC4443: Internet Control Message Protocol (ICMPv6)
       for the Internet Protocol Version 6 (IPv6)
       Specification";
  }
  identity transport-protocol {
    base protocol;
    description
      "Base identity for Layer 4 protocol condition
       capabilities, e.g., TCP, UDP, SCTP, DCCP, and
       ICMP.";
  }
  identity tcp {
    base transport-protocol;
    description
      "TCP protocol type.";
    reference
      "[RFC9293]: Transmission Control
       Protocol (TCP).";
  }
  identity udp {
    base transport-protocol;
    description
      "UDP protocol type.";
    reference
      "RFC0768: User Datagram Protocol";
  }
  identity sctp {
    base transport-protocol;
    description
      "Identity for SCTP condition capabilities";
    reference
      "RFC9260: Stream Control
       Transmission Protocol";
  }
  identity dccp {
    base transport-protocol;
    description
      "Identity for DCCP condition capabilities";
    reference
      "RFC4340: Datagram Congestion Control Protocol";
  }
  identity application-protocol {
    base protocol;
    description
      "Base identity for Application protocol. Note that a
      subset of application protocols (e.g., HTTP, HTTPS,
      FTP, POP3, and IMAP) are handled in this YANG module,
      rather than all the existing application protocols.";
  }
  identity http {
    base application-protocol;
    description
      "The identity for Hypertext Transfer Protocol
       version 1.1 (HTTP/1.1).";
    reference
      "[RFC9110]: HTTP Semantics
       [RFC9112]: HTTP/1.1";
  }
  identity https {
    base application-protocol;
    description
      "The identity for Hypertext Transfer Protocol
       version 1.1 (HTTP/1.1) over TLS.";
    reference
      "[RFC9110]: HTTP Semantics
       [RFC9112]: HTTP/1.1";
  }
  identity http2 {
    base application-protocol;
    description
      "The identity for Hypertext Transfer Protocol
       version 2 (HTTP/2).";
    reference
      "RFC9113: HTTP/2";
  }
  identity https2 {
    base application-protocol;
    description
      "The identity for Hypertext Transfer Protocol
       version 2 (HTTP/2) over TLS.";
    reference
      "RFC9113: HTTP/2";
  }
  identity ftp {
    base application-protocol;
    description
      "FTP protocol type.";
    reference
      "RFC0959: File Transfer Protocol";
  }
  identity ssh {
    base application-protocol;
    description
      "SSH protocol type.";
    reference
      "RFC6242: Using the NETCONF Protocol over
       Secure Shell (SSH)";
  }
  identity telnet {
    base application-protocol;
    description
      "The identity for telnet.";
    reference
      "RFC0854: Telnet Protocol";
  }
  identity smtp {
    base application-protocol;
    description
      "The identity for smtp.";
    reference
      "RFC5321: Simple Mail Transfer Protocol (SMTP)";
  }
  identity pop3 {
    base application-protocol;
    description
      "The identity for Post Office
       Protocol 3 (POP3).";
    reference
      "RFC1939: Post Office Protocol - Version 3 
       (POP3)";
  }
  identity pop3s {
    base application-protocol;
    description
      "The identity for Post Office Protocol 3
       (POP3) over TLS";
    reference
      "RFC1939: Post Office Protocol -Version 3(POP3)
      RFC2595: Using TLS with IMAP, POP3 and ACAP";
  }
  identity imap {
    base application-protocol;
    description
      "The identity for Internet Message Access
       Protocol (IMAP).";
    reference
      "RFC9051: Internet Message Access Protocol
       (IMAP) - Version 4rev2";
  }
  identity imaps {
    base application-protocol;
    description
      "The identity for Internet Message Access
       Protocol (IMAP) over TLS";
    reference
      "RFC9051: Internet Message Access Protocol
                  (IMAP) - Version 4rev2
       RFC2595: Using TLS with IMAP, POP3 and ACAP";
  }
/*
 * Grouping
 */
  grouping common-monitoring-data {
    description
      "A set of common monitoring data that is needed
      as the basic information.";
    leaf vendor-name {
      type string;
      description
        "The name of the NSF vendor. The string is
         unrestricted to identify the provider or
         vendor of the NSF.";
    }
    leaf device-model {
      type string;
      description
        "The model of the device, can be represented
         by the device model name or serial number.
         This field is used to identify the model of
         the device that provides the security
         service.";
    }
    leaf software-version {
      type string;
      description
        "The version of the software used to provide the
        security service.";
    }
    leaf nsf-name {
      type union{
        type string;
        type inet:ip-address-no-zone;
      }
      mandatory true;
      description
        "The name or IP address of the NSF generating
         the message.If the given nsf-name is not an
         IP address, the name can be an arbitrary string
         including a FQDN (Fully Qualified Domain Name).
         The name MUST be unique in the scope of
         management domain for a different NSF to
         identify the NSF that generates the message.";
    }
  }
  grouping message {
    description
      "A set of common monitoring data that is needed
      as the basic information.";
    leaf message {
      type string;
      description
        "This is a freetext annotation for
        monitoring a notification's content.";
    }
    leaf language {
      type string {
        pattern '((([A-Za-z]{2,3}(-[A-Za-z]{3}(-[A-Za-z]{3})'
          + '{0,2})?)|[A-Za-z]{4}|[A-Za-z]{5,8})(-[A-Za-z]{4})?'
          + '(-([A-Za-z]{2}|[0-9]{3}))?(-([A-Za-z0-9]{5,8}'
          + '|([0-9][A-Za-z0-9]{3})))*(-[0-9A-WYZa-wyz]'
          + '(-([A-Za-z0-9]{2,8}))+)*(-[Xx](-([A-Za-z0-9]'
          + '{1,8}))+)?|[Xx](-([A-Za-z0-9]{1,8}))+|'
          + '(([Ee][Nn]-[Gg][Bb]-[Oo][Ee][Dd]|[Ii]-'
          + '[Aa][Mm][Ii]|[Ii]-[Bb][Nn][Nn]|[Ii]-'
          + '[Dd][Ee][Ff][Aa][Uu][Ll][Tt]|[Ii]-'
          + '[Ee][Nn][Oo][Cc][Hh][Ii][Aa][Nn]'
          + '|[Ii]-[Hh][Aa][Kk]|'
          + '[Ii]-[Kk][Ll][Ii][Nn][Gg][Oo][Nn]|'
          + '[Ii]-[Ll][Uu][Xx]|[Ii]-[Mm][Ii][Nn][Gg][Oo]|'
          + '[Ii]-[Nn][Aa][Vv][Aa][Jj][Oo]|[Ii]-[Pp][Ww][Nn]|'
          + '[Ii]-[Tt][Aa][Oo]|[Ii]-[Tt][Aa][Yy]|'
          + '[Ii]-[Tt][Ss][Uu]|[Ss][Gg][Nn]-[Bb][Ee]-[Ff][Rr]|'
          + '[Ss][Gg][Nn]-[Bb][Ee]-[Nn][Ll]|[Ss][Gg][Nn]-'
          + '[Cc][Hh]-[Dd][Ee])|([Aa][Rr][Tt]-'
          + '[Ll][Oo][Jj][Bb][Aa][Nn]|[Cc][Ee][Ll]-'
          + '[Gg][Aa][Uu][Ll][Ii][Ss][Hh]|'
          + '[Nn][Oo]-[Bb][Oo][Kk]|[Nn][Oo]-'
          + '[Nn][Yy][Nn]|[Zz][Hh]-[Gg][Uu][Oo][Yy][Uu]|'
          + '[Zz][Hh]-[Hh][Aa][Kk][Kk][Aa]|[Zz][Hh]-'
          + '[Mm][Ii][Nn]|[Zz][Hh]-[Mm][Ii][Nn]-'
          + '[Nn][Aa][Nn]|[Zz][Hh]-[Xx][Ii][Aa][Nn][Gg])))';
      }
      default "en-US";
      description
        "The value in this field indicates the language tag
        used for the human readable fields (i.e., '../message',
        '/i2nsf-log/i2nsf-nsf-system-access-log/output', and
        '/i2nsf-log/i2nsf-system-user-activity-log/additional-info
        /cause').
        The attribute is encoded following the rules in Section 2.1
        in RFC 5646. The default language tag is 'en-US'";
      reference
        "RFC 5646: Tags for Identifying Languages.";
    }
  }
  grouping characteristics {
    description
      "A set of characteristics of a monitoring information.";
    leaf acquisition-method {
      type identityref {
        base acquisition-method;
      }
      description
        "The acquisition-method for characteristics";
     }
     leaf emission-type {
       when "derived-from-or-self(../acquisition-method, "
         + "'i2nsf-exmi:subscription')";
       type identityref {
         base emission-type;
       }
       description
         "The emission-type for characteristics. This attribute is
          used only when the acquisition-method is a
'subscription'.";
     }
   }
   grouping characteristics-extended {
     description
       "An extended characteristics for the monitoring
information.";
     uses characteristics;
     leaf dampening-type {
       type identityref {
         base dampening-type;
       }
       description
         "The dampening-type for characteristics";
     }
   }
   grouping attack-rates {
     description
       "A set of traffic rates for monitoring attack traffic data.";
     leaf attack-rate {
       type uint64;
       units "pps";
       description
         "The average packets per second (pps) rate of
          attack traffic.";
     }
     leaf attack-throughput {
       type uint64;
       units "Bps";
       description
         "The average bytes per second (Bps) throughput of
         attack traffic.";
     }
   }
/*
 * Notification nodes
 */
  notification i2nsf-event {
    description
      "Notification for I2NSF Event. This notification provides
      general information that can be supported by most types of
      NSFs.";
    uses common-monitoring-data;
    uses message;
    uses characteristics-extended;
    choice sub-event-type {
      description
        "This choice must be augmented with cases for each allowed
        sub-event. Only 1 sub-event will be instantiated in each
        i2nsf-event message. Each case is expected to define one
        container with all the sub-event fields.";
      case i2nsf-flow-features {
        container i2nsf-traffic-flow-features {
          description
            "This notification is sent to inform about the traffic
             flow features.";
          leaf measurement-time {
            type uint32;
            units "seconds";
            description
              "The duration of the measurement in seconds
               for the features of traffic flows. These
               traffic flow features are measured over the
               past measurement duration before now.";
          }
          leaf packets-per-second {
            type uint64;
            description
              "Average number of packets forwarded per
               second measured over the past 'measurement-time'.";
          }
          leaf bytes-per-second {
            type uint64;
            description
              "Average number of bytes forwarded per second
               measured over the past 'measurement-time'.";
          }
          leaf packet-size-mean {
            type uint64;
            description
              "Average packet length of packets measured over
              the past 'measurement-time'.";
          }
             leaf src-ip-entropy {
               type uint64;
               description
                 "Entropy of the source IP address measured over
                 the past 'measurement-time'.";
             }
             leaf dst-ip-entropy {
               type uint64;
               description
                 "The entropy of the destination IP address
                  measured over the past 'measurement-time'.";
             }
             leaf TTL-entropy {
               type uint64;
               description
                 "Packet lifetime TTL entropy measured over
                 the past 'measurement-time'.";
             }
             leaf tcp-src-port-entropy {
               type uint64;
               description
                 "TCP Packet source port entropy measured
                 over the past 'measurement-time'.";
             }
             leaf tcp-dst-port-entropy {
               type uint64;
               description
                 "TCP Packet destination port entropy measured
                 over the past 'measurement-time'.";
             }
             leaf udp-src-port-entropy {
               type uint64;
               description
                 "UDP Packet source port entropy measured
                 over the past 'measurement-time'.";
             }
             leaf udp-dst-port-entropy {
               type uint64;
               description
                 "UDP Packet destination port entropy measured
                 over the past 'measurement-time'.";
             }
             leaf packet-size-entropy {
               type uint64;
               description
                 "The entropy of packet length measured over the
                 past 'measurement-time'.";
             }
             leaf packets-variance {
                    type uint64;
                    description
                      "Variance of packets measured over the
                       past 'measurement-time'.";
                }
            }
        }
    }
  }
  notification i2nsf-log {
    description
      "Notification for I2NSF log. The notification
      is generated from the logs of the NSF.";
    uses common-monitoring-data;
    uses message;
    uses characteristics-extended;
    choice sub-logs-type {
      description
        "This choice must be augmented with cases for each
         allowed sub-logs. Only 1 sub-event will be
         instantiated in each i2nsf-logs message. Each case
         is expected to define one container with all the
         sub-logs fields.";
      case i2nsf-system-res-util-log {
        container i2nsf-system-res-util-log {
          description
            "This notification is sent, if there is a new log
            entry representing resource utilization updates.";
          leaf system-status {
            type enumeration {
              enum running {
                description
                  "The system is active and running the
                   security service.";
              }
              enum waiting {
                description
                  "The system is active but waiting for an
                  event to provide the security service.";
              }
              enum inactive {
                description
                  "The system is inactive and not running the
                  security service.";
              }
            }
            description
                 "The current system's running status.";
             }
             leaf cpu-usage {
               type uint8;
               units "percent";
               description
                 "Specifies the aggregated CPU usage in 
                   percentage.";
             }
             leaf cpu-freq {
               type uint64;
               units "MHz";
               description
                 "Specifies the frequency of CPU in MHz.";
             }
             leaf memory-usage {
               type uint64;
               units "MB";
               description
                 "Specifies the MB of memory usage.";
             }
             leaf memory-total {
               type uint64;
               units "MB";
               description
                 "Specifies the MB of total memory.";
             }
             leaf memory-available {
               type uint64;
               units "MB";
               description
                 "Specifies the MB of available memory.";
             }
             list disks {
               key disk-id;
               description
                 "Disk is the hardware to store information for a
                 long period, i.e., Hard Disk or Solid-State Drive.";
               leaf disk-id {
                 type string;
                 description
                   "The ID of the storage disk. It is a free form
                   identifier to identify the storage disk.";
               }
               leaf disk-usage {
                 type uint8;
                 units "percent";
                 description
                   "Specifies the percentage of disk usage.";
               }
               leaf disk-space-left {
                 type uint8;
                 units "percent";
                 description
                   "Specifies the available disk space left of
                    disk-id in percentage.";
               }
             }
             list interface {
               key interface-id;
               description
                 "The network interface for connecting a device
                  with the network.";
               leaf interface-id {
                 type string;
                 description
                   "The ID of the network interface. It is a free
                   form identifier to identify the network
                   interface.";
               }
               leaf in-traffic-rate {
                 type uint64;
                 units "pps";
                 description
                   "The total inbound traffic rate in packets
                   per second";
               }
               leaf out-traffic-rate {
                 type uint64;
                 units "pps";
                 description
                   "The total outbound traffic rate in packets
                   per second";
               }
               leaf in-traffic-throughput {
                 type uint64;
                 units "Bps";
                 description
                   "The total inbound traffic throughput in
                   bytes per second";
               }
               leaf out-traffic-throughput {
                 type uint64;
                 units "Bps";
                 description
                   "The total outbound traffic throughput in
                    bytes per second.";
               }
               leaf packet-loss-rate {
                      type uint64;
                      units "percent";
                      description
                        "The percentage of discarded packets.";
                  }
              }
          }
      }
    }
  }
  notification i2nsf-nsf-event {
    description
      "Notification for I2NSF NSF Event. This notification
      provides specific information that can only be
      provided by an NSF that supports additional features
      (e.g., DDoS attack detection).";
    uses common-monitoring-data;
    uses message;
    uses characteristics-extended;
    choice sub-event-type {
      description
      "This choice must be augmented with cases for
       each allowed sub-event. Only 1 sub-event will be
       instantiated in each container with all the
       sub-event fields.";
      case i2nsf-nsf-detection-module {
        container i2nsf-nsf-detection-module {
          description
            "This notification is sent, when a specific
              attack is detected.";
          list detection-module {
            key detection-module-name;
            description
            "The specific detection module.";
            leaf detection-module-name {
               type string;
               description
               "The name of the specific detection module.";
            }
            leaf time-stamp {
               type yang:date-and-time;
               description
               "Specify the time of a message being delivered.";
            }
            leaf response-time {
               type yang:date-and-time;
               description
               "The time taken for the detection.";
             }
             leaf start-time {
               type yang:date-and-time;
               description
               "The start time for the detection.";
             }
             leaf end-time {
               type yang:date-and-time;
               description
               "The end time for the detection.";
             }
             container detected-attacks {
               description
               "The information of detected attacks.";
               list attack-traffic{
                 key attack-id;
                 description
                 "The five-tuple (src/dst ip, port and protocol)
                 and attack type information of specific attack
                 traffic.";
                 leaf attack-id {
                   type string;
                   description
                   "The ID of the specific attack traffic which
                   has the same src/dst IP,protocol and attack
                   type.";
                 }
                 leaf attack-type {
                   type string;
                   description
                   "The type of the detected attack.";
                 }
                 leaf attack-src-ip {
                   type inet:ip-address-no-zone;
                   description
                     "The source IPv4 or IPv6 addresses of attack
                     traffic. ";
                 }
                 leaf attack-dst-ip {
                   type inet:ip-address-no-zone;
                   description
                     "The destination IPv4 or IPv6 addresses of
                     attack traffic. ";
                 }
                 leaf-list attack-src-port {
                   type inet:port-number;
                   description
                     "The transport-layer source ports of the
                       attack. It can hold multiple ports.";
                  }
                  leaf-list attack-dst-port {
                     type inet:port-number;
                     description
                         "The transport-layer destination
                          ports of the attack. It can hold multiple
                          ports.";
                   }
                   leaf protocol {
                     type identityref {
                        base protocol;
                      }
                      description
                         "The type of network protocol for the 
                           attack.";
                       }
                       uses attack-rates;
                   }
                }
             }
           }
         }
       }
     }
   }
