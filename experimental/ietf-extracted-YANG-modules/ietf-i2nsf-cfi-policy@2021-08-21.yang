module ietf-i2nsf-cfi-policy {
  yang-version 1.1;
  namespace
    "urn:ietf:params:xml:ns:yang:ietf-i2nsf-cfi-policy";
  prefix nsfcfi;

  import ietf-inet-types{
    prefix inet;
    reference "RFC 6991";
  }

  import ietf-yang-types{
    prefix yang;
    reference "RFC 6991";
  }

  organization
    "IETF I2NSF (Interface to Network Security Functions)
     Working Group";

  contact
    "WG Web: <http://tools.ietf.org/wg/i2nsf>
     WG List: <mailto:i2nsf@ietf.org>

     Editor: Jaehoon Paul Jeong
     <mailto:pauljeong@skku.edu>

     Editor: Patrick Lingga
     <mailto:patricklink@skku.edu>";

  description
    "This module is a YANG module for Consumer-Facing Interface.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  // RFC Ed.: replace XXXX with an actual RFC number and remove
  // this note.

  revision "2021-08-21"{
    description "Initial revision.";
    reference
      "RFC XXXX: I2NSF Consumer-Facing Interface YANG Data Model";

    // RFC Ed.: replace XXXX with an actual RFC number and remove
    // this note.
  }

  identity resolution-strategy {
    description
      "Base identity for resolution strategy";
    reference
      "draft-ietf-i2nsf-capability-data-model-17:
       I2NSF Capability YANG Data Model - Resolution Strategy";
  }

  identity fmr {
    base resolution-strategy;
    description
      "Identity for First Matching Rule (FMR)";
    reference
      "draft-ietf-i2nsf-capability-data-model-17:
       I2NSF Capability YANG Data Model - Resolution Strategy";
  }

  identity lmr {
    base resolution-strategy;
    description
      "Identity for Last Matching Rule (LMR)";
    reference
      "draft-ietf-i2nsf-capability-data-model-17:
       I2NSF Capability YANG Data Model - Resolution Strategy";
  }

  identity pmr {
    base resolution-strategy;
    description
      "Identity for Prioritized Matching Rule (PMR)";
    reference
      "draft-ietf-i2nsf-capability-data-model-17:
       I2NSF Capability YANG Data Model - Resolution Strategy";
  }

  identity pmre {
    base resolution-strategy;
    description
      "Identity for Prioritized Matching Rule
      with Errors (PMRE)";
    reference
      "draft-ietf-i2nsf-capability-data-model-17:
       I2NSF Capability YANG Data Model - Resolution Strategy";
  }

  identity pmrn {
    base resolution-strategy;
    description
      "Identity for Prioritized Matching Rule
      with No Errors (PMRN)";
    reference
      "draft-ietf-i2nsf-capability-data-model-17:
       I2NSF Capability YANG Data Model - Resolution Strategy";
  }

  identity security-event-type {
    description
      "Base identity for security event types.";
  }

  identity ddos {
    base security-event-type;
    description
      "Identity for DDoS event types.";
  }

  identity intrusion {
    base security-event-type;
    description
      "Identity for intrusion event types.";
  }

  identity web-attack {
    base security-event-type;
    description
      "Identity for web-attack event types.";
  }

  identity voip-volte {
    base security-event-type;
    description
      "Identity for VoIP/VoLTE event types.";
  }

  identity protocol {
    description
      "This identity represents the protocol types.";
  }

  identity layer-4-protocol {
    base protocol;
    description
      "Base identity for the Layer 4 (i.e., Transport Layer)
      Protocols";
  }

  identity tcp {
    base layer-4-protocol;
    description
      "Base identity for TCP condition capabilities";
    reference
      "RFC 793: Transmission Control Protocol
       draft-ietf-tcpm-rfc793bis: Transmission Control Protocol
       (TCP) Specification";
  }

  identity udp {
    base layer-4-protocol;
    description
      "Base identity for UDP condition capabilities";
    reference
      "RFC 768: User Datagram Protocol";
  }

  identity sctp {
    base layer-4-protocol;
    description
      "Identity for SCTP condition capabilities";
    reference
      "RFC 4960: Stream Control Transmission Protocol";
  }

  identity dccp {
    base layer-4-protocol;
    description
      "Identity for DCCP condition capabilities";
    reference
      "RFC 4340: Datagram Congestion Control Protocol";
  }

  identity layer-7-protocol {
    base protocol;
    description
      "Base identity for the Layer 7 (i.e., Application Layer)
       Protocols";
  }

  identity ftp {
    base layer-7-protocol;
    description
      "The identity for ftp protocol.";
    reference
      "RFC 959: File Transfer Protocol (FTP)";
  }

  identity ssh {
    base layer-7-protocol;
    description
      "The identity for ssh protocol.";
    reference
      "RFC 4250: The Secure Shell (SSH) Protocol";
  }

  identity telnet {
    base layer-7-protocol;
    description
      "The identity for telnet.";
    reference
      "RFC 854: Telnet Protocol";
  }

  identity smtp {
    base layer-7-protocol;
    description
      "The identity for smtp.";
    reference
      "RFC 5321: Simple Mail Transfer Protocol (SMTP)";
  }

  identity http {
    base layer-7-protocol;
    description
      "The identity for http.";
    reference
      "RFC7230: Hypertext Transfer Protocol (HTTP/1.1): Message
       Syntax and Routing
       RFC7231: Hypertext Transfer Protocol (HTTP/1.1): Semantics
       and Content";
  }

  identity https {
    base layer-7-protocol;
    description
      "The identity for https.";
    reference
      "RFC 2818: HTTP over TLS (HTTPS)";
  }

  identity pop3 {
    base layer-7-protocol;
    description
      "The identity for pop3.";
    reference
      "RFC 1939: Post Office Protocol - Version 3 (POP3)";
  }

  identity nat {
    base layer-7-protocol;
    description
      "The identity for nat.";
    reference
      "RFC 3022: Traditional IP Network Address Translator (Traditional
       NAT)";
  }

  identity action {
    description
      "Base identity for action";
  }

  identity ingress-action {
    base action;
    description
      "Base identity to represents the ingress actions, such as
       pass, drop, rate-limit, and mirror.";
  }

  identity egress-action {
    base action;
    description
      "Base identity represents the egress actions, such as
       pass, drop, rate-limit, mirror, invoke-signaling,
       tunnel-encapsulation, forwarding, and transformation.";
  }

  identity pass {
    base ingress-action;
    description
      "The identity for pass.";
  }

  identity drop {
    base ingress-action;
    description
      "The identity for drop.";
  }

  identity rate-limit {
    base ingress-action;
    description
      "The identity for rate-limit.";
  }

  identity mirror {
    base ingress-action;
    description
      "The identity for mirroring.";
  }

  identity invoke-signaling {
    base egress-action;
    description
      "Identity for invoke signaling action capability";
    reference
      "RFC 8329: Framework for Interface to Network Security
       Functions - Invoke-signaling action";
  }

  identity tunnel-encapsulation {
    base egress-action;
    description
      "Identity for tunnel encapsulation action capability";
    reference
      "RFC 8329: Framework for Interface to Network Security
       Functions - Tunnel Encapsulation";
  }

  identity forwarding {
    base egress-action;
    description
      "Identity for forwarding action capability";
    reference
      "RFC 8329: Framework for Interface to Network Security
       Functions - Forwarding action";
  }

  identity transformation {
    base egress-action;
    description
      "Identity for transformation action capability";
    reference
      "RFC 8329: Framework for Interface to Network Security
       Functions - Redirection action";
  }

  identity log-action {
    description
      "Base identity for representing log actions, such as rule-log and
      session-log action.";
  }

  identity rule-log {
    base log-action;
    description
      "Identity for rule log-action capability.
       Log the received packet based on the rule";
  }

  identity session-log {
    base log-action;
    description
      "Identity for session log-action capability.
       Log the received packet based on the session.";
  }

  identity signature-type {
    description
      "This represents the base identity for signature types.";
  }

  identity signature-yara {
    base signature-type;
    description
      "This represents the YARA signatures.";
    reference
      "YARA: YARA signatures are explained.";
  }

  identity signature-snort {
    base signature-type;
    description
      "This represents the SNORT signatures.";
    reference
      "SNORT: SNORT signatures are explained.";
  }

  identity signature-suricata {
    base signature-type;
    description
      "This represents the SURICATA signatures.";
    reference
      "SURICATA: SURICATA signatures are explained.";
  }

  identity threat-feed-type {
    description
      "This represents the base identity for threat-feed.";
  }

  identity day {
    description
      "This represents the base for days.";
  }

  identity monday {
    base day;
    description
      "This represents Monday.";
  }

  identity tuesday {
    base day;
    description
      "This represents Tuesday.";
  }

  identity wednesday {
    base day;
    description
      "This represents Wednesday.";
  }

  identity thursday {
    base day;
    description
      "This represents Thursday.";
  }

  identity friday {
    base day;
    description
      "This represents Friday.";
  }

  identity saturday {
    base day;
    description
      "This represents Saturday.";
  }

  identity sunday {
    base day;
    description
      "This represents Sunday.";
  }
  identity continent {
    description
      "Base Identity for continent types.";
  }

  identity africa {
    base continent;
    description
      "Identity for Africa.";
  }

  identity asia {
    base continent;
    description
      "Identity for Asia.";
  }

  identity europe {
    base continent;
    description
      "Identity for Europe.";
  }

  identity north-america {
    base continent;
    description
      "Identity for North America.";
  }

  identity south-america {
    base continent;
    description
      "Identity for South America.";
  }

  identity oceania {
    base continent;
    description
      "Identity for Oceania";
  }

 /*
  * Typedefs
  */
  typedef time {
    type string {
      pattern '(0[0-9]|1[0-9]|2[0-3]):[0-5][0-9]:[0-5][0-9](\.\d+)?'
        + '(Z|[\+\-]((1[0-3]|0[0-9]):([0-5][0-9])|14:00))?';
    }
    description
      "The time type represents an instance of time of zero-duration
       that recurs every day.";
  }

 /*
  * Groupings
  */

  grouping ipv4-list {
    description
      "Grouping for an IPv4 address list.";
    leaf-list ipv4 {
      type inet:ipv4-address;
      description
        "This is the entry for an IPv4 address list.";
    }
  }

  grouping ipv6-list {
    description
      "Grouping for an IPv6 address list.";
    leaf-list ipv6 {
      type inet:ipv6-address;
      description
        "This is the entry for an IPv6 address list.";
    }
  }

  grouping ipv4 {
    description
      "Grouping for an IPv4 address.";
    leaf ipv4 {
      type inet:ipv4-address;
      description
        "This is the entry for an IPv4 address.";
    }
  }

  grouping ipv6 {
    description
      "Grouping for an IPv6 address.";
    leaf ipv6 {
      type inet:ipv6-address;
      description
        "This is the entry for an IPv6 address.";
    }
  }

  grouping ip-address-info {
    description
      "There are two types to configure a security policy
       for an IP address, such as IPv4 adress and IPv6 address.";
    choice match-type {
      description
        "User can choose between IPv4 and IPv6.";
      case range-match-ipv4 {
        container range-ipv4-address {
          leaf start-ipv4-address {
            type inet:ipv4-address;
            mandatory true;
            description
              "A start IPv4 address for a range match.";
          }
          leaf end-ipv4-address {
            type inet:ipv4-address;
            mandatory true;
            description
              "An end IPv4 address for a range match.";
          }
          description
            "A range match for IPv4 addresses is provided.
             Note that the start IPv4 address must be lower than
             the end IPv4 address.";
        }
      }
      case range-match-ipv6 {
        container range-ipv6-address {
          leaf start-ipv6-address {
            type inet:ipv6-address;
            mandatory true;
            description
              "A start IPv6 address for a range match.";
          }
          leaf end-ipv6-address {
            type inet:ipv6-address;
            mandatory true;
            description
              "An end IPv6 address for a range match.";
          }
          description
            "A range match for IPv6 addresses is provided.
             Note that the start IPv6 address must be lower than
             the end IPv6 address.";
        }
      }
    }
  }

  grouping user-group {
    description
      "This group represents user group information such as name and
       ip-address.";
    leaf name {
      type string;
      description
        "This represents the name of a user-group.  A user-group name
         is used to map a user-group's name (e.g., employees) to IP
         address(es), MAC address(es).
         It is dependent on implementation.";
    }
    leaf-list mac-address {
      type yang:mac-address;
      description
        "Represent the MAC Address of a user-group. A user-group
         can have multiple MAC Addresses.";
    }
    uses ip-address-info{
      description
        "This represents the IP addresses of a user-group.";
      refine match-type{
        mandatory true;
      }
    }
  }

  grouping device-group {
    description
      "This group represents device group information such as
       ip-address protocol.";
    leaf name {
      type string;
      description
        "This represents the name of a device-group.";
    }
    uses ip-address-info{
      refine match-type{
        mandatory true;
      }
    }
    leaf-list application-protocol {
      type identityref {
        base layer-7-protocol;
      }
      description
        "This represents the application layer protocols of devices.
         If this is not set, it cannot support the appropriate
         protocol";
    }
  }

  grouping location-group {
    description
      "This group represents location-group information such as geo-ip
       and continent.";
    leaf name {
      type string;
      description
        "This represents the name of a location.";
    }
    list geo-ip-ipv4 {
      key "ipv4-address";
      description
        "This represents the list of IPv4 addresses based on a
         location.";
      leaf ipv4-address{
        type inet:ipv4-address;
        description
          "This represents an IPv4 geo-ip address of a location.";
      }
      leaf ipv4-prefix{
        type inet:ipv4-prefix;
        description
          "This represents the prefix for the IPv4 addresses.";
      }
    }
    list geo-ip-ipv6 {
      key "ipv6-address";
      description
        "This represents the list of IPv6 addresses based on a
         location.";
      leaf ipv6-address{
        type inet:ipv6-address;
        description
          "This represents an IPv6 geo-ip address of a location.";
      }
      leaf ipv6-prefix{
        type inet:ipv6-prefix;
        description
          "This represents the prefix for the IPv6 addresses.";
      }
    }
    leaf continent {
      type identityref {
        base continent;
      }
      default asia;
      description
        "location-group has geo-ip addresses of the corresponding
         continent.";
    }
  }

  grouping payload-string {
    description
      "The grouping for payload-string content.  It contains information
       such as name and string content.";
    leaf description {
      type string;
      description
        "This represents the description of a payload.  If this is not
         set, it cannot support the description of how the payload
         content is related to a security attack.";
    }
    leaf-list content {
      type string;
      description
        "This represents the string of the payload contents.
         This content leaf-list contains the payload of a packet to
         analyze a threat. Due to the types of threats, the type of
         the content is defined as a string to accommodate any kind
         of a payload type such as HTTP, HTTPS, and SIP.  If this is
         not set, it cannot support the payload contents involved in
         a security attack as a string.";
    }
  }

  list i2nsf-cfi-policy {
    key "policy-name";
    description
      "This is a security policy list.  Each policy in the list contains
       a list of security policy rules, and is a policy instance to have
       the information of where and when a policy needs to be applied.";
    leaf policy-name {
      type string;
      description
        "The name which identifies the policy.";
    }
    leaf resolution-strategy {
      type identityref {
        base resolution-strategy;
      }
      default fmr;
      description
        "The resolution strategies that can be used to
        specify how to resolve conflicts that occur between
        actions of the same or different policy rules that
        are matched and contained in this particular NSF";

      reference
        "draft-ietf-i2nsf-capability-data-model-17:
         I2NSF Capability YANG Data Model - Resolution strategy";
    }
    list rules {
      key "rule-name";

      description
        "There can be a single or multiple number of rules.";
      leaf rule-name {
        type string;
        description
          "This represents the name for a rule.";
      }

      leaf priority {
        type uint8 {
          range "1..255";
        }
        description
          "The priority keyword comes with a mandatory
           numeric value which can range from 1 through 255.
           Note that a higher number means a higher priority";
      }

      container event {
        description
          "This represents an event (i.e., a security event), for which
           a security rule is made.";
        leaf security-event {
          type identityref {
            base security-event-type;
          }
          description
            "This contains the description of a security event.  If this
             is not set, it cannot support what security event will be
             enforced.";
        }
        container time {
          description
            "The time when a security policy rule should be applied.";
          leaf start-date-time {
            type yang:date-and-time;
            description
              "This is the start date and time for a security policy
               rule.";
          }
          leaf end-date-time {
            type yang:date-and-time;
            description
              "This is the end date and time for a policy rule.  The
               policy rule will stop working after the specified
               end-date-time.";
          }
          container period{
            when
              "../frequency!='only-once'";
            description
              "This represents the repetition time.  In the case where
               the frequency is weekly, the days can be set.";
            leaf start-time {
              type time;
              description
                "This is a period's start time for an event.";
            }
            leaf end-time {
              type time;
              description
                "This is a period's end time for an event.";
            }
            leaf-list day {
              when
                "../../frequency='weekly'";
              type identityref{
                base day;
              }
              min-elements 1;
              description
                "This represents the repeated day of every week (e.g.,
                 Monday and Tuesday).  More than one day can be
                 specified.";
            }
            leaf-list date {
              when
                "../../frequency='monthly'";
              type int32{
                range "1..31";
              }
              min-elements 1;
              description
                "This represents the repeated date of every month.
                 More than one date can be specified.";
            }
            leaf-list month {
              when
                "../../frequency='yearly'";
              type string{
                pattern '\d{2}-\d{2}';
              }
              min-elements 1;
              description
                "This represents the repeated date and month of every
                 year.  More than one can be specified.  A pattern
                 used here is Month and Date (MM-DD).";
            }
          }

          leaf frequency {
            type enumeration {
              enum only-once {
                description
                  "This represents that the rule is immediately
                   enforced only once and not repeated. The policy
                   will continuously be active from the start-time
                   to the end-time.";
              }
              enum daily {
                description
                  "This represents that the rule is enforced on a
                   daily basis. The policy will be repeated daily
                   until the end-date.";
              }
              enum weekly {
                description
                  "This represents that the rule is enforced on a
                   weekly basis. The policy will be repeated weekly
                   until the end-date. The repeated days can be
                   specified.";
              }
              enum monthly {
                description
                  "This represents that the rule is enforced on a
                   monthly basis. The policy will be repeated monthly
                   until the end-date.";
              }
              enum yearly {
                description
                  "This represents that the rule is enforced on a
                   yearly basis.  The policy will be repeated yearly
                   until the end-date.";
              }
            }
            default only-once;
            description
              "This represents how frequently the rule should be
               enforced.";
          }
        }
      }

      container condition {
        description
        "Conditions for general security policies.";
        container firewall-condition {
          description
            "A general firewall condition based on the packet header.";
          leaf-list source {
            type union {
              type leafref {
                path
                  "/i2nsf-cfi-policy/endpoint-groups/user-group/name";
              }
              type leafref {
                path
                  "/i2nsf-cfi-policy/endpoint-groups/device-group/name";
              }
            }
            description
            "This describes the path of the source.";
          }

          leaf-list destination {
            type union {
              type leafref {
                path
                  "/i2nsf-cfi-policy/endpoint-groups/user-group/name";
              }
              type leafref {
                path
                  "/i2nsf-cfi-policy/endpoint-groups/device-group/name";
              }
            }
            description
              "This describes the path to the destinations.";
          }

          leaf transport-layer-protocol {
            type identityref {
              base layer-4-protocol;
            }
            description
              "The transport-layer protocol to be matched.";
          }

          container range-port-number {
            leaf start-port-number {
              type inet:port-number;
              description
                "A start port number for range match.";
            }
            leaf end-port-number {
              type inet:port-number;
              description
                "An end port number for range match.";
            }
            description
              "A range match for transport-layer port number. Note that
               the start port number value must be lower than the end
               port  number value";
          }

          list icmp {
            key "version";
            description
               "Represents the ICMP packet header information to
                determine if the set of policy actions in this ECA
                policy rule should be executed or not.";
             reference
               "RFC  792: Internet Control Message Protocol
                RFC 8335: PROBE: A Utility for Probing Interfaces";

            leaf version {
              type enumeration {
                enum icmpv4 {
                  value "1";
                  description
                    "The ICMPv4 Protocol as defined in RFC 792";
                }
                enum icmpv6 {
                  value "2";
                  description
                    "The ICMPv6 Protocol as defined in RFC 4443";
                }
              }
              description
                "The ICMP version to be matched. This value
                 affected the type and code values.";
              reference
                "RFC  792: Internet Control Message Protocol
                 RFC 4443: Internet Control Message Protocol (ICMPv6)
                 for the Internet Protocol Version 6 (IPv6)
                 Specification";
            }

            leaf-list type {
              type uint8;
              description
                "The security policy rule according to
                 ICMP type parameter.";
              reference
                "RFC  792: Internet Control Message Protocol
                 RFC 8335: PROBE: A Utility for Probing Interfaces
                 IANA: Internet Control Message Protocol (ICMP)
                 Parameters
                 IANA: Internet Control Message Protocol version 6
                 (ICMPv6) Parameters";
            }

            leaf-list code {
              type uint8;
              description
                "The security policy rule according to
                 ICMP code parameter.";
              reference
                "RFC  792: Internet Control Message Protocol
                 RFC 8335: PROBE: A Utility for Probing Interfaces
                 IANA: Internet Control Message Protocol (ICMP)
                 Parameters
                 IANA: Internet Control Message Protocol version 6
                 (ICMPv6) Parameters";
            }
          }
        }

        container ddos-condition {
          description
            "A condition for a DDoS attack.";
          container rate-limit {
            description
              "This describes the rate-limit.";
            leaf packet-rate-threshold {
              type uint32;

              description
                "This is a trigger value for a rate limit of packet rate
                 for a DDoS-attack mitigation.";
            }
            leaf byte-rate-threshold {
              type uint32;
              description
                "This is a trigger value for a rate limit of byte rate
                 for a  DDoS-attack mitigation.";
            }
            leaf flow-rate-threshold {
              type uint32;
              description
                "This is a trigger value for a rate limit of flow rate
                 for a DDoS-attack mitigation.";
            }
          }
        }

        container anti-virus-condition {
          description
           "A condition for anti-virus";

          leaf-list exception-files {
            type string;
            description
              "The type or name of the files to be excluded by the
               anti-virus. This can be used to keep the known harmless
               files.";
          }
        }

        container payload-condition {
          description
            "A condition based on a packet's content.";
          leaf-list content {
            type leafref {
              path "/i2nsf-cfi-policy/threat-preventions/"
                 + "payload-content/name";
            }
            description
              "This describes the paths to a packet content's";
          }
        }

        container url-condition {
          description
            "Condition for url category";
          leaf url-name {
            type leafref {
              path "/i2nsf-cfi-policy/endpoint-groups/url-group/name";
            }
            description
              "This is description for the condition of a URL's
               category such as SNS sites, game sites, ecommerce
               sites, company sites, and university sites.";
          }
        }

        container voice-condition {
          description
            "For the VoIP/VoLTE security system, a VoIP/
             VoLTE security system can monitor each
             VoIP/VoLTE flow and manage VoIP/VoLTE
             security rules controlled by a centralized
             server for VoIP/VoLTE security service
             (called VoIP IPS). The VoIP/VoLTE security
             system controls each switch for the
             VoIP/VoLTE call flow management by
             manipulating the rules that can be added,
             deleted, or modified dynamically.";
          reference
            "RFC 3261: SIP: Session Initiation Protocol";

          leaf-list source-id {
            type string;
            description
              "The security policy rule according to
               a source voice ID for VoIP and VoLTE.";
          }

          leaf-list destination-id {
            type string;
            description
              "The security policy rule according to
               a destination voice ID for VoIP and VoLTE.";
          }

          leaf-list user-agent {
            type string;
            description
              "The security policy rule according to
               an user agent for VoIP and VoLTE.";
          }
        }

        container context-condition {
          description
            "Condition for matching the context of the packet, such as
             geographic location, time, packet direction";
          container geography-location-condition {
            description
              "A condition for a location-based connection";
            leaf-list source {
              type leafref {
                path "/i2nsf-cfi-policy/endpoint-groups/"
                   + "location-group/name";
              }
              description
                "This describes the paths to a location's sources.";
            }
            leaf-list destination {
              type leafref {
                path "/i2nsf-cfi-policy/endpoint-groups/"
                   + "location-group/name";
              }
              description
                "This describes the paths to a location's
                 destinations.";
            }
          }
        }

        container threat-feed-condition {
          description
            "A condition based on the threat-feed information.";
          leaf-list name {
            type leafref {
              path
                "/i2nsf-cfi-policy/threat-preventions/"
               +"threat-feed-list/name";
            }
            description
              "This describes the paths to a threat-feed's sources.";
          }
        }
      }

      container actions {
        description
          "This is the action container.";
        container primary-action {
          description
            "This represent primary actions (e.g., ingress and egress
             action) to be applied to a condition.
             If this is not set, it cannot support the primary
             actions.";
          leaf action {
            type identityref {
              base action;
            }
            description
              "Ingress Action: pass, drop, reject, rate-limit,
               and mirror.
               Egress action: mirror, invoke-signaling,
               tunnel-encapsulation, forwarding, and redirection.";
          }
        }
        container secondary-action {
          description
            "This represents secondary actions (e.g., log and syslog)
             to be applied if they are needed.  If this is not set,
             it cannot support the secondary actions.";
          leaf log-action {
            type identityref {
              base log-action;
            }
            description
              "Log action: rule log and session log";
          }
        }
      }
    }

    container endpoint-groups {
      description
        "A logical entity in a business environment, where a security
         policy is to be applied.";
      list user-group{
        uses user-group;
        key "name";
        description
          "This represents a user group.";
      }
      list device-group {
        key "name";
        uses device-group;
        description
          "This represents a device group.";
      }
      list location-group{
        key "name";
        uses location-group;
        description
          "This represents a location group.";
      }
      list url-group {
        key "name";
        description
          "This describes the list of URL.";
        leaf name {
          type string;
          description
            "This is the name of URL group, e.g., SNS sites,
             gaming sites, ecommerce sites";
        }
        leaf-list url {
          type string;
          description
            "Specifies the URL to be added into the group.";
        }
      }
    }

    container threat-preventions {
      description
        "This describes the list of threat-preventions.";
      list threat-feed-list {
        key "name";
        description
          "There can be a single or multiple number of threat-feeds.";
        leaf name {
          type string;
          description
            "This represents the name of the threat-feed.";
        }
        leaf description {
          type string;
          description
            "This represents the descriptions of a threat-feed.  The
             description should include information, such as type,
             threat, method, and file type.  Structured Threat
             Information Expression (STIX) can be used for description
             of a threat [STIX].";
        }
        leaf-list signatures {
          type identityref {
            base signature-type;
          }
          description
            "This contains a list of signatures or hashes of the
             threats.";
        }
      }
      list payload-content {
        key "name";
        leaf name {
          type string;
          description
            "This represents the name of a packet's payload-content. It
             should give an idea of why a specific payload content is
             marked as a threat.  For example, the name 'backdoor'
             indicates the payload content is related to a backdoor
             attack.";
        }
        description
          "This represents a payload-string group.";
        uses payload-string;
      }
    }
  }
}
