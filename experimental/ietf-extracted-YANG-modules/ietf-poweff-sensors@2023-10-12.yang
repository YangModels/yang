module ietf-poweff-sensors {
  yang-version 1.1;
  namespace "urn:ietf:params:xml:ns:yang:ietf-poweff-sensors";
  prefix ietf-poweff-sensors;

  import ietf-poweff-types {
    prefix ietf-poweff-types;
  }

  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
     Editor:  Marisol Palmero
              <mailto:mpalmero@cisco.com>";
  description
    "This YANG module defines basic groupings for POWEFF sensor
    management.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2023-10-12 {
    description
      "Initial revision of POWEFF sensors";
    reference
      "RFC XXXX: ...";
  }

  grouping sensors-g {
    description "sensors grouping";
    container sensors {
      description "list of sensors";

      list sensor {
        key "sensor-type";
        description "list of sensors attached to this asset";
        leaf sensor-type {
          type identityref {
            base ietf-poweff-types:sensor-type;
          }
          // FIXME: Are we fine with a single sensor of each type
          // for each asset? I.e. is there ever a need for more than
          // one Vin-sensor on a particular asset? Ever more than one
          // Temp-sensor? If so, we need to add a second key here.
          description
            "Type of sensor sending data per asset:
            Vin, Iin, Vout, Iout, Pin, Pout, Palloc, Temp, etc.
            Sensor type specifies which unit of measurement is used.";
        }
        leaf sensor-location {
          type string;
          mandatory "true";
          description
            "Indicates the current location where the sensor is located
              in the chassis,typically refers to slot";
        }
        leaf sensor-state {
          type string;
          description
            "Current state of the sensor";
            // FIXME: What does this mean?
        }
        leaf sensor-current-reading {
          type string;
          config false;
          description
            "Current reading of the sensor";
        }
        leaf sensor-accuracy-eligible {
          type boolean;
          default false;
          description
            "Used to identify which sensor/assets reading shall be
            included in real metrics";
          }
        leaf sensor-accuracy {
          type string;
          must "../sensor-accuracy-eligible = 'true'";
          description
            "Maximum deviation to be considered. This attribute mainly
            will apply to drawn power, which corresponds to PSU PowerIn
            measured power or calculated power; assuming discrepancy
            between Real Power, power collected from a power meter, and
            power measured or calculated from the metrics provided by
            the sensors";
          }

        container sensor-thresholds {
          description
            "Threshold values for the particular sensor.
            Default values shall beprovided as part of static data
            but when configurable need to be pulledfrom the device.
            Ideally, the sensor should allow configuing
            thesethreshold values";

          leaf minor-low {
            type string;
            description
              "minor-low";
          }
          leaf minor-high {
            type string;
            description
              "minor-high";
          }
          leaf major-low {
            type string;
            description
              "major-low";
          }
          leaf major-high {
            type string;
            description
              "major-high";
          }
          leaf critical-low {
            type string;
            description
              "critical-low";
          }
          leaf critical-high {
            type string;
            description
              "critical-high";
          }
          leaf shutdown {
            type string;
            description
              "shutdown";
          }
        }
      }
    }
  }

  grouping power-derived-g {
    description
      "define derived metrics";
    container power-derived {
      config false;
      description "power derived attributes";

      leaf heat-dissipation {
        type string;
        description
          "It refers to Heat Transfer, i.e. heat transferred from
          hotter object to coolerobject (1W = 3.412BTU/h)";
      }
      leaf rated-input-pwr-value {
        type string;
        mandatory "true";
        description
          "Total Input Power for the chassis and specific inventory
          inside. The sum for all assets for specific hardware
          configuration. Can be calculated for Typical, Operating, or
          Maximum anticipated Capacity Load. Mainly used for
          dimensioning based on benchmark data";
      }
      leaf asset-input-pwr {
        type string;
        mandatory "true";
        description
          "For a given asset, assumed input power means the rate of
          electricity consumption in Watts provided by the network
          device or sensor. Conditionally derived - if
          the device/sensor can give actualpower draw then this
          calculation is not required, and will be taken directly
          from the sensor.";
      }
      leaf asset-output-pwr {
        type string;
        description
          "Watts provided to the internal components for a given
          asset. Only applicable to assets that provide output power,
          such as PSUs. This is present here to accommodate chassis
          that donât provide Watt value currently. Ideal
          implementation should provide Pout sensor reading";
          //FIXME: add condition this is mandatory for when asset is
          //chassis or PSU and not LC or Port;
      }
      leaf  psu-input-power {
        type string;
        mandatory "true";
        description
          "Total input power per chassis, rate of the electricity
          consumption in Watts. Sum of asset-input-pwr when uid=PSU.
          It considers all operational PSU'Ìs to the chassis";
      }
      leaf psu-output-power {
        type string;
        mandatory "true";
        description
          "Total input power for chassis, rate of the electricity
          consumption inWatts. Sum of asset-output-pwr when uid=PSU.
          It considers alloperational PSU's to the chassis";
      }
      leaf psu-pwr-ratio {
        type string;
        mandatory "true";
        description
          "Define dynamic (current) power ratio taking into
          consideration total system real power input vs used. Not
          expected to be the same as PSU efficiency. Formula:
          (psu-output-power / psu-input-power) * 100.0.
          It considers all operational PSU Ìs to the chassis.";
      }
      leaf energy-traffic-ratio {
        type string;
        mandatory "true";
        description
          "How much Watts is spent to move 100Gigaytes per
          chassis within thetime period; Formula:
          psu-output-power [Watt] /SUM of all interfaces
          (input-data-rate-bits + output-data-rate-bits).
          Measured over a period of 1hr. energy-traffic-ratio is
          the value considered for the complete chassis and all
          operational LC Ìs/interfaces.";
      }
    }
  }

  grouping power-static-g {
    description
      "define static attributes";
    container power-static {
      description "power static attributes";

      leaf max-amp {
        type string;
        mandatory "true";
        description
          "For a given asset, it is the current in Amperes that the
          asset could withdraw at Maximum capacity";
      }
      leaf output-amp {
        type string;
        mandatory "true";
        description
          "For a given asset, it is the current in Amperes that the
          asset couldwithdraw at Operating capacity.";
      }
      leaf input-amp {
        type string;
        mandatory "true";
        description
          "Current of an asset at a typical power consumption of
          switch in Amperes. Somethimes refered to as input-current";
      }
      leaf  max-output-pwr {
        type string;
        mandatory "true";
        description
          "For a given asset, it is the maximum power in Watts that
          the asset could draw at Maximum capacity";
      }
      leaf  output-pwr {
        type string;
        mandatory "true";
        description
          "For a given asset, it is the power in Watts that the
          asset could withdraw at Operating capacity";
      }
      leaf typical-output-pwr {
        type string;
        mandatory "true";
        description
          "This value is an estimation of the average power usage
          in Watts that the same configuration will use at Typical
          capacity";
      }
      leaf accuracy-pwr {
        type string;
        description
          "If known, the maximum deviation of power to be considered.
          BU shouldprovide an estimation";
      }
      leaf inline-pwr {
        type string;
        mandatory "true";
        description
          "Available PoE Power i.e the power which can be passed over
          ethernet cables to power devices.";
      }
      leaf psu-efficiency {
        type string;
        mandatory "true";
        description
          "Rating the PSU has been certified for against 80plus
          certification specification. The amount of the actual power
          delivered to the assetdivided by the electrical power drawn
          from the main supply socket.i.e. Output Power of System/
          Input Power of PSU. The objective for psu-efficiency values
          is to reach 80+ certification.
          Please refer to https://www.clearesult.com/80plus";
      }
      leaf voltage-type {
        type string;
        mandatory "true";
        description
          "AC/DC/HVDC. Note: DC typically gives an accurate measure,
          but AC, due to the nature of the metric is not accurate";
      }
      leaf idle-pwr {
        type string;
        mandatory "true";
        description
          "Initial power allocated to the asset with no traffic load";
      }
      leaf max-temperature {
        type string;
        mandatory "true";
        description
          "Operating temperature - i.e max temperature tolerance
          (temperaturerange expands to approximately -40Â°C to 85Â°C).
          If the asset exceeds themax temperature limit, it either
          slows down or stops completely";
      }
      leaf pwr-saving-mode {
        type string;
        mandatory "true";
        description
          "Does the asset support any power-saving software feature Y/N.
          Will beexpanded in future releases";
      }
    }
  }
}
