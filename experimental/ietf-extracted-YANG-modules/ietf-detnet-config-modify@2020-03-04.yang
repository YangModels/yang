module ietf-detnet-config-modify {
  namespace "urn:ietf:params:xml:ns:yang:ietf-detnet-config";
  prefix "ietf-detnet";

  import ietf-yang-types {
    prefix "yang";
  }

  import ietf-inet-types{
    prefix "inet";
  }

  import ietf-ethertypes {
    prefix "eth";
  }

  import ietf-routing-types {
    prefix "rt-types";
  }

  import ietf-routing {
    prefix "rt";
  }

  import ietf-packet-fields {
    prefix "packet-fields";
  }
  import ietf-interfaces {
    prefix "if";
  }

  organization "IETF DetNet Working Group";

  contact
    "WG Web:   <http://tools.ietf.org/wg/detnet/>
     WG List:  <mailto: detnet@ietf.org>
     WG Chair: Lou Berger
                 <mailto:lberger@labn.net>

                 Janos Farkas
                 <mailto:janos.farkas@ericsson.com>

     Editor:   Xuesong Geng
                <mailto:gengxuesong@huawei.com>

     Editor:   Mach Chen
                <mailto:mach.chen@huawei.com>

     Editor:   Zhenqiang Li
                <mailto:lizhenqiang@chinamobile.com>

     Editor:   Reshad Rahman
                <mailto:rrahman@cisco.com>

     Editor:   Yeoncheol Ryoo
                <mailto:dbduscjf@etri.re.kr>";

  description
    "This YANG module describes the parameters needed
     for DetNet flow configuration and flow status
  reporting";

  revision 2020-03-04 {
    description "initial revision";
    reference "RFC XXXX: draft-ietf-detnet-yang-02";
  }

  typedef app-flow-ref {
    type leafref {
      path "/ietf-detnet:app-flows"
         + "/ietf-detnet:app-flow"
         + "/ietf-detnet:name";
    }
  }

  typedef service-sub-layer-ref {
    type leafref {
      path "/ietf-detnet:service-sub-layer"
         + "/ietf-detnet:service-sub-layer-list"
         + "/ietf-detnet:name";
    }
  }

  typedef forwarding-sub-layer-ref {
    type leafref {
      path "/ietf-detnet:forwarding-sub-layer"
         + "/ietf-detnet:forwarding-sub-layer-list"
         + "/ietf-detnet:name";
    }
  }

  typedef sub-network-ref {
    type leafref {
      path "/ietf-detnet:sub-network"
         + "/ietf-detnet:sub-network-list"
         + "/ietf-detnet:name";
    }
  }

  typedef ipsec-spi {
    type uint32 {
      range "1..max";
    }
    description
      "SPI";
  }

  typedef service-operation-type {
    type enumeration {
      enum service-initiation {
        description
          "Operation for DetNet service sub-layer encapsulation";
      }
      enum service-termination {
        description
          "Operation for DetNet service sub-layer decapsulation";
      }
      enum service-relay {
        description
          "Operation for DetNet service sub-layer swap";
      }
      enum non-detnet {
        description
          "No operation for DetNet service sub-layer";
      }
    }
  }

  typedef forwarding-operations-type {
    type enumeration {
      enum forward {
        description
          "Operation forward to next-hop";
      }
      enum impose-and-forward {
        description
          "Operation impose outgoing label(s) and forward to
           next-hop";
      }
      enum pop-and-forward {
        description
          "Operation pop incoming label and forward to next-hop";
      }
      enum pop-impose-and-forward {
        description
          "Operation pop incoming label, impose one or more
           outgoing label(s) and forward to next-hop";
      }
      enum swap-and-forward {
        description
          "Operation swap incoming label, with outgoing label and
           forward to next-hop";
      }
      enum pop-and-lookup {
        description
          "Operation pop incoming label and perform a lookup";
      }
    }
    description "MPLS operations types";
  }

  typedef service-protection-type {
    type enumeration {
      enum none {
        description
          "no service protection provide";
      }
      enum replication {
        description
          "A Packet Replication Function (PRF) replicates
           DetNet flow packets and forwards them to one or
           more next hops in the DetNet domain.  The number
           of packet copies sent to each next hop is a
           DetNet flow specific parameter at the node doing
           the replication.  PRF can be implemented by an
           edge node, a relay node, or an end system";
      }
      enum elimination {
        description
          "A Packet Elimination Function (PEF) eliminates
           duplicate copies of packets to prevent excess
           packets flooding the network or duplicate
           packets being sent out of the DetNet domain.
           PEF can be implemented by an edge node, a relay
           node, or an end system.";
      }
      enum ordering {
        description
          "A Packet Ordering Function (POF) re-orders
           packets within a DetNet flow that are received
           out of order.  This function can be implemented
           by an edge node, a relay node, or an end system.";
      }
      enum elimination-ordering {
        description
          "A combination of PEF and POF that can be
           implemented by an edge node, a relay node, or
           an end system.";
      }
      enum elimination-replication {
        description
          "A combination of PEF and PRF that can be
           implemented by an edge node, a relay node, or
           an end system";
      }
      enum elimination-ordering-replicaiton {
        description
          "A combination of PEF, POF and PRF that can be
           implemented by an edge node, a relay node, or
           an end system";
      }
    }
  }

  typedef sequence-number-generation-type {
    type enumeration {
      enum copy-from-app-flow {
        description
          "Copy the app-flow sequence number to the DetNet-flow";
      }
      enum generate-by-detnet-flow {
        description
          "Generate the sequence number by DetNet flow";
      }
    }
  }

  typedef sequence-number-field {
    type enumeration {
      enum zero-sn {
        description "there is no DetNet sequence number field.";
      }
      enum short-sn {
        description "there is 16bit DetNet sequence number field";
        value 16;
      }
      enum long-sn {
        description "there is 28bit DetNet sequence number field";
        value 28;
      }
    }
  }

  grouping ip-header {
    description
      "The IPv4/IPv6 packet header information";
    leaf src-ip-address {
      type inet:ip-address;
      description
        "The source IP address of the header";
    }
    leaf dest-ip-address {
      type inet:ip-address;
      description
        "The destination IP address of the header";
    }
    leaf next-header {
      type uint8;
      description
        "The next header of the IPv6 header";
    }
    leaf traffic-class {
      type uint8;
      description
        "The traffic class value of the header";
    }
    leaf flow-label {
      type inet:ipv6-flow-label;
      description
        "The flow label value of the header";
    }
    leaf source-port {
      type inet:port-number;
      description
      "The source port number";
    }
    leaf destination-port {
      type inet:port-number;
      description
      "The destination port number";
    }
  }

  grouping l2-header {
    description
      "The Ethernet or TSN packet header information";
    leaf source-mac-address {
      type yang:mac-address;
      description
        "The source MAC address value of the ethernet header";
    }
    leaf destination-mac-address {
      type yang:mac-address;
      description
        "The destination MAC address value of the ethernet header";
    }
    leaf ethertype {
      type eth:ethertype;
      description
        "The ethernet packet type value of the ethernet header";
    }
    leaf vlan-id {
      type uint16;
      description
        "The Vlan value of the ethernet header";
    }
    leaf pcp {
      type uint8;
      description
        "The priority value of the ethernet header";
    }
  }
  grouping destination-ip-port-identification {
    description
    "The TCP/UDP port(source/destination) identification information";
      container destination-port {
      uses packet-fields:port-range-or-operator;
      }
  }

  grouping source-ip-port-identification {
    description
    "The TCP/UDP port(source/destination) identification information";
      container source-port {
      uses packet-fields:port-range-or-operator;
      }
  }

  grouping ip-flow-identification {
    description
    "The IPv4/IPv6 packet header identification information";
    leaf src-ip-prefix {
      type inet:ip-prefix;
      description
      "The source IP address of the header";
    }
    leaf dest-ip-prefix {
      type inet:ip-prefix;
      description
      "The destination IP address of the header";
    }
    leaf next-header {
      type uint8;
      description
      "The next header of the IPv6 header";
    }
    leaf traffic-class {
      type uint8;
      description
      "The traffic class value of the header";
    }
    leaf flow-label {
      type inet:ipv6-flow-label;
      description
      "The flow label value of the header";
    }
      uses source-ip-port-identification;
      uses destination-ip-port-identification;
    leaf ipsec-spi {
      type ipsec-spi;
      description "Security parameter index of SA entry";
    }
  }

  grouping mpls-flow-identification {
    description
    "The MPLS packet header identification information";
    choice label-space {
      description "";
      case context-label-space {
        uses rt-types:mpls-label-stack;
      }
      case platform-label-space {
        leaf label {
          type rt-types:mpls-label;
        }
      }
    }
  }

  grouping traffic-specification {
    container traffic-specification {
    description
      "traffic-specification specifies how the Source
       transmits packets for the flow.  This is the
       promise/request of the Source to the network.
       The network uses this traffic specification
       to allocate resources and adjust queue
       parameters in network nodes.";
    reference
      "draft-ietf-detnet-flow-information-model";
    leaf interval {
      type uint32;
        description
          "The period of time in which the traffic
           specification cannot be exceeded";
    }
    leaf max-packets-per-interval{
      type uint32;
      description
        "The maximum number of packets that the
         source will transmit in one Interval.";
    }
    leaf max-payload-size{
      type uint32;
      description
        "The maximum payload size that the source
         will transmit.";
    }
    leaf average-packets-per-interval {
      type uint32;
      description
        "The average number of packets that the
         source will transmit in one Interval";
    }
    leaf average-payload-size {
      type uint32;
      description
        "The average payload size that the
         source will transmit.";
    }
    }
  }

  grouping traffic-requirements {
    container traffic-requirements {
      description
        "FlowRequirements: defines the attributes of the App-flow
        regarding bandwidth, latency, latency variation, loss, and
        misordering tolerance.";
      leaf min-bandwidth {
        type uint64;
        description
          "MinBandwidth is the minimum bandwidth that has to be
          guaranteed for the DetNet service.  MinBandwidth is
          specified in octets per second.";
      }
      leaf max-latency {
        type uint32;
        description
          "MaxLatency is the maximum latency from Ingress to Egress(es)
          for a single packet of the DetNet flow.  MaxLatency is
          specified as an integer number of nanoseconds";
      }
      leaf max-latency-variation {
        type uint32;
        description
          "MaxLatencyVariation is the difference between the minimum and
          the maximum end-to-end one-way latency.  MaxLatencyVariation
          is specified as an integer number of nanoseconds.";
      }
      leaf max-loss {
        type uint8;
        description
          "MaxLoss defines the maximum Packet Loss Ratio (PLR) parameter
          for the DetNet service between the Ingress and Egress(es) of
          the DetNet domain.";
      }
      leaf max-consecutive-loss-tolerance {
        type uint32;
        description
          "Some applications have special loss requirement, such as
          MaxConsecutiveLossTolerance.  The maximum consecutive loss
          tolerance parameter describes the maximum number of
          consecutive packets whose loss can be tolerated.  The maximum
          consecutive loss tolerance can be measured for example based
          on sequence number";
      }
      leaf max-misordering {
        type uint32;
        description
          "MaxMisordering describes the tolerable maximum number of
          packets that can be received out of order.  The maximum
          allowed misordering can be measured for example based on
          sequence number.  The value zero for the maximum allowed
          misordering indicates that in order delivery is required,
          misordering cannot be tolerated.";
      }
      }
  }

  grouping data-flow-spec {
    description "app-flow identification";
    choice data-flow-type {
      case tsn-app-flow {
        uses l2-header;
      }
      case ip-app-flow {
        uses ip-flow-identification;
      }
      case mpls-app-flow {
        uses mpls-flow-identification;
      }
    }
  }
  grouping detnet-flow-spec {
    description "detnet-flow identificatioin";
    choice detnet-flow-type {
      case ip-detnet-flow {
        uses ip-flow-identification;
      }
      case mpls-detnet-flow {
        uses mpls-flow-identification;
      }
    }
  }

  grouping app-flows-ref {
    description "incoming or outgoing app-flow reference group";
    leaf-list app-flow {
      type app-flow-ref;
      description "List of ingress or egress app-flows";
    }
  }

  grouping service-sub-layer-ref {
    description "incoming or outgoing service sub-layer reference group";
    leaf-list service-sub-layer {
      type service-sub-layer-ref;
      description
      "List of incoming or outgoing service sub-layer
       that has to aggregate or disaggregate";
    }
  }

  grouping forwarding-sub-layer-ref {
    description "incoming or outgoing forwarding sub-layer reference group";
    leaf-list forwarding-sub-layer {
      type forwarding-sub-layer-ref;
      description
      "List of incoming or outgoing forwarding sub-layer
       that has to aggregate or disaggregate";
    }
  }

  grouping detnet-header {
    description "DetNet header info for DetNet encapsulation or swap";
    choice header-type {
      case detnet-mpls-header {
        description
        "MPLS label stack for DetNet MPLS encapsulation or forwarding";
        uses rt-types:mpls-label-stack;
      }
      case detnet-ip-header {
        description
        "IPv4/IPv6 packet header for DetNet IP encapsulation";
        uses ip-header;
      }
    }
  }

  grouping detnet-app-next-hop-content {
    description
      "Generic parameters of DetNet next hops.";
    choice next-hop-options {
      mandatory true;
      description
        "Options for next hops.
         It is expected that further cases will be added through
         augments from other modules, e.g., for recursive
         next hops.";
      case simple-next-hop {
        description
          "This case represents a simple next hop consisting of the
           next-hop address and/or outgoing interface.
           Modules for address families MUST augment this case with a
           leaf containing a next-hop address of that address
           family.";
        container mpls-header {
          description
          "MPLS label stack for DetNet MPLS encapsulation or forwarding";
          uses rt-types:mpls-label-stack;
        }
        leaf outgoing-interface {
          type if:interface-ref;
        }
      }
      case next-hop-list {
        container next-hop-list {
          description
            "Container for multiple next hops.";
          list next-hop {
            key "hop-index";
            description
              "An entry in a next-hop list.

               Modules for address families MUST augment this list
               with a leaf containing a next-hop address of that
               address family.";
            leaf hop-index {
              type uint8;
              description "";
            }
            container mpls-header {
              description
              "MPLS label stack for DetNet MPLS encapsulation or forwarding";
              uses rt-types:mpls-label-stack;
            }
            leaf outgoing-interface {
              type if:interface-ref;
            }
          }
        }
      }
    }
  }

  grouping detnet-forwarding-next-hop-content {
    description
      "Generic parameters of DetNet next hops.";
    choice next-hop-options {
      mandatory true;
      description
        "Options for next hops.
         It is expected that further cases will be added through
         augments from other modules, e.g., for recursive
         next hops.";
      case simple-next-hop {
        description
          "This case represents a simple next hop consisting of the
           next-hop address and/or outgoing interface.
           Modules for address families MUST augment this case with a
           leaf containing a next-hop address of that address
           family.";
        uses detnet-header;
        leaf outgoing-interface {
          type if:interface-ref;
        }
      }
      case next-hop-list {
        container next-hop-list {
          description
            "Container for multiple next hops.";
          list next-hop {
            key "hop-index";
            description
              "An entry in a next-hop list.

               Modules for address families MUST augment this list
               with a leaf containing a next-hop address of that
               address family.";
            leaf hop-index {
              type uint8;
              description "";
            }
            uses detnet-header;
            leaf outgoing-interface {
              type if:interface-ref;
            }
          }
        }
      }
    }
  }

  container app-flows {
    description
    "The DetNet app-flow configuration";
    list app-flow {
      key "name";
      description "";
      leaf name {
        type "string";
        description "The name to identify the DetNet app-flow";
      }
      leaf app-id {
        type uint16;
        config false;
        description
          "The DetNet Application ID";
      }
      leaf app-flow-bidir-congruent {
        type boolean;
        description
        "Defines the data path requirement of the App-flow whether
         it must share the same data path and physical path
         for both directions through the network,
         e.g., to provide congruent paths in the two directions.";
      }
      uses traffic-requirements;
      uses traffic-specification;
      container in-segment {
        description "app-flow identification";
        leaf interface {
          type if:interface-ref;
          description "";
        }
        uses data-flow-spec;
      }
      container out-segment {
        description
        "ingress proxy that incoming app-flow map to detnet-flow
         and egress proxy that next-hop for outging app-flow";
        choice outgoing-options {
          mandatory true;
          description
           "";
          case ingress-proxy {
            leaf service-sub-layer {
              type service-sub-layer-ref;
            }
          }
          case egress {
            uses detnet-app-next-hop-content;
          }
        }
      }
    }
  }
  container service-sub-layer {
    description "The DetNet service sub-layer configuration";
    list service-sub-layer-list {
      key "name";
      description "";
      leaf name {
        type string;
        description "The name of the DetNet service sub-layer";
      }
      leaf service-id {
        type uint16;
        config false;
        description
          "The DetNet service ID";
      }
      leaf service-rank {
        type uint8;
        description
          "The DetNet rank for this service";
      }
      uses traffic-requirements;
      uses traffic-specification;
      container service-protection {
        leaf service-protection-type {
          type service-protection-type;
          description
          "The DetNet service protection type
           such as PRF, PEF, PEOF,PERF, and PEORF";
        }
        leaf sequence-number-length {
          type sequence-number-field;
          description
          "sequence number filed can choice 0 bit, 16bit, 28 bit filed";
        }
      }
      leaf service-operation-type {
        type service-operation-type;
      }
      container in-segment {
        description
        "The DetNet service sub-layer inbound configuration.
         This should not be used if this service operation is initiation";
        choice incoming-options {
          mandatory true;
          description
           "";
          case ingress-proxy {
            uses app-flows-ref;
          }
          case detnet-service-identification {
            uses detnet-flow-spec;
          }
        }
      }
      container out-segment {
        description
        "The DetNet service sub-layer outbound configuration.
         This should not be used
         if this service operation is termination";
        choice outgoing-options {
          mandatory true;
          description
           "";
          case egress-proxy {
            uses app-flows-ref;
          }
          case detnet-service-output {
            //uses detnet-service-next-hop-content;
            list service-output-list {
              key "service-output-index";
              leaf service-output-index {
                type uint8;
              }
              uses detnet-header;
              list next-layer{
                key "index";
                description "lower-layer info";
                leaf index {
                  type uint8;
                }
                leaf forwarding-sub-layer {
                  type forwarding-sub-layer-ref;
                }
              }
            }
          }
        }
      }
    }
  }
  container forwarding-sub-layer {
    description "The DetNet forwarding sub-layer configuration";
    list forwarding-sub-layer-list {
      key "name";
      description "";
      leaf name {
        type string;
        description "The name of the DetNet forwarding sub-layer";
      }
      leaf forwarding-id {
        type uint16;
        config false;
        description
          "The DetNet forwarding ID";
      }
      uses traffic-requirements;
      uses traffic-specification;
      leaf forwarding-operation-type {
        type forwarding-operations-type;
      }
      container in-segment {
        description
        "The DetNet forwarding sub-layer inbound configuration. This should not be used
         if this forwarding operation is impose-and-forward";

        choice incoming-options {
          mandatory true;
          description
           "";
          case detnet-service-forwarding {
            uses service-sub-layer-ref;
          }
          case detnet-forwarding-identification {
            leaf interface {
              type if:interface-ref;
              description "";
            }
            uses detnet-flow-spec;
          }
        }
      }
      container out-segment {
        description
        "The DetNet forwarding sub-layer outbound configuration. This should not be used
         if this forwarding operation is pop-and-lookup";
        choice outgoing-options {
          mandatory true;
          description
           "";
          case service-operation {
            uses service-sub-layer-ref;
          }
          case detnet-forwarding-output {
            uses detnet-forwarding-next-hop-content;
          }
        }
      }
    }
  }
  container sub-network {
    description "";
    list sub-network-list {
      key "name";
      description "";
      leaf name {
        type string;
        description "";
      }
    }
  }
}
