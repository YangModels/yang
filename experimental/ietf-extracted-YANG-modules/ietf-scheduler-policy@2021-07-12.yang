module ietf-scheduler-policy {
  yang-version 1.1;
  namespace "urn:ietf:params:xml:ns:yang:ietf-scheduler-policy";
  prefix scheduler-policy;

  import ietf-qos-classifier {
    prefix classifier;
  }
  import ietf-qos-policy {
    prefix policy;
  }
  import ietf-qos-action {
    prefix action;
  }

  organization "IETF RTG (Routing Area) Working Group";
  contact
    "WG Web:   <http://tools.ietf.org/wg/netmod/>
     WG List:  <mailto:netmod@ietf.org>
     WG Chair: Jurgen Schonwalder
               <mailto:j.schoenwaelder@jacobs-university.de>
     WG Chair: Lou Berger
               <mailto:lberger@labn.net>
     WG Chair: Kent Watsen
               <mailto:kwatsen@juniper.net>
     Editor:   Aseem Choudhary
               <mailto:asechoud@cisco.com>
     Editor:   Mahesh Jethanandani
               <mailto:mjethanandani@gmail.com";
  description
    "This module contains a collection of YANG definitions for
     configuring diffserv specification implementations.
     Copyright (c) 2021 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";

  revision 2021-07-12 {
    description
      "Initial revision of QoS Scheduler Policy";
    reference "RFC XXXX";
  }
  feature scheduler-policy-support {
    description
      " This feature allows sheduler policy configuration
        as a separate policy type support.";
  }

  identity scheduler-policy-type {
    if-feature scheduler-policy-support;
    base policy:policy-type;
    description
      "This defines scheduler policy-type";
  }

  identity filter-match-all {
    base classifier:filter-type;
    description
      "Traffic-group filter type";
  }

  grouping filter-match-all {
    container match-all-cfg {
      leaf match-all-action {
        type empty;
        description
          "match all packets";
      }
      description
        "the match-all action";
    }
    description
      "the match-all filter grouping";
  }

  augment "/policy:policies/policy:policy/policy:classifier" +
          "/policy:filter" {
        when "../../policy:type =" +
                        "'scheduler-policy:scheduler-policy-type'" {
            description
               "Only when policy type is scheduler-policy";
        }
    if-feature scheduler-policy-support;
    choice filter-params {
      description
        "Choice of action types";
      case filter-match-all {
        uses filter-match-all;
        description
          "filter match-all";
      }
    }
    description
      "Augments Queue policy Classifier with common filter types";
  }

  identity queue-policy-name {
    base policy:action-type;
    description
      "queue policy name";
  }

  grouping queue-policy-name-cfg {
    container queue-policy-name {
      leaf queue-policy {
        type string ;
        mandatory true;
        description
          "This leaf defines name of the queue-policy";
      }
    description
      "container for queue-policy name";
    }
    description
      "queue-policy name grouping";
  }

  augment "/policy:policies/policy:policy/policy:classifier" +
          "/policy:action/policy:action-params" {
        when "../../policy:type =" +
                        "'scheduler-policy:scheduler-policy-type'" {
            description
               "Only when policy type is scheduler-policy";
        }
      if-feature scheduler-policy-support;
      case scheduler {
        uses action:scheduler;
      }
      case queue-policy-name {
        uses queue-policy-name-cfg;
      }
    description
      "augments scheduler template reference to scheduler policy";
  }
}
