module ietf-l2vpn {
  namespace "urn:ietf:params:xml:ns:yang:ietf-l2vpn";
  prefix "l2vpn";

  import ietf-inet-types {
    prefix "inet";
  }

  import ietf-yang-types {
    prefix "yang";
  }

  import ietf-mpls {
    prefix "mpls";
  }

  organization  "ietf";
  contact       "ietf";
  description   "l2vpn";

  revision "2016-10-24" {
    description "Fifth revision " +
                "  - Edits based on Giles's comments " +
                "    5) Remove relative leafrefs in groupings, " +
                "       and the resulting new groupings are: " +
                "       <a> bgp-auto-discovery-parameters-grp " +
                "       <b> bgp-signaling-parameters-grp " +
                "       <c> endpoint-grp " +
                "    11) Merge VPLS and VPWS into one single list " +
                "       and use augment statements to handle " +
                "       differences between VPLS and VPWS " +
                "  - Add a new grouping l2vpn-common-parameters-grp " +
                "    to make VPLS and VPWS more consistent";
    reference "";
  }

  revision "2016-05-31" {
    description "Fourth revision " +
                "  - Edits based on Giles's comments " +
                "    1) Change enumeration to identityref type for: " +
                "       <a> l2vpn-service-type " +
                "       <b> l2vpn-discovery-type " +
                "       <c> l2vpn-signaling-type " +
                "       bgp-rt-type, cw-negotiation, and " +
                "       pbb-component remain enumerations " +
                "    2) Define i-sid-type for leaf 'i-sid' " +
                "       (which is renamed from 'i-tag') " +
                "    3) Rename 'vpn-targets' to 'vpn-target' " +
                "    4) Import ietf-mpls.yang and reuse the " +
                "       'mpls-label' type defined in ietf-mpls.yang " +
                "       transmit-label and receive-label " +
                "    8) Change endpoint list's key to name " +
                "    9) Changed MTU to type uint16 " +
                "";
    reference "";
  }

  revision "2016-03-07" {
    description "Third revision " +
                "  - Changed the module name to ietf-l2vpn " +
                "  - Merged EVPN into L2VPN " +
                "  - Eliminated the definitions of attachment " +
                "    circuit with the intention to reuse other " +
                "    layer-2 definitions " +
                "  - Added state branch";
    reference "";
  }

  revision "2015-10-08" {
    description "Second revision " +
                "  - Added container vpls-instances " +
                "  - Rearranged groupings and typedefs to be " +
                "    reused across vpls-instance and vpws-instances";
    reference "";
  }

  revision "2015-06-30" {
    description "Initial revision";
    reference   "";
  }

  /* identities */

  identity l2vpn-instance-type {
    description "Base identity from which identities of " +
                "l2vpn service instance types are derived";
  }

  identity vpws-instance-type {
    base l2vpn-instance-type;
    description "This identity represents VPWS instance type";
  }

  identity vpls-instance-type {
    base l2vpn-instance-type;
    description "This identity represents VPLS instance type";
  }

  identity link-discovery-protocol {
    description "Base identiy from which identities describing " +
                "link discovery protocols are derived";
  }

  identity lacp {
    base "link-discovery-protocol";
    description "This identity represents LACP";
  }

  identity lldp {
    base "link-discovery-protocol";
    description "This identity represents LLDP";
  }

  identity bpdu {
    base "link-discovery-protocol";
    description "This identity represens BPDU";
  }

  identity cpd {
    base "link-discovery-protocol";
    description "This identity represents CPD";
  }

  identity udld {
    base "link-discovery-protocol";
    description "This identity represens UDLD";
  }

  identity l2vpn-service {
    description "Base identity from which identities describing " +
                "L2VPN services are derived";
  }

  identity Ethernet {
    base "l2vpn-service";
    description "This identity represents Ethernet service";
  }

  identity ATM {
    base "l2vpn-service";
    description "This identity represents Asynchronous Transfer " +
                "Mode service";
  }

  identity FR {
    base "l2vpn-service";
    description "This identity represent Frame-Relay service";
  }

  identity TDM {
    base "l2vpn-service";
    description "This identity represent Time Devision " +
                "Multiplexing service";
  }

  identity l2vpn-discovery {
    description "Base identity from which identities describing " +
                "L2VPN discovery protocols are derived";
  }

  identity manual-discovery {
    base "l2vpn-discovery";
    description "Manual configuration of l2vpn service";
  }

  identity bgp-auto-discovery {
    base "l2vpn-discovery";
    description "Border Gateway Protocol (BGP) auto-discovery of " +
                "l2vpn service";
  }

  identity ldp-discovery {
    base "l2vpn-discovery";
    description "Label Distribution Protocol (LDP) discovery of " +
                "l2vpn service";
  }

  identity mixed-discovery {
    base "l2vpn-discovery";
    description "Mixed discovery methods of l2vpn service";
  }

  identity l2vpn-signaling {
    description "Base identity from which identities describing " +
                "L2VPN signaling protocols are derived";
  }

  identity static-configuration {
    base "l2vpn-signaling";
    description "Static configuration of labels (no signaling)";
  }

  identity ldp-signaling {
    base "l2vpn-signaling";
    description "Label Distribution Protocol (LDP) signaling";
  }

  identity bgp-signaling {
    base "l2vpn-signaling";
    description "Border Gateway Protocol (BGP) signaling";
  }

  identity mixed-signaling {
    base "l2vpn-signaling";
    description "Mixed signaling methods";
  }

  /* typedefs */

  typedef l2vpn-service-type {
    type identityref {
      base "l2vpn-service";
    }
    description "L2VPN service type";
  }

  typedef l2vpn-discovery-type {
    type identityref {
      base "l2vpn-discovery";
    }
    description "L2VPN discovery type";
  }

  typedef l2vpn-signaling-type {
    type identityref {
      base "l2vpn-signaling";
    }
    description "L2VPN signaling type";
  }

  typedef bgp-rt-type {
    type enumeration {
      enum import {
        description "For import";
      }
      enum export {
        description "For export";
      }
      enum both {
        description "For both import and export";
      }
    }
    description "BGP route-target type. Import from BGP YANG";
  }
  typedef cw-negotiation-type {
    type enumeration {
      enum "non-preferred" {
        description "No preference for control-word";
      }
      enum "preferred" {
        description "Prefer to have control-word negotiation";
      }
    }
    description "control-word negotiation preference type";
  }

  typedef link-discovery-protocol-type {
    type identityref {
      base "link-discovery-protocol";
    }
    description "This type is used to identify " +
                "link discovery protocol";
  }

  typedef pbb-component-type {
    type enumeration {
      enum "b-component" {
        description "Identifies as a b-component";
      }
      enum "i-component" {
        description "Identifies as an i-component";
      }
    }
    description "This type is used to identify " +
                "the type of PBB component";
  }

  typedef pw-template-ref {
    type leafref {
      path "/l2vpn/common/pw-templates/pw-template/name";
    }
    description "pw-template-ref";
  }

  typedef redundancy-group-template-ref {
    type leafref {
      path "/l2vpn/common/redundancy-group-templates" +
           "/redundancy-group-template/name";
    }
    description "redundancy-group-template-ref";
  }

  typedef l2vpn-instance-name-ref {
    type leafref {
      path "/l2vpn/l2vpn-instances" +
           "/l2vpn-instance/name";
    }
    description "l2vpn-instance-name-ref";
  }

  typedef l2vpn-instance-type-ref {
    type leafref {
      path "/l2vpn/l2vpn-instances" +
           "/l2vpn-instance/type";
    }
    description "l2vpn-instance-type-ref";
  }

  typedef operational-state-type {
    type enumeration {
      enum 'up' {
        description "Operational state is up";
      }
      enum 'down' {
        description "Operational state is down";
      }
    }
    description "operational-state-type";
  }

  typedef i-sid-type {
    type uint32 {
      range "0..16777216";
    }
    description "I-SID type that is 24-bits. " +
                "This should be moved to ieee-types.yang at " +
                "http://www.ieee802.org/1/files/public/docs2015" +
                "/new-mholness-ieee-types-yang-v01.yang";
  }

  /* groupings */

  grouping pbb-parameters-grp {
    description "PBB parameters grouping";
    container pbb-parameters {
      description "pbb-parameters";
      choice component-type {
        description "PBB component type";
        case i-component {
          leaf i-sid {
            type i-sid-type;
            description "I-SID";
          }
          leaf backbone-src-mac {
            type yang:mac-address;
            description "backbone-src-mac";
          }
        }
        case b-component {
          leaf bind-b-component-name {
            type l2vpn-instance-name-ref;
            description "Reference to the associated b-component";
          }
          must "/l2vpn" +
               "/l2vpn-instances[name=current()/bind-b-component]" +
               "/type = 'vpls-instance-type'" {
            description "A b-component must be an L2VPN instance " +
                        "of type vpls-instance-type";
          }
        }
      }
    }
  }

  grouping pbb-parameters-state-grp {
    description "PBB parameters grouping";
    container pbb-parameters {
      description "pbb-parameters";
      choice component-type {
        description "PBB component type";
        case i-component {
          leaf i-sid {
            type i-sid-type;
            description "I-SID";
          }
          leaf backbone-src-mac {
            type yang:mac-address;
            description "backbone-src-mac";
          }
        }
        case b-component {
          leaf bind-b-component-name {
            type string;
            description "Name of the associated b-component";
          }
          leaf bind-b-component-type {
            type identityref {
              base l2vpn-instance-type;
            }
            must ". = 'vpls-instance-type'" {
              description "The associated b-component must have " +
                          "type vpls-instance-type";
            }
            description "Type of the associated b-component";
          }
        }
      }
    }
  }

  grouping l2vpn-common-parameters-grp {
    description "L2VPN common parameters";
    leaf name {
      type string;
      description "Name of L2VPN service instance";
    }
    leaf type {
      type identityref {
        base l2vpn-instance-type;
      }
      description "Type of L2VPN service instance";
    }
    leaf mtu {
      type uint16;
      description "MTU of L2VPN service";
    }
    leaf mac-aging-timer {
      type uint32;
      description "mac-aging-timer, the duration after which" +
                  "a MAC entry is considered aged out";
    }
    leaf service-type {
      type l2vpn-service-type;
      default Ethernet;
      description "L2VPN service type";
    }
    leaf discovery-type {
      type l2vpn-discovery-type;
      default manual-discovery;
      description "L2VPN service discovery type";
    }
    leaf signaling-type {
      type l2vpn-signaling-type;
      mandatory true;
      description "L2VPN signaling type";
    }
  }

  grouping bgp-auto-discovery-parameters-grp {
    description "BGP parameters for auto-discovery";
    leaf route-distinguisher {
      type string;
      description "BGP RD";
    }
    list vpn-target {
      key rt-value;
      description "Route Targets";
      leaf rt-value {
        type string;
        description "Route-Target value";
      }
      leaf rt-type {
        type bgp-rt-type;
        mandatory true;
        description "Type of RT";
      }
    }
    leaf vpn-id {
      type string;
      description "VPN ID";
    }
  }

  grouping bgp-signaling-parameters-grp {
    description "BGP parameters for signaling";
    leaf site-id {
      type uint16;
      description "Site ID";
    }
    leaf site-range {
      type uint16;
      description "Site Range";
    }
  }

  grouping pw-common-parameters-grp {
    description "Pseudowire parameters common to both " +
                "VPWS and VPLS pseudowires";
    leaf name {
      type string;
      description "pseudowire name";
    }
    leaf template {
      type pw-template-ref;
      description "pseudowire template";
    }
    leaf mtu {
      type uint16;
      description "PW MTU";
    }
    leaf mac-withdraw {
      type boolean;
      default false;
      description "Enable (true) or disable (false) MAC withdraw";
    }
    leaf cw-negotiation {
      type cw-negotiation-type;
      description "cw-negotiation";
    }
    leaf tunnel-policy {
      type string;
      description "tunnel policy name";
    }
    uses pw-type-grp;
  }

  grouping pw-type-grp {
    description "pseudowire type grouping";
    choice pw-type {
      description "A choice of pseudowire type";
      case ldp-or-static-pw {
        leaf peer-ip {
          type inet:ip-address;
          description "peer IP address";
        }
        leaf pw-id {
          type uint32;
          description "pseudowire id";
        }
        leaf icb {
          type boolean;
          description "inter-chassis backup";
        }
        leaf transmit-label {
          type mpls:mpls-label;
          description "transmit lable";
        }
        leaf receive-label {
          type mpls:mpls-label;
          description "receive label";
        }
      }
      case bgp-pw {
        leaf remote-pe-id {
          type inet:ip-address;
          description "remote pe id";
        }
      }
      case bgp-ad-pw {
        leaf remote-ve-id {
          type uint16;
          description "remote ve id";
        }
      }
    }
  }

  grouping redundancy-group-properties-grp {
    description "redundancy-group-properties-grp";
    leaf protection-mode {
      type enumeration {
        enum "frr" {
          value 0;
          description "fast reroute";
        }
        enum "master-slave" {
          value 1;
          description "master-slave";
        }
        enum "independent" {
          value 2;
          description "independent";
        }
      }
      description "protection-mode";
    }
    leaf reroute-mode {
      type enumeration {
        enum "immediate" {
          value 0;
          description "immediate reroute";
        }
        enum "delayed" {
          value 1;
          description "delayed reroute";
        }
        enum "never" {
          value 2;
          description "never reroute";
        }
      }
      description "reroute-mode";
    }
    leaf dual-receive {
      type boolean;
      description
      "allow extra traffic to be carried by backup";
    }
    leaf revert {
      type boolean;
      description "allow forwarding to revert to primary " +
                  "after restoring primary";
    }
  }

  grouping endpoint-grp {
    description "A grouping that defines the structure of " +
                "an endpoint";
    choice ac-or-pw-or-redundancy-grp {
      description "A choice ofattachment circuit or " +
                  "pseudowire or redundancy group";
      case ac {
        description "Attachment circuit(s) as an endpoint";
      }
      case pw {
        description "Pseudowire(s) as an endpoint";
      }
      case redundancy-grp {
        description "Redundancy group as an endpoint";
        choice primary {
          mandatory true;
          description "primary options";
          case primary-ac {
            description "primary-ac";
          }
          case primary-pw {
            description "primary-pw";
          }
        }
        choice backup {
          description "backup options";
          case backup-ac {
            description "backup-ac";
          }
          case backup-pw {
            description "backup-pw";
          }
        }
        leaf template {
          type leafref {
            path "/l2vpn/common/redundancy-group-templates" +
                 "/redundancy-group-template/name";
          }
          description "Reference a redundancy group " +
                      "properties template";
        }
        uses redundancy-group-properties-grp;
      }
    }
  }

  grouping vpls-pw-state-grp {
    description "vpls-pw-state-grp";
    leaf name {
      type string;
      description "pseudowire name";
    }
    leaf state {
      type operational-state-type;
      description "pseudowire up/down state";
    }
    leaf mtu {
      type uint16;
      description "pseudowire mtu";
    }
    leaf mac-withdraw {
      type boolean;
      description "MAC withdraw is enabled (true) or disabled (false)";
    }
    leaf cw-negotiation {
      type cw-negotiation-type;
      description "cw-negotiation";
    }
    leaf discovery-type {
      type l2vpn-discovery-type;
      description "VPLS discovery type";
    }
    leaf signaling-type {
      type l2vpn-signaling-type;
      description "VPLS signaling type";
    }
    leaf peer-ip {
      type inet:ip-address;
      description "peer IP address";
    }
    leaf pw-id {
      type uint32;
      description "pseudowire id";
    }
    leaf transmit-label {
      type mpls:mpls-label;
      description "transmit lable";
    }
    leaf receive-label {
      type mpls:mpls-label;
      description "receive label";
    }
    leaf tunnel-policy {
      type string;
      description "tunnel policy name";
    }
  }

  grouping ac-state-grp {
    description "vpls-ac-state-grp";
    leaf name {
      type string;
      description "attachment circuit name";
    }
    leaf state {
      type operational-state-type;
      description "attachment circuit up/down state";
    }
  }

  grouping vpws-pw-state-grp {
    description "vpws-pw-state-grp";
    leaf name {
      type string;
      description "pseudowire name";
    }
    leaf state {
      type operational-state-type;
      description "pseudowire operation state up/down";
    }
    leaf mtu {
      type uint16;
      description "PW MTU";
    }
    leaf mac-withdraw {
      type boolean;
      description "MAC withdraw is enabled (ture) or disabled (false)";
    }
    leaf cw-negotiation {
      type cw-negotiation-type;
      description "Override the control-word negotiation " +
                  "preference specified in the " +
                  "pseudowire template.";
    }
    leaf vccv-ability {
      type boolean;
      description "vccv-ability";
    }
    leaf tunnel-policy {
      type string;
      description "Used to override the tunnel policy name " +
                  "specified in the pseduowire template";
    }
    leaf request-vlanid {
      type uint16;
      description "request vlanid";
    }
    leaf vlan-tpid {
      type string;
      description "vlan tpid";
    }
    leaf ttl {
      type uint8;
      description "time-to-live";
    }
    uses pw-type-grp;
  }

  /* L2VPN YANG Model */

  container l2vpn {
    description "l2vpn";
    container common {
      description "common l2pn attributes";
      container pw-templates {
        description "pw-templates";
        list pw-template {
          key "name";
          description "pw-template";
          leaf name {
            type string;
            description "name";
          }
          leaf mtu {
            type uint16;
            description "pseudowire mtu";
          }
          leaf cw-negotiation {
            type cw-negotiation-type;
            default "preferred";
            description
              "control-word negotiation preference";
          }
          leaf tunnel-policy {
            type string;
            description "tunnel policy name";
          }
        }
      }
      container redundancy-group-templates {
        description "redundancy group templates";
        list redundancy-group-template {
          key "name";
          description "redundancy-group-template";
          leaf name {
            type string;
            description "name";
          }
          uses redundancy-group-properties-grp;
          leaf reroute-delay {
            when "../reroute-mode = 'delayed'" {
              description "Specify amount of time to " +
                          "delay reroute only when " +
                          "delayed route is configured";
            }
            type uint16;
            description "amount of time to delay reroute";
          }
          leaf revert-delay {
            when "../revert = 'true'" {
              description "Specify the amount of time to " +
                          "wait to revert to primary " +
                          "only if reversion is configured";
            }
            type uint16;
            description "amount ot time to wait to " +
                        "revert to primary";
          }
        }
      }
    }

    container l2vpn-instances {
      description "A list of L2VPN instances";
      list l2vpn-instance {
        key "name type";
        description "An L2VPN service instance";
        uses l2vpn-common-parameters-grp;
        container bgp-auto-discovery {
          when "../discovery-type = 'bgp-auto-discovery'" {
            description "Check discovery type: " +
                        "Can only configure BGP discovery if " +
                        "discovery type is BGP-AD";
          }
          description "BGP auto-discovery parameters";
          uses bgp-auto-discovery-parameters-grp;
        }
        container bgp-signaling {
          when "../signaling-type = 'bgp-signaling'" {
            description "Check signaling type: " +
                        "Can only configure BGP signaling if " +
                        "signaling type is BGP";
          }
          description "BGP signaling parameters";
          uses bgp-signaling-parameters-grp;
        }
        list pw {
          key "name";
          description "A pseudowire";
          uses pw-common-parameters-grp;
        }
      }
    }
  }

  container l2vpn-state {
    config false;
    description "l2vpn state";

    container l2vpn-instances {
      description "L2VPN instances state";
      list l2vpn-instance {
        description "An L2VPN instance's state";
        uses l2vpn-common-parameters-grp;
        container bgp-auto-discovery {
          description "BGP auto-discovery parameters";
          uses bgp-auto-discovery-parameters-grp;
        }
        container bgp-signaling {
          description "BGP signaling parameters";
          uses bgp-signaling-parameters-grp;
        }
      }
    }
  }

  /* augments */

  augment "/l2vpn/l2vpn-instances/l2vpn-instance/pw" {
    when "../type = 'vpws-l2vpn-instance-type'" {
      description "Pseudowire parameters only for VPWS pseudowires";
    }
    description "Augment for peudowire parameters for " +
                "VPWS pseudowires";
    leaf vccv-ability {
      type boolean;
      description "vccvability";
    }
    leaf request-vlanid {
      type uint16;
      description "request vlanid";
    }
    leaf vlan-tpid {
      type string;
      description "vlan tpid";
    }
    leaf ttl {
      type uint8;
      description "time-to-live";
    }
  }

  augment "/l2vpn/l2vpn-instances/l2vpn-instance" {
    when "type = 'vpws-l2vpn-instance-type'" {
      description "Endpoints specifically for a VPWS instance";
    }
    description "Augment for endpoints for a VPWS instance";
    container endpoint-a {
      description "endpoint-a";
      uses endpoint-grp {
        description "endpoint configuration";
        augment "ac-or-pw-or-redundancy-grp/ac" {
          description "An attachment circuits as the endpoint";
          leaf ac {
            type string;
            description "Name of attachment circuit.  " +
                        "This field is intended to " +
                        "reference standardized " +
                        "layer-2 definitions.";
          }
        }
        augment "ac-or-pw-or-redundancy-grp/pw" {
          description "A pseudowire as the endpoint";
          leaf pw {
            type leafref {
              path "../../pw/name";
            }
            description "name of pseudowire";
          }
        }
        augment "ac-or-pw-or-redundancy-grp/redundancy-grp/" +
                "primary/primary-ac" {
          description "The primary attachment circuit of a " +
                      "redundancy group endpoint";
          leaf primary-ac {
            type string;
            description "Name of primary attachment circuit.  " +
                        "This field is intended to reference " +
                        "standardized layer-2 definitions.";
          }
        }
        augment "ac-or-pw-or-redundancy-grp/redundancy-grp/" +
                "primary/primary-pw" {
          description "The primary pseudowires of a " +
                      "redundancy group endpoint";
          leaf primary-pw {
            type leafref {
              path "../../pw/name";
            }
            description "name of pseudowire";
          }
        }
        augment "ac-or-pw-or-redundancy-grp/redundancy-grp/" +
                "backup/backup-ac" {
          description "The backup attachment circuit of a " +
                      "redundancy group endpoint";
          leaf backup-ac {
            type string;
            description "Name of backup attachment circuit.  " +
                        "This field is intended to reference " +
                        "standardized layer-2 definitions.";
          }
        }
        augment "ac-or-pw-or-redundancy-grp/redundancy-grp/" +
                "backup/backup-pw" {
          description "The backup pseudowires of a " +
                      "redundancy group endpoint";
          leaf backup-pw {
            type leafref {
              path "../../pw/name";
            }
            description "Reference an attachment circuit";
          }
        }
        augment "ac-or-pw-or-redundancy-grp/redundancy-grp" {
          description "Additional conditional " +
                      "redunadancy group parameters";
          leaf reroute-delay {
            when "../reroute-mode = 'delayed'" {
              description "Specify amount of time to " +
                          "delay reroute only when " +
                          "delayed route is configured";
            }
            type uint16;
            description "amount of time to delay reroute";
          }
          leaf revert-delay {
            when "../revert = 'true'" {
              description "Specify the amount of time to " +
                          "wait to revert to primary " +
                          "only if reversion is configured";
            }
            type uint16;
            description "amount ot time to wait to " +
                        "revert to primary";
          }
        }
      }
    }
    container endpoint-z {
      description "endpoint-z";
      uses endpoint-grp {
        description "endpoint configuration";
        augment "ac-or-pw-or-redundancy-grp/ac" {
          description "An attachment circuits as the endpoint";
          leaf ac {
            type string;
            description "Name of attachment circuit.  " +
                        "This field is intended to " +
                        "reference standardized " +
                        "layer-2 definitions.";
          }
        }
        augment "ac-or-pw-or-redundancy-grp/pw" {
          description "A pseudowire as the endpoint";
          leaf pw {
            type leafref {
              path "../../pw/name";
            }
            description "name of pseudowire";
          }
        }
        augment "ac-or-pw-or-redundancy-grp/redundancy-grp/" +
                "primary/primary-ac" {
          description "The primary attachment circuit of a " +
                      "redundancy group endpoint";
          leaf primary-ac {
            type string;
            description "Name of primary attachment circuit.  " +
                        "This field is intended to reference " +
                        "standardized layer-2 definitions.";
          }
        }
        augment "ac-or-pw-or-redundancy-grp/redundancy-grp/" +
                "primary/primary-pw" {
          description "The primary pseudowires of a " +
                      "redundancy group endpoint";
          leaf primary-pw {
            type leafref {
              path "../../pw/name";
            }
            description "name of pseudowire";
          }
        }
        augment "ac-or-pw-or-redundancy-grp/redundancy-grp/" +
                "backup/backup-ac" {
          description "The backup attachment circuit of a " +
                      "redundancy group endpoint";
          leaf backup-ac {
            type string;
            description "Name of backup attachment circuit.  " +
                        "This field is intended to reference " +
                        "standardized layer-2 definitions.";
          }
        }
        augment "ac-or-pw-or-redundancy-grp/redundancy-grp/" +
                "backup/backup-pw" {
          description "The backup pseudowires of a " +
                      "redundancy group endpoint";
          leaf backup-pw {
            type leafref {
              path "../../pw/name";
            }
            description "Reference an attachment circuit";
          }
        }
        augment "ac-or-pw-or-redundancy-grp/redundancy-grp" {
          description "Additional conditional " +
                      "redunadancy group parameters";
          leaf reroute-delay {
            when "../reroute-mode = 'delayed'" {
              description "Specify amount of time to " +
                          "delay reroute only when " +
                          "delayed route is configured";
            }
            type uint16;
            description "amount of time to delay reroute";
          }
          leaf revert-delay {
            when "../revert = 'true'" {
              description "Specify the amount of time to " +
                          "wait to revert to primary " +
                          "only if reversion is configured";
            }
            type uint16;
            description "amount ot time to wait to " +
                        "revert to primary";
          }
        }
      }
    }
  }

  augment "/l2vpn/l2vpn-instances/l2vpn-instance" {
    when "type = 'vpls-l2vpn-instance-type'" {
      description "Parameters specifically for a VPLS instance";
    }
    description "Augment for parameters for a VPLS instance";
    uses pbb-parameters-grp;
    leaf evpn-instance {
      type string;
      description "Eventual reference to standard EVPN instance";
    }
    list endpoint {
      key "name";
      leaf name {
        type string;
        description "endpoint name";
      }
      leaf split-horizon-group {
        type string;
        description "Identify a split horizon group";
      }
      uses endpoint-grp {
        description "endpoint configuration";
        augment "ac-or-pw-or-redundancy-grp/ac" {
          description "A list of attachment circuits as the endpoint";
          list ac {
            key "name";
            leaf name {
              type string;
              description "Name of attachment circuit.  " +
                          "This field is intended to " +
                          "reference standardized " +
                          "layer-2 definitions.";
            }
            description "A bridge table instance's " +
                        "attachment circuit list";
          }
        }
        augment "ac-or-pw-or-redundancy-grp/pw" {
          description "A list of pseudowires as the endpoint";
          list pw {
            key "name";
            leaf name {
              type leafref {
                path "../../../pw/name";
              }
              description "name of pseudowire";
            }
            description "A VPLS instance's pseudowire list";
          }
        }
        augment "ac-or-pw-or-redundancy-grp/redundancy-grp/" +
                "primary/primary-ac" {
          description "The primary attachment circuit of a " +
                      "redundancy group endpoint";
          leaf primary-ac {
            type string;
            description "Name of primary attachment circuit.  " +
                        "This field is intended to reference " +
                        "standardized layer-2 definitions.";
          }
        }
        augment "ac-or-pw-or-redundancy-grp/redundancy-grp/" +
                "primary/primary-pw" {
          description "The primary pseudowires of a " +
                      "redundancy group endpoint";
          list primary-pw {
            key "name";
            leaf name {
              type leafref {
                path "../../../pw/name";
              }
              description "name of pseudowire";
            }
            description "A bridge table instance's pseudowire list";
          }
        }
        augment "ac-or-pw-or-redundancy-grp/redundancy-grp/" +
                "backup/backup-ac" {
          description "The backup attachment circuit of a " +
                      "redundancy group endpoint";
          leaf backup-ac {
            type string;
            description "Name of backup attachment circuit.  " +
                        "This field is intended to reference " +
                        "standardized layer-2 definitions.";
          }
        }
        augment "ac-or-pw-or-redundancy-grp/redundancy-grp/" +
                "backup/backup-pw" {
          description "The backup pseudowires of a " +
                      "redundancy group endpoint";
          list backup-pw {
            key "name";
            leaf name {
              type leafref {
                path "../../../pw/name";
              }
              description "Reference an attachment circuit";
            }
            leaf precedence {
              type uint32;
              description "precedence of the pseudowire";
            }
            description "A list of backup pseudowires";
          }
        }
        augment "ac-or-pw-or-redundancy-grp/redundancy-grp" {
          description "Additional conditional " +
                      "redunadancy group parameters";
          leaf reroute-delay {
            when "../reroute-mode = 'delayed'" {
              description "Specify amount of time to " +
                          "delay reroute only when " +
                          "delayed route is configured";
            }
            type uint16;
            description "amount of time to delay reroute";
          }
          leaf revert-delay {
            when "../revert = 'true'" {
              description "Specify the amount of time to " +
                          "wait to revert to primary " +
                          "only if reversion is configured";
            }
            type uint16;
            description "amount ot time to wait to revert to primary";
          }
        }
      }
      description "List of endpoints";
    }
  }

  augment "/l2vpn-state/l2vpn-instances/l2vpn-instance" {
    when "type = 'vpws-l2vpn-instance-type'" {
      description "Additional perational state specifically for " +
                  "a VPWS instance";
    }
    description "Augment for a VPWS instance's " +
                "operational state";
    container endpoint-a {
      description "endpoint-a";
      uses endpoint-grp {
        description "endpoint configuration";
        augment "ac-or-pw-or-redundancy-grp/ac" {
          description "An attachment circuit as the endpoint";
          container ac {
            description "The attachment circuit";
            uses ac-state-grp;
          }
        }
        augment "ac-or-pw-or-redundancy-grp/pw" {
          description "A pseudowire as the endpoint";
          container pw {
            description "The pseuduowire";
            uses vpws-pw-state-grp;
          }
        }
        augment "ac-or-pw-or-redundancy-grp/redundancy-grp/" +
                "primary/primary-ac" {
          description "The primary attachment circuit of a " +
                      "redundancy group endpoint";
          container primary-ac {
            description "The primary attachment circuit";
            uses ac-state-grp;
          }
        }
        augment "ac-or-pw-or-redundancy-grp/redundancy-grp/" +
                "primary/primary-pw" {
          description "The primary pseudowires of a " +
                      "redundancy group endpoint";
          container primary-pw {
            description "The primary pseudowire";
            uses vpws-pw-state-grp;
          }
        }
        augment "ac-or-pw-or-redundancy-grp/redundancy-grp/" +
                "backup/backup-ac" {
          description "The backup attachment circuit of a " +
                      "redundancy group endpoint";
          container backup-ac {
            description "The backup attachment circuit";
            uses ac-state-grp;
          }
        }
        augment "ac-or-pw-or-redundancy-grp/redundancy-grp/" +
                "backup/backup-pw" {
          description "The backup pseudowires of a " +
                      "redundancy group endpoint";
          container backup-pw {
            description "The backup pseudowire";
            uses vpws-pw-state-grp;
          }
        }
        augment "ac-or-pw-or-redundancy-grp/redundancy-grp" {
          description "Additional conditional " +
                      "redunadancy group parameters";
          leaf reroute-delay {
            when "../reroute-mode = 'delayed'" {
              description "Specify amount of time to " +
                          "delay reroute only when " +
                          "delayed route is configured";
            }
            type uint16;
            description "amount of time to delay reroute";
          }
          leaf revert-delay {
            when "../revert = 'true'" {
              description "Specify the amount of time to " +
                          "wait to revert to primary " +
                          "only if reversion is configured";
            }
            type uint16;
            description "amount ot time to wait to revert to primary";
          }
        }
      }
    }
    container endpoint-z {
      description "endpoint-z";
      uses endpoint-grp {
        description "endpoint configuration";
        augment "ac-or-pw-or-redundancy-grp/ac" {
          description "An attachment circuit as the endpoint";
          container ac {
            description "The attachment circuit";
            uses ac-state-grp;
          }
        }
        augment "ac-or-pw-or-redundancy-grp/pw" {
          description "A pseudowire as the endpoint";
          container pw {
            description "The pseuduowire";
            uses vpws-pw-state-grp;
          }
        }
        augment "ac-or-pw-or-redundancy-grp/redundancy-grp/" +
                "primary/primary-ac" {
          description "The primary attachment circuit of a " +
                      "redundancy group endpoint";
          container primary-ac {
            description "The primary attachment circuit";
            uses ac-state-grp;
          }
        }
        augment "ac-or-pw-or-redundancy-grp/redundancy-grp/" +
                "primary/primary-pw" {
          description "The primary pseudowires of a " +
                      "redundancy group endpoint";
          container primary-pw {
            description "The primary pseudowire";
            uses vpws-pw-state-grp;
          }
        }
        augment "ac-or-pw-or-redundancy-grp/redundancy-grp/" +
                "backup/backup-ac" {
          description "The backup attachment circuit of a " +
                      "redundancy group endpoint";
          container backup-ac {
            description "The backup attachment circuit";
            uses ac-state-grp;
          }
        }
        augment "ac-or-pw-or-redundancy-grp/redundancy-grp/" +
                "backup/backup-pw" {
          description "The backup pseudowires of a " +
                      "redundancy group endpoint";
          container backup-pw {
            description "The backup pseudowire";
            uses vpws-pw-state-grp;
          }
        }
        augment "ac-or-pw-or-redundancy-grp/redundancy-grp" {
          description "Additional conditional " +
                      "redunadancy group parameters";
          leaf reroute-delay {
            when "../reroute-mode = 'delayed'" {
              description "Specify amount of time to " +
                          "delay reroute only when " +
                          "delayed route is configured";
            }
            type uint16;
            description "amount of time to delay reroute";
          }
          leaf revert-delay {
            when "../revert = 'true'" {
              description "Specify the amount of time to " +
                          "wait to revert to primary " +
                          "only if reversion is configured";
            }
            type uint16;
            description "amount ot time to wait to revert to primary";
          }
        }
      }
    }
  }

  augment "/l2vpn-state/l2vpn-instances/l2vpn-instance" {
    when "type = 'vpls-l2vpn-instance-type'" {
      description "Additional perational state specifically for " +
                  "a VPLS instance";
    }
    description "Augment for a VPLS instance's " +
                "operational state";
    uses pbb-parameters-state-grp;
    leaf evpn-instance-name {
      type string;
      description "Name of associated an EVPN instance";
    }
    list endpoint {
      leaf name {
        type string;
        description "endpoint name";
      }
      leaf split-horizon-group {
        type string;
        description "Identify a split horizon group";
      }
      uses endpoint-grp {
        description "endpoint configuration";
        augment "ac-or-pw-or-redundancy-grp/ac" {
          description "A list of attachment circuits as the endpoint";
          list ac {
            uses ac-state-grp;
            description "The attachment circuits";
          }
        }
        augment "ac-or-pw-or-redundancy-grp/pw" {
          description "A list of pseudowires as the endpoint";
          list pw {
            uses vpls-pw-state-grp;
            description "The pseudowires";
          }
        }
        augment "ac-or-pw-or-redundancy-grp/redundancy-grp/" +
                "primary/primary-ac" {
          description "The primary attachment circuit of a " +
                      "redundancy group endpoint";
          container primary-ac {
            description "The primary attachment circuit";
            uses ac-state-grp;
          }
        }
        augment "ac-or-pw-or-redundancy-grp/redundancy-grp/" +
                "primary/primary-pw" {
          description "The primary pseudowires of a " +
                      "redundancy group endpoint";
          list primary-pw {
            uses vpls-pw-state-grp;
            description "The pseudowires";
          }
        }
        augment "ac-or-pw-or-redundancy-grp/redundancy-grp/" +
                "backup/backup-ac" {
          description "The backup attachment circuit of a " +
                      "redundancy group endpoint";
          container backup-ac {
            description "The backup attachment circuit";
            uses ac-state-grp;
          }
        }
        augment "ac-or-pw-or-redundancy-grp/redundancy-grp/" +
                "backup/backup-pw" {
          description "The backup pseudowires of a " +
                      "redundancy group endpoint";
          list backup-pw {
            uses vpls-pw-state-grp;
            leaf precedence {
              type uint32;
              description "precedence of the pseudowire";
            }
            description "The backup pseudowires";
          }
        }
        augment "ac-or-pw-or-redundancy-grp/redundancy-grp" {
          description "Additional conditional " +
                      "redunadancy group parameters";
          leaf reroute-delay {
            when "../reroute-mode = 'delayed'" {
              description "Specify amount of time to " +
                          "delay reroute only when " +
                          "delayed route is configured";
            }
            type uint16;
            description "amount of time to delay reroute";
          }
          leaf revert-delay {
            when "../revert = 'true'" {
              description "Specify the amount of time to " +
                          "wait to revert to primary " +
                          "only if reversion is configured";
            }
            type uint16;
            description "amount ot time to wait to revert to primary";
          }
        }
      }
      description "List of endpoints";
    }
  }

}
