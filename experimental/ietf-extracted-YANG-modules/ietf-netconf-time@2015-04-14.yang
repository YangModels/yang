module ietf-netconf-time {

   namespace "urn:ietf:params:xml:ns:yang:ietf-netconf-time";

   prefix nct;

   import ietf-netconf { prefix nc; }

   import ietf-yang-types { prefix yang; }

   import ietf-netconf-monitoring { prefix ncm; }

   contact
     "Editor: Tal Mizrahi
         <dew@tx.technion.ac.il>
      Editor: Yoram Moses
         <moses@ee.technion.ac.il>";

   description
     "This module defines a capability-based extension to the
      Network Configuration Protocol (NETCONF) that allows
      time-triggered configuration and management operations.
      This extension allows NETCONF clients to invoke configuration
      updates according to scheduled times, and allows NETCONF
      servers to attach timestamps to the data they send to NETCONF
      clients.

      Copyright (c) 2015 IETF Trust and the persons identified as
      the document authors.  All rights reserved.

      Redistribution and use in source and binary forms, with or
      without modification, is permitted pursuant to, and subject
      to the license terms contained in, the Simplified BSD License
      set forth in Section 4.c of the IETF Trust's Legal Provisions
      Relating to IETF Documents
      (http://trustee.ietf.org/license-info).";

   revision 2015-04-14 {
      description
        "Initial version.";
      reference
        "draft-mm-netconf-time-capability:
         Time Capability in NETCONF";
   }

   typedef time-interval {
      type string {
         pattern '\d{2}:\d{2}:\d{2}(\.\d+)?';
      }
   }

   grouping scheduling-tolerance-parameters {
      description
        "Contains the parameters of the scheduling tolerance.";

      leaf sched-max-future {
         description
           "When the scheduled time is in the future, i.e., greater
            than the present time, this leaf defines the maximal
            difference between the scheduled time
            and the present time that the server is willing to
            accept. If the difference exceeds this number, the
            server responds with an error.";
         type time-interval;
         default 00:00:15.0;
      }

      leaf sched-max-past {
         description
           "When the scheduled time is in the past, i.e., less
            than the present time, this leaf defines the maximal
            difference between the present time
            and the scheduled time that the server is willing to
            accept. If the difference exceeds this number, the
            server responds with an error.";
         type time-interval;
         default 00:00:15.0;
      }
   }

   // extending the get-config operation
   augment /nc:get-config/nc:input {
      description
        "Adds the time element to <get-config>.";

      leaf scheduled-time {
         description
           "The time at which the RPC is scheduled to be performed.";
         type yang:date-and-time;
      }

      leaf get-time {
         description
           "Indicates that the rpc-reply should include the
            execution-time.";
         type empty;
      }
   }

   augment /nc:get-config/nc:output {
      description
        "Adds the time element to <get-config>.";
      leaf execution-time {
         description
           "The time at which the RPC was executed.";
         type yang:date-and-time;
      }
   }

   augment /nc:get/nc:input {
      description
        "Adds the time element to <get>.";

      leaf scheduled-time {
         description
           "The time at which the RPC is scheduled to be performed.";
         type yang:date-and-time;
      }

      leaf get-time {
         description
           "Indicates that the rpc-reply should include the
            execution-time.";
         type empty;
      }
   }

   augment /nc:get/nc:output {
      description
        "Adds the time element to <get>.";

      leaf execution-time {
         description
           "The time at which the RPC was executed.";
         type yang:date-and-time;
      }
   }

   augment /nc:copy-config/nc:input {
      description
        "Adds the time element to <copy-config>.";
      leaf scheduled-time {
         description
           "The time at which the RPC is scheduled to be performed.";
         type yang:date-and-time;
      }

      leaf get-time {
         description
           "Indicates that the rpc-reply should include the
            execution-time.";
         type empty;
      }
   }

   augment /nc:copy-config/nc:output {
      description
        "Adds the time element to <copy-config>.";

      leaf execution-time {
         description
           "The time at which the RPC was executed.";
         type yang:date-and-time;
      }
   }

   augment /nc:edit-config/nc:input {
      description
        "Adds the time element to <edit-config>.";

      leaf scheduled-time {
         description
           "The time at which the RPC is scheduled to be performed.";
         type yang:date-and-time;
      }

      leaf get-time {
         description
           "Indicates that the rpc-reply should include the
            execution-time.";
         type empty;
      }
   }

   augment /nc:edit-config/nc:output {
      description
        "Adds the time element to <edit-config>.";

      leaf execution-time {
         description
           "The time at which the RPC was executed.";
         type yang:date-and-time;
      }
   }

   augment /nc:delete-config/nc:input {
      description
        "Adds the time element to <delete-config>.";

      leaf scheduled-time {
         description
           "The time at which the RPC is scheduled to be performed.";
         type yang:date-and-time;
      }

      leaf get-time {
         description
           "Indicates that the rpc-reply should include the
            execution-time.";
         type empty;
      }
   }

   augment /nc:delete-config/nc:output {
      description
        "Adds the time element to <delete-config>.";

      leaf execution-time {
         description
           "The time at which the RPC was executed.";
         type yang:date-and-time;
      }
   }

   augment /nc:lock/nc:input {
      description
        "Adds the time element to <lock>.";

      leaf scheduled-time {
         description
           "The time at which the RPC is scheduled to be performed.";
         type yang:date-and-time;
      }

      leaf get-time {
         description
           "Indicates that the rpc-reply should include the
            execution-time.";
         type empty;
      }
   }

   augment /nc:lock/nc:output {
      description
        "Adds the time element to <lock>.";

      leaf execution-time {
         description
           "The time at which the RPC was executed.";
         type yang:date-and-time;
      }
   }

   augment /nc:unlock/nc:input {
      description
        "Adds the time element to <unlock>.";

      leaf scheduled-time {
         description
           "The time at which the RPC is scheduled to be performed.";
         type yang:date-and-time;
      }
      leaf get-time {
         description
           "Indicates that the rpc-reply should include the
            execution-time.";
         type empty;
      }
   }

   augment /nc:unlock/nc:output {
      description
        "Adds the time element to <unlock>.";

      leaf execution-time {
         description
           "The time at which the RPC was executed.";
         type yang:date-and-time;
      }
   }

   augment /nc:close-session/nc:input {
      description
        "Adds the time element to <close-session>.";

      leaf scheduled-time {
         description
           "The time at which the RPC is scheduled to be performed.";
         type yang:date-and-time;
      }

      leaf get-time {
         description
           "Indicates that the rpc-reply should include the
            execution-time.";
         type empty;
      }
   }

   augment /nc:close-session/nc:output {
      description
        "Adds the time element to <close-session>.";
      leaf execution-time {
         description
           "The time at which the RPC was executed.";
         type yang:date-and-time;
      }
   }

   augment /nc:kill-session/nc:input {
      description
        "Adds the time element to <kill-session>.";

      leaf scheduled-time {
         description
           "The time at which the RPC is scheduled to be performed.";
         type yang:date-and-time;
      }

      leaf get-time {
         description
           "Indicates that the rpc-reply should include the
            execution-time.";
         type empty;
      }
   }

   augment /nc:kill-session/nc:output {
      description
        "Adds the time element to <kill-session>.";

      leaf execution-time {
         description
           "The time at which the RPC was executed.";
         type yang:date-and-time;
      }
   }

   augment /nc:commit/nc:input {
      description
        "Adds the time element to <commit>.";

      leaf scheduled-time {
         description
           "The time at which the RPC is scheduled to be performed.";
         type yang:date-and-time;
      }

      leaf get-time {
         description
           "Indicates that the rpc-reply should include the
            execution-time.";
         type empty;
      }
   }

   augment /nc:commit/nc:output {
      description
        "Adds the time element to <commit>.";

      leaf execution-time {
         description
           "The time at which the RPC was executed.";
         type yang:date-and-time;
      }
   }

   augment /ncm:netconf-state {
      container scheduling-tolerance {
         description
           "The scheduling tolerance when the time capability
            is enabled.";
         uses scheduling-tolerance-parameters;
      }
   }

   rpc cancel-schedule {
      description
        "Cancels a scheduled message.";
      reference
        "draft-mm-netconf-time-capability:
         Time Capability in NETCONF";

      input {
         leaf cancelled-message-id {
            description
              "The ID of the message to be cancelled.";
               type string;
         }
         leaf get-time {
            description
              "Indicates that the rpc-reply should include
               the execution-time.";
            type empty;
         }
      }
      output {
         leaf execution-time {
            description
              "The time at which the RPC was executed.";
            type yang:date-and-time;
         }
      }
   }

   notification netconf-scheduled-message {
      description
        "Indicates that a scheduled message was received.";
      reference
        "draft-mm-netconf-time-capability:
         Time Capability in NETCONF";

      leaf schedule-id {
         description
           "The ID of the scheduled message.";
         type string;
      }

      leaf scheduled-time {
         description
           "The time at which the RPC is scheduled to be performed.";
         type yang:date-and-time;
      }
   }
}
