module ietf-l1csm {
  yang-version 1.1;
  namespace "urn:ietf:params:xml:ns:yang:ietf-l1csm";
  prefix "l1csm";

  import ietf-yang-types {
    prefix "yang";
    reference
      "RFC6991: Common YANG Data Types";
  }

  import ietf-layer1-types {
    prefix "l1-types";
    reference
      "RFCYYYY: A YANG Data Model for Layer 1 Types";
  }
  organization
    "Internet Engineering Task Force (IETF) CCAMP WG";

  contact
    "WG Web:  <http://tools.ietf.org/wg/ccamp/>
     WG List: <mailto:ccamp@ietf.org>

     Editor:  Young Lee
              <mailto:younglee.tx@gmail.com>

     Editor:  Haomian Zheng
              <mailto:zhenghaomian@huawei.com>

     Editor:  Dhruv Dhody
              <mailto:dhruv.ietf@gmail.com>

     Editor:  Oscar Gonzalez de Dios
              <mailto:oscar.gonzalezdedios@telefonica.com>

     Editor:  Daniele Ceccarelli
              <mailto:daniele.ceccarelli@ericsson.com>";

  description
    "This module describes L1 connectivity service based on MEF 63:
     Subscriber Layer 1 Service Attribute Technical Specification.
     Refer to MEF 63 for all terms and the original references
     used in the module.

     Copyright (c) 2021 IETF Trust and the persons identified as
     authors of the code.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).

     This version of this YANG module is part of RFC XXXX; see
     the RFC itself for full legal notices.";

  revision "2021-02-19" {
    description
      "Initial revision.";
    reference
      "RFC XXXX: A Yang Data Model for L1 Connectivity Service Model
       (L1CSM)";
  // Note: The RFC Editor will replace XXXX with the number
  // assigned to the RFC once this draft becomes an RFC.
  }

  /*
   * Identities
   */

  identity service-performance-metric {
    description
      "Base identity of service-specific performance metric";
    reference
      "MEF63: Subscriber Layer 1 Service Attributes";
  }

  identity one-way-delay {
    base service-performance-metric;
    description
      "One way delay.";
    reference
      "MEF63: Subscriber Layer 1 Service Attributes";
  }

  identity one-way-errored-second {
    base service-performance-metric;
    description
      "One way errored second";
    reference
      "MEF63: Subscriber Layer 1 Service Attributes";
  }

  identity one-way-severely-errored-second {
    base service-performance-metric;
    description
      "One way severely errored second";
    reference
      "MEF63: Subscriber Layer 1 Service Attributes";
  }

  identity one-way-unavailable-second {
    base service-performance-metric;
    description
      "One way unavailable second";
    reference
      "MEF63: Subscriber Layer 1 Service Attributes";
  }

  identity one-way-availability {
    base service-performance-metric;
    description
      "One way availability";
    reference
      "MEF63: Subscriber Layer 1 Service Attributes";
  }

  /*
   * Groupings
   */

  grouping protocol-coding-optical-interface {
    description
      "The 3-tuple <p,c,o> where p:protocol type;
       c:coding function; o:optical interface function.

       Valid combinations are defined in Tables 4, 5, 6 and 7
       of MEF 63.";
    reference
      "MEF63: Subscriber Layer 1 Service Attributes";

    leaf protocol {
      type identityref {
        base l1-types:protocol;
      }
      mandatory true;
      description
        "The protocol being used at the UNI.";
    }
    leaf coding {
      type identityref {
        base l1-types:coding-func;
      }
      mandatory true;
      description
        "The coding function being used at the UNI.";
    }
    leaf optical-interface {
      type identityref {
        base l1-types:optical-interface-func;
      }
      mandatory true;
      description
        "The optical interface function being used at the UNI.";
    }
  }

  grouping subscriber-l1vc-sls-service-attributes {
    description
      "The value of the Subscriber L1VC SLS (Service Level
       Specification) Service Attribute";
    reference
      "MEF63: Subscriber Layer 1 Service Attributes";

    leaf start-time {
      type yang:date-and-time;
      description
        "A time that represent the date and time for the start of
         the SLS";
    }
    leaf time-interval {
      type int32;
      units seconds;
      description
        "A time interval (e.g., 2,419,200 seconds which is 28 days)
         that is used in conjunction with time-start to specify a
         contiguous sequence of time intervals T for determining
         when performance objectives are met.";
    }
    leaf-list performance-metric {
      type identityref {
        base service-performance-metric;
      }
      description
        "List of service performance metric.";
    }
  }

  grouping subscriber-l1vc-endpoint-attributes {
    description
      "Subscriber layer 1 connection endpoint attributes";
    reference
      "MEF63: Subscriber Layer 1 Service Attributes";

    container endpoint-1 {
      description
        "One end of UNI id's - string and id";
      leaf id {
        type string;
        mandatory true;
        description
          "Subscriber end point ID of one end";
      }
      leaf uni {
        type leafref {
          path "/l1-connectivity/access/unis/uni/id";
        }
        mandatory true;
        description
          "This is one end of subscriber L1VC end point ID value =
           UNI-1";
      }
    }
    container endpoint-2 {
      description
        "One end of UNI id's - string and id";
      leaf id {
        type string;
        must '. != ../../endpoint-1/id' {
          error-message
            "The two end points must not be equal to each other. ";
        }
        mandatory true;
        description
          "Subscriber end point ID of the other end";
      }
      leaf uni {
        type leafref {
          path "/l1-connectivity/access/unis/uni/id";
        }
        mandatory true;
        description
          "This is one other end of subscriber L1VC end point
           ID value = UNI-2";
      }
    }
  }

  /*
   * Data nodes
   */

  container l1-connectivity {
    description
      "Serves as a top-level container for a list of layer 1
       connection services (l1cs)";

    container access {
      description
        "UNI configurations for access networks";

      container unis {
        description
          "The list of UNI's to be configured";

        list uni {
          key "id";
          description
            "UNI identifier";
          leaf id {
            type string;
            description "The UNI id of UNI Service Attributes";
          }
          choice uni-access-type {
            description
              "The UNI access type can be specified either by the
               protocol, coding function and optical interface
               function, defined in MEF, or by the client-signal,
               defined in ITU-T.";
            case mef {
              uses protocol-coding-optical-interface;
            }
            case itu {
              leaf client-signal {
                type identityref {
                  base l1-types:client-signal;
                }
                mandatory true;
                description
                  "The client signal being used at the UNI";
              }
            }
          }
        }
      }
    }

    container services {
      description
        "L1VC services";
      list service {
        key "service-id";
        description
          "A unique identifier of a subscriber L1VC service";

        leaf service-id {
          type string;
          mandatory true;
          description
            "A unique service identifier for subscriber L1VC.";
        }
        uses subscriber-l1vc-endpoint-attributes;
        uses subscriber-l1vc-sls-service-attributes;

      } //end of service list
    } //end of service container
  } //service top container
}
