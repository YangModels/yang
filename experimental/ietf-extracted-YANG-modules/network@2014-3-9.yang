module network {
  yang-version 1;
  namespace "urn:TBD:params:xml:ns:yang:nodes";
  prefix nd;

  import ietf-inet-types { prefix inet; }

  organization "TBD";
  contact
    "WILL-BE-DEFINED-LATER";
  description
    "This module defines a common base model for a collection
     of nodes in a network. Node definitions s are further used
     in network topologies and inventories.";

  revision 2014-3-9 {
    description
      "Initial revision.";
    reference "draft-clemm-i2rs-yang-network-topo-04";
  }

  typedef node-id {
    type inet:uri;
  }

  typedef network-id {
    type inet:uri;
  }

  grouping network-ref {
    leaf network-ref {
      type leafref {
        path "/network/topology-id";
      }
    }
  }

  grouping node-ref {
    uses network-ref;
    leaf node-ref {
      type leafref {
        path "/network[network-id=current()" +
             "/../network-ref]/node/node-id";
      }
    }
  }

  list network {
    key "network-id";

    leaf network-id {
      type network-id;
    }

    leaf server-provided {
      type boolean;
      config false;
    }

    container network-types {
    }

    list supporting-network {
      key "network-ref";
      leaf network-ref {
        type leafref {
          path "/network/network-id";
        }
      }
    }

    list node {
      key "node-id";
      leaf node-id {
        type node-id;
      }
      list supporting-node {
        key "network-ref node-ref";
        leaf network-ref {
          type leafref {
            path "../../../supporting-network/network-ref";
          }
        }
        leaf node-ref {
          type leafref {
          // path "/network[network-id=current()" +
          // "/../network-ref]/node/node-id";
          path "/network/node/node-id";
          }
        }
      }
    }
  }

}
