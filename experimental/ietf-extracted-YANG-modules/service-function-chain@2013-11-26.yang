module service-function-chain {

  namespace "urn:cisco:params:xml:ns:yang:sfc-sf";

  prefix sfc-sf;

  import ietf-inet-types { prefix inet; }
  import ietf-yang-types { prefix yang; }

  organization "Cisco Systems, Inc.";
  contact "Reinaldo Penno <repenno@cisco.com>";

  description
    "This module contains a collection of YANG definitions for
     managing service function chains.
     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2013-11-26 {
    description
    "Initial revision.";
  }

  // Service Function

  // Service Function Type definitions

  identity service-function-type-indentity {
    description
      "Base identity from which specific service function types are
      derived.";
  }

  identity firewall {
    base "service-function-type-indentity";
    description "Firewall";
  }

  identity dpi {
    base "service-function-type-indentity";
    description "Deep Packet Inspection";
  }

  identity napt44 {
    base "service-function-type-indentity";
    description "Network Address and Port Translation 44";
  }

  typedef service-function-type {
    type identityref {
      base "service-function-type-indentity";
    }
  }

  container service-function {
    description
      "A network or application based packet
      treatment, application, compute or storage resource, used
      singularly or in concert with other service functions within a
      service chain to enable a service offered by an operator.

      A non-exhaustive list of Service Functions includes: firewalls,
      WAN and application acceleration, Deep Packet Inspection (DPI),
      server load balancers, NAT44 [RFC3022], NAT64 [RFC6146], HOST_ID
      injection, HTTP Header Enrichment functions, TCP optimizer, etc.";
    leaf name {
      type string;
      description
             "The name of the service function.";
      mandatory true;
    }
    leaf type {
      type service-function-type;
    }
    leaf ip-host-address {
      type inet:ip-address;
    }
    uses network-service-context-header;
  }

  // Service Function Chain

  container service-function-chain {
    description
      "A service chain defines the required functions and
      associated order (service-function1 --> service-function 2) that
      must be applied to packets and/or frames.  A service chain does
      not specify the network location or specific instance of service
      functions (e.g. firewall1 vs. firewall2).";
    leaf-list service-function {
      type string;
      ordered-by user;
      description
        "A list of service functions that compose the service chain";
    }
  }

/*
    0                   1                   2                   3
    0 1 2 3 4 5 6 7 8 9 0 1 2 3 4 5 6 7 8 9 0 1 2 3 4 5 6 7 8 9 0 1
   +-+-+-+-+-+-+-+-+-+-+-+-+-+-+-+-+-+-+-+-+-+-+-+-+-+-+-+-+-+-+-+-+
   |                  Network Platform Context                     |
   +-+-+-+-+-+-+-+-+-+-+-+-+-+-+-+-+-+-+-+-+-+-+-+-+-+-+-+-+-+-+-+-+
   |                  Network Shared Context                       |
   +-+-+-+-+-+-+-+-+-+-+-+-+-+-+-+-+-+-+-+-+-+-+-+-+-+-+-+-+-+-+-+-+
   |                  Service Platform Context                     |
   +-+-+-+-+-+-+-+-+-+-+-+-+-+-+-+-+-+-+-+-+-+-+-+-+-+-+-+-+-+-+-+-+
   |                  Service Shared Context                       |
   +-+-+-+-+-+-+-+-+-+-+-+-+-+-+-+-+-+-+-+-+-+-+-+-+-+-+-+-+-+-+-+-+

*/

  grouping network-service-context-header {
    description "Network Service context header";
    leaf-list context-headers {
      type uint32;
      min-elements 4;
      max-elements 4;
    }
  }
}
