module ietf-rpki-rtr {
  yang-version 1.1;
  namespace "urn:ietf:params:xml:ns:yang:ietf-rpki-rtr";
  prefix rpki-rtr;

  import ietf-yang-types {
    prefix yang;
    reference
      "RFC 9911: Common YANG Data Types";
  }
  import ietf-inet-types {
    prefix inet;
    reference
      "RFC 9911: Common YANG Data Types";
  }
  import ietf-routing {
    prefix rt;
    reference
      "RFC 8349: A YANG Data Model for Routing Management
                 (NMDA Version)";
  }
  import ietf-routing-types {
    prefix rt-types;
    reference
      "RFC 8294: Common YANG Data Types for the Routing Area";
  }
  import iana-crypt-hash {
    prefix ianach;
    reference
      "RFC 7317: A YANG Data Model for System Management";
  }
  import ietf-ssh-client {
    prefix sshc;
    reference
      "RFC 9644: YANG Groupings for SSH Clients and SSH Servers";
  }
  import ietf-interfaces {
    prefix if;
    reference
      "RFC 8343: A YANG Data Model for Interface Management";
  }
  import ietf-key-chain {
    prefix key-chain;
    reference
      "RFC 8177: YANG Data Model for Key Chains";
  }

  organization
    "IETF Secure Inter-Domain Routing Operations (SIDROPS)
     Working Group";
  contact
    "WG Web:   <https://datatracker.ietf.org/wg/sidrops/>
     WG List:  SIDROPS <mailto:sidrops@ietf.org>

     Editor:   Yisong Liu
               <mailto:liuyisong@chinamobile.com>
     Editor:   Changwang Lin
               <mailto:linchangwang.04414@h3c.com>
     Editor:   Haibo Wang
               <mailto:rainsword.wang@huawei.com>
     Editor:   Jishnu Roy
               <mailto:jishnu.roy@hpe.com>
     Editor:   Jeffrey Haas
               <mailto:jeffrey.haas@hpe.com>
     Editor:   Hongwei Liu
               <mailto:liu.hongwei3@zte.com.cn>
     Editor:   Di Ma
               <mailto:madi@zdns.cn>";
  description
    "This module describes a YANG model for the Resource Public
     Key Infrastructure (RPKI) to Router (RTR) protocol management.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see the
     RFC itself for full legal notices.";

  revision 2026-09-03 {
    description
      "Initial Version";
    reference
      "RFC XXXX: YANG Data Model for RPKI to Router Protocol";
  }

  identity rpki-rtr {
    base rt:routing-protocol;
    description
      "RTR protocol.";
  }

  grouping records-limit {
    description
      "Limit of records that can be received from the RPKI
       cache server.";
    leaf max-number {
      type uint64;
      description
        "Configures the maximum number of records that can be
         received from the RPKI cache server.";
    }
    leaf threshold-percentage {
      type rt-types:percentage;
      units "percent";
      description
        "Configures the threshold percentage for record maximum
         number.";
    }
    leaf over-threshold-action {
      type enumeration {
        enum alert-only {
          description
            "Generates alert messages.";
        }
        enum discard {
          description
            "Discards excess records.";
        }
        enum reconnect {
          description
            "Disconnects with the RPKI cache server,
             and tries to reconnect after reconnection
             timer expires.";
        }
        enum idle-forever {
          description
            "Disconnects with the RPKI cache server
             forever.";
        }
      }
      description
        "The action to taken when record number exceeds
         threshold.";
    }
  }

  augment "/rt:routing/rt:control-plane-protocols/"
        + "rt:control-plane-protocol" {
    when "derived-from-or-self(rt:type, 'rpki-rtr')" {
      description
        "This augmentation is valid for a routing protocol
         instance of RTR.";
    }
    description
      "RTR protocol augmentation of ietf-routing module
       control-plane-protocol.";
    container rpki-rtr {
      description
        "Configuration parameters for the RTR protocol.";
      container sessions {
        description
          "Parameters of RPKI sessions to cache servers.";
        list session {
          key "server-address";
          description
            "Each entry contains parameters for a RPKI session
             identified by the 'server-address' key.";
          leaf server-address {
            type inet:ip-address;
            mandatory true;
            description
              "The IP address of the RPKI cache server resembling
               a session.";
          }
          leaf server-port {
            type inet:port-number;
            description
              "The remote port for the connection
               to the RPKI cache server.";
          }
          leaf local-address {
            type union {
              type inet:ip-address;
              type if:interface-ref;
            }
            description
              "The local IP (either IPv4 or IPv6) address to use for
               the connection to the RPKI cache server. This may be
               expressed as either an IP address or reference to the
               name of an interface.";
          }
          leaf local-port {
            type inet:port-number;
            description
              "The local port for the connection
               to the RPKI cache server.";
          }
          leaf enabled {
            type boolean;
            default "true";
            description
              "Whether the RPKI cache server is enabled.";
          }
          leaf preference {
            type uint32;
            description
              "The router's preference to connect to that cache.
               The lower the value, the more preferred.";
          }
          leaf description {
            type string;
            description
              "Textual description of the RPKI cache server.";
          }
          leaf reconnect-interval {
            type uint32 {
              range "1..30000";
            }
            units "minutes";
            description
              "Time interval for the reconnection timer.";
          }
          leaf session-state {
            type enumeration {
              enum idle {
                description
                  "The session is down.";
              }
              enum connect {
                description
                  "The session is waiting for the underlying
                   transport session to be established.";
              }
              enum establish {
                description
                  "The session is up.";
              }
              enum ex-incr {
                description
                  "Incremental update of records in progress.";
              }
              enum ex-full {
                description
                  "Full update of records in progress.";
              }
            }
            config false;
            description
              "The session state.";
          }
          leaf enable-authentication {
            type boolean;
            default "false";
            description
              "Whether the session is secured.";
          }
          container authentication {
            when "../enable-authentication = 'true'";
            description
              "Container for describing how a particular session
               is to be secured.";
            choice option {
              description
                "Choice for session securing methods.";
              case md5 {
                leaf md5-password {
                  type ianach:crypt-hash;
                  description
                    "The password for md5 authentication.";
                }
                description
                  "Uses TCP-MD5 to secure the session.";
              }
              case ssh {
                uses sshc:ssh-client-grouping {
                  reference
                    "RFC 9644: YANG Groupings for SSH Clients and
                               SSH Servers";
                }
                description
                  "Uses SSH to secure the session.";
              }
              case tcp-ao-keychain {
                leaf keychain-name {
                  type key-chain:key-chain-ref;
                  description
                    "Name of key chain.";
                  reference
                    "RFC 8177: YANG Data Model for Key Chains";
                }
                description
                  "Uses key-chain to secure the session.";
              }
            }
          }
          container vrp-limit {
            description
              "Limit of Validated ROA Payload records that can be
               received from the RPKI cache server.";
            uses records-limit;
          }
          container aspa-limit {
            description
              "Limit of Autonomous System Provider Authorization
               (ASPA) records that can be received from the RPKI
               cache server.";
            uses records-limit;
          }
          container statistics {
            config false;
            description
              "Statistics of the RPKI cache server.";
            leaf total-vrp-records {
              type yang:zero-based-counter64;
              description
                "The total number of Validated ROA Payloads
                 received from the RPKI cache server.";
            }
            leaf ipv4-vrp-records {
              type yang:zero-based-counter64;
              description
                "The number of Validated ROA Payloads for IPv4
                 prefixes received from the RPKI cache server.";
            }
            leaf ipv6-vrp-records {
              type yang:zero-based-counter64;
              description
                "The number of Validated ROA Payloads for IPv6
                 prefixes received from the RPKI cache server.";
            }
            leaf router-key-records {
              type yang:zero-based-counter64;
              description
                "The number of Router Keys received from the RPKI
                 cache server.";
            }
            leaf aspa-records {
              type yang:zero-based-counter64;
              description
                "The number of ASPAs received from the RPKI
                 cache server.";
            }
            leaf in-total-messages {
              type yang:zero-based-counter64;
              description
                "The total number of messages received from the
                 RPKI cache server.";
            }
            leaf out-total-messages {
              type yang:zero-based-counter64;
              description
                "The total number of messages transmitted to the
                 RPKI cache server.";
            }
          }
          container connection-data {
            config false;
            description
              "State information relating to the connection
               with the RPKI cache server.";
            leaf flaps {
              type uint32;
              description
                "Count for number of flaps observed on the
                 session.";
            }
            leaf last-session-up-down {
              type yang:date-and-time;
              description
                "The date and time the RPKI-RTR session last
                 transitioned in or out of the UP state.";
              reference
                "RFC 6810: The Resource Public Key Infrastructure
                           (RPKI) to Router Protocol";
            }
            leaf last-update-sync {
              type yang:date-and-time;
              description
                "The date and time of the last serial sync with the
                 cache server.";
            }
            leaf last-full-sync {
              type yang:date-and-time;
              description
                "The date and time of the last reset sync with the
                 cache server.";
            }
            leaf last-serial-query {
              type yang:date-and-time;
              description
                "The date and time the last serial query was sent to
                 the cache server.";
            }
            leaf last-reset-query {
              type yang:date-and-time;
              description
                "The date and time the last reset query was sent to
                 the cache server.";
            }
            leaf last-eod-received {
              type yang:date-and-time;
              description
                "The date and time the last EOD was received.";
            }
            leaf last-config-change {
              type yang:date-and-time;
              description
                "The date and time of the last host, port, VRF or
                 local interface change.";
            }
            leaf last-error {
              type yang:date-and-time;
              description
                "The date and time of the last protocol error sent to
                 or received from the cache server.";
            }
            leaf last-connection-error {
              type yang:date-and-time;
              description
                "The date and time of the last connection error to
                 the cache server.";
            }
            leaf last-connection {
              type yang:date-and-time;
              description
                "The date and time of the last connection to the
                 cache server.";
            }
            leaf error-reason {
              type string;
              description
                "Reason for error in connection.";
            }
          }
          container protocol-data {
            description
              "Parameters related to the RTR protocol.";
            leaf preferred-protocol-version {
              type uint32;
              description
                "The preferred version number of the RTR protocol
                 to be used when establishing the session. If not
                 configured, the router will use its default
                 protocol version.";
            }
            leaf refresh-interval {
              type uint32;
              description
                "Number of seconds a router waits in between
                 sending periodic serial queries to the RPKI
                 cache server.";
            }
            leaf retry-interval {
              type uint32;
              description
                "Number of seconds between poll error and cache
                 server poll.";
            }
            leaf expire-interval {
              type uint32;
              description
                "Number of seconds to retain data synced from
                 cache server.";
            }
            leaf purge-interval {
              type uint32;
              description
                "Number of seconds after the session drops before
                 data from the RPKI cache server is purged.";
            }
            leaf hold-interval {
              type uint32;
              description
                "Maximum number of seconds to wait without receiving
                 any RTR PDUs from the cache server before tearing
                 down the RTR session. Any incoming PDU resets this
                 timer. The hold-interval value must be at least
                 twice the configured refresh-interval. Defaults to
                 600 seconds.";
            }
            leaf protocol-version {
              type uint32;
              config false;
              description
                "The negotiated version number of the RTR protocol
                 currently in use for this session.";
            }
            leaf refresh-time {
              type yang:date-and-time;
              config false;
              description
                "The date and time when the next refresh of RPKI
                 data from the RPKI cache server will occur.";
            }
            leaf response-time {
              type yang:date-and-time;
              config false;
              description
                "The date and time when a response to a serial or
                 reset query to the RPKI cache server is expected.";
            }
            leaf record-lifetime {
              type yang:date-and-time;
              config false;
              description
                "The date and time when the records received from
                 the RPKI cache server will expire.";
            }
            leaf purge-time {
              type yang:date-and-time;
              config false;
              description
                "The date and time when the data from the RPKI cache
                 server will be purged after the session drops.";
            }
            leaf hold-time {
              type yang:date-and-time;
              config false;
              description
                "The date and time when the RTR session will be torn
                 down if no RTR PDUs are received from the cache
                 server.";
            }
            leaf session-id {
              type uint16;
              config false;
              description
                "When a cache server is started, it generates a
                 Session ID to identify the instance of the cache
                 and to bind it to the sequence of Serial Numbers
                 that cache instance will generate.";
              reference
                "RFC 6810: The Resource Public Key Infrastructure
                           (RPKI) to Router Protocol
                 RFC 8210: The Resource Public Key Infrastructure
                           (RPKI) to Router Protocol, Version 1";
            }
            leaf serial-full {
              type uint32;
              config false;
              description
                "A 32-bit strictly increasing unsigned integer which
                 wraps from 2^32-1 to 0. It denotes the logical
                 version of a cache. It resembles the latest full
                 query.";
              reference
                "RFC 6810: The Resource Public Key Infrastructure
                           (RPKI) to Router Protocol
                 RFC 8210: The Resource Public Key Infrastructure
                           (RPKI) to Router Protocol, Version 1";
            }
            leaf serial-incremental {
              type uint32;
              config false;
              description
                "A 32-bit strictly increasing unsigned integer which
                 wraps from 2^32-1 to 0. It denotes the logical
                 version of a cache. It resembles the latest
                 incremental query.";
              reference
                "RFC 6810: The Resource Public Key Infrastructure
                           (RPKI) to Router Protocol
                 RFC 8210: The Resource Public Key Infrastructure
                           (RPKI) to Router Protocol, Version 1";
            }
          }
          container pdu-counters {
            config false;
            description
              "Counters of RTR PDUs exchanged with the RPKI cache
               server, by PDU type.";
            leaf serial-notify {
              type yang:zero-based-counter64;
              description
                "Serial Notify (PDU Type 0) count.";
            }
            leaf serial-query {
              type yang:zero-based-counter64;
              description
                "Serial Query (PDU Type 1) count.";
            }
            leaf reset-query {
              type yang:zero-based-counter64;
              description
                "Reset Query (PDU Type 2) count.";
            }
            leaf cache-response {
              type yang:zero-based-counter64;
              description
                "Cache Response (PDU Type 3) count.";
            }
            leaf ipv4-prefix {
              type yang:zero-based-counter64;
              description
                "IPv4 Prefix (PDU Type 4) count.";
            }
            leaf ipv6-prefix {
              type yang:zero-based-counter64;
              description
                "IPv6 Prefix (PDU Type 6) count.";
            }
            leaf end-of-data {
              type yang:zero-based-counter64;
              description
                "End of Data (PDU Type 7) count.";
            }
            leaf cache-reset {
              type yang:zero-based-counter64;
              description
                "Cache Reset (PDU Type 8) count.";
            }
            leaf router-key {
              type yang:zero-based-counter64;
              description
                "Router Key (PDU Type 9) count.";
            }
            leaf aspa {
              type yang:zero-based-counter64;
              description
                "ASPA (PDU Type 11) count.";
            }
          }
          container error-pdu-counters {
            config false;
            description
              "Counters of Error Report PDUs exchanged with the
               RPKI cache server, by error code.";
            leaf corrupt-data {
              type yang:zero-based-counter64;
              description
                "Corrupt Data (Error Code 0) Error Report PDU
                 count.";
            }
            leaf internal-error {
              type yang:zero-based-counter64;
              description
                "Internal Error (Error Code 1) Error Report PDU
                 count.";
            }
            leaf no-data-available {
              type yang:zero-based-counter64;
              description
                "No Data Available (Error Code 2) Error Report PDU
                 count.";
            }
            leaf invalid-request {
              type yang:zero-based-counter64;
              description
                "Invalid Request (Error Code 3) Error Report PDU
                 count.";
            }
            leaf unsupported-protocol-version {
              type yang:zero-based-counter64;
              description
                "Unsupported Protocol Version (Error Code 4) Error
                 Report PDU count.";
            }
            leaf unsupported-pdu-type {
              type yang:zero-based-counter64;
              description
                "Unsupported PDU Type (Error Code 5) Error Report
                 PDU count.";
            }
            leaf withdrawal-unknown-record {
              type yang:zero-based-counter64;
              description
                "Withdrawal of Unknown Record (Error Code 6) Error
                 Report PDU count.";
            }
            leaf duplicate-announcement-received {
              type yang:zero-based-counter64;
              description
                "Duplicate Announcement Received (Error Code 7)
                 Error Report PDU count.";
            }
            leaf unexpected-protocol-version {
              type yang:zero-based-counter64;
              description
                "Unexpected Protocol Version (Error Code 8) Error
                 Report PDU count.";
            }
            leaf aspa-provider-list-error {
              type yang:zero-based-counter64;
              description
                "ASPA Provider List Error (Error Code 9) Error
                 Report PDU count.";
            }
            leaf transport-failure {
              type yang:zero-based-counter64;
              description
                "Transport Failure (Error Code 10) Error Report
                 PDU count.";
            }
            leaf ordering-error {
              type yang:zero-based-counter64;
              description
                "Ordering Error (Error Code 11) Error Report PDU
                 count.";
            }
            leaf cache-restart {
              type yang:zero-based-counter64;
              description
                "Cache Restart (Error Code 12) Error Report PDU
                 count.";
            }
            leaf cache-shutdown {
              type yang:zero-based-counter64;
              description
                "Cache Shutdown (Error Code 13) Error Report PDU
                 count.";
            }
          }
        }
      }
    }
  }
}
