module ietf-yang-package-types {
  yang-version 1.1;
  namespace "urn:ietf:params:xml:ns:yang:ietf-yang-package-types";
  prefix "pkg-types";

  import ietf-yang-revisions {
    prefix rev;
    reference "XXXX: Updated YANG Module Revision Handling";
  }

  import ietf-yang-semver  {
    prefix ys;
    reference "XXXX: YANG Semantic Versioning";
  }

  import ietf-yang-types {
    prefix yang;
    rev:recommended-min-date 2019-07-21;
    reference "RFC 6991bis: Common YANG Data Types.";
  }

  import ietf-inet-types {
    prefix inet;
    rev:recommended-min-date 2013-07-15;
    reference "RFC 6991: Common YANG Data Types.";
  }

  organization
    "IETF NETMOD (Network Modeling) Working Group";

  contact
    "WG Web:   <http://tools.ietf.org/wg/netmod/>
     WG List:  <mailto:netmod@ietf.org>

     Author:   Rob Wilton
               <mailto:rwilton@cisco.com>";

  description
    "This module provides type and grouping definitions for YANG
     packages.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.
  // RFC Ed.: replace XXXX with actual RFC number and remove this
  // note.
  revision 2026-01-30 {
    ys:version 0.8.0;
    description
      "Initial revision";
    reference
      "RFC XXXX: YANG Packages";
  }

  /*
   * Typedefs
   */

  typedef pkg-name {
    type yang:yang-identifier;
    description
      "Package names are typed as YANG identifiers.";
  }

  typedef pkg-version {
    type ys:version;
    description
      "Packages are versioning using YANG Semver version labels.";
  }

  typedef module-name {
    type yang:yang-identifier;
    description
      "Module names are typed as YANG identifiers.";
  }

  typedef version-or-rev-date {
    type union {
      type rev:revision-date;
      type ys:version;
    }
    description
      "Identifies a module by YANG semantic version or revision
       date";
  }

  typedef scoped-feature {
    type string {
      pattern '[a-zA-Z_][a-zA-Z0-9\-_.]*:[a-zA-Z_][a-zA-Z0-9\-_.]*';
    }
    description
      "Represents a feature name scoped to a particular module,
       identified as the '<module-name>:<feature-name>', where both
       <module-name> and <feature-name> are YANG identifier strings,
       as defiend by Section 12 or RFC 6020.";
    reference
      "RFC XXXX, YANG Packages.";
  }

  typedef mount-ypath {
    type string;

    description
      "A path that identifies a set of data nodes in the schema tree.

      This leaf is encoded as a JSON style encoded
      instance-identifier (regardless of whether the format
      used to encode the YANG instance data), as specified in
      RFC 7951, section 6.11, except that keys are optional.

      For optional keys, the name and value of the key is
      excluded from the key list.

      TODO - Check if this definition is sufficient.";
  }

  /*
   * Groupings
   */
  grouping yang-pkg-identification-leafs {
    description
      "Parameters for identifying a specific version of a YANG
       package";

    leaf name {
      type pkg-name;
      mandatory true;
      description
        "The YANG package name.";
    }

    leaf version {
      type pkg-version;
      mandatory true;
      description
        "Uniquely identies a particular version of a YANG package.

         Follows the definition for revision labels defined in
         draft-verdt-nemod-yang-module-versioning, section XXX";
    }
  }
  grouping yang-pkg-exclusions {
    description
      "Parameters for excluding modules and packages from a YANG
       package definition";

    container excludes {
      description
        "Contains parameters for excluding modules and packages
         from a YANG package definition";

      leaf-list module {
        type module-name;
        description
          "Lists implemented modules, of any version, that may have
           have been brought in by included packages, but are
           explicitly excluded from this package definition.

           Excluding a module can affect the compliance and
           correctness of any included packages that expect that
           module to be implemented.

           Excluding a module also implicitly excludes any submodules
           and mandatory-features defined in the excluded module.

           It is an error to list a module in both this list and the
           'includes/module' list.";
      }

      list import-only-module {
        key "name";
        description
          "Lists import-only modules that may have have been brought
           in by included packages, but are explicitly excluded from
           this package definition.

           It is an error to list a module in both this list and the
           'includes/import-only-module' list.";

        leaf name {
          type module-name;
          mandatory true;
          description
            "The name of the import-only module to exclude some
             versions of.";
        }

        leaf-list version {
          type version-or-rev-date;
          description
            "Lists specific versions of the import-only module being
              excluded.  If no versions are listed, all versions of
              the import-only module are excluded.

              If required, the YANG Semantic Version SHOULD be used to
              identify the module version, otherwise the YANG module
              revision date is used.";
        }
      }

      leaf-list feature {
        type scoped-feature;
        description
          "Lists features from the mandatory-features exported by an
          included package that are reclassified as being OPTIONAL
          to support by any server implementing the package,
          overriding the behavior specified by the included package.

          Features MUST NOT be specified both in this list and also
          the 'includes/feature' list.

          Features are identified using
          <module-name>:<feature-name>.";
      }
    }
  }

  grouping yang-pkg-location {
    description
      "Parameters for locating a YANG package instance";

    leaf-list location {
      type inet:uri;
      description
        "Contains a URL that represents where an instance data file
         (RFC 9195) for this YANG package can be found.

         This leaf will only be present if there is a URL available
         for retrieval of the schema for this entry.";
    }
  }

  grouping yang-pkg-instance {
    description
      "Specifies the data node for a full YANG package instance
       represented either on a server or as a YANG instance data
       document.";
    uses yang-pkg-identification-leafs;

    leaf timestamp {
      type yang:date-and-time;
      description
        "An optional timestamp for when this package was created.
         This does not need to be unique across all versions of a
         package.";
    }

    leaf organization {
      type string;
      description "Organization responsible for this package";
    }

    leaf contact {
      type string;
      description
        "Contact information for the person or organization to whom
         queries concerning this package should be sent.";
    }

    leaf description {
      type string;
      description "Provides a description of the package";
    }

    leaf reference {
      type string;
      description "Allows for a reference for the package";
    }

    leaf complete {
      type boolean;
      default true;
      description
        "Indicates whether the schema defined by this package is
         referentially complete.  I.e. all module imports can be
         resolved to a module explicitly defined in this package or
         one of the included packages.";
    }

    container includes {
      description
        "Lists package and modules that are included in the package
         definition.";

      list package {
        key "name";
        description
          "An entry in this list represents a package that is
           included as part of the package definition, or to change
           the version of a descendent included package.

           An entry in this list overrides any other package version
           'included' by an included package, which can be used for
           resolving conflicting package versions from included
           packages.

           A package definition MUST resolve to including only a
           single version of any YANG package.";

        uses yang-pkg-identification-leafs;
        uses yang-pkg-location;
      }

      list module {
        key "name";
        description
          "An entry in this list represents a module that MUST be
          implemented by a server implementing this package, as per
          RFC 7950 section 5.6.5.

          A entry in this list overrides any module version
          'implemented' by an included package.";
        reference
          "RFC 7950: The YANG 1.1 Data Modeling Language.";

        leaf name {
          type module-name;
          mandatory true;
          description
            "The YANG module name.";
        }

        leaf version {
          type version-or-rev-date;
          mandatory true;
          description
            "Identifies the module version.  If available, the YANG
             Semantic Version SHOULD be used, otherwise the YANG
             module revision date is used.";
        }

        leaf-list location {
          type inet:uri;
          description
            "Contains a URL that represents the YANG schema resource
             for this module.

             This leaf will only be present if there is a URL
             available for retrieval of the schema for this entry.";
        }

        list submodule {
          key "name";
          description
            "Each entry represents one submodule within the
             parent module.";

          leaf name {
            type module-name;
            mandatory true;
            description
              "The YANG submodule name.";
          }

          leaf version {
            type version-or-rev-date;
            mandatory true;
            description
              "The YANG submodule revision date or YANG Semantic
               version.

               If the parent module include statement for this
               submodule includes a revision date then it MUST match
               the revision date specified here or it MUST match the
               revision-date associated with the version specified
               here.";
          }

          leaf-list location {
            type inet:uri;
            description
              "Contains a URL that represents the YANG schema
               resource for this submodule.

               This leaf will only be present if there is a URL
               available for retrieval of the schema for this
               entry.";
          }
        }
      }

      list import-only-module {
        key "name version";
        description
          "An entry in this list indicates that the server imports
           reusable definitions from the specified revision of the
           module, but does not implement any protocol accessible
           objects from this revision.

           Multiple entries for the same module name MAY exist.
           This can occur if multiple modules import the same
           module, but specify different revision-dates in the
           import statements.";

        leaf name {
          type module-name;
          mandatory true;
          description
            "The YANG module name.";
        }

        leaf version {
          type version-or-rev-date;
          mandatory true;
          description
            "Identifies the module version.  If available, the YANG
             Semantic Version SHOULD be used, otherwise the YANG
             module revision date is used.";
        }

        leaf-list location {
          type inet:uri;
          description
            "Contains a URL that represents the YANG schema resource
             for this module.

             This leaf will only be present if there is a URL
             available for retrieval of the schema for this entry.";
        }

        list submodule {
          key "name";
          description
            "Each entry represents one submodule within the
             parent module.";

          leaf name {
            type module-name;
            mandatory true;
            description
              "The YANG submodule name.";
          }

          leaf version {
            type version-or-rev-date;
            mandatory true;
            description
              "The YANG submodule revision date or YANG Semantic
               version.

               If the parent module include statement for this
               submodule includes a revision date then it MUST match
               the revision date specified here or it MUST match the
               revision-date associated with the version specified
               here.";
          }

          leaf-list location {
            type inet:uri;
            description
              "Contains a URL that represents the YANG schema resource
               for this submodule.

               This leaf will only be present if there is a URL
               available for retrieval of the schema for this
               entry.";
          }
        }
      }

      leaf-list feature {
        type scoped-feature;
        description
          "Lists features from any modules included in the package
           that MUST be supported by any server implementing the
           package.

           Mandatory-features specified by any directly included
           packages MUST also be supported by server
           implementations, unless excluded by an entry in the
           'excludes/feature' list, and do not need to be repeated
           in this list.

           All other features defined in modules included in the
           package are OPTIONAL to implement.

           Features are identified using
           <module-name>:<feature-name>.";
      }
    }

    uses yang-pkg-exclusions;

    list mount {
      key "mount-path";
      description
        "An entry in this list represents additions to, or a
         replacement of, the schema found at the specified mount
         point.

         The full schema at the mount point depends on the
         setting of the inherit-packages leaf:

         If set to true (the default) - the schema is defined
         as the union of the resolved package schema at the mount
         point by any packages in the 'includes/package' list
         combined with the resolve package schema of all packages
         listed in the 'packages' list.

         If set to false - the schema is defined as the union of
         only the resolved package schema of all packages
         listed in the 'packages' list.";

      leaf "mount-path" {
        type mount-ypath;
        mandatory true;
        description
          "This path identifies a mount point in the schema.

           This leaf is encoded as a JSON style encoded
           instance-identifier (regardless of whether the format
           used to encode the YANG instance data), as specified in
           RFC 7951, section 6.11, except that keys are optional.

           For optional keys, the name and value of the key is
           excluded from the key list.

           Mount paths MUST only be used for schema mount points
           defined in the package schema.

           For example, if an example module 'ex-module' defines a
           mount point under list entry'/modules/module/' then a
           mount path of

           - '/modules/module[name=foo]' would indicate the mounted
             package schema for only the 'foo' entry in the module
             list.  Each entry in the list could have a different
             mounted schema specified.

           - '/modules/module[]' would indicate that the same
             mounted package schema is available for all list
             entries in the module list.";
      }

      leaf inherit-packages {
        type boolean;
        default true;
        description
          "Indicates whether the packages and parent-references
           available at the mount point for this package definition
           automatically include all packages and parent-references
           mounted at the same mount path in any
           'includes/packages' entries.

           If set to false, then only packages and
           parent-references listed here in the 'packages' list are
           included.  This allows the definitions in the mounted
           packages to be modified (e.g., remove or change module
           versions).  To help conformance, the packages listed
           here SHOULD include all the packages that would be have
           been automatically included.
          ";
      }

      list package {
        key "name";
        description
          "The packages that will be mounted at the specified mount
           path either in addition to, or instead of, the mounted
           packages from the 'included/package' list.

           Also see the 'inherit-packages' leaf.";
        uses yang-pkg-identification-leafs;
        uses yang-pkg-location;
      }

      leaf-list parent-reference {
        type mount-ypath;
        description
          "Represents paths in the parent schema that are accessible
           from the mounted schema for the evaluation of XPath
           expressions.

           See Mount Point path and parent-reference in Schema Mount
           (RFC 8528) for a more detailed description.

           Unlike the YANG module defined in RFC 8528, this leaf is
           encoded as a JSON style encoded instance-identifier
           (regardless of whether the format used to encode the YANG
           instance data), as specified in RFC 7951, section 6.11,
           except that keys are optional.

           For optional keys, the name and value of the key is
           excluded from the key list.";
      }
    }
  }
}
