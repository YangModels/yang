submodule ietf-bgp-rib-ext {
  yang-version "1.1";
  belongs-to ietf-bgp {
    prefix "bre";
  }

  include ietf-bgp-rib-types;

  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "Defines additional data nodes for the OpenConfig BGP RIB model.
     These items reflect extensions that are desirable features but
     are not currently supported in a majority of BGP
     implementations.";

  revision "2019-03-21" {
    description
      "Initial Revision.";
    reference
      "RFC XXXX: BGP YANG Model for Service Providers.";
  }

  grouping rib-ext-route-annotations {
    description
      "Extended annotations for routes in the routing tables";

    leaf reject-reason {
      type union {
        type identityref {
          base bgp-not-selected-bestpath;
        }
        type identityref {
          base bgp-not-selected-policy;
        }
      }
      description
        "Indicates the reason the route is not used, either due to
        policy filtering or bestpath selection";
    }
  }
}
