module ietf-ose-gateway-svc {
  namespace "urn:ietf:params:xml:ns:yang:ietf-ose-gateway-svc";
  prefix ose-gw-svc;

  organization
    "IETF foo Working Group.";
  contact
    "WG List: foo@ietf.org
     Editor:  ";
  description
    "The YANG module defines a generic service configuration
     model for interworking between different SD-WAN domains.";

  revision 2019-06-10 {
    description
      "Initial revision";
    reference
      "A YANG Data Model for SD-WAN service configuration of
       gateway-svc.";
  }

  feature ose-option-a {
    description
      "This feature means that ose reachability service option-A is
       supported by the Serving SDWAN manager";
    reference "ONUG-OSE-2 SDWAN Reachability and Segmentation
              Specification";
  }

  feature ose-option-b {
    description
      "This feature means that ose reachability service option-B
       is supported by the Serving SDWAN manager";
    reference "ONUG-OSE-2 SDWAN Reachability and Segmentation
              Specification";
  }

  container ose-gateways {
    list ose-gateway {
      key "gw-id";
      leaf gw-id {
        type uint32;
        description
          "Identifier for Gateway.";
      }
      leaf gw-name {
        type string;
        description
          "OSE gateway name.";
      }
      list peer-list {
        key "name";
        leaf name {
          type string;
          description
            "Peer Name.";
        }
        leaf peer-gw-id {
          type uint32;
          description
            "Identifier for the remote peer gateway.";
        }
        leaf peer-gw-name {
          type string;
          description
            "Name of remote peer gateway. ";
        }
        leaf ose-interworking-option {
          type enumeration {
            enum ose-option-a {
              description
                "MP-BGP based Inter-AS VPN Option A with MPLS labels.";
            }
            enum ose-option-b {
              description
                "MP-BGP based L3VPN Inter-AS Option B with MPLS
                 labels.";
            }
          }
          default "ose-option-b";
          description
            "OSE Gateway interworking options.";
        }
        leaf encap-type {
          type enumeration {
            enum ipsec_tunnel {
              description
                "The encapsulation option is IPSec Tunnel mode per
                 RFC4303.";
            }
            enum ipsec_transport {
              description
                "The encapsulation option is IPSec Transport mode
                  per RFC4303.";
            }
            enum gre {
              description
                "The encapsulation option is GRE tunnel per.";
            }
          }
          description
            "The encapsulation options of OSE Gateway interworking.";
        }
        leaf auth-type {
          type enumeration {
            enum psk {
              description
                "Pre-Shared Key(PSK).";
            }
            enum pki {
              description
                "Public Key Infrastructure.";
            }
          }
          description
            "authentication type.";
        }
        leaf crypto-option {
          type enumeration {
            enum aes-128 {
              description
                "crypto algorithm.";
            }
            enum aes-256 {
              description
                "crypto algorithm.";
            }
            enum aes-256-gcm {
              description
                "crypto algorithm.";
            }
          }
          description
            "Crypto algorithm selection. Others to be added.";
        }
        description
          "OSE Gateway peer gateway list.";
      }
      list segment-list {
        key "segment-name";
        leaf segment-name {
          type string;
          description
            "segment name.";
        }
        leaf vlan-id {
          if-feature "ose-option-a";
          type uint16;
          description
            "vlan ID.";
        }
        leaf vrf-id {
          if-feature "ose-option-b";
          type uint16;
          description
            "vrf ID.";
        }
        leaf segment-type {
          type enumeration {
            enum overlay {
              description
                "overlay NNI interworking.";
            }
            enum nsw {
              description
                "underlay NNI interworking.";
            }
          }
          description
            "segment type.";
        }
        list crossconnects {
          key "ccname";
          leaf ccname {
            type string;
            description
              "cross connection name.";
          }
          leaf gateway-reference {
            type leafref {
              path "../../../peer-list/peer-gw-id";
            }
            description
              "Specify the OSE gateway to be cross-connected
               with the segment.";
          }
          leaf peer-seg-name {
            type string;
            description
              "Peer segment name.";
          }
          leaf peer-seg-id-vlan {
            if-feature "ose-option-a";
            type uint16;
            description
              "Peer segment vlan ID.";
          }
          leaf peer-seg-id-vrf {
            if-feature "ose-option-b";
            type uint16;
            description
              "Peer Segment vrf ID.";
          }
          description
            "Cross connection List";
        }
        description
          "Segment List";
      }
      description
        "OSE gateway list.";
    }
    description
      "OSE gateway container.";
  }
}
