module ietf-yang-instance-data {
  yang-version 1.1;
  namespace
    "urn:ietf:params:xml:ns:yang:ietf-yang-instance-data";
  prefix ida ;

  import ietf-yang-data-ext { prefix yd; }

  organization  "IETF NETMOD Working Group";
  contact
   "WG Web:   <https://datatracker.ietf.org/wg/netmodf/>
    WG List:  <mailto:netmod@ietf.org>

    Author:  Balazs Lengyel
       <mailto:balazs.lengyel@ericsson.com>";

  description "The module defines the structure and content of YANG
       Instance Data Sets.";

  revision 2018-06-04 {
    description  "Initial revision.";
    reference "RFC XXXX: YANG Instance Data";
  }

  yd:yang-data instance-data-format {
    container instance-data-set {
      description "Auxiliary container to carry meta-data for
        the complete instance data set.";

      leaf name {
        type string;
        mandatory true;
        description "Name of a YANG instance data set.";
      }

      leaf description { type string; }

      leaf contact {
        type string;
        description "Contains the same information the contact
            statement carries for a YANG module.";
      }

      leaf organization {
        type string;
        description "Contains the same information the
            organization statement carries for a YANG module.";
      }

      list revision {
        key date;
        description "An instance-data-set SHOULD have at least
            one revision entry.  For every published
            editorial change, a new one SHOULD be added in front
            of the revisions sequence so that all revisions are
            in reverse chronological order.";

        leaf date {
          type string {
            pattern '\d{4}-\d{2}-\d{2}';
          }
          description "Specifies the data the revision
              was last modified.";
        }

        leaf description { type  string; }
      }

      anydata instance-data {
        mandatory true;
        description "Contains the real instance data.
            The data MUST conform to the relevant YANG Modules.";
      }
    }
  }
}
