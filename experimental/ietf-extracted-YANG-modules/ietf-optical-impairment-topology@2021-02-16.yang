module ietf-optical-impairment-topology {
  yang-version 1.1;

  namespace "urn:ietf:params:xml"
  +":ns:yang:ietf-optical-impairment-topology";

  prefix "optical-imp-topo";

  import ietf-network {
    prefix "nw";
  }

  import ietf-network-topology {
    prefix "nt";
  }

  import ietf-te-topology {
    prefix "tet";
  }

  import ietf-layer0-types {
    prefix "l0-types";
  }

  import ietf-layer0-types-ext {
    prefix "l0-types-ext";
  }

  organization
    "IETF CCAMP Working Group";

  contact
    "Editor:   Young Lee <younglee.tx@gmail.com>
     Editor:   Haomian Zheng <zhenghaomian@huawei.com>
     Editor:   Nicola Sambo <nicosambo@gmail.com>
     Editor:   Victor Lopez <victor.lopezalvarez@telefonica.com>
     Editor:   Gabriele Galimberti <ggalimbe@cisco.com>
     Editor:   Giovanni Martinelli <giomarti@cisco.com>
     Editor:   Jean-Luc Auge <jeanluc.auge@orange.com>
     Editor:   Le Rouzic Esther <esther.lerouzic@orange.com>
     Editor:   Julien Meuric <julien.meuric@orange.com>
     Editor:   Italo Busi <Italo.Busi@huawei.com>
     Editor:   Dieter Beller <dieter.beller@nokia.com>
     Editor:   Sergio Belotti <Sergio.belotti@nokia.com>
     Editor:   Griseri Enrico <enrico.griseri@nokia.com>
     Editor:   Gert Grammel <ggrammel@juniper.net>";

  description
    "This module contains a collection of YANG definitions for
     impairment-aware optical networks.

     Copyright (c) 2021 IETF Trust and the persons identified as
     authors of the code.  All rights reserved.

     Redistribution and use in source and binary forms, with or
     without modification, is permitted pursuant to, and subject
     to the license terms contained in, the Simplified BSD
     License set forth in Section 4.c of the IETF Trust's Legal
     Provisions Relating to IETF Documents
     (http://trustee.ietf.org/license-info).
     This version of this YANG module is part of RFC XXXX; see
     the RFC itself for full legal notices.";

// RFC Ed.: replace XXXX with actual RFC number and remove
// this note

// replace the revision date with the module publication date
// the format is (year-month-day)

  revision 2021-02-16 {
    description
      "Initial Version";
    reference
      "RFC XXXX: A Yang Data Model for Impairment-aware
       Optical Networks";
  }

  // grouping

  grouping transponder-attributes {
    description "Configuration of an optical transponder";

    leaf-list available-modulation-types {
      type identityref {
      base l0-types-ext:modulation;
      }
      config false;
    description
      "List of modulation types the OTSi supports";
    }

    leaf configured-modulation-type {
      type identityref {
      base l0-types-ext:modulation;
      }
    config false;
      description
      "Currently configured OTSi modulation type";
    }

    leaf-list available-baud-rates {
      type uint32;
        units Bd;
      config false;
      description
        "list of available baud-rates.
         Baud-rate is the unit for
         symbol rate or modulation rate
         in symbols per second or
         pulses per second.
         It is the number of distinct symbol
         changes (signal events) made to the
         transmission medium
         per second in a digitally
         modulated signal or a line code";
    }

    leaf configured-baud-rate {
      type uint32;
      units Bd;
    config false;
      description "configured baud-rate";
    }

    leaf-list available-FEC-types {
      type identityref {
      base l0-types-ext:fec-type;
      }
      config false;
      description "List determining all the available FEC";
    }

    leaf configured-FEC-type {
      type identityref {
      base l0-types-ext:fec-type;
      }
      config false;
    description
      "FEC type configured for the transponder";
    }

    leaf FEC-code-rate {
      type decimal64 {
      fraction-digits 8;
      range "0..max";
      }
      config false;
      description "FEC-code-rate";
    }

    leaf FEC-threshold {
      type decimal64 {
      fraction-digits 8;
      range "0..max";
      }
      config false;
    description
        "Threshold on the BER, for which FEC
         is able to correct errors";
    }

  }

  grouping sliceable-transponder-attributes {
    description
      "Configuration of a sliceable transponder.";
    list sliceable-transponder-list {
      key "carrier-id";
      config false;
      description "List of carriers";
      leaf carrier-id {
        type uint32;
        config false;
        description "Identifier of the carrier";
      }
    }
  }

  grouping optical-fiber-data {
    description
    "optical link (fiber) attributes with impairment data";
    leaf fiber-type {
      type fiber-type;
      config false;
      description "fiber-type";
    }

    leaf span-length {
      type decimal64 {
        fraction-digits 2;
      }
      units "km";
      config false;
      description "the lenght of the fiber span in km";
    }

    leaf input-power {
      type decimal64 {
        fraction-digits 2;
      }
      units "dBm";
      config false;
      description
      "Average input power level estimated at the receiver
         of the link";
    }

    leaf output-power {
      type decimal64 {
        fraction-digits 2;
      }
      units "dBm";
      description
      "Mean launched power at the transmitter of the link";
    }

    leaf pmd {
      type decimal64 {
        fraction-digits 8;
        range "0..max";
      }
      units "ps/(km)^0.5";
      config false;
      description
      "Polarization Mode Dispersion";
    }

    leaf cd {
      type decimal64 {
        fraction-digits 5;
      }
      units "ps/nm/km";
      config false;
      description
      "Cromatic Dispersion";
    }

    leaf osnr {
      type l0-types-ext:snr;
      config false;
      description
      "Optical Signal-to-Noise Ratio (OSNR) estimated
         at the receiver";
    }

    leaf sigma {
      type decimal64 {
        fraction-digits 5;
      }
      units "dB";
      config false;
      description
      "sigma in the Gausian Noise Model";
    }
  }

  grouping optical-channel-data {
  description
    "optical impairment data per channel/wavelength";
  leaf bit-rate {
    type decimal64 {
      fraction-digits 8;
        range "0..max";
    }
    units "Gbit/s";
    config false;
    description
      "Gross bit rate";
  }

    leaf BER {
    type decimal64 {
      fraction-digits 18;
            range "0..max";
    }
    config false;
      description
      "BER (Bit Error Rate)";
  }

    leaf ch-input-power {
          type decimal64 {
           fraction-digits 2;
        }
        units "dBm";
        config false;
        description
    "Per channel average input power level
          estimated at the receiver of the link";
        }

  leaf ch-pmd {
    type decimal64 {
        fraction-digits 8;
      range "0..max";
    }
    units "ps/(km)^0.5";
    config false;
    description
      "per channel Polarization Mode Dispersion";
  }

  leaf ch-cd {
    type decimal64 {
            fraction-digits 5;
    }
    units "ps/nm/km";
    config false;
          description
      "per channel Cromatic Dispersion";
  }

  leaf ch-osnr {
    type l0-types-ext:snr;
    config false;
    description
      "per channel Optical Signal-to-Noise Ratio
            (OSNR) estimated at the receiver";
   }

    leaf q-factor {
    type decimal64 {
      fraction-digits 5;
    }
    units "dB";
    config false;
      description
      "q-factor estimated at the receiver";
    }
  }

  /*
   * Identities
   */

  identity type-power-mode {
    description
      "power equalization mode used within the
       OMS and its elements";
  }

  identity power-spectral-density {
    base type-power-mode;
    description
      "all elements must use power spectral density (W/Hz)";
  }

  identity channel-power {
    base type-power-mode;
    description
      "all elements must use power (dBm)";
  }

  /*
   * Typedefs
   */

  typedef fiber-type {
    type enumeration {
      enum G.652 {
      description "G.652 Standard Singlemode Fiber";
      }
      enum G.654 {
        description "G.654 Cutoff Shifted Fiber";
      }
      enum G.653 {
        description "G.653 Dispersion Shifted Fiber";
      }
      enum G.655 {
        description "G.655 Non-Zero Dispersion Shifted Fiber";
      }
      enum G.656 {
        description "G.656 Non-Zero Dispersion for Wideband
               Optical Transport";
      }
      enum G.657 {
        description "G.657 Bend-Insensitive Fiber";
      }
    }
    description
      "ITU-T based fiber-types";
  }

  /*
   * Groupings
   */

  grouping amplifier-params {
    description "describes parameters for an amplifier";
    container amplifier{
      description
        "amplifier type, operatonal parameters are described.";
      leaf type-variety {
        type string ;
        mandatory true ;
        description
          "String identifier of amplifier type referencing
          a specification in a separate equipment catalog";
      }
      container operational {
        description "amplifier operational parameters";
        list amplifier-element {
          description
            "The list of parallel amplifier elements within an
            amplifier used to amplify different frequency ranges.";
          leaf name {
            type string;
            description
              "The name of the amplifier element as specified in
              the vendor's specification associated with the
              type-variety.";
          }
          container frequency-range {
            description
              "The frequency range amplified by the amplifier
              element.";
            leaf lower-frequency {
              type l0-types-ext:frequency-thz;
              description
                "The lower frequency boundary of the
                frequency range.";
            }
            leaf upper-frequency {
              type l0-types-ext:frequency-thz;
              description
                "The upper frequency boundary of the
                frequency range.";
            }
          }
          leaf actual-gain {
            type decimal64 {
              fraction-digits 2;
            }
            units dB ;
            mandatory true ;
            description "..";
          }
          leaf tilt-target {
            type decimal64 {
              fraction-digits 2;
            }
            mandatory true ;
            description "..";
          }
          leaf out-voa {
            type decimal64 {
              fraction-digits 2;
            }
            units dB;
            mandatory true;
            description "..";
          }
          leaf in-voa {
            type decimal64 {
              fraction-digits 2;
            }
            units dB;
            mandatory true;
            description "..";
          }
          uses power-param;
        }  // list amplifier-element
      }  // container operational
    }  // container amplifier
  }  // grouping amplifier-params

  grouping fiber-params {
    description
      "String identifier of fiber type referencing a
       specification in a separate equipment catalog";
    container fiber {
    description "fiber characteristics";
      leaf type-variety {
        type string ;
    mandatory true ;
        description "fiber type";
      }
      leaf length {
        type decimal64 {
          fraction-digits 2;
        }
        units km;
    mandatory true ;
    description "length of fiber";
      }
      leaf loss-coef {
        type decimal64 {
          fraction-digits 2;
        }
        units dB/km;
    mandatory true ;
    description "loss coefficient of the fiber";
      }
      leaf total-loss {
        type decimal64 {
          fraction-digits 2;
        }
        units dB;
    mandatory true ;
        description
          "includes all losses: fiber loss and conn-in and
           conn-out losses";
      }
      leaf pmd{
        type decimal64 {
          fraction-digits 2;
        }
        units sqrt(ps);
    description "pmd of the fiber";
      }
      leaf conn-in{
        type decimal64 {
          fraction-digits 2;
        }
        units dB;
    description "connector-in";
      }
      leaf conn-out{
        type decimal64 {
          fraction-digits 2;
        }
        units dB;
    description "connector-out";
      }
    }
  }

  grouping roadm-express-path {
    description "roadm express path optical impairments";

    container roadm-express-path {
      description "roadm parameters per express path";

      leaf roadm-pmd {
        type decimal64 {
          fraction-digits 8;
          range "0..max";
        }
        units "ps/(km)^0.5";
        description
          "Polarization Mode Dispersion";
      }
      leaf roadm-cd {
        type decimal64 {
          fraction-digits 5;
        }
        units "ps/nm";
        description "Chromatic Dispersion";
      }
      leaf roadm-pdl {
        type decimal64 {
          fraction-digits 2;
        }
        units dB ;
        description "Polarization dependent loss";
      }
      leaf roadm-inband-crosstalk {
        type decimal64 {
          fraction-digits 2;
        }
        units dB;
        description
          "In-band crosstalk, or coherent crosstalk, can occur in
           components that can have multiple same wavelength inputs
           with the inputs either routed to different output ports,
           or all but 1 blocked";
      }
      leaf roadm-maxloss {
        type decimal64 {
          fraction-digits 2;
        }
        units dB;
        description
          "This is the maximum expected add path loss from the
           ROADM ingress to the ROADM egress
           assuming no additional add path loss is added";
      }
    }
  }

  grouping roadm-add-path {
    description "roadm add block path optical impairments";

    container roadm-add-path {
      description "roadm optical impairment parameters
      per add path";

      leaf roadm-pmd {
        type decimal64 {
          fraction-digits 8;
          range "0..max";
        }
        units "ps";
        description
          "Polarization Mode Dispersion";
      }
      leaf roadm-cd {
        type decimal64 {
          fraction-digits 5;
        }
        units "ps/nm";
        description "Cromatic Dispersion";
      }
      leaf roadm-pdl {
        type decimal64 {
          fraction-digits 2;
        }
        units dB ;
        description "Polarization dependent loss";
      }
      leaf roadm-inband-crosstalk {
        type decimal64 {
          fraction-digits 2;
        }
        units dB ;
        description
          "In-band crosstalk, or coherent crosstalk,
           can occur in components that can have multiple same
           wavelength inputs,with the inputs either
           routed to different output ports,
           or all but 1 blocked.
           In the case of add path it is the total
           of the add block
           + egress WSS crosstalk contributions.";
      }
      leaf roadm-maxloss {
        type decimal64 {
          fraction-digits 2;
        }
        units dB ;
        description
          "This is the maximum expected add path loss from
           the add/drop port input to the ROADM egress,
           assuming no additional add path loss is added.
           This is used to establish the minimum required
           transponder output power required
           to hit the ROADM egress target power
           levels and preventing
           to hit the WSS attenuation limits.
           If the add path contains an internal amplifier
           this loss value should be based
           on worst case expected amplifier gain due to
           ripple or gain uncertainty";
      }
      leaf roadm-pmax {
        type decimal64 {
          fraction-digits 2;
        }
        units dBm ;
        description
          "This is the maximum (per carrier) power level
           permitted at the add block input ports,
           that can be handled by the ROADM node.
           This may reflect either add amplifier power
           contraints or WSS adjustment limits.
           Higher power transponders would need to have
           their launch power reduced
           to this value or lower";
      }
      leaf roadm-osnr {
        type l0-types-ext:snr;
        description
          "Optical Signal-to-Noise Ratio (OSNR).
           If the add path contains the ability to adjust the
           carrier power levels into an add path amplifier
           (if present) to a target value,
           this reflects the OSNR contribution of the
           add amplifier assuming this target value is obtained.
           The worst case OSNR based on the input power and
           NF calculation method, and this value, should be used
           (if both are defined).";
      }
      leaf roadm-noise-figure {
        type decimal64 {
          fraction-digits 5;
        }
        units "dB";
        description
          "Noise Figure. If the add path contains an amplifier,
           this is the noise figure of that amplifier inferred
           to the add port.
           This permits add path OSNR calculation based
           on the input power levels to the add block
           without knowing the ROADM path losses to
           the add amplifier.";
      }
    }
  }

  grouping roadm-drop-path {
    description "roadm drop block path optical impairments";

    container roadm-drop-path {
      description "roadm optical impairment parameters
      per drop path";

      leaf roadm-pmd {
        type decimal64 {
          fraction-digits 8;
          range "0..max";
        }
        units "ps/(km)^0.5";
        description
          "Polarization Mode Dispersion";
      }
      leaf roadm-cd {
        type decimal64 {
          fraction-digits 5;
        }
        units "ps/nm";
        description "Chromatic Dispersion";
      }
      leaf roadm-pdl {
        type decimal64 {
          fraction-digits 2;
        }
        units dB ;
        description "Polarization dependent loss";
      }
      leaf roadm-inband-crosstalk {
        type decimal64 {
          fraction-digits 2;
        }
        units dB;
        description
          "In-band crosstalk, or coherent crosstalk, can occur in
           components that can have multiple same wavelength
           inputs,with the inputs either routed to different
           output ports,or all but 1 blocked.
           In the case of drop path it is the total
           of the ingress
           to drop e.g. WSS and drop block crosstalk
           contributions.";
      }
      leaf roadm-maxloss {
        type decimal64 {
          fraction-digits 2;
        }
        units dB ;
        description
          "The net loss from the ROADM input,to the output
           of the drop block.
           If ROADM ingress to drop path includes an amplifier,
           the amplifier gain reduces the net loss.
           This is before any additional drop path attenuation
           that may be required
           due to drop amplifier power contraints.
           The max value correspond to worst case expected loss,
           including amplifier gain ripple or uncertainty.
           It is the maximum output power of the drop
           amplifier.";
      }
      leaf roadm-minloss {
        type decimal64 {
          fraction-digits 2;
        }
        units dB ;
        description
          "The net loss from the ROADM input, to the
           output of the drop block.
           If this ROADM ingress to drop path includes
           an amplifier,the amplifier gain reduces the net loss.
           This is before any additional drop path attenuation
           that may be required due to drop amplifier power
           contraints.
           The min value correspond to best case expected loss,
           including amplifier gain ripple or uncertainty.";
      }
      leaf roadm-typloss {
        type decimal64 {
          fraction-digits 2;
        }
        units dB ;
        description
          "The net loss from the ROADM input,
           to the output of the drop block.
           If this ROADM ingress to drop path
           includes an amplifier,
           the amplifier gain reduces the net loss.
           This is before any additional drop path
           attenuation
           that may be required due to drop amplifier
           power contraints.
           The typ value correspond to typical case
           expected loss.";
      }
      leaf roadm-pmin {
        type decimal64 {
          fraction-digits 2;
        }
        units dBm ;
        description
          "If the drop path has additional loss
           that is added, for example,
           to hit target power levels into a
           drop path amplifier, or simply, to reduce the
           power of a strong carrier
           (due to ripple,for example),
           then the use of the ROADM input power levels and
           the above drop losses is not appropriate.
           This parameter corresponds to the min per
           carrier power levels
           expected at the output of the drop block.
           A detail example of the comparison using
           these parameters is
           detailed in section xxx of the document yyy.";
      }
      leaf roadm-pmax {
        type decimal64 {
          fraction-digits 2;
        }
        units dBm ;
        description
          "If the drop path has additional loss that is added,
           for example, to hit target power levels into a
           drop path amplifier,or simply,to reduce the power
           of a strong carrier(due to ripple,for example),
           then the use of the ROADM input power levels and the
           above drop losses is not appropriate.
           This parameter corresponds to the best case per
           carrier power levels expected at the output of the
           drop block.
           A detail example of the comparison using
           these parameters
           is detailed in section xxx of the document yyy";
      }
      leaf roadm-ptyp {
        type decimal64 {
          fraction-digits 2;
        }
        units dBm ;
        description
          "If the drop path has additional loss that is added,
           for example, to hit target power levels into a
           drop path amplifier,or simply,to reduce the
           power of a strong carrier(due to ripple,for example),
           then the use of the ROADM input power levels and
           the above drop losses is not appropriate.
           This parameter corresponds to the typical case
           per carrier power levels expected
           at the output of the drop block.";
      }
      leaf roadm-osnr {
        type l0-types-ext:snr;
        description
          "Optical Signal-to-Noise Ratio (OSNR).
           Expected OSNR contribution of the drop path
           amplifier(if present)
           for the case of additional drop path loss
           (before this amplifier)
           in order to hit a target power level (per carrier).
           If both, the OSNR based on the ROADM
           input power level
           (Pcarrier =
           Pref+10Log(carrier-baudrate/ref-baud) + delta-power)
           and the input inferred NF(NF.drop),
           and this OSNR value, are defined,
           the minimum value between these two should be used";
      }
      leaf roadm-noise-figure {
        type decimal64 {
          fraction-digits 5;
        }
        units "dB";
        description
          "Drop path Noise Figure.
           If the drop path contains an amplifier,
           this is the noise figure
           of that amplifier, inferred to the
           ROADM ingress port.
           This permits to determine
           amplifier OSNR contribution
           without having to specify the
           ROADM node's losses to that amplifier.
           This applies for the case of no
           additional drop path loss,
           before the amplifier, in order to reduce the power
           of the carriers to a target value";
      }
    }
  }

  grouping concentratedloss-params{
    description "concentrated loss";
    container concentratedloss{
    description "concentrated loss";
      leaf loss {
        type decimal64 {
          fraction-digits 2;
        }
        units dB ;
        mandatory true;
        description "..";
      }
    }
  }

  grouping power-param{
    description
      "optical power or PSD after the ROADM or after the out-voa";
    choice power-param {
      description
        "select the mode: channel power or power spectral density";
      case channel-power {
 /*       when "equalization-mode='channel-power'"; */
        leaf nominal-channel-power{
          type decimal64 {
              fraction-digits 1;
          }
          units dBm ;
          description
            " Reference channel power after the ROADM or after
            the out-voa. ";
        }
      }
      case power-spectral-density{
 /*       when "equalization-mode='power-spectral-density'"; */
        leaf nominal-power-spectral-density{
          type decimal64 {
              fraction-digits 16;
          }
          units W/Hz ;
          description
            " Reference power spectral density after
              the ROADM or after the out-voa.
              Typical value : 3.9 E-14, resolution 0.1nW/MHz";
        }
      }
    }
  }

  grouping oms-general-optical-params {
    description "OMS link optical parameters";
    leaf generalized-snr {
      type l0-types-ext:snr;
      description "generalized snr";
    }
    leaf equalization-mode{
      type identityref {
        base type-power-mode;
      }
      mandatory true;
      description "equalization mode";
    }
    uses power-param;
  }

  grouping OTSiG {
    description "OTSiG definition , representing client
     digital information stream supported by 1 or more OTSi";

     list otsi {
       key "otsi-carrier-id";
       config false;
       description
         "list of OTSi contained in 1 OTSiG.
        The list could also be of only 1 element";
       leaf otsi-carrier-id {
         type int16;
         description "OTSi carrier-id";
       }

/*any OTSi as signal generated by transceiver and*/
/* attached to a transponder.*/

       leaf transponder-ref {
            type leafref {
              path "/nw:networks/nw:network/nw:node/tet:te" +
                "/tet:tunnel-termination-point" +
                "/transponder/transponder-id";
            }
          description
              "Reference to the configured transponder";
       }
       leaf transceiver-ref {
            type leafref {
              path "/nw:networks/nw:network/nw:node/tet:te" +
                "/tet:tunnel-termination-point/"
               +"transponder[transponder-id=current()"
               +"/../transponder-ref]/"
               + "transceiver/transceiver-id" ;
              }
          description
             "Reference to the configured transceiver " ;
       }
       leaf configured-mode {
         type leafref {
           path "/nw:networks/nw:network/nw:node/tet:te" +
                "/tet:tunnel-termination-point/"
               +"transponder[transponder-id=current()"
               +"/../transponder-ref]/"+
               "transceiver[transceiver-id=current()/"+
               "../transceiver-ref]/supported-modes/"+
               "supported-mode/mode-id";
         }
          description
             "Reference to the configured mode for transceiver
              compatibility approach";
       }
       uses l0-types-ext:common-transceiver-configured-param;
     } // OTSi list
  } // OTSiG grouping

  grouping media-channel-groups {
    description "media channel groups";
    list media-channel-group {
    key "i";
      description
        "list of media channel groups";
      leaf i {
        type int16;
          description "index of media channel group member";
      }

      list media-channels {
        key "flexi-n";
        description
          "list of media channels represented as (n,m)";

 // this grouping add both n.m values
        uses l0-types:flexi-grid-frequency-slot;

        leaf OTSiG-ref {
          type leafref {
           path "/nw:networks/nw:network/nw:node/tet:te" +
                "/tet:tunnel-termination-point" +
                "/otsi-group/otsi-group-id" ;

          }
          description
             "Reference to the otsi-group list to get otsi-group
              identifier of the
              OTSiG carried by this media channel
              that reports the transient stat";
        }
        leaf OTSi-ref {
          type leafref {
            path "/nw:networks/nw:network/nw:node/tet:te" +
                "/tet:tunnel-termination-point/"
               +"otsi-group[otsi-group-id=current()"
               +"/../OTSiG-ref]/"
               + "otsi/otsi-carrier-id" ;
          }
          description
             "Reference to the otsi list supporting
             the related OTSiG to get otsi identifier";
        }

      } // media channels list
    } // media-channel-groups list
  } // media media-channel-groups grouping

  grouping oms-element {
    description "OMS description";
    list OMS-elements {
        key "elt-index";
        description
          "defines the spans and the amplifier blocks of
          the amplified lines";
        leaf elt-index {
          type uint16;
          description
            "ordered list of Index of OMS element
            (whether it's a Fiber, an EDFA or a
Concentratedloss)";
        }
        leaf oms-element-uid {
          type string;
          description
            "unique id of the element if it exists";
        }

          choice element {
            mandatory true;
            description "OMS element type";
            case amplifier {
              uses amplifier-params ;
            }
            case fiber {
              uses fiber-params ;
            }
            case concentratedloss {
              uses concentratedloss-params ;
            }
          }

    }
  }

/* Data nodes */

  augment "/nw:networks/nw:network/nw:network-types"
   + "/tet:te-topology" {
   description "optical-impairment topology augmented";
   container optical-impairment-topology {
     presence "indicates an impairment-aware topology of
     optical networks";
     description
     "Container to identify impairment-aware topology type";
   }
  }

  augment "/nw:networks/nw:network/nt:link/tet:te"
   + "/tet:te-link-attributes"   {
   when "/nw:networks/nw:network/nw:network-types"
    +"/tet:te-topology/"
    +"optical-imp-topo:optical-impairment-topology" {
    description
      "This augment is only valid for Optical Impairment.";
   }
   description "Optical Link augmentation for impairment data.";
   container OMS-attributes {
       config false;
       description "OMS attributes";
     uses oms-general-optical-params;
     uses media-channel-groups;
     uses oms-element;
     }
  }

  augment "/nw:networks/nw:network/nw:node/tet:te"
   + "/tet:tunnel-termination-point" {
   when "/nw:networks/nw:network/nw:network-types"
    +"/tet:te-topology/optical-imp-topo:optical-impairment-topology"{
    description
      "This augment is only valid for Impairment with non-sliceable
       transponder model";
   }
   description
     "Tunnel termination point augmentation for non-sliceable
      transponder model.";

     list otsi-group {
         key "otsi-group-id";
         config false;
         description
         "the list of possible OTSiG representing client digital
          stream";

         leaf otsi-group-id {
            type int16;
             description "index of otsi-group element";
         }
         uses OTSiG;
     } // list of OTSiG

     list transponder {
       key "transponder-id";
       config false;
       description "list of transponder";
       leaf transponder-id {
         type uint32;
         description "transponder identifier";
       }

       list transceiver {
         key "transceiver-id";
         config false;
         description "list of transceiver related to a transponder";
         leaf transceiver-id {
           type uint32;
           description "transceiver identifier";
         }
         uses l0-types-ext:transceiver-capabilities;
       } // end of list of transceiver

     } // end list of transponder

  } // end of augment

  augment "/nw:networks/nw:network/nw:node/tet:te"
   + "/tet:tunnel-termination-point" {
   when "/nw:networks/nw:network/nw:network-types"
    +"/tet:te-topology/"
    + "optical-imp-topo:optical-impairment-topology" {
    description
      "This augment is only valid for optical impairment
       with sliceable transponder model";
   }
   description
     "Tunnel termination point augmentation for sliceable
      transponder model.";
   uses sliceable-transponder-attributes;
  }

  augment "/nw:networks/nw:network/nw:node/tet:te"
        + "/tet:te-node-attributes" {
    when "/nw:networks/nw:network/nw:network-types"
       + "/tet:te-topology"
       + "/optical-imp-topo:optical-impairment-topology" {
      description
        "This augment is only valid for Optical Impairment
        topology";
    }
    description
      "node attributes augmentantion for optical-impairment ROADM
       node";

    list roadm-path-impairments {
      key "roadm-path-impairments-id";
      config false;
      description "list of set of optical impairments related
      to ROADM ";

      leaf roadm-path-impairments-id {
        type uint32;
        description "index of the ROADM path-impairment list";
      }
      choice impairment-type {
        description "type path impairment";
        case roadm-express-path {
          uses roadm-express-path;
        }
        case roadm-add-path {
          uses roadm-add-path;
        }
        case roadm-drop-path {
          uses roadm-drop-path;
        }
      }
    } // list path impairments
  } // augmentation for optical-impairment ROADM

  augment "/nw:networks/nw:network/nw:node/tet:te/"
        + "tet:information-source-entry/tet:connectivity-matrices"{
    when "/nw:networks/nw:network/nw:network-types"
       + "/tet:te-topology/"
       + "optical-imp-topo:optical-impairment-topology" {
      description
        "This augment is only valid for Optical Impairment
        topology ";
    }

    description
      "Augment default TE node connectivity matrix information
      source.";

    leaf roadm-path-impairments {
      type leafref {
        path "../../../tet:te-node-attributes/"
        + "roadm-path-impairments/roadm-path-impairments-id";
      }
      description "pointer to the list set of ROADM optical
      impairments";
    }
  } // augmentation connectivity-matrices information-source

  augment "/nw:networks/nw:network/nw:node/tet:te/"
        + "tet:information-source-entry/tet:connectivity-matrices/"
        + "tet:connectivity-matrix" {
    when "/nw:networks/nw:network/nw:network-types"
       + "/tet:te-topology/"
       + "optical-imp-topo:optical-impairment-topology" {
      description
        "This augment is only valid for Optical Impairment
         topology ";
    }

    description
      "Augment TE node connectivity matrix entry information
      source.";

    leaf roadm-path-impairments {
      type leafref {
        path "../../../../tet:te-node-attributes/"
        + "roadm-path-impairments/roadm-path-impairments-id";
      }
      description "pointer to the list set of ROADM optical
      impairments";
    }
  } // augmentation connectivity-matrix information-source

  augment "/nw:networks/nw:network/nw:node/tet:te/"
        + "tet:te-node-attributes/tet:connectivity-matrices" {
    when "/nw:networks/nw:network/nw:network-types"
       + "/tet:te-topology/"
       + "optical-imp-topo:optical-impairment-topology" {
      description
        "This augment is only valid for Optical Impairment
        topology ";
    }

    description
      "Augment default TE node connectivity matrix.";
    leaf roadm-path-impairments {
      type leafref {
        path "../../roadm-path-impairments/"
        + "roadm-path-impairments-id";
      }
      config false; /*the identifier in the list */
       /*"roadm-path-impairments" of ROADM optical impairment*/
                    /*is read-only as the rest of attributes*/
      description "pointer to the list set of ROADM optical
      impairments";
    }
  } // augmentation connectivity-matrices

  augment "/nw:networks/nw:network/nw:node/tet:te/"
        + "tet:te-node-attributes/"
        + "tet:connectivity-matrices/tet:connectivity-matrix" {
    when "/nw:networks/nw:network/nw:network-types"
       + "/tet:te-topology/"
       + "optical-imp-topo:optical-impairment-topology" {
      description
        "This augment is only valid for
        Optical Impairment topology ";
    }

    description
      "Augment TE node connectivity matrix entry.";

    leaf roadm-path-impairments {
      type leafref {
        path "../../../roadm-path-impairments/"
        + "roadm-path-impairments-id";
      }
      config false;
      description "pointer to the list set of ROADM optical
       impairments";
    }
  } // augmentation connectivity-matrix

  augment "/nw:networks/nw:network/nw:node/tet:te/"
        + "tet:tunnel-termination-point/"
        + "tet:local-link-connectivities" {

    when "/nw:networks/nw:network/nw:network-types"
       + "/tet:te-topology/"
       + "optical-imp-topo:optical-impairment-topology" {
      description
      "This augment is only valid for Optical Impairment topology ";
    }

    description
      "Augment default TTP LLC.";
    leaf add-path-impairments {
      type leafref {
        path "../../../tet:te-node-attributes/"
        + "roadm-path-impairments/roadm-path-impairments-id" ;
      }
      config false;
      description "pointer to the list set of ROADM optical
       impairments";
    }
    leaf drop-path-impairments {
      type leafref {
        path "../../../tet:te-node-attributes/"
        + "roadm-path-impairments/roadm-path-impairments-id" ;
      }
      config false;
      description "pointer to the list set of ROADM
      optical impairments";
    }
  } // augmentation local-link-connectivities

  augment "/nw:networks/nw:network/nw:node/tet:te/"
        + "tet:tunnel-termination-point/"
        + "tet:local-link-connectivities/"
        + "tet:local-link-connectivity" {

    when "/nw:networks/nw:network/nw:network-types"
       + "/tet:te-topology/"
       + "optical-imp-topo:optical-impairment-topology" {
      description
        "This augment is only valid for
         Optical Impairment topology ";
    }

    description
      "Augment TTP LLC entry.";
    leaf add-path-impairments {
      type leafref {
        path "../../../../tet:te-node-attributes/"
        + "roadm-path-impairments/roadm-path-impairments-id" ;
      }
      config false;
      description "pointer to the list set of ROADM optical
       impairments";
    }
    leaf drop-path-impairments {
      type leafref {
        path "../../../../tet:te-node-attributes/"
        + "roadm-path-impairments/roadm-path-impairments-id" ;
      }
      config false;
      description "pointer to the list set of ROADM optical
      impairments";
    }
  } // augmentation local-link-connectivity
}
