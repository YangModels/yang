module ietf-qos-oper {
  yang-version 1.1;
  namespace "urn:ietf:params:xml:ns:yang:ietf-qos-oper";
  prefix oper;

  import ietf-yang-types {
    prefix yang;
    reference
      "RFC 6991:Common YANG Data Types";
  }
  import ietf-interfaces {
    prefix if;
    reference
      "RFC8343: A YANG Data Model for Interface Management";
  }
  import iana-qos-types {
    prefix qos-types;
    reference
      "RFC XXXX: YANG Models for Quality of Service (QoS).";
  }

  organization "IETF RTG (Routing Area) Working Group";

  contact
    "WG Web:   <http://tools.ietf.org/wg/rtgwg/>
     WG List:  <mailto:rtgwg@ietf.org>
     Editor:   Aseem Choudhary
               <mailto:achoudhary@aviatrix.com>
     Editor:   Mahesh Jethanandani
               <mailto:mjethanandani@gmail.com>";
  description
    "This module contains a collection of YANG definitions for
     qos operational specification.

     Copyright (c) 2021 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2023-03-10 {
    description
      "Initial version";
    reference
      "RFC XXXX: YANG Models for Quality of Service (QoS).";
  }

  grouping named-stats {
    description
      "QoS matching statistics associated with a stats-name";
    leaf pkts {
      type yang:zero-based-counter64;
      description
        " Number of total matched packets associated
          to a statistics name";
    }
    leaf bytes {
      type yang:zero-based-counter64;
      description
        " Number of total matched bytes associated
          to a statistics name";
    }
    leaf rate {
      type yang:gauge64;
      units "bits-per-second";
      description
        " Rate of average matched data which is associated
          to a statistics name";
    }
  }
  grouping meter-stats {
    description
      "Metering counters";
    leaf conform-pkts {
      type yang:zero-based-counter64;
      description
        "Number of packets within conform rate and burst";
    }
    leaf conform-bytes {
      type yang:zero-based-counter64;
      description
        "Total bytes count within conform rate and burst";
    }
    leaf conform-rate {
      type yang:gauge64;
      units "bits-per-second";
      description
        "Traffic Rate measured as conformimg";
    }
    leaf exceed-pkts {
      type yang:zero-based-counter64;
      description
        "Number of non-conforming packets which are within peak rate
         and peak burst";
    }
    leaf exceed-bytes {
      type yang:zero-based-counter64;
      description
        "Total non-conforming bytes count which is within peak rate
         and peak burst";
    }
    leaf exceed-rate {
      type yang:gauge64;
      units "bits-per-second";
      description
        "Traffic Rate measured as exceeding";
    }
    leaf violate-pkts {
      type yang:zero-based-counter64;
      description
        "Number of packets which are beyond peak rate
         and peak burst";
    }
    leaf violate-bytes {
      type yang:zero-based-counter64;
      description
        "Total bytes count which is beyond peak rate and peak burst";
    }
    leaf violate-rate {
      type yang:gauge64;
      units "bits-per-second";
      description
        "Traffic Rate measured as violating";
    }
    leaf meter-drop-pkts {
      type yang:zero-based-counter64;
      description
        "Number of packets dropped by meter";
    }
    leaf meter-drop-bytes {
      type yang:zero-based-counter64;
      description
        "Bytes of packets dropped by meter";
    }
  }
  grouping classifier-statistics {
    description
      "Statistics for a classifier";
    leaf name {
      type string;
      description
        "Classifier Name";
    }
    leaf classified-pkts {
      type yang:zero-based-counter64;
      description
        " Number of total packets which filtered
          to a classifier";
    }
    leaf classified-bytes {
      type yang:zero-based-counter64;
      description
        " Number of total bytes which filtered
          to a classifier";
    }
    leaf classified-rate {
      type yang:gauge64;
      units "bits-per-second";
      description
        " Rate of average data flow through a
          classifier";
    }
  }
  grouping queuing-stats {
    description
      "Statistics for a queue";
    leaf queue-id {
      type string;
      description
        "Queue Identifier";
    }
    leaf transmit-pkts {
      type yang:zero-based-counter64;
      description
        "Number of packets transmitted from queue";
    }
    leaf transmit-bytes {
      type yang:zero-based-counter64;
      description
        "Number of bytes transmitted from queue";
    }
    leaf queue-current-size-bytes {
      type yang:gauge64;
      description
        "Number of bytes currently buffered";
    }
    leaf queue-average-size-bytes {
      type yang:gauge64;
      description
        "Average queue size in number of bytes";
    }
    leaf queue-peak-size-bytes {
      type yang:gauge64;
      description
        "Peak buffer queue size in bytes";
    }
    leaf tail-drop-pkts {
      type yang:zero-based-counter64;
      description
        "Total number of packets tail-dropped";
    }
    leaf tail-drop-bytes {
      type yang:zero-based-counter64;
      description
        "Total number of bytes tail-dropped";
    }
    leaf red-drop-pkts {
      type yang:zero-based-counter64;
      description
        "Total number of packets dropped through RED mechanism";
    }
    leaf red-drop-bytes {
      type yang:zero-based-counter64;
      description
        "Total number of bytes dropped through RED mechanism";
    }
    leaf red-ecn-marked-pkts {
      type yang:zero-based-counter64;
      description
        "Total number of packets ECN marked through RED mechanism";
    }
    leaf red-ecn-marked-bytes {
      type yang:zero-based-counter64;
      description
        "Total number of bytes ECN marked through RED mechanism";
    }
    list wred-stats {
      config false;
      description
        "Qos WRED statistics";
      leaf profile {
        type uint8;
        description
          "profile identifier for each color of traffic";
      }
      leaf drop-pkts {
        type yang:zero-based-counter64;
        description
          "Total number of packets dropped through WRED mechanism";
      }
      leaf drop-bytes {
        type yang:zero-based-counter64;
        description
          "Total number of bytes dropped through WRED mechanism";
      }
      leaf ecn-marked-pkts {
        type yang:zero-based-counter64;
        description
          "Total number of packets ECN marked through
           WRED mechanism";
      }
      leaf ecn-marked-bytes {
        type yang:zero-based-counter64;
        description
          "Total number of bytes ECN marked through WRED mechanism";
      }
    }
  }
  grouping metering-stats {
    description
      "Statistics for a meter";
    leaf meter-id {
      type string;
      description
        "Meter Identifier";
    }
    uses meter-stats;
  }

  augment "/if:interfaces/if:interface" {
    description
      "Augments Qos Target Entry to Interface module";

    container qos-interface-statistics {
      config false;
      description
        "Qos Interface statistics";

      list stats-per-direction {
        description
          "Qos Interface statistics for ingress or egress direction";

        leaf direction {
          type identityref {
            base qos-types:direction;
          }
          description
            "Direction of the traffic flow either inbound
             or outbound";
        }
        leaf policy-name {
          type string;
          description
            "Policy name for single level policy as well as
             for Hierarchical policies. For Hierarchical policies,
             this represent relative path as well as the last level
             policy name.";
        }

        list classifier {
          description
            "Statistics for each Classifier in a
             Policy applied in a particular direction";
          uses classifier-statistics;
        }
        list named {
          description
            "Statistics for a statistics-name";
          leaf name {
            type string;
            description
              "Statistics name";
          }
          container aggregated {
            description
              "Matched aggregated statistics for a statistics-name";
            uses named-stats;
          }
          container non-aggregated {
            description
              "Statistics for non-aggregated statistics-name";
            list classifier {
              description
                "Statistics for each Classifier in a
                 Policy applied in a particular direction";
              uses classifier-statistics;
            }
            list metering {
              description
                "Statistics for each Meter associated with
                 the Policy";
              reference
                "RFC2697: A Single Rate Three Color Marker
                 RFC2698: A Two Rate Three Color Marker";
              uses metering-stats;
            }
            list queueing {
              description
                "Statistics for each Queue associated with
                 the Policy";
              uses queuing-stats;
            }
          }
        }
        list metering {
          description
            "Statistics for each Meter associated with the Policy";
          reference
            "RFC2697: A Single Rate Three Color Marker
             RFC2698: A Two Rate Three Color Marker";
          uses metering-stats;
        }
        list queueing {
          description
            "Statistics for each Queue associated with the Policy";
          uses queuing-stats;
        }
      }
      action clear {
        description
          "Clear statistics action command. Execution of this command
           should result in all the QoS interface counters to be
           cleared and set to 0.";
        input {
          leaf category {
            type identityref {
              base qos-types:clear-counters-type;
            }
            description
              "category of counters which is being cleared";
          }
        }
      }
    }
  }
}
