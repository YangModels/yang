module nvo3-base {
  namespace "http://www.huawei.com/netconf/nvo3";
  //namespace need to be assigned by IANA
  prefix "nvo3";
  import ietf-inet-types {
    prefix "inet";
  }
  organization "IETF NVO3 Working Group";
  contact "vero.zheng@huawei.com
    zhangmingui@huawei.com
    habby.zheng@huawei.com";
  description "nvo3 yang module";
  revision "2014-10-21";

  typedef flags-vxlan {
    type bits {
      bit validVni {
        position 4;
      }
    }
  }

  typedef  flags-nvgre {
    type bits {
      bit zero{
        position 0;
      }
      bit KeyPresent{
        position 2;
      }
      bit three{
        position 3;
      }
    }      
  }

  container nvo3Nves {
    list nvo3Nve {
      key "ifName";
      leaf ifName {
        description
          "Interface name.";
        type string;
        mandatory "true";
      }
      leaf srcAddr {
        description
          "Local NVE address.";      
        type inet:ip-address;
      }
      choice encapType{
        case vxlan{
          leaf srcUdpPortGenRule {
            description
              "The rule of generating source udp port.";
            type uint8;
          }
          leaf destUdpPort {
            description
              "Destination udp port.";
            default "4789";
            type uint16{
              range "0 .. 65535";
            }
          }
        }
      }
      container members {
        list member {
          key "VNI";
          leaf VNI {
            description 
              "Virutal Network Instance (VNI). For VxLAN, it is 
              VXLAN Network Identifier; For NVGRE, it is Virtual 
              Subnet Identifier.";
            mandatory "true";
            type uint32 {
              range "1 .. 16777215";
            }
          }
          leaf bdId {
            description
              "Bridge Domain ID";
            mandatory "true";
            type uint32 {
              range "1 .. 32768";
            }
          }
          choice encapType{
            case vxlan{
              leaf vxlanFlag {
                description
                  "The 8 bits flags of VXLAN. The I flag MUST be 
                  set to 1 for a valid VNI. Others are reserved.";
                type flags-vxlan;
              }
            }
            case nvgre{
              leaf nvgreFlag {
                  description
                    "The 13 bits flags of NVGRE. Bit 0 and 3 are set 
                    to 0 while bit 2 is set to 1. 
                    Others are reserved";
                  type flags-nvgre;
              }
              leaf flowId {
                description
                  "This is an 8-bit value that is used to provide 
                  per-flow entropy for flows in the same VSID. 
                  If a FlowID is not generated, it MUST be set to 
                  all zero.";
                type uint8;
              }
            }
          }
          choice bumMode{
            case headEnd{
              leaf-list peerAddr {
                description
                  "Remote NVE address.";
                type inet:ip-address;
              }
            }
            case multiGroup{
              leaf multiAddr {
                description
                  "The multicast group address.";
                type inet:ip-address;
              }
            }
          }

        }
      }//container members
    }
  }//container nvo3Nves

  container nvo3Infos {
    list nvo3Info {
      key "VNI";
      leaf VNI {
        description
          "Virutal Network Instance (VNI). For VxLAN, it is 
          VXLAN Network Identifier; For NVGRE, it is Virtual 
          Subnet Identifier.";
        mandatory "true";
        type uint32 {
        range "1 .. 16777215";
        }
      }
      leaf statisticsEnable {
        type enumeration {
          enum enable {
            value "0";
            description
              "Enable";
          }
          enum disable {
            value "1";
            description
              "Disable";
          }
        }
      }
      leaf status {
        config "false";
        type enumeration {
          enum up {
            value "0";
            description
              "Up";
          }
          enum down {
            value "1";
            description
              "Down";
          }
        }
      }      
    }
  }//container nvo3Infos

  container nvo3Statistics {
    list localNVE {
      config "false";
      leaf count {
        description
          "The value of count.";
        config "false";
        type uint64;
      }  
      leaf-list ipAddr {
        description
          "List of local NVE address.";
        config "false";
        type inet:ip-address;
      }
    }  
    list remoteNVE {
      config "false";
      leaf count {
        description
          "The value of count.";
        config "false";
        type uint64;
      }  
      leaf-list ipAddr {
        description
          "List of remote NVE address.";
        config "false";
        type inet:ip-address;
      }
    }  
    container flowStatistics {
      grouping inputStatistics {
        leaf inPacketsCount {
          config "false";
          type uint64;
        }  
        leaf inBytesCount {
          config "false";
          type uint64;
        }  
        leaf inUnicasts {
          config "false";
          type uint64;
        }  
        leaf inMulticasts {
          config "false";
          type uint64;
        }  
        leaf inBroadcasts {
          config "false";
          type uint64;
        }  
        leaf inUnknownUnicastDrops {
          config "false";
          type uint64;
        }
        leaf inUnknownMulticastDrops {
          config "false";
          type uint64;
        }  
        leaf inBroadcastsDrops {
          config "false";
          type uint64;
        }
      }
      grouping outputStatistics {
        leaf outPacketsCount {
          config "false";
          type uint64;
        }  
        leaf outBytesCount {
          config "false";
          type uint64;
        }  
        leaf outUnicasts {
          config "false";
          type uint64;
        }  
        leaf outMulticasts {
          config "false";
          type uint64;
        }  
        leaf outBroadcasts {
          config "false";
          type uint64;
        }  
      }
      leaf instanceCount {
        config "false";
        type uint64;
      }  
      list flowStatistic{
        config "false";
        leaf VNI {
          description
            "Virutal Network Instance (VNI). For VxLAN, it is 
            VXLAN Network Identifier; For NVGRE, it is Virtual 
            Subnet Identifier.";
          config "false";
          type uint32;
        }
        uses inputStatistics;
        uses outputStatistics;
      }
    }//container flowStatistics
    container MacStatistics {
      list MacStatistic{
        config "false";
        leaf VNI {
          description
            "Virutal Network Instance (VNI). For VxLAN, it is 
            VXLAN Network Identifier; For NVGRE, it is Virtual 
            Subnet Identifier.";
          config "false";
          type uint32;
        }
        leaf vmMacCount {
          description
            "Count of learning Mac addresses for the VNI.";
          config "false";
          type uint64;
        }
      }
    }//container MacStatistics
  }//container nvo3Statistics
}
