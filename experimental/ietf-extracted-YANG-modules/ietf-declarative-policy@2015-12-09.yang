module ietf-declarative-policy {

   yang-version 1;

   namespace "urn:ietf:params:xml:ns:yang:ietf-declarative-policy";

   prefix "dpolicy";

   import ietf-yang-types {
        prefix yang;
   }

   organization
     "Individual I-D as input to SUPA WG";

     contact
       "Editor:   Bert Wijnen
                  <mailto:bwietf@bwijnen.net>

        Author:   Tianran Zhou
                  <mailto:zhoutianran@huawei.com>

        Author:   Yinben Xia
                  <mailto:xiayinben@huawei.com>
       ";

   description
     "This YANG module defines essential components for the
      management of declarative policies.
      Copyright (c) 2015 IETF Trust and the persons identified as
      authors of the code. All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      The key words 'MUST', 'MUST NOT', 'REQUIRED', 'SHALL', 'SHALL
      NOT', 'SHOULD', 'SHOULD NOT', 'RECOMMENDED', 'MAY', and
      'OPTIONAL' in the module text are to be interpreted as
      described in RFC 2119 (http://tools.ietf.org/html/rfc2119).

      This version of this YANG module is part of RFC XXXX
      (http://tools.ietf.org/html/rfcXXXX); see the RFC itself for
      full legal notices.";

      revision "2015-12-09" {
          description
             "Initial revision.";
          reference
             "RFC XXXX: A YANG Data Model for Delcarative Policy.";
      }

      typedef uuid {
          type string {
              pattern '[0-9a-fA-F]{8}-[0-9a-fA-F]{4}-' +
              '[0-9a-fA-F]{4}-[0-9a-fA-F]{4}-[0-9a-fA-F]{12}';
          }
          description
              "A Universally Unique Identifier in the string
               representation defined in RFC 4122. The canonical
               representation uses lower case characters.

               The following is an example of a UUID in string
               representation:
               f81d4fae-7dec-11d0-a765-00a0c91e6bf6";
          reference
              "RFC 4122: A Universally Unique IDentifier (UUID) URN
               Namespace";
      }

      typedef unique-id {
          type uuid;
          description
              "A globally unique identifier.";
      }

      typedef name {
          type string {
              length "1..256";
              pattern '[a-zA-Z]([a-zA-Z0-9\-_.])*';
          }
          description
              "A generic string name type. Must start with a
               letter";
      }

      typedef parameter-name {
          type name;
          description
              "A name for a parameter.";
      }

      typedef action-name {
          type name;
          description
              "A name for an action.";
      }

      typedef condition-segment-id {
          type unique-id;
          description
              "A unique ID for a segment of the condition in an
               operation.";
      }

      typedef constraint-segment-id {
          type unique-id;
          description
              "A unique ID for a segment of the constraint in
              an operation.";
      }

      typedef condition-parameter-name {
          type name;
          description
              "A name for a parameter of condition.";
      }

      typedef constraint-parameter-name {
          type name;
          description
              "A name for a parameter of constraint.";
      }

      typedef policy-id {
          type unique-id;
          description
              "A unique ID for a policy.";
      }

      typedef policy-name {
          type string;
          description
              "A name for a policy.";
      }

      typedef object-id {
          type unique-id;
          description
              "A unique ID for a parameterized object.";
      }

      typedef match-pattern-operator {
          type enumeration {
              enum less-than {
                 description "less than";
              }
              enum not-less-than {
                 description "not less than";
              }
              enum equal {
                 description "equal";
              }
              enum not-equal {
                 description "not equal";
              }
              enum greater-than {
                 description "greater than";
              }
              enum not-greater-than {
                 description "not greater than";
              }
              enum between {
                 description "between";
              }
              enum periodical {
                 description "periodical";
              }
          }
          description "pattern matching operators";
      }

  container top_declarative_policy {
      description "Top level declarative policy container";

      container condition-parameter-definitions {
          description "List of condition parameters";
          list condition-parameter-definition {
              key "parameter-name";
              description
                  "Defines the condition parameter with its
                   metadata.";
              leaf parameter-name {
                  type parameter-name;
                  mandatory true;
                  description
                      "A name for the condition parameter.";
              }

              leaf parameter-value-type {
                  type enumeration {
                      enum string {
                          description
                              "A string-valued parameter.";
                      }
                      enum int {
                          description
                              "An integer-valued parameter.";
                      }
                      enum range {
                          description
                              "An integer-range parameter.";
                      }
                  }
                  description
                      "A type of value for the condition
                       parameter.";
              }

              container parameter-match-patterns {
                  description
                      "Defines the match patterns of the condition
                       parameter.";

                  leaf-list parameter-match-pattern {
                      type match-pattern-operator;
                      description
                          "pattern matching operator";
                  }
              }
          }
      }

      container constraint-parameter-definitions {
          description "Parameter definitions fro constraints";
          list constraint-parameter-definition {
              key "parameter-name";
              description
                  "Defines the constraint parameter with its
                   metadata.";

              leaf parameter-name {
                  type parameter-name;
                  mandatory true;
                  description
                      "A name for the constraint parameter.";
              }

              leaf parameter-value-type {
                  type enumeration {
                      enum string {
                          description
                              "A string-valued parameter.";
                      }
                      enum int {
                          description
                              "An integer-valued parameter.";
                      }
                      enum range {
                          description
                              "An integer-range parameter.";
                      }
                  }
                  description
                      "A type of value for the constraint
                       parameter.";
              }

              container parameter-match-patterns {
                  description
                      "Defines the match patterns of the constraint
                       parameter.";

                  leaf-list parameter-match-pattern {
                      type match-pattern-operator;
                      description
                          "pattern matching operator";
                  }
              }
          }
      }

      container action-definitions {
          description "Action definitions";
          list action-definition {
              key "action-name";
              description
                  "Defines the actions which will be supported.";

              leaf action-name {
                  type action-name;
                  mandatory true;
                  description
                      "A name for the action definition.";
              }

              leaf parameter-value-type {
                  type enumeration {
                      enum string {
                          description
                              "A string-valued parameter.";
                      }
                      enum int {
                          description
                              "An integer-valued parameter.";
                      }
                      enum range {
                          description
                              "An integer-range parameter.";
                      }
                  }
                  default string;
                  description
                      "The type of the action parameter.";
              }
          }
      }

      grouping condition-instance {
          description
              "Specific a instance of condition whose metadata has
               been filled in.";

          list condition-segment {
              key "condition-segment-id";
              description
                  "The segment entities will be composed into a
                   whole condition entity. Each segment will be
                   a sub expression of the condition.";

              leaf condition-segment-id {
                  type condition-segment-id;
                  mandatory true;
                  description
                      "A unique ID for a condition segment.";
              }

              leaf condition-parameter-name {
                  type condition-parameter-name;
                  description
                      "A name for a condition parameter.";
              }

              leaf condition-parameter-match-pattern {
                      type match-pattern-operator;
                      description
                         "The operator for the condition parameter
                          and it's target value.";
              }

              container condition-parameter-target-value {
                  description
                      "The target value of condition parameter.";

                  leaf string-value {
                      type string;
                      description "The value is of type 'string'";
                  }

                  leaf int-value {
                      type int64;
                      description "The value is of type 'int64'";
                  }

                  container range-value {
                      description
                          "The min/max of a range.";
                      leaf min {
                          type int64;
                          mandatory true;
                          description "minimum value of the range";
                      }

                      leaf max {
                          type int64;
                          mandatory true;
                          description "maximum value of the range";
                      }
                  }
              }

              leaf precursor-relation-operator {
                  type enumeration {
                      enum none {
                         description
                            "no precursor-relation-operator";
                      }
                      enum and {
                         description
                            "'and' precursor-relation-operator";
                      }
                      enum or {
                         description
                            "'or' precursor-relation-operator";
                      }
                      enum not {
                         description
                            "'not' precursor-relation-operator";
                      }
                  }
                  description "the pre-cursor relation operation.";
              }

              leaf order {
                  type uint32;
                  description
                      "The order of the segment in the whole
                       condition entity.";
              }
          }
      }

      grouping constraint-instance {
          description
              "Specific a instance of constraint whose metadata
               has been filled in.";

          list constraint-segment {
              key "constraint-segment-id";
              description
                  "The segment entities will be composed into a
                   whole constraint entity. Each segment will be
                   a sub expression of the constraint.";

              leaf constraint-segment-id {
                  type constraint-segment-id;
                  mandatory true;
                  description
                      "A unique ID for a constraint segment.";
              }

              leaf constraint-parameter-name {
                  type constraint-parameter-name;
                  description
                      "A name for a constraint parameter.";
              }

              leaf constraint-parameter-match-pattern {
                  type match-pattern-operator;
                  description
                      "The operator for the constraint parameter
                       and it's target value.";
              }

              container constraint-parameter-target-value {
                  description
                      "The target value of constraint parameter.";

                  leaf string-value {
                      type string;
                      description "the string value.";
                  }

                  leaf int-value {
                      type int64;
                      description "the int64 value.";
                  }

                  container range-value {
                      description "a range of values.";
                      leaf min {
                         type int64;
                         mandatory true;
                         description "the min value in the range.";
                      }

                      leaf max {
                         type int64;
                         mandatory true;
                         description "the max value in the range.";
                      }

                  }
              }

              leaf precursor-relation-operator {
                  type enumeration {
                      enum none {
                         description "no relational operation.";
                      }
                      enum and {
                         description "'and' relational operation.";
                      }
                      enum or {
                         description "'or' relational operation.";
                      }
                      enum not {
                         description "'not' relational operation.";
                      }
                  }
                  description
                      "The logical operator between current segment
                       and the next segment.";
              }

              leaf order {
                  type uint32;
                  description
                      "The order of the segment in the whole
                       constraint entity.";
              }
          }
      }

      grouping action-instance {
          description
              "Specific a action instance whose metadata has
               been filled in.";

          leaf action-name {
              type action-name;
              mandatory true;
              description
                  "A name for a action instance.";
          }

          container parameter-values {
              description
                  "The parameter value list of an action.";

              list string-value {
                  key "value order";
                  description "list of string values.";
                  leaf value {
                      type string;
                      description "The string value.";
                  }

                  leaf order {
                      type uint32;
                      description "The order of the value in the
                                   list.";
                  }
              }

              list int-value {
                  key "value order";
                  description "list of integer values.";
                  leaf value {
                      type int64;
                      description "The int64 value.";
                  }

                  leaf order {
                      type uint32;
                      description "The order of the value in the
                                   list.";
                  }
              }

              container range-value {
                  description "a value range.";
                  leaf min {
                      type int64;
                      mandatory true;
                      description "The min value in the range.";
                  }

                  leaf max {
                      type int64;
                      mandatory true;
                      description "The max value in the range.";
                  }
              }
          }
      }

      grouping operation {
          description "Defines an operation.";
          container condition {
              uses condition-instance;
              description "Defines a condition";
          }

          list action {
              key "action-name";
              uses action-instance;
              min-elements 1;
              description
                  "The action list for the operation instance.";
              leaf order {
                  type uint32;
                  description
                      "The order of an action instance in
                       execution sequence.";
              }
          }

          container constraint{
              uses constraint-instance;
              description "The constraint definition.";
          }
      }

      grouping relational-expression-value {
          description "The relational expression.";
          choice value-type {

              description
                  "The value of the relation expression can be
                   different type.";
              case string{
                  leaf single-string-value {
                      type string;
                      description "The string value of the
                                   variable.";
                  }
              }
              case string-list {
                  list string-value {
                      key "value order";
                      description "List of string values.";
                      leaf value {
                          type string;
                          description "The string value of the
                                       variable.";
                      }
                      leaf order {
                          type uint32;
                          description "the order in the list.";
                      }
                  }
              }
              case int {
                  leaf single-int-value {
                      type int64;
                      description "The value of the int64
                                   variable.";
                  }
              }
              case int-list {
                  list int-value {
                      key "value order";
                      description "List of integer values.";
                      leaf value {
                          type int64;
                          description "the value of the int64
                                       variable.";
                      }

                      leaf order {
                          type uint32;
                          description "the order in the list.";
                      }
                  }
              }
              case variable {
                  leaf variable-name {
                      type string;
                      description "the name of the variable.";
                  }
              }

              case calculation-expression {

                  leaf calculation-operator{
                      type enumeration {
                          enum add {
                               description "'add' operator";
                          }
                          enum minus {
                               description "'subtract' operator";
                          }
                          enum multiply {
                               description "'multiply' operator";
                          }
                          enum divide {
                               description "'divide' operator";
                          }
                          enum any {
                               description "'any' operator";
                          }
                          enum all {
                               description "'all' operator";
                          }
                          enum max {
                               description "'max' operator";
                          }
                          enum min {
                               description "'min' operator";
                          }
                          enum average {
                               description "'avg' operator";
                          }
                          enum sum {
                               description "'sum' operator";
                          }
                          enum count {
                               description "'count' operator";
                          }
                          enum and {
                               description "'and' operator";
                          }
                          enum or {
                               description "'or' operator";
                          }
                          enum not {
                               description "'not' operator";
                          }
                          enum intersection {
                               description "'intersetion'
                                            operator";
                          }
                          enum union {
                               description "'union' operator";
                          }
                          enum complement {
                               description "'complement' operator";
                          }
                      }
                      description
                          "The calculation to be performed";
                  }

                  leaf calculation-leaf-value {
                      type string;
                      description
                          "The content of the leaf value for a
                           calculation expression is an instance
                           of relational-expression-value.";
                  }

                  leaf calculation-right-value {
                      type string;
                      description
                          "The content of the right value for a
                           calculation expression is an instance
                           of relational-expression-value.";
                  }
              }
          }
      }

      grouping result {
          description "The result.";
          container left-value {
              description "The 'left' value for the relational
                           operation.";
              uses relational-expression-value;
          }

          container relational-operator {
              description
                 "The relational operation to be performed";
              leaf relational-operator {
                  type enumeration {
                      enum eq {
                           description "'equal' operator.";
                      }
                      enum ne {
                           description "'not equal' operator.";
                      }
                      enum gt {
                           description "'greater than' operator.";
                      }
                      enum ge {
                           description "greater than or equal'
                                        operator.";
                      }
                      enum lt {
                           description "'less than' operator.";
                      }
                      enum le {
                           description "'less than or equal'
                                         operator.";
                      }
                      enum bl {
                           description "'belongs to' or
                                        'is an element of'
                                         operator.";
                      }
                      enum nb {
                           description "'does not belong to' or
                                        'is not an element of'
                                        operator.";
                      }
                  }
                  description "the relational operation to be
                               performed.";
              }
          }
          container right-value {
              description "The 'right' value for the relational
                           operation.";
              uses relational-expression-value;
          }
      }

      container declarative-policy {
          description
              "Aarative policy definition";

          leaf policy-id {
              type policy-id;
              mandatory true;
              description
                  "A unique ID for a policy.";
          }

          leaf policy-name {
              type policy-name;
              mandatory true;
              description
                  "A user-visible and unique name for a policy.";
          }

          leaf priority {
              type uint8;
              default 0;
              description
                  "Defines the priority of a operation instance.";
          }

          container policy-validity-period {
              description
                  "The valid time of the policy. E.g., the policy
                   will be valid 9am-9am daily";
              leaf start {
                  type yang:date-and-time;
                  description "date and time to start the policy";
              }
              leaf end {
                  type yang:date-and-time;
                  description "date and time to end the policy";
              }
              leaf duration {
                  type uint32;
                  description "duration of the policy";
              }
              leaf periodicity {
                  type enumeration {
                      enum daily {
                          value 0;
                          description
                              "The policy is repeated daily";
                      }
                      enum monthly {
                          value 1;
                          description
                              "The policy is repeated monthly";
                      }
                  }
                  description "How the policy is repeated";
              }
          }

          leaf policy-rule-deploy-status {
              type enumeration {
                  enum undefined {
                      description "undefined";
                  }
                  enum deployed_and_enabled {
                      description "deployed and enabled";
                  }
                  enum deployed_and_testing {
                      description "deployed and in test";
                  }
                  enum deployed_and_disabled {
                      description "deployed but not enabled";
                  }
                  enum ready_to_be_deployed {
                      description "ready to be deployed";
                  }
                  enum not_deployed {
                      description "not deployed";
                  }
              }
              description
                  "The deploy status of the policy.";
          }

          leaf policy-rule-exec-status {
              type enumeration {
                  enum undefined {
                     description "undefined";
                  }
                  enum executed_and_succeeded{
                     description
                        "executed and SUCEEDED (operational mode)";
                  }
                  enum executed_and_failed{
                     description
                        "executed and FAILED (operational mode)";
                  }
                  enum executing {
                     description
                        "currently executing (operational mode)";
                  }
                  enum tested_and_succeeded {
                     description
                        "executed and SUCEEDED (test mode)";
                 }
                  enum tested_and_failed {
                     description
                        "executed and FAILED (test mode)";
                  }
                  enum testing {
                     description
                        "currently executing (test mode)";
                  }
              }
              description
                  "The executing status of the policy.";
          }

          leaf target-object {
              type object-id;
              mandatory true;
              description
                  "The target object which the operation instanc
                   will apply to.";
          }

          container declarative-policy-rule {
              description "declarative policy rules.";
              container operation {
                  uses operation;
                  description
                      "An operation based declarative policy rule";
              }
              container result {
                  uses result;
                  description
                      "A result based declarative policy rule";
              }
          }
      }
  }
  }
