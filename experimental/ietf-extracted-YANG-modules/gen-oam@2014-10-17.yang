module gen-oam {
  namespace "urn:ietf:params:xml:ns:yang:gen-oam";
  prefix goam;

  import ietf-interfaces {
    prefix if;
  }
  import ietf-yang-types {
    prefix yang;
  }
  import ietf-inet-types {
    prefix inet;
  }

  organization "IETF LIME Working Group";
  contact
    "Tissa Senevirathne tsenevir@cisco.com";
  description
    "This YANG module defines the generic configuration,
     statistics and rpc for OAM to be used within IETF in
     a protocol indpendent manner. Functional level
     abstraction is indendent with YANG modeling. It is
     assumed that each protocol maps corresponding
     abstracts to its native format.
     Each protocoal may extend the YANG model defined
     here to include protocol specific extensions";

  revision 2014-10-17 {
    description
      "Initial revision. - 02 version";
    reference "draft-tissa-lime-oam";
  }

  identity technology-types {
    description
      "this is the base identy of technology types which are
       vpls, nvo3, TRILL, ipv4, ipv6, mpls, etc";
  }

  identity ipv4 {
    base technology-types;
    description
      "technology of ipv4";
  }
  identity ipv6 {
    base technology-types;
    description
      "technology of ipv6";
  }

  identity command-sub-type {
    description
      "defines different rpc command subtypes, e.g rfc792 ping
       vs udp ping, this is optional for most cases";
  }

  identity icmp-rfc792 {
    base command-sub-type;
    description
      "Defines the command subtypes for ICMP ping";
    reference "RFC 792";
  }

  identity name-format {
    description
      "This defines the name format, IEEE 8021Q CFM defines varying
      styles of names. It is expected name format as an identity ref
      to be extended with new types.";
  }

  identity name-format-null {
    base name-format;
    description
      "defines name format as null";
  }

  identity identifier-format {
    description
      "identifier-format identity can be augmented to define other
     format identifiers used in MEPD-ID etc";
  }

  identity identifier-format-integer {
    base identifier-format;
    description
      "defines identifier-format to be integer";
  }

  typedef MEP-direction {
    type enumeration {
      enum "Up" {
        value 0;
      }
      enum "Down" {
        value 1;
      }
    }
  }

  typedef MEP-name {
    type string;
    description
      "Generic administrative name for a MEP";
  }

  typedef Interval {
    type uint32;
    units "milliseconds";
    default "1000";
    description
      "Interval between packets in milliseconds.
       0 means no packets are sent.";
  }

  typedef ecmp-choices {
    type enumeration {
      enum "ecmp-use-platform-hash" {
        value 0;
      }
      enum "ecmp-use-round-robin" {
        value 1;
      }
    }
  }

  typedef MD-name-string {
    default "";
    type string;
    description
      "Generic administrative name for an MD";
  }

  typedef MA-name-string {
    default "";
    type string;
    description
      "Generic administrative name for an MA";
  }

  typedef oam-counter32 {
    type yang:zero-based-counter32;
    description
      "defines 32 bit counter for OAM";
  }

  typedef MD-level {
    type uint32 {
      range "0..255";
    }
    description
      "Maintenance Domain level.  The level may be restricted in
       certain protocols (eg to 0-7)";
  }

  grouping mp-address {
    choice mp-address {
      case mac-address {
        leaf mac-address {
          type yang:mac-address;
        }
      }
      case ipv4-address {
        leaf ipv4-address {
          type inet:ipv4-address;
        }
      }
      case ipv6-address {
        leaf ipv6-address {
          type inet:ipv6-address;
        }
      }
    }
  }

  grouping maintenance-domain-id {
    status current;
    description
      "Grouping containing leaves sufficient to identify an MD";
    leaf technology {
      status current;
      type identityref {
        base technology-types;
      }
      mandatory true;
      description
        "Defines the technology";
    }
    leaf MD-name-string {
      status current;
      description
        "Defines the generic administrative maintenance domain name";
      type MD-name-string;
      mandatory true;
    }
  }

  grouping MD-name {
    leaf MD-name-format {
      type identityref {
        base name-format;
      }
    }
    choice MD-name {
      case MD-name-null {
        leaf MD-name-null {
          when "../../../MD-name-format = name-format-null";
          type empty;
        }
      }

    }

  }

  grouping ma-identifier {
    description
      "Grouping containing leaves sufficient to identify an MA";
    leaf MA-name-string {
      type MA-name-string;
    }
  }

  grouping MA-name {
    leaf MA-name-format {
      type identityref {
        base name-format;
      }
    }
    choice MA-name {
      case MA-name-null {
        leaf MA-name-null {
          when "../../../MA-name-format = name-format-null";
          type empty;
        }
      }

    }

  }

  grouping MEP-ID {
    choice MEP-ID {
      default "MEP-ID-int";
      case MEP-ID-int {
        leaf MEP-ID-int {
          type int32;
        }
      }

    }
    leaf MEP-ID-format {
      type identityref {
        base identifier-format;
      }

    }
  }

  grouping MEP {
    status current;
    description
      "Defines elements within the MEP";
    leaf mep-name {
      mandatory true;
      type MEP-name;
      status current;
      description
        "Generic administrative name of the MEP";
    }
    uses MEP-ID;

    uses mp-address;
    uses connectivity-context;
    leaf Interface {
      type if:interface-ref;
      description
        "Interface name as defined by ietf-interfaces";
    }
  }

  grouping monitor-stats {
    leaf tx-packt-count {
      type oam-counter32;
      description
        "Transmitted Packet count";
    }
    leaf rx-packet-count {
      type oam-counter32;
      description
        "Received packet count";
    }
    leaf min-delay {
      units "milliseconds";
      type oam-counter32;
      description
        "Delay is specified in milliseconds";
    }
    leaf average-delay {
      units "milliseconds";
      type oam-counter32;
      description
        "average delay in milliseconds";
    }
    leaf max-delay {
      type oam-counter32;
      units "millisecond";
    }
  }

  grouping MIP {
    description
      "defines MIP";
    leaf interface {
      type if:interface-ref;
    }
  }

  grouping related-oam-layer {
    leaf offset {
      type int32 {
        range "-255..255";
      }
      description
        "defines offset (in MD levels) to a related OAM layer
         +1 is the layer immediately above
         -1 is the layer immediately below";
    }
    uses maintenance-domain-id;
    uses ma-identifier;
  }

  grouping interface-status {
    description
      "collection of interface related status";
    leaf admin-status {
      config false;
      type leafref {
        path "/if:interfaces-state/if:interface/if:admin-status";
      }
      description
        "oper status from ietf-interface module";
    }
    leaf oper-status {
      config false;
      type leafref {
        path "/if:interfaces-state/if:interface/if:oper-status";
      }
      description
        "oper status from ietf-interface module";
    }
  }

  grouping connectivity-context {
    description
      "Grouping defining the connectivity context for an MA; for
       example, a VRF for IP, or an LSP for MPLS.  This will be
       augmented by each protocol who use this component";
    choice connectivity-context {
      default "context-null";
      case context-null {
        description
          "this is a place holder when no context is needed";
        leaf context-null {
          type empty;
          description
            "there is no context define";
        }
      }
    }
  }

  grouping priority {
    description
      "Priority used in transmitted packets; for example, in the
       TOS/DSCP field in IP or the Traffic Class field in MPLS";
    leaf priority {
      type uint8;
    }
  }

  grouping flow-entropy {
    description
      "defines the grouping statement for flow-entropy";
    choice flow-entropy {
      default "flow-entropy-null";
      case flow-entropy-null {
        description
          "this is a place holder when no flow entropy is needed";
        leaf flow-entropy-null {
          type empty;
          description
            "there is no flow entropy defined";
        }
      }
    }
  }

  container domains {
    status current;
    config true;
    description
      "Contains configuration related data. Within the container
       is list of fault domains. Wihin each domian has List of MA.";
    list domain {
      key "technology MD-name-string";
      ordered-by system;
      status current;
      config true;
      description
        "Define the list of Domains within the IETF-OAM";
      uses maintenance-domain-id;
      uses MD-name;
      leaf md-level {
        mandatory true;
        status current;
        description
          "Defines the MD-Level";
        type MD-level;
      }
      container MAs {
        status current;
        config true;
        description
          "This container defines MA, within that have multiple MA
           and within MA have MEP, MIP";
        list MA {
          ordered-by system;
          status current;
          config true;
          key "MA-name-string";
          uses ma-identifier;
          uses MA-name;
          uses connectivity-context;
          leaf mep-direction {
            type MEP-direction;
            mandatory true;
            description
              "Direction for MEPs in this MA";
          }
          leaf interval {
            default "0";
            description
              "Defines default Keepalive/CC Interval.  May be
               overridden for specific sessions if supported by the
               protocol.";
            type Interval;
          }
          leaf loss-threshold {
            default "3";
            type uint32;
            description
              "number of consecutive Keepalive/CC messages missed
               before declaring loss of continuity fault. This is
               monitored per each remote MEP session";
          }
          leaf ttl {
            type uint8;
            default "255";
          }
          uses flow-entropy {
            description
              "Default flow entropy in this MA, which may be
               overridden for particular MEPs, sessions or
               operations";
          }
          uses priority {
            description
              "Default priority for this MA, which may be overridden
               for particular MEPs, sessions or operations.";
          }
          list MEP {
            key "mep-name";
            ordered-by system;
            status current;
            config true;
            description
              "contain list of MEPS";
            uses MEP {
              status current;
            }
            uses interface-status {
              description
                "status of associated interface";
            }
            uses flow-entropy;
            uses priority;
            list session {
              key "session-cookie";
              ordered-by user;
              config true;
              description
                "Monitoring session to/from a particular remote MEP.
                 Depending on the protocol, this could represent CC
                 messages received from a single remote MEP (if the
                 protocol uses multicast CCs) or a target to which
                 unicast echo request CCs are sent and from which
                 responses are received (if the protocol uses a
                 unicast request/response mechanism).";
              leaf session-cookie {
                config true;
                type uint32;
                description
                  "Cookie to identify different sessions, when there
                   are multiple remote MEPs or multiple sessions to
                   the same remote MEP.";
              }
              leaf ttl {
                config true;
                type uint8;
                default "255";
              }
              leaf interval {
                type Interval;
                description
                  "Transmission interval for CC packets for this
                   session.";
              }
              leaf enable {
                default "false";
                config true;
                type boolean;
                description
                  "enable or disable a monitor session";
              }
              leaf ecmp-choice {
                config true;
                type ecmp-choices;
                description
                  "0 means use the specified interface
                   1 means use round robin";
              }
              leaf source-mep {
                type MEP-name;
                description
                  "Source MEP for this session, if applicable";
              }
              container destination-mep {
                uses MEP-ID;
              }
              container destination-mep-address {
                uses mp-address;
              }
              uses connectivity-context;
              uses flow-entropy;
              uses priority;
              list outgoing-interface {
                key "interface";
                config true;
                leaf interface {
                  type leafref {
                    path "/if:interfaces/if:interface/if:name";
                  }
                  config true;
                }
              }
            }
          }
          list MIP {
            key "interface";
            uses MIP;
          }
          list related-oam-layer {
            key "offset";
            description
              "List of OAM layers above and below that are related to
               current MA. This allow users to easily navigate up and
               down to efficiently troubleshoot a connectivity
               issue";
            uses related-oam-layer;
          }
        }
      }
    }
  }
  notification RDI-notification {
    description
      "When RDI is received this notificiation is sent";
   uses maintenance-domain-id {
      description
        "defines the MD (Maintenance Domain) identifier, which is the
         Generic MD-name-string and the technology.";
    }
    uses ma-identifier;
    leaf mep-name {
      type MEP-name;
      description
        "Indicate which MEP is seeing the error";
    }
    container remote-mepid {
      uses MEP-ID;
      description
        "Who is seeing the error (if known) if unknown make it 0.";
    }
    leaf error-message {
      type string {
        length "0..255";
      }
      description
        "Error message to indicate more details.";
    }
  }
  rpc ping {
    description
      "Generates Ping and return response";
    input {
      uses maintenance-domain-id {
        description
          "defines the MD (Maintenance Domain) identifier, which is
the generic
           MD-name-string and the technology.";
      }

      uses ma-identifier {
        description
          "identfies the Maintenance association";
      }
      uses flow-entropy;
      uses priority;
      leaf ttl {
        type uint8;
        default "255";
      }
      leaf ecmp-choice {
        type ecmp-choices;
        description
          "0 means use the specified interface
           1 means use round robin";
      }
      leaf sub-type {
        type identityref {
          base command-sub-type;
        }
        description
          "defines different command types";
      }
      list outgoing-interfaces {
        key "interface";
        leaf interface {
          type if:interface-ref;
        }
      }
      leaf source-mep {
        type MEP-name;
      }
      container destination-mp {
        uses mp-address;
        uses MEP-ID {
          description "Only applicable if the destination is a MEP";
        }
      }
      leaf count {
        type uint32;
        default "3";
        description
          "Number of ping echo request message to send";
      }
      leaf interval {
        type Interval;
        description
          "Interval between echo requests";
      }
      leaf packet-size {
        type uint32 {
          range "64..10000";
        }
        default "64";
        description
          "Size of ping echo request packets, in octets";
      }
    }
    output {
      uses monitor-stats {
        description
          "Stats of Ping is same as that of monitor sessions";
      }
    }
  }
  rpc trace-route {
    description
      "Generates Trace-route and return response. Starts with TTL
       of one and increment by one at each hop. Untill destination
       reached or TTL reach max valune";
    input {
      uses maintenance-domain-id {
        description
          "defines the MD (Maintenance Domain) identifier, which is
the generic
           MD-name-string and the technology.";
      }
      uses ma-identifier {
        description
          "identfies the Maintenance association";
      }
      uses flow-entropy;
      uses priority;
      leaf ttl {
        type uint8;
        default "255";
      }
      leaf command-sub-type {
        type identityref {
          base command-sub-type;
        }
        description
          "defines different command types";
      }
      leaf ecmp-choice {
        type ecmp-choices;
        description
          "0 means use the specified interface
           1 means use round robin";
      }
      list outgoing-interfaces {
        key "interface";
        leaf interface {
          type if:interface-ref;
        }
      }
      leaf source-mep {
        type MEP-name;
      }
      container destination-mp {
        uses mp-address;
        uses MEP-ID {
          description "Only applicable if the destination is a MEP";
        }
      }
      leaf count {
        type uint32;
        default "1";
        description
          "Number of traceroute probes to send.  In protocols where a
           separate message is sent at each TTL, this is the number
           of packets to send at each TTL.";
      }
      leaf interval {
        type Interval;
        description
          "Interval between echo requests";
      }
    }
    output {
      list response {
        key "response-index";
        leaf response-index {
          description
            "Arbitrary index for the response.  In protocols that
             guarantee there is only a single response at each TTL
             (eg IP Traceroute), the TTL can be used as the response
             index.";
          type uint8;
        }
        leaf ttl {
          type uint8;
        }
        container destination-mp {
          description "MP from which the response has been received";
          uses mp-address;
          uses MEP-ID {
            description
              "Only applicable if the destination is a MEP";
          }
        }
        uses monitor-stats {
          description
            "If count is 1, there is a single delay value reported.";
        }
      }
    }
  }
}
