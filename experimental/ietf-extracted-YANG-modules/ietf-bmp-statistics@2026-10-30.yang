module ietf-bmp-statistics {
  yang-version 1.1;
  namespace "urn:ietf:params:xml:ns:yang:ietf-bmp-statistics";
  prefix bst;

  import ietf-yang-types {
    prefix yang;
    reference
      "RFC 9911: Common YANG Data Types";
  }
  import iana-routing-types {
    prefix iana-rt-types;
    reference
      "RFC 8294: Common YANG Data Types for the Routing Area";
  }

  organization
    "IETF Draft";
  contact
    "Author:    Thomas Graf
                <mailto:thomas.graf@swisscom.com>
                Paolo Lucente
                <mailto:paolo@ntt.net>
                Leonardo Rodoni
                <mailto:leonardo.rodoni@swisscom.com>
                Maxence Younsi
                <mailto:maxence.younsi4@swisscom.com>";

  description
    "Defines the statistics grouping used by the BMP Statistics
     Report message. Each Statistics Type of the IANA 'BMP
     Statistics Types' registry is modeled as a named data node
     whose YANG type carries the Stat Data shape defined by
     RFC 7854, RFC 8671 and RFC 9972: a leaf of type counter32
     (32-bit counter), a leaf of type gauge64 (global 64-bit
     gauge), or a list keyed by AFI and SAFI with a gauge64 value
     (AFI/SAFI-scoped 64-bit gauge). The 'unknown' list is a raw
     fallback for Stat Types without a corresponding data node.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2026 IETF Trust and the persons identified as
     authors of the code. All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC XXXX; see the RFC
     itself for full legal notices.";

  revision 2026-10-30 {
    description
      "Initial Version";
    reference
      "RFC XXXX";
  }

  grouping afi-safi-gauge {
    description
      "Stat Data scoped to an AFI/SAFI: a 2-byte AFI, a 1-byte
       SAFI and a 64-bit gauge (Stat Len = 11).";
    reference
      "RFC 9972: Advanced BGP Monitoring Protocol (BMP)
       Statistics Types, Section 3.1.";
    leaf afi {
      type iana-rt-types:address-family;
      description
        "Address Family Identifier.";
    }
    leaf safi {
      type iana-rt-types:bgp-safi;
      description
        "Subsequent Address Family Identifier.";
    }
    leaf value {
      type yang:gauge64;
      mandatory true;
      description
        "64-bit gauge for the AFI/SAFI.";
    }
  }

  grouping statistics {
    description
      "BMP Statistics Report. Carries the statistics reported by
       the monitored router, each as a named data node.";
    reference
      "RFC 7854: BGP Monitoring Protocol (BMP), Section 4.8.
       RFC 8671: Support for Adj-RIB-Out in the BGP Monitoring
       Protocol (BMP), Section 6.2.
       RFC 9972: Advanced BGP Monitoring Protocol (BMP)
       Statistics Types, Section 3.";
    container statistics {
      must 'count(*) > 0' {
        error-message
          "At least one statistic must be present.";
      }
      description
        "BMP statistics. Each child node corresponds to one Stat
         Type of the IANA 'BMP Statistics Types' registry.";

      // RFC 7854 Section 4.8: Stat Types 0-13.
      leaf prefixes-rejected-by-inbound-policy {
        type yang:counter32;
        description
          "Stat Type 0: Number of prefixes rejected by inbound
           policy.";
        reference
          "RFC 7854: BGP Monitoring Protocol (BMP), Section 4.8.";
      }
      leaf duplicate-prefix-advertisements {
        type yang:counter32;
        description
          "Stat Type 1: Number of (known) duplicate prefix
           advertisements.";
        reference
          "RFC 7854: BGP Monitoring Protocol (BMP), Section 4.8.";
      }
      leaf duplicate-withdraws {
        type yang:counter32;
        description
          "Stat Type 2: Number of (known) duplicate withdraws.";
        reference
          "RFC 7854: BGP Monitoring Protocol (BMP), Section 4.8.";
      }
      leaf updates-invalidated-due-to-cluster-list-loop {
        type yang:counter32;
        description
          "Stat Type 3: Number of updates invalidated due to
           CLUSTER_LIST loop.";
        reference
          "RFC 7854: BGP Monitoring Protocol (BMP), Section 4.8.";
      }
      leaf updates-invalidated-due-to-as-path-loop {
        type yang:counter32;
        description
          "Stat Type 4: Number of updates invalidated due to
           AS_PATH loop.";
        reference
          "RFC 7854: BGP Monitoring Protocol (BMP), Section 4.8.";
      }
      leaf updates-invalidated-due-to-originator-id {
        type yang:counter32;
        description
          "Stat Type 5: Number of updates invalidated due to
           ORIGINATOR_ID.";
        reference
          "RFC 7854: BGP Monitoring Protocol (BMP), Section 4.8.";
      }
      leaf updates-invalidated-due-to-as-confed-loop {
        type yang:counter32;
        description
          "Stat Type 6: Number of updates invalidated due to a
           loop found in AS_CONFED_SEQUENCE or AS_CONFED_SET.";
        reference
          "RFC 7854: BGP Monitoring Protocol (BMP), Section 4.8.";
      }
      leaf routes-in-adj-rib-in {
        type yang:gauge64;
        description
          "Stat Type 7: Number of routes in Adj-RIBs-In.";
        reference
          "RFC 7854: BGP Monitoring Protocol (BMP), Section 4.8.";
      }
      leaf routes-in-loc-rib {
        type yang:gauge64;
        description
          "Stat Type 8: Number of routes in Loc-RIB.";
        reference
          "RFC 7854: BGP Monitoring Protocol (BMP), Section 4.8.";
      }
      list routes-in-per-afi-safi-adj-rib-in {
        key "afi safi";
        description
          "Stat Type 9: List of the number of routes in
           per-AFI/SAFI Adj-RIB-In.";
        reference
          "RFC 7854: BGP Monitoring Protocol (BMP), Section 4.8.";
        uses afi-safi-gauge;
      }
      list routes-in-per-afi-safi-loc-rib {
        key "afi safi";
        description
          "Stat Type 10: List of the number of routes in
           per-AFI/SAFI Loc-RIB.";
        reference
          "RFC 7854: BGP Monitoring Protocol (BMP), Section 4.8.";
        uses afi-safi-gauge;
      }
      leaf updates-subjected-to-treat-as-withdraw {
        type yang:counter32;
        description
          "Stat Type 11: Number of updates subjected to
           treat-as-withdraw.";
        reference
          "RFC 7854: BGP Monitoring Protocol (BMP), Section 4.8.";
      }
      leaf prefixes-subjected-to-treat-as-withdraw {
        type yang:counter32;
        description
          "Stat Type 12: Number of prefixes subjected to
           treat-as-withdraw.";
        reference
          "RFC 7854: BGP Monitoring Protocol (BMP), Section 4.8.";
      }
      leaf duplicate-update-messages-received {
        type yang:counter32;
        description
          "Stat Type 13: Number of duplicate update messages
           received.";
        reference
          "RFC 7854: BGP Monitoring Protocol (BMP), Section 4.8.";
      }

      // RFC 8671 Section 6.2: Stat Types 14-17.
      leaf routes-in-pre-policy-adj-rib-out {
        type yang:gauge64;
        description
          "Stat Type 14: Number of routes in pre-policy
           Adj-RIB-Out.";
        reference
          "RFC 8671: Support for Adj-RIB-Out in the BGP Monitoring
           Protocol (BMP), Section 6.2.";
      }
      leaf routes-in-post-policy-adj-rib-out {
        type yang:gauge64;
        description
          "Stat Type 15: Number of routes in post-policy
           Adj-RIB-Out.";
        reference
          "RFC 8671: Support for Adj-RIB-Out in the BGP Monitoring
           Protocol (BMP), Section 6.2.";
      }
      list routes-in-per-afi-safi-pre-policy-adj-rib-out {
        key "afi safi";
        description
          "Stat Type 16: List of the number of routes in
           per-AFI/SAFI pre-policy Adj-RIB-Out.";
        reference
          "RFC 8671: Support for Adj-RIB-Out in the BGP Monitoring
           Protocol (BMP), Section 6.2.";
        uses afi-safi-gauge;
      }
      list routes-in-per-afi-safi-post-policy-adj-rib-out {
        key "afi safi";
        description
          "Stat Type 17: List of the number of routes in
           per-AFI/SAFI post-policy Adj-RIB-Out.";
        reference
          "RFC 8671: Support for Adj-RIB-Out in the BGP Monitoring
           Protocol (BMP), Section 6.2.";
        uses afi-safi-gauge;
      }

      // RFC 9972 Section 3: Stat Types 18-23, 26-43.
      // Stat Types 24-25 (primary/backup route) are intentionally
      // not modeled here: they were only temporarily registered and
      // expiring on 2026-10-18, and were dropped from the final
      // RFC 9972 text; if needed use the unknown list.
      leaf routes-in-pre-policy-adj-rib-in {
        type yang:gauge64;
        description
          "Stat Type 18: Number of routes currently in the
           pre-policy Adj-RIB-In.";
        reference
          "RFC 9972: Advanced BGP Monitoring Protocol (BMP)
           Statistics Types, Section 3.2.";
      }
      list routes-in-per-afi-safi-pre-policy-adj-rib-in {
        key "afi safi";
        description
          "Stat Type 19: List of the number of routes currently in
           the per-AFI/SAFI pre-policy Adj-RIB-In.";
        reference
          "RFC 9972: Advanced BGP Monitoring Protocol (BMP)
           Statistics Types, Section 3.2.";
        uses afi-safi-gauge;
      }
      leaf routes-in-post-policy-adj-rib-in {
        type yang:gauge64;
        description
          "Stat Type 20: Number of routes currently in the
           post-policy Adj-RIB-In.";
        reference
          "RFC 9972: Advanced BGP Monitoring Protocol (BMP)
           Statistics Types, Section 3.2.";
      }
      list routes-in-per-afi-safi-post-policy-adj-rib-in {
        key "afi safi";
        description
          "Stat Type 21: List of the number of routes currently in
           the per-AFI/SAFI post-policy Adj-RIB-In.";
        reference
          "RFC 9972: Advanced BGP Monitoring Protocol (BMP)
           Statistics Types, Section 3.2.";
        uses afi-safi-gauge;
      }
      list routes-in-per-afi-safi-pre-policy-adj-rib-in-rejected {
        key "afi safi";
        description
          "Stat Type 22: List of the number of routes currently in
           the per-AFI/SAFI pre-policy Adj-RIB-In rejected by an
           inbound policy.";
        reference
          "RFC 9972: Advanced BGP Monitoring Protocol (BMP)
           Statistics Types, Section 3.2.";
        uses afi-safi-gauge;
      }
      list routes-in-per-afi-safi-post-policy-adj-rib-in-accepted {
        key "afi safi";
        description
          "Stat Type 23: List of the number of routes currently in
           the per-AFI/SAFI post-policy Adj-RIB-In accepted by an
           inbound policy.";
        reference
          "RFC 9972: Advanced BGP Monitoring Protocol (BMP)
           Statistics Types, Section 3.2.";
        uses afi-safi-gauge;
      }
      list routes-suppressed-by-route-damping {
        key "afi safi";
        description
          "Stat Type 26: List of the number of routes currently in
           the per-AFI/SAFI post-policy Adj-RIB-In or Loc-RIB
           suppressed by a configured route-damping policy.";
        reference
          "RFC 9972: Advanced BGP Monitoring Protocol (BMP)
           Statistics Types, Section 3.2.";
        uses afi-safi-gauge;
      }
      list routes-marked-stale-by-gr {
        key "afi safi";
        description
          "Stat Type 27: List of the number of routes currently in
           the per-AFI/SAFI post-policy Adj-RIB-In or Loc-RIB
           marked as stale by Graceful Restart (GR) events.";
        reference
          "RFC 9972: Advanced BGP Monitoring Protocol (BMP)
           Statistics Types, Section 3.2.";
        uses afi-safi-gauge;
      }
      list routes-marked-stale-by-llgr {
        key "afi safi";
        description
          "Stat Type 28: List of the number of routes currently in
           the per-AFI/SAFI post-policy Adj-RIB-In or Loc-RIB
           marked as stale by Long-Lived Graceful Restart (LLGR).";
        reference
          "RFC 9972: Advanced BGP Monitoring Protocol (BMP)
           Statistics Types, Section 3.2.";
        uses afi-safi-gauge;
      }
      leaf routes-left-before-received-route-threshold {
        type yang:gauge64;
        description
          "Stat Type 29: Number of routes currently in the
           post-policy Adj-RIB-In left before exceeding the
           received-route threshold.";
        reference
          "RFC 9972: Advanced BGP Monitoring Protocol (BMP)
           Statistics Types, Section 3.2.";
      }
      list routes-in-per-afi-safi-left-before-received-route-threshold {
        key "afi safi";
        description
          "Stat Type 30: List of the number of routes currently in
           the per-AFI/SAFI post-policy Adj-RIB-In left before
           exceeding the received-route threshold.";
        reference
          "RFC 9972: Advanced BGP Monitoring Protocol (BMP)
           Statistics Types, Section 3.2.";
        uses afi-safi-gauge;
      }
      leaf routes-left-before-license-route-threshold {
        type yang:gauge64;
        description
          "Stat Type 31: Number of routes currently in the
           post-policy Adj-RIB-In or Loc-RIB left before exceeding
           a license-customized route threshold.";
        reference
          "RFC 9972: Advanced BGP Monitoring Protocol (BMP)
           Statistics Types, Section 3.2.";
      }
      list routes-in-per-afi-safi-left-before-license-route-threshold {
        key "afi safi";
        description
          "Stat Type 32: List of the number of routes currently in
           the per-AFI/SAFI post-policy Adj-RIB-In or Loc-RIB left
           before exceeding a license-customized route threshold.";
        reference
          "RFC 9972: Advanced BGP Monitoring Protocol (BMP)
           Statistics Types, Section 3.2.";
        uses afi-safi-gauge;
      }
      leaf routes-rejected-due-to-as-path-length {
        type yang:gauge64;
        description
          "Stat Type 33: Number of routes currently in the
           pre-policy Adj-RIB-In rejected due to exceeding the
           locally configured maximum AS_PATH length.";
        reference
          "RFC 9972: Advanced BGP Monitoring Protocol (BMP)
           Statistics Types, Section 3.2.";
      }
      list routes-in-per-afi-safi-rejected-due-to-as-path-length {
        key "afi safi";
        description
          "Stat Type 34: List of the number of routes currently in
           the per-AFI/SAFI pre-policy Adj-RIB-In rejected due to
           exceeding the locally configured maximum AS_PATH
           length.";
        reference
          "RFC 9972: Advanced BGP Monitoring Protocol (BMP)
           Statistics Types, Section 3.2.";
        uses afi-safi-gauge;
      }
      list routes-in-per-afi-safi-invalidated-by-rpki {
        key "afi safi";
        description
          "Stat Type 35: List of the number of routes currently in
           the per-AFI/SAFI post-policy Adj-RIB-In invalidated
           after verifying the route origin AS number through the
           ROA of the RPKI, due to a mismatch of origin ASN and/or
           prefix length.";
        reference
          "RFC 9972: Advanced BGP Monitoring Protocol (BMP)
           Statistics Types, Section 3.2.
           RFC 6811: BGP Prefix Origin Validation.";
        uses afi-safi-gauge;
      }
      list routes-in-per-afi-safi-validated-by-rpki {
        key "afi safi";
        description
          "Stat Type 36: List of the number of routes currently in
           the per-AFI/SAFI post-policy Adj-RIB-In validated after
           verifying the route origin AS number through the ROA of
           the RPKI.";
        reference
          "RFC 9972: Advanced BGP Monitoring Protocol (BMP)
           Statistics Types, Section 3.2.
           RFC 6811: BGP Prefix Origin Validation.";
        uses afi-safi-gauge;
      }
      list routes-in-per-afi-safi-rpki-not-found {
        key "afi safi";
        description
          "Stat Type 37: List of the number of routes currently in
           the per-AFI/SAFI post-policy Adj-RIB-In whose RPKI
           route origin validation state is NotFound due to the
           absence of a matching ROA of the RPKI.";
        reference
          "RFC 9972: Advanced BGP Monitoring Protocol (BMP)
           Statistics Types, Section 3.2.
           RFC 6811: BGP Prefix Origin Validation.";
        uses afi-safi-gauge;
      }
      list routes-in-per-afi-safi-pre-policy-adj-rib-out-rejected {
        key "afi safi";
        description
          "Stat Type 38: List of the number of routes currently in
           the per-AFI/SAFI pre-policy Adj-RIB-Out rejected by an
           outbound policy.";
        reference
          "RFC 9972: Advanced BGP Monitoring Protocol (BMP)
           Statistics Types, Section 3.3.";
        uses afi-safi-gauge;
      }
      leaf routes-in-pre-policy-adj-rib-out-filtered-due-to-as-path-length {
        type yang:gauge64;
        description
          "Stat Type 39: Number of routes currently in the
           pre-policy Adj-RIB-Out filtered due to AS_PATH length
           exceeding the locally configured maximum.";
        reference
          "RFC 9972: Advanced BGP Monitoring Protocol (BMP)
           Statistics Types, Section 3.3.";
      }
      list routes-in-per-afi-safi-pre-policy-adj-rib-out-filtered-due-to-as-path-length {
        key "afi safi";
        description
          "Stat Type 40: List of the number of routes currently in
           the per-AFI/SAFI pre-policy Adj-RIB-Out filtered due to
           AS_PATH length exceeding the locally configured
           maximum.";
        reference
          "RFC 9972: Advanced BGP Monitoring Protocol (BMP)
           Statistics Types, Section 3.3.";
        uses afi-safi-gauge;
      }
      list routes-in-per-afi-safi-post-policy-adj-rib-out-invalidated-by-rpki {
        key "afi safi";
        description
          "Stat Type 41: List of the number of routes currently in
           the per-AFI/SAFI post-policy Adj-RIB-Out invalidated
           after verifying the route origin AS number through the
           ROA of the RPKI, due to a mismatch of origin ASN and/or
           prefix length.";
        reference
          "RFC 9972: Advanced BGP Monitoring Protocol (BMP)
           Statistics Types, Section 3.3.
           RFC 6811: BGP Prefix Origin Validation.";
        uses afi-safi-gauge;
      }
      list routes-in-per-afi-safi-post-policy-adj-rib-out-validated-by-rpki {
        key "afi safi";
        description
          "Stat Type 42: List of the number of routes currently in
           the per-AFI/SAFI post-policy Adj-RIB-Out validated
           after verifying the route origin AS number through the
           ROA of the RPKI.";
        reference
          "RFC 9972: Advanced BGP Monitoring Protocol (BMP)
           Statistics Types, Section 3.3.
           RFC 6811: BGP Prefix Origin Validation.";
        uses afi-safi-gauge;
      }
      list routes-in-per-afi-safi-post-policy-adj-rib-out-rpki-not-found {
        key "afi safi";
        description
          "Stat Type 43: List of the number of routes currently in
           the per-AFI/SAFI post-policy Adj-RIB-Out whose RPKI
           route origin validation state is NotFound due to the
           absence of a matching ROA of the RPKI.";
        reference
          "RFC 9972: Advanced BGP Monitoring Protocol (BMP)
           Statistics Types, Section 3.3.
           RFC 6811: BGP Prefix Origin Validation.";
        uses afi-safi-gauge;
      }

      list unknown {
        key "type";
        description
          "List of statistics whose Stat Type has no corresponding
           data node in this module. Each entry carries the
           raw Stat Type and Stat Data.

           Statistics whose Stat Type has a corresponding data node
           in this module SHOULD be reported using that node. They
           MAY be reported in this list instead when their Stat
           Data cannot be decoded (e.g., unexpected Stat Len).";
        reference
          "RFC 7854: BGP Monitoring Protocol (BMP), Section 10.4.";
        leaf type {
          type uint16;
          description
            "Raw Stat Type value.";
        }
        leaf data {
          type binary {
            length "0..65535";
          }
          mandatory true;
          description
            "Raw Stat Data, opaque to this module. May be empty if
             the original Stat Len was 0.";
        }
      }
    }
  }
}
