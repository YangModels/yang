module softwire {
  namespace "urn:ietf:params:xml:ns:yang:softwire";
  prefix "softwire";

  import ietf-inet-types { prefix inet; }
  import ietf-yang-types { prefix yang; }

  organization "softwire";

  contact
    "
    Qi Sun sunqi@csnet1.cs.tsinghua.edu.cn
    Hao Wang wangh13@mails.tsinghua.edu.cn
    Yong Cui yong@csnet1.cs.tsinghua.edu.cn
    Ian Farrer ian.farrer@telekom.de
    Mohamed Boucadair mohamed.boucadair@orange.com
    Rajiv Asati rajiva@cisco.com
    ";

  description
    "This document defines a YANG data model for the configuration and
    management of IPv4-in-IPv6 Softwire Border Routers and Customer Premises
    Equipment. It covers Lightweight 4over6, MAP-E and MAP-T Softwire
    mechanisms.

    Copyright (c) 2014 IETF Trust and the persons identified
    as authors of the code. All rights reserved.
    This version of this YANG module is part of RFC XXX; see the RFC
    itself for full legal notices.";

  revision 2014-12-14 {
    description
      "Initial revision.";
  }

/*
 * Typedef
 */

/*
 * Features
 */

  feature lw4over6 {
    description
      "Lightweight 4over6 moves the Network Address and Port
      Translation (NAPT) function from the centralized DS-Lite tunnel
      concentrator to the tunnel client located in the Customer
      Premises Equipment (CPE).  This removes the requirement for a
      Carrier Grade NAT function in the tunnel concentrator and
      reduces the amount of centralized state that must be held to a
      per-subscriber level.  In order to delegate the NAPT function
      and make IPv4 Address sharing possible, port-restricted IPv4
      addresses are allocated to the CPEs.";
    reference
      "I-D.ietf-softwire-lw4over6";
  }

  feature lw4over6-aftr {
    if-feature lw4over6;
    description
      "The AFTRs (BRs) for Lightweight 4over6, so-called lwAFTR.
      It means an AFTR element (Address Family Transition Router
      element [RFC6333]), which supports Lightweight 4over6 extension.
      An lwAFTR is an IPv4-in-IPv6 tunnel endpoint which maintains
      per-subscriber address binding only and does not perform a NAPT44
      function.";
  }

  feature lw4over6-b4 {
    if-feature lw4over6;
    description
      "The B4s (CPEs) for Lightweight 4over6, so-called lwB4.
      It means A B4 element (Basic Bridging BroadBand element [RFC6333]),
      which supports Lightweight 4over6 extensions. An lwB4 is a function
      implemented on a dual-stack capable node, (either a directly
      connected device or a CPE), that supports port-restricted IPv4
      address allocation, implements NAPT44 functionality and creates a
      tunnel to an lwAFTR.";
  }

  feature map-e {
    description
      "MAP-E is a mechanism for transporting IPv4 packets across an
      IPv6 network using IP encapsulation, and a generic mechanism
      for mapping between IPv6 addresses and IPv4 addresses and
      transport layer ports.";
    reference
      "I-D.ietf-softwire-map";
  }

  feature map-e-cpe {
    if-feature map-e;
    description
      "The CPEs for MAP-E.";
  }

  feature map-t {
    description
      "MAP-T is a mechanism for transporting IPv4 packets across an
      IPv6 network using IP translation, and a generic mechanism
      for mapping between IPv6 addresses and IPv4 addresses and
      transport layer ports.";
    reference
      "I-D.ietf-softwire-map-t";
  }

  feature map-t-cpe {
    if-feature map-t;
    description
      "The CPEs for MAP-T.";
  }

/*
 * Grouping
 */

  grouping port-set {
    description
      "A range of transport layer ports.";
    leaf offset {
      type uint8;
      default "6";
      description
        "The number of offset bits.";
    }
    leaf psid {
      type yang:hex-string;
      description
        "Port Set Identifier (PSID), which identifies a set of ports
        algorithmically.";
    }
    leaf psid-len {
      type uint8;
      description
        "The length of PSID.";
    }
  }

  grouping binding-table {
    description
      "The lwAFTR maintains an address binding table containing the
      binding between the lwB4's IPv6 address, the allocated IPv4
      address and restricted port-set.";
    list binding-entry {
      key "id";
      leaf id {
        type uint32;
      }
      leaf binding-ipv4-addr {
        type inet:ipv4-address;
        description
          "The IPv4 address assigned to a lwB4, which is used as the
          IPv4 External Address for lwB4 local NAPT44. One of three
          elemnts constructing a binding-entry.";
      }
      container port-set {
        uses port-set {
          refine offset {
            default "0";
          }
        }
      }
      leaf binding-ipv6-addr {
        type inet:ipv6-address;
        description
          "The IPv6 address of the lwB4, which is used to bind the
          IPv4 address and port-set.";
      }
      leaf binding-ipv6-prefix {
        type inet:ipv6-prefix;
        description
          "The IPv6 prefix of the lwB4.";
      }
      leaf active {
        type boolean;
        default "1";
        description
          "Used to add or delete a particular binding-entry.";
      leaf lifetime {
        type yang:timestamp;
        description
          "Lifetime for a binding-entry.";
      }
    }
  }

  grouping nat-table {
    description
      "Grouping 'nat-table' is not extended. It means that we are
      focusing on the provisioning of external IP address and port set;
      other NAT-specific considerations are out of scope."
  }

  grouping map-rule-table {
    description
      "The (conceptual) table containing rule Information for a
      specific mapping rule. It can also be used for row creation.";
    list map-rule-entry {
      key "id";
      leaf id {
        type uint8;
      }
      leaf IPv6-prefix {
        type inet:ipv6-prefix;
        description
          "The IPv6 prefix defined in the mapping rule which will be
          assigned to CE.";
      }
      leaf IPv6-prefix-len {
        type uint8;
        description
          "The length of the IPv6 prefix defined in the mapping rule.
          As a parameter for the mapping rule, it will be also
          assigned to CE.";
      }
      leaf IPv4-prefix {
        type inet:ipv4-prefix;
        description
          "The IPv4 prefix defined in the mapping rule which will be
          assigned to CE.";
      }
      leaf IPv4-prefix-len {
        type uint8;
        description
          "The length of the IPv4 prefix defined in the mapping
          rule. As a parameter for the mapping rule, it will be also
          assigned to CE.";
      }
      container port-set {
        uses port-set;
      }
      leaf ea-len {
        type uint8;
        description
          "The length of the Embedded-Address (EA) defined in
          mapping rule for a MAP domain. This dictates the sharing
          ratio (i.e. Maximum number of CE sharing the same IPv4
          address) used in MAP domain.";
      }
      leaf active {
        type boolean;
        default "1";
        description
            "Used to add or delete a particular map-rule-entry.";
      }
    }
  }

  grouping map-rules {
    list map-rules {
      key "id";
      leaf id {
        type uint8;
      }
      leaf map-rule-type {
        type enumeration {
          enum "BMR";
          enum "FMR";
        }
      }
      container map-rule-table {
        uses map-rule-table;
      }
    }
  }

/*
 * Configuration Data Nodes
 */

  container softwire-config {
    description
      "The configuration data for devices in Softwire. ";
    leaf enable {
      type boolean;
      default "1";
      description
        "Enable/disable the Softwire function.";
    }
    leaf name {
      type string;
      description
        "The name of Softwire.";
    }
    leaf description {
      type string;
      description
        "A textual description of Softwire.";
    }
    leaf tunnel-mtu {
      type uint32;
      description
        "The MTU of tunnel payload on the Softwire devices.";
    }
    container lw4over6-aftr {
      if-feature lw4over6-aftr;
      description
        "Indicate this device supports the lwAFTR function. Devices
        advertise the lw4over6-aftr feature through the capability
        exchange mechanism when a NETCONF session is established.";
      leaf enable {
        type boolean;
        default "1";
        description
          "Enable/disable the lwAFTR function.";
      }
      container lw4over6-aftr-devices {
        description
          "Refer to lwAFTRs.";
        list lw4over6-aftr-device {
          key "id";
          leaf id {
            type uint32;
          }
          leaf softwire-num-threshold {
            type uint32;
            description
              "The maximum number of tunnels that can be created on
              the lwAFTR.";
          }
          container binding-table {
            uses binding-table;
          }
        }
      }
    }
    container lw4over6-b4 {
      if-feature lw4over6-b4;
      description
        "Indicate this device supports the lwB4 function. Devices
        advertise the lw4over6-b4 feature through the capability
        exchange mechanism when a NETCONF session is established.";
      leaf enable {
        type boolean;
        default "1";
        description
          "Enable/disable the lwB4 function.";
      }
      container lw4over6-b4-devices {
        description
          "Refer to lwB4s.";
        list lw4over6-b4-device {
          key "id";
          leaf id {
            type uint32;
          }
          leaf b4-ipv6-addr-format {
            type boolean;
            default "1";
            description
              "The format of lwB4 IPv6 address. If set to "1" indicates
              that the default mode for building the lwB4 IPv6 address
              is used   ([I-D.ietf-softwire-lw4over6]); if set to "0", the
              lwB4 can use any address from the assigned IPv6 prefix.";
          }
          leaf binding-ipv4-addr {
            type inet:ipv4-address;
            description
              "The allocated IPv4 address of lwB4, which binding with
              the port-set.";
          }
          container port-set {
            uses port-set {
              refine offset {
                default "0";
              }
            }
          }
          leaf hint-ipv6-prefix {
            type inet:ipv6-prefix;
            description
              "'hint-ipv6-prefix' is used to longest prefix match.";
          }
          leaf aftr-ipv6-addr {
            type inet:ipv6-address;
            description
              "The IPv6 address of lwAFTR.";
          }
          container nat-table {
            uses nat-table;
          }
        }
      }
    }
    container map-e {
      if-feature map-e;
      description
        "Indicate the devices support the MAP-E function. Devices
        advertise the map-e feature through the capability exchange
        mechanism when a NETCONF session is established.";
      leaf enable {
        type boolean;
        default "1";
        description
          "Enable/disable the MAP-E function.";
      }
      container map-e-devices {
        description
          "Refer to the MAP-E devices, includes BRs and CPEs.";
        list map-e-device {
          key "id";
          leaf id {
            type uint32;
          }
          uses map-rules;
          container map-e-cpe {
            if-feature map-e-cpe;
            leaf cpe-ipv6-prefix {
              type inet:ipv6-prefix;
              description
                "The IPv6 prefix of the MAP-E CPE.";
            }
          }
        }
      }
    }
    container map-t {
      if-feature map-t;
      description
        "Indicate the devices support the MAP-T function. Devices
        advertise the map-t feature through the capability exchange
        mechanism when a NETCONF session is established.";
      leaf enable {
        type boolean;
        default "1";
        description
          "Enable/disable the MAP-T function.";
      }
      container map-t-devices {
        description
          "Refer to the MAP-T devices, includes BRs and CPEs.";
        list map-t-device {
          key "id";
          leaf id {
            type uint32;
          }
          uses map-rules {
            refine map-rule-type {
              type enumeration {
                enum "DMR";
                enum "BMR";
                enum "FMR";
              }
            }
          }
          container map-t-cpe {
            if-feature map-t-cpe;
            leaf cpe-ipv6-prefix {
              type inet:ipv6-prefix;
              description
                "The IPv6 prefix of the MAP-T CPE.";
            }
          }
        }
      }
    }
  }
