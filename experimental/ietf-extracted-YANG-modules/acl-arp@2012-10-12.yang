module acl-arp {
    namespace "urn:cisco:params:xml:ns:yang:acl-arp";
    // replace with IANA namespace when assigned
    prefix acl-arp;

    import acl { prefix acl; }
    import acl-ip { prefix acl-ip; }
    import acl-mac { prefix acl-mac; }

    organization
       "IETF NETMOD (NETCONF Data Modeling Language) Working Group";

    contact
         "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com
        Editor: Alexander Clemm
        alex@cisco.com

        Editor: Andy Bierman
        andy@yumaworks.com";
    description
        "This YANG module augments the 'acl' module with
        configuration and operational data for ARP access control list

        An ACL is an ordered set of rules and actions used to filter
        traffic.
        Each set of rules and actions is represented as an Access
        Control Entries (ACE). Each ACE is evaluated sequentially.
        When the rule matches then action for that rule is applied
        to the packet.

        ARP ACLs - The device applies ARP ACLs to IP traffic.

        Terms and Acronyms
         ACE (ace): Access Control Entry

         ACL (acl): Access Control List

         ARP (arp): Address Resolution Protocol

         IP (ip): Internet Protocol

         MAC: Media Access Control

         VLAN (vlan): Virtual Local Area Network
       ";
    reference
        "Access List Commands on Cisco IOS XR Software,
        Cisco Nexus 7000 Series NX-OS Security Configuration Guide,
        Catalyst 6500 Release 12.2SX Software Configuration Guide,
        ACL TCP Flags Filtering";

    revision 2012-10-12 {
        description "Initial revision. ";
    }

    /* Identities */

    identity arp-acl {
        base "acl:acl-type";
        description "ARP ACL type";
    }

    /* Data Nodes */

    augment "/acl:acls/acl:acl" {
        when "acl:acl-type = 'arp-acl'";

        description "ARP Access Control Entry (ACE).";
        container arp-aces {
            list arp-ace {
              key "name";
              ordered-by user;

              leaf name {
                  type acl:acl-name-string;
              }

              choice remark-or-arp-ace {
                leaf remark {
                    type acl:acl-remark;
                    // mandatory true;
                }
                case arp-ace {
                  container filters {
                     leaf direction {
                        default "bi-direction";
                        type enumeration {
                           enum bi-direction;
                           enum request;
                           enum response;
                        }
                        description "ARP request/response.";
                     }

                     uses acl-ip:IP-SOURCE-NETWORK;
                     uses acl-ip:IP-DESTINATION-NETWORK {
                       when "../direction = 'response'";
                     }

                     uses acl-mac:MAC-SOURCE-NETWORK;
                     uses acl-mac:MAC-DESTINATION-NETWORK {
                       when "../direction = 'response'";
                     }

                     uses acl:FILTER-COMMON;

                  }  // container filters

                  uses acl:ACE-COMMON;

                } // case arp-ace
              }  // choice remark-or-arp-ace
            }  // list arp-ace
        } // container arp-aces
    } // augment

}
