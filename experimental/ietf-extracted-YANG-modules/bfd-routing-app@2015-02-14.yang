module bfd-routing-app {
   namespace "urn:cisco:params:xml:ns:yang:bfdroutingapp";
   prefix bfd-routing-app;

   import bfd {
     prefix "bfd";
   }

   import ietf-interfaces {
     prefix "if";
   }

   organization
     "ACME";
   contact
     "acme@acme.com";

   description
     "Testing BFD grouping (simulating a routing application)";

   revision 2015-02-14 {
     description
       "Initial revision.";
   }

   feature routing-app-bfd {
     description "BFD configuration under routing-app";
   }

   list area {
     description
       "Specify a routing area.";

     key "area-id";

     leaf area-id {
       type uint32;
     }

     uses bfd:bfd-client-base-cfg-parms {
       if-feature routing-app-bfd;
     }

     list interface {
       key "interface";
       leaf interface {
         type if:interface-ref;
       }
       uses bfd:bfd-client-base-cfg-parms {
         if-feature routing-app-bfd;
       }
     }

   }
}
