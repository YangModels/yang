module ietf-event {
  yang-version 1.1;
  namespace "urn:ietf:params:xml:ns:yang:ietf-event";
  prefix evt;

  import ietf-yang-types {
    prefix yang;
  }

  import ietf-event-trigger {
    prefix trig;
  }

  organization
    "IETF xxx Working Group";
  contact
    "Zitao Wang: wangzitao@huawei.com
     Qin Wu: bill.wu@huawei.com";
  description
    "This module defines a model for the service topology.";

  revision 2018-12-18 {
    description
      "Initial revision.";
    reference "foo";
  }

  identity event-type {
    description
      "Base identity for event type";
  }

  identity frequency {
    description
      "Base identity for frequency";
  }

  identity periodic {
    base frequency;
    description
      "Identity for periodic trigger";
  }

  identity scheduling {
    base frequency;
    description
      "Identity for scheduling trigger";
  }

  typedef match-value {
    type union {
      type yang:xpath1.0;
      type yang:object-identifier;
      type string;
    }
    description
      "This type is used to match resources of type 'target'.
       Since the type 'target' is a union of different types,
       the 'match-value' type is also a union of corresponding
       types.";
  }

  typedef target {
    type union {
      type instance-identifier;
      type yang:object-identifier;
      type yang:uuid;
      type string;
    }
    description
      "If the target is modelled in YANG, this type will
       be an instance-identifier.
       If the target is an SNMP object, the type will be an
       object-identifier.
       If the target is anything else, for example a distinguished
       name or a CIM path, this type will be a string.
       If the target is identified by a UUID use the uuid
       type.
       If the server supports several models, the presedence should
       be in the order as given in the union definition.";
  }

  grouping start-end-grouping {
    description
      "A grouping that provides start and end times for
       Event objects.";
    leaf start {
      type yang:date-and-time;
      description
        "The date and time when the Event object
         starts to create triggers.";
    }
    leaf end {
      type yang:date-and-time;
      description
        "The date and time when the Event object
         stops to create triggers.
         It is generally a good idea to always configure
         an end time and to refresh the end time as needed
         to ensure that agents that lose connectivity to
         their Controller do not continue executing Schedules
         forever.";
    }
  }

  container events {
    leaf min-data-object {
      type uint32;
      description
        "Sets the minimum number for a set of data collected
         or selected during the service monitoring.";
    }
    leaf max-data-object {
      type uint32;
      description
        "Sets the maximum number for a set of data collected or selected
        during the service monitoring.";
    }
    list event {
      key "event-name type";
      leaf event-name {
        type string;
        description
          "Event name";
      }
      leaf type {
        type identityref {
          base event-type;
        }
        description
          "Type of event";
      }
      leaf event-description {
        type string;
        description
          "Event description";
      }
      leaf-list target {
        type target;
        description
          "targeted objects";
      }
      leaf clear {
        type boolean;
        default "false";
        description
          "A flag indicate whether the event be closed";
      }
      list related-event {
        key "event-name type";
        leaf event-name {
          type string;
          description
            "Event name";
        }
        leaf type {
          type identityref {
            base event-type;
          }
          description
            "Type of event";
        }
        description
          "List for related events";
      }

    uses trig:trigger-grouping;

      list action {
        key "action-name";
        leaf action-name {
          type string;
          description
            "Action name";
        }
        notification event-notification {
          leaf event-name {
            type leafref {
              path "/events/event/event-name";
            }
            description
              "Report the event name";
          }
          leaf type {
            type leafref {
              path "/events/event/type";
            }
            description
              "Report the event type";
          }
          leaf-list target {
            type target;
            description
              "Report the target objects";
          }
          description
            "This notification is used to report that an operator
             acted upon an Event.";
        }
        action set {
          input {
            leaf-list target {
              type target;
              description
                "Report the target objects";
            }
            anydata value {
              description
                "Inline set content.";
            }
          }
        }
        leaf-list trigger-event {
          type leafref {
            path "../../event-name";
          }
          description
            "This action trigger another event";
        }
        description
          "List for Actions";
      }
      description
        "List for Events";
    }
    description
      "YANG data module for defining event triggers and
       actions for network management purposes";
  }
}
