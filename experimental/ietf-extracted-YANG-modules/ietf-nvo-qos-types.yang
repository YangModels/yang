module ietf-nvo-qos-types {
    namespace "urn:ietf:params:xml:ns:yang:ietf-nvo-qos-types";
    prefix QosTypes;

    import ietf-yang-types { prefix yang; }

    organization "";
    contact "";
    description "ietf-nvo-qos-types";
    revision 2016-10-24 {
        reference "draft-chen-opsawg-composite-vpn-dm-00";
    }

    /*****************************************************************
    * Type definitions
    *****************************************************************/
    typedef qosPriorityType {
        type enumeration {
            enum nop{
                description "nop";
            }
            enum 802dot1p{
                description "802dot1p";
            }
            enum dscp{
                description "dscp";
            }
            enum mplsExp{
                description "mplsExp";
            }
            enum cos{
                description "cos";
            }
            enum ipPrecedence{
                description "ipPrecedence";
            }
        }
        description "qosPriorityType";
    }

    typedef classifierDetailType {
        type enumeration {
            enum nop{
                description "nop";
            }
            enum ipPrefixList{
                description "ipPrefixList";
            }
        }
        description "classifierDetailType";
    }

    typedef ActionType {
        type enumeration {
            enum nop{
                description "nop";
            }
            enum bandwidth{
                description "bandwidth";
            }
            enum pass{
                description "pass";
            }
            enum discard{
                description "discard";
            }
            enum remark{
                description "remark";
            }
            enum redirect{
                description "redirect";
            }
            enum recolor{
                description "recolor";
            }
            enum addRt{
                description "addRt";
            }
        }
        description "ActionType";
    }

    typedef QosConfigType {
        type enumeration {
            enum nop{
                description "nop";
            }
            enum template{
                description "template";
            }
            enum agile{
                description "agile";
            }
        }
        description "QosConfigType";
    }

    typedef flowClassifierType {
        type enumeration {
            enum nop{
                description "nop";
            }
            enum aluFlowClassifier{
                description "aluFlowClassifier";
            }
        }
        description "flowClassifierType";
    }

    typedef QosDetailType {
        type enumeration {
            enum nop{
                description "nop";
            }
            enum car{
                description "car";
            }
            enum qosProfile{
                description "qosProfile";
            }
            enum diffServDomain{
                description "diffServDomain";
            }
            enum diffServ{
                description "diffServ";
            }
            enum aluDiffServ{
                description "aluDiffServ";
            }
        }
        description "QosDetailType";
    }

    typedef ClassifierType {
        type enumeration {
            enum 802dot1p{
                description "802dot1p";
            }
            enum dscp{
                description "dscp";
            }
            enum cos{
                description "cos";
            }
            enum mpls-exp{
                description "mpls-exp";
            }
            enum sourceIP{
                description "sourceIP";
            }
            enum destinationIP{
                description "destinationIP";
            }
        }
        description "ClassifierType";
    }

    typedef OrchPermitType {
        type enumeration {
            enum readUse{
                description "readUse";
            }
            enum crud{
                description "crud";
            }
        }
        description "OrchPermitType";
    }

    typedef ruleType {
        type enumeration {
            enum 802dot1p{
                description "802dot1p";
            }
            enum dscp{
                description "dscp";
            }
            enum cos{
                description "cos";
            }
            enum mpls_exp{
                description "mpls_exp";
            }
            enum source_ip{
                description "source_ip";
            }
            enum destination_ip{
                description "destination_ip";
            }
        }
        description "ruleType";
    }

    typedef MatchModeType {
        type enumeration {
            enum nop{
                description "nop";
            }
            enum match{
                description "match";
            }
            enum unmatch{
                description "unmatch";
            }
        }
        description "MatchModeType";
    }
    typedef qosBehaviorType {
        type enumeration {
            enum qosCarBehavior{
                description "qosCarBehavior";
            }
            enum qosServiceChainBehavior{
                description "qosServiceChainBehavior";
            }
        }
        description "qosBehaviorType";
    }

    typedef qosBehaviorDirectionType {
        type enumeration {
            enum upstream{
                description "upstream";
            }
            enum downstream{
                description "downstream";
            }
            enum bidirectional{
                description "bidirectional";
            }
        }
        description "qosBehaviorDirectionType";
    }

    typedef dataKind {
        type enumeration {
            enum green{
                description "green";
            }
            enum yellow{
                description "yellow";
            }
            enum red{
                description "red";
            }
            enum all{
                description "all";
            }
        }
        description "dataKind";
    }

    typedef profileType {
        type enumeration {
            enum profile{
                description "profile";
            }
        }
        description "profileType";
    }

    typedef ruleOperatorType {
        type enumeration {
            enum and{
                description "and";
            }
            enum or{
                description "or";
            }
        }
        description "ruleOperatorType";
    }

    /*****************************************************************
    * Groupings
    *****************************************************************/
    grouping TPQosNode {
        description "TPQosNode Grouping.";

        leaf qosConfigType {
            type QosConfigType;
            description "qosConfigType";
        }
        leaf qosDetailType {
            type QosDetailType;
            description "qosDetailType";
        }
        list inTpCar {
            key index;
            uses FlowBehavior;
            description "inTpCar";
        }
        list outTpCar {
            key index;
            uses FlowBehavior;
            description "outTpCar";
         }
        leaf inQosProfileId {
            type yang:uuid;
            description "inQosProfileId";
        }
        leaf outQosProfileId {
            type yang:uuid;
            description "outQosProfileId";
        }
    }

    grouping FlowAndBehavior {
        description "FlowAndBehavior Grouping.";

        leaf flowClassifierId {
            type yang:uuid;
            description "flowClassifierId";
        }
        list flowBehaviors {
            key index;
            uses FlowBehavior;
            description "flowBehaviors";
        }
    }

    grouping FlowBehavior {
        description "FlowAndBehavior Grouping.";

        leaf index {
            type uint32;
            description "index";
        }
        leaf dataKind {
            type dataKind;
            description "dataKind";
        }
        leaf actionType {
            type ActionType;
            description "actionType";
        }
        leaf action {
            type string;
            description "action";
        }
    }

    grouping FlowClassifierRule {
        description "FlowClassifierRule Grouping.";

        leaf index {
            type uint32;
            description "index";
        }
        leaf matchMode {
            type MatchModeType;
            description "matchMode";
        }
        leaf type {
            type ClassifierType;
            description "type";
        }
        leaf-list flowClassifierValue {
            type string;
            description "flowClassifierValue";
        }
        leaf appendix {
            type string;
            description "appendix";
        }
    }

    grouping BandWidthNode {
        description "BandWidthNode Grouping.";

        leaf cir {
            type uint32;
            description "cir";
        }
        leaf pir {
            type uint32;
            description "pir";
        }
        leaf cbs {
            type uint32;
            description "cbs";
        }
        leaf pbs {
            type uint32;
            description "pbs";
        }
    }

    grouping FlowServices {
        description "FlowServices Grouping.";

        leaf qosConfigType {
            type QosConfigType;
            description "qosConfigType";
        }
        leaf flowQosTemplateID {
            type yang:uuid;
            description "flowQosTemplateID";
        }
        leaf qosDetailType {
            type QosTypes:QosDetailType;
            description "qosDetailType";
        }
        leaf inFlowQosTemplateID {
            type yang:uuid;
            description "inFlowQosTemplateID";
        }
        leaf outFlowQosTemplateID {
            type yang:uuid;
            description "outFlowQosTemplateID";
        }

        list flowServices {
            key flowClassifierId;
            description "default in flow and behaviors";
            uses FlowAndBehavior;
        }
    }
}
