module ietf-gre-tunnel {

  namespace "urn:ietf:params:xml:ns:yang:ietf-gre-tunnel";

  prefix "gretln";

  import ietf-interfaces {

    prefix "if";

  }

  import ietf-inet-types {

    prefix inet;

  }

  import ietf-routing {

    prefix "rt";

  }

  organization
    "Ericsson.";

  contact

    "Mandy.Liu@ericsson.com

   Adam.Foldes@ericsson.com";

  description

    "This YANG model defines the configuration data

   and operational state data for GRE tunnel.";

  revision 2015-10-13 {

    description

      "Initial revision.";

    reference

      "RFC XXXX: A YANG Data Model for GRE Tunnel.";

  }

  grouping tunnel-gre-components {

    description

      "This grouping provides common attributes for

       GRE tunnels and tunnel circuits.";

    leaf description {

      type string;
      description

        "Textual description for a tunnel. Can be any

      alphanumeric string, including spaces, not to

      exceed 255 ASCII characters.";

    }

    leaf bind-interface {

      type if:interface-ref;

      description

         "Bind to an interface.";

    }

    leaf clear-df {

      type empty;

      description

        "If clear-df is absent, it means that fragmentation

      of tunnel packets are permitted. If clear-df is

      present, it means that fragmentation of tunnel packets

      are not permitted.";

    }

    container keepalive {

      description

        "Enables sending keepalive packets on GRE tunnels,

         and specifies the interval and number of retries.";

      leaf interval {

        type uint32 {
          range "5..40";

        }

        units "seconds";

        default "10";

        description

          "Number of seconds between sending keepalive packets.";

      }

      leaf retry-num {

        type uint32 {

          range "2..255";

        }

        default "4";

        description

          "Number of times a keepalive packet is sent without

           response before the tunnel is brought down.";

      }

    }

    leaf mirror-destination {

      type string;

      description

        "Designate the name of a tunnel as a circuit

      mirror destination. ";

    }

    leaf mtu {
      type uint16 {

        range "256..16384";

      }

      description

        "Sets the Maximum Transmission Unit (MTU) size for

        packets sent in a tunnel. The default MTU is the MTU

        for the interface to which the tunnel is bound.";

    }

    leaf shutdown {

      type empty;

      description

        "Disable/enable the tunnel.";

    }

    leaf hop-limit {

     type uint8 {

       range "0|1..255";

     }

     description

       "The IPv4 TTL or IPv6 Hop Limit which is used in the outer IP

      header. A value of 0 indicates that the value is copied from

      the payload's header.";

   }

   leaf tos {

     type int8 {
       range "-1..63";

     }

     description

       "The method used to set the high 6 bits (the differentiated

      services codepoint) of the IPv4 TOS or IPv6 Traffic Class in

      the outer IP header. A value of -1 indicates that the bits are

      copied from the payload's header. A value between 0 and 63

      inclusive indicates that the bit field is set to the indicated

      value.";

   }

  }

  /*Configuration Data*/

  container gre-tunnels {

    description

     "Configuration data for tunnels.";

    list gre {

      key "name";

      description

        "Configuration of GRE tunnel.";

      leaf name {

        type string;

        description
          "Name of the tunnel.";

      }

      uses tunnel-gre-components;

      container peer-end-point {

        description

          "Assigns IP addresses to tunnel endpoints.";

        leaf local {

          type inet:ipv4-address-no-zone;

          description

            "IP address of the local end of the tunnel.";

        }

        leaf remote {

          type inet:ipv4-address-no-zone;

          description

            "IP address of the remote end of the tunnel.";

        }

        leaf routing-instance {

          type rt:routing-instance-ref;

          description

            "Name of the reference routing instance.";

        }

      }

      list tunnel-circuits {

        key "key-id";
        description

          "Configuration of GRE tunnel circuit.";

        leaf key-id {

          type uint32;

          description

            "Specifies a key ID in the current GRE tunnel.";

        }

        uses tunnel-gre-components;

      }

    }

  }

  /*Operational state data*/

  grouping tunnel-gre-states {

    description

     "The basic tunnel information to be displayed.";

    leaf name {

      type string;

      description

        "Name of the tunnel.";

    }

    leaf local-ip {

      type inet:ipv4-address-no-zone;

      description
        "IP address of the local end of the tunnel.";

    }

    leaf remote-ip {

      type inet:ipv4-address-no-zone;

      description

        "IP address of the remote end of the tunnel.";

    }

    leaf state {

      type enumeration {

        enum Down {

        description

          "Tunnel down state.";

        }

        enum Up {

          description

            "Tunnel up state.";

        }

        enum Shutdown {

          description

            "Tunnel shutdown state.";

        }

        enum Keep-down {

          description

            "Tunnel keepalive down state.";
        }

        enum Wait-on-SA {

          description

            "Tunnel pending SA UP state.";

        }

        enum Not-used {

          description

            "Tunnel is not in used.";

        }

      }

      description

        "Indicates the state of the tunnel.";

    }

    leaf bind-interface {

      type if:interface-state-ref;

      description

        "The name of the interface to which the tunnel is bound.";

    }

    leaf routing-instance {

      type rt:routing-instance-ref;

      description

        "Indicates the name of the reference routing instance.";

    }

    leaf mtu {
      type uint16;

      description

        "The Maximum Transmission Unit (MTU) size for

      packets sent in a tunnel.";

    }

    leaf clear-df {

      type empty;

      description

        "Indicate that the DF bit is cleared.";

    }

    leaf tunnel-id {

      type uint32;

      description

        "Tunnel id.";

    }

    leaf down-reason {

      type string;

      description

        "Indicate the down reason of the tunnel.";

    }

    leaf resolved-interface-name{

      type string;

      description

        "The egress interface name of the tunnel.";
    }

   leaf hop-limit {

     type uint8;

     description

       "The IPv4 TTL or IPv6 Hop Limit which is used in the outer IP

      header. A value of 0 indicates that the calue is copied from

      the payload's header.";

   }

   leaf tos {

     type int8;

     description

       "The high 6 bits (the differentiated

      services codepoint) of the IPv4 TOS or IPv6 Traffic Class in

      the outer IP header. A value of -1 indicates that the bits are

      copied from the payload's header. A value between 0 and 63

      inclusive indicates that the bit field is set to the indicated

      value.";

   }

  }

  container tunnel-state {

    config "false";

    description

      "Contain the information currently configured tunnels.";
    list gre {

      description

        "Operational state data of GRE tunnel.";

      uses tunnel-gre-states;

      container keepalive {

        description

          "The interval and number of retries for

           sending keepalive packets on GRE tunnels.";

        leaf interval {

          type uint32;

          units "seconds";

          description

            "Number of seconds between sending keepalive packets.";

        }

        leaf retry-num {

          type uint32;

          description

            "Number of times a keepalive packet is sent without

             response before the tunnel is brought down.";

        }

      }

      list tunnel-circuits {

        description
          "Operational state data of GRE tunnel circuit.";

        leaf key-id {

          type uint32;

          description

            "Key ID of the GRE tunnel circuit.";

        }

        uses tunnel-gre-states;

        container keepalive {

          description

            "The interval and number of retries for

             sending keepalive packets on GRE tunnels.";

          leaf interval {

            type uint32;

            units "seconds";

            description

              "Number of seconds between sending keepalive
packets.";

          }

          leaf retry-num {

            type uint32;

            description

              "Number of times a keepalive packet is sent without

               response before the tunnel is brought down.";

          }
        }

      }

    }

  }

  //Augment operational state data of IP interfaces

  augment "/if:interfaces-state/if:interface" {

    when "if:type = 'ianaift:tunnel'" {

      description

        "Augment IP interface.";

    }

    description

      "Augment operational state data of IP interfaces.";

    leaf gre-tunnel-enabled {

      type boolean;

     description

        "Indicate the type of the IP tunnel interface.

        TRUE means GRE tunnel interface.";

    }

  }

}// end of module ietf-gre-tunnel
