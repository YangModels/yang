submodule openconfig-mpls-static {

  yang-version "1";

  belongs-to "openconfig-mpls" {
    prefix "mpls";
  }

  // import some basic types
  import openconfig-mpls-types {prefix mplst; }
  import ietf-inet-types { prefix inet; }

  // meta
  organization "OpenConfig working group";

  contact
    "OpenConfig working group
    netopenconfig@googlegroups.com";

  description
    "Defines static LSP configuration";

  revision "2015-07-04" {
    description
      "Initial revision";
    reference "TBD";
  }

  // extension statements

  // feature statements

  // identity statements

  // typedef statements

  // grouping statements

  grouping static-lsp-common {
    description "common definitions for static LSPs";

    leaf next-hop {
      type inet:ip-address;
      description "next hop IP address for the LSP";
    }

    leaf incoming-label {
      type mplst:mpls-label;
      description "label value on the incoming packet";
    }

    leaf push-label {
      type mplst:mpls-label;
      description "label value to push at the current hop for the
      LSP";
    }
  }

  grouping static-lsp-main {
    description "grouping for top level list of static LSPs";

    list label-switched-path {
      key name;
      description "list of defined static LSPs";

      leaf name {
        type string;
        description "name to identify the LSP";
      }

      // TODO: separation into ingress, transit, egress may help
      // to figure out what exactly is configured, but need to
      // consider whether implementations can support the
      // separation
      container ingress {
        description "Static LSPs for which the router is an
          ingress node";
        uses static-lsp-common;
      }

      container transit {
        description "static LSPs for which the router is a
          transit node";

        uses static-lsp-common;
      }

      container egress {
        description "static LSPs for which the router is a
          egress  node";

        uses static-lsp-common;
      }
    }
  }

  // data definition statements

  // augment statements

  // rpc statements

  // notification statements

}
