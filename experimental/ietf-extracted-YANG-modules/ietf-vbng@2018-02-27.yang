module ietf-vbng{
namespace "urn:ietf:params:xml:ns:yang:ietf-vbng";
prefix "vbng";

import ietf-inet-types {
   prefix "inet";
 }

import ietf-interfaces {
  prefix if;
 }

import ietf-logical-network-element {
      prefix lne;
    }

organization
  "IETF NETCONF Working Group";

  contact
   "
     WG List:  <mailto:netconf@ietf.org>

     Editor:   Fangwei Hu
               <mailto:hu.fangwei@zte.com.cn>
    ";

description
   "The YANG module defines a generic configuration
     model for vbng";

    revision 2018-02-27{
  description "Correct some type of nodes.";
  reference
     "draft-hu-rtgwg-cu-separation-yang-model-02";
}

    revision 2018-01-18{
  description "add multicast service configuration and pppox configuration,
      and update the OpenFlow channel parameters.";
  reference
     "draft-hu-rtgwg-cu-separation-yang-model-01";
}

revision 2017-07-16{
  description "Initial revision";
  reference
     "draft-hu-rtgwg-cu-separation-yang-model-00";
}

/* Typedefs  */

      typedef vlan-id {
   type uint16 {
        range "0..4094";
       }
   description
     "Typedef for VLAN ID.";
 }

     typedef vxlan-id {
   type uint32;
   description
     "Typedef for VxLAN ID.";
 }

      typedef address-family-type {
    type enumeration {
      enum ipv4 {
        description
          "IPv4";
      }
      enum ipv6 {
        description
          "IPv6";
      }
    }
    description
      "Typedef for address family type.";
  }

 /* Configuration Data */

 augment /lne:logical-network-elements/lne:logical-network-element {
 container ietf-vbng{
      container bng-cp {
    leaf bng-cp-name  {
             type string;
             description "configure bng-cp name";
       }

       leaf enable  {
             type boolean;
             description "'true' to support bng control plane and user plane separation";
        }
       description "configure bng-cp";
      }

 container bng-up {
   presence bng-up;
   list bng-up {
     key shelf-no ;
     leaf shelf-no {
       type uint8 {
         range 1..127 ;
       }
       description 'Configure shelf-no of forwarder,1-127.';
     }

     leaf bng-up-name {
       type string {
         length 1..31 ;
       }
       description 'Configure bng up name.' ;
     }

     container netconf-server {
       presence netconf-server ;
       leaf ip {
         type inet:ipv4-address;
                     mandatory true ;
         description 'Configure ip address of netconf server.';

       }

       leaf user-name {
         type string {
           length 1..65 ;
         }
         description 'configure user name, default: "who".';
       }

       leaf password {
         type string {
           length 3..32 ;
         }
         description 'configure password, default: "who".';
       }

       leaf port {
                 type uint32;
         description 'Configure port.';
       }
      description 'Configure netconf server.';
     }

     leaf keepalive-sink {
       type enumeration {
         enum enable {
           value 1 ;
           description 'enable the keepalive-sink function';
         }
         enum disable {
           value 0 ;
           description 'disable keepalive-sink function';
         }
       }
               description "configure keepalive-sink";
              }
              description "configure bng up list";
     }
         description "configure bng up container";
        }

     container interfaces {
               list interface {
                 key name;
                     leaf name {
                        type if:interface-ref;
                        description "interface name";
                       }
                     container ethernet {
           leaf lacp {
            type boolean;
            description "enable lacp function";
            }
                        description "configure ethernet interface";
                       }
         leaf mac-offset {
            type uint32;
            description "configure mac offset";
           }

                     container vlans {
             list tag {
                                 key index;
                                     max-elements 2;
                 leaf index {
                    type uint8 {
                                          range "0..1";
                                              }
                                      must ". = 0 or
                    count(../../tag[index = 0]/index) > 0" {
                    error-message "An inner tag can only be specified if an
                             outer tag has also been specified";
                   description "Ensure that an inner tag cannot be
                           specified without an outer tag'";
                   }

                  description "The index into the tag stack, outermost tag
                         assigned index 0";
                 }

                                     container tag{
                                       leaf tag-type {
                                          type string;
                                              description "tag type";
                                              }
                                       leaf vlan-id {
                                         type vlan-id;
                                         description "vlan id value";
                                        }

                     description "tag";
                }
               description "tag list";
             }
           description "vlans";
                     }
                description "interfaces list";
       }
      description "interface container";
     }

             container openflow-channel {
       list address-family {
          key "af";
          leaf af {
            type address-family-type;
             description "Address family type value.";
          }
          leaf control-ip {
              type inet:ip-address;
              description
              "Set the IP address of for openflow session";
            }
                  description "Per-af params.";
               }

               leaf ofls-name {
                 type string;
                     description "openflow logical name";
               }

               leaf dpid {
                 type uint32;
                     description "dpid value";
               }

               leaf of-port {
         type uint32;
         description "openflow channel udp port number";
        }

       container openflow-disconnect {
         choice response-delay {
           default range ;
           case nolimitflag {
             leaf forever {
              type enumeration {
                enum forever {
                 value 1 ;
                                     description "Delay forever";
                }
             }
                             description 'Delay forever';
            }
                        description 'The flag of no time limite';
           }
           case range {
             leaf delay-time {
                type uint32 {
                  range 0..2880 ;
                }
                             description 'Delay time ,default 240 minutes';
             }
                        description 'Set delay time range';
           }
                  description 'Set delay time';
         }
            description 'Set delay time after openflow disconnect';
       }
               description "configure openflow channel value";
     }

     list vxlan-channel{
         key vxlan-tunnel-id;
         leaf vxlan-tunnel-id {
            type uint32;
            description
                  "Static VxLAN tunnel ID.";
         }

         leaf vxlan-tunnel-name {
            type string;
            description
            "Name of the static VxLAN tunnel.";
         }

         list address-family {
            key "af";
            leaf af {
              type address-family-type;
              description
              "Address family type value.";
            }

            leaf tunnel-source-ip {
              type inet:ip-address;
              description
              "Source IP address for the static VxLAN tunnel";
            }

            leaf tunnel-destination-ip {
               type inet:ip-address;
               description
                "Destination IP address for the static VxLAN tunnel";
            }

            list bind-vxlan-id {
               key vxlan-id;
               leaf vxlan-id {
                 type vxlan-id;
                 description
                    "VxLAN ID.";
               }
               description
                  "VxLAN ID list for the VTEP.";
            }

             description
                "Per-af params.";
          }
         description
           "Configure VxLAN channel";
     }

  container multicast-service{
       container multicast-global {
     leaf keepalive-timer {
       type enumeration {
         enum start {
           value 1 ;
           description 'open switch';
         }
         enum stop {
           value 2 ;
           description 'close switch';
         }
         enum always {
           value 3 ;
                       description 'always keepalive';
         }
       }
       default start ;
       description 'the switch of sending keepalive packet';
     }
     leaf query-interval {
       type uint16 {
         range 1..65535 ;
       }
       default 125 ;
       description 'multicast query interval';
     }
     description 'multicast global configuration';
   }

   container igmp-service-profile {
     list igmp-service-profile {
       key service-profile-num ;
       leaf service-profile-num {
         type uint8 {
           range 1..100 ;
         }
         description 'service profile number';
       }
       leaf access-group {
         type string {
           length 1..31 ;
         }
         description 'acl name';
       }

       leaf description {
         type string {
           length 1..31 ;
         }
         description 'description of service profile';
       }

       leaf max-groups {
         type uint8 {
           range 1..128 ;
         }
         default 10 ;
         description 'max groups of the service profile';
       }

       leaf max-prw-groups {
         type uint8 {
           range 1..128 ;
         }
         default 10 ;
         description 'max preview groups of the service profile';
       }

       list prw-group {
         key 'ipv4-address ipv4-address-mask';
         leaf ipv4-address {
           type inet:ipv4-address ;
           description 'ipv4 address of the preview group';
         }

         leaf ipv4-address-mask {
           type inet:ipv4-address;
           description 'ipv4 mask of the preview group';
         }

         leaf max-prw-count {
           type uint32 {
             range 1..1800 ;
           }
           default 10 ;
           description 'max preview times';
         }

         leaf prw-resume-interval {
           type uint32 {
             range 1..86400 ;
           }
           default 60 ;
           description 'preview interval';
         }
         description 'configure preview group';
       }

       list static-group {
         key ipv4-address ;
         leaf ipv4-address {
           type inet:ipv4-address ;
           description 'ipv4 address of the static group';
         }
         description 'configure static group';
       }
       description 'configuration of igmp service profile';
     }
     description 'configuration of igmp service profile';
   }

  container mld-service-profile {
     list mld-service-profile {
       key service-profile-num ;
       leaf service-profile-num {
         type uint8 {
           range 1..100 ;
         }
         description 'service profile number';
       }
       leaf access-group {
         type string {
           length 1..31 ;
         }
         description 'acl name';
       }
       leaf description {

         type string {
           length 1..31 ;
         }
         description 'description of service profile';
       }
       leaf max-groups {
         type uint8 {
           range 1..128 ;
         }
         default 10 ;
         description 'max groups of the service profile';
       }
       leaf max-prw-groups {
         type uint8 {
           range 1..128 ;
         }
         default 10 ;
         description 'max preview groups of the service profile';
       }
       list prw-group {
         key 'ipv6-address ipv6-prefixlen'
             ;
         leaf ipv6-address {
           type inet:ipv6-address ;
           description 'ipv6 address of the preview group';
         }
         leaf ipv6-prefixlen {

           type uint8 {
             range 1..128 ;
           }
           description 'ipv6 prefix length';
         }
         leaf max-prw-count {
           type uint32 {
             range 1..1800 ;
           }
           default 10 ;
           description 'max preview times';
         }
         leaf prw-resume-interval {
           type uint32 {
             range 1..86400 ;
           }
           default 60 ;
           description 'preview interval';
         }
         description 'configure preview group';
       }
       list static-group {
         key ipv6-address ;
         leaf ipv6-address {
           type inet:ipv6-address;
           description 'ipv6 address of the static group';
         }
         description 'configure static group';
       }
       description 'configuration of mld service profile';
     }
     description 'configuration of mld service profile';
    }
        description 'multicast service configuration';
   }

 container bras-pppox {
   container pppox-ipv6cp-cfg {
     leaf ipv6cp-extension {
       type enumeration {
         enum enable {
           value 1 ;
                       description "enable the IPv6cp extension!";
         }
         enum disable {
           value 0 ;
                       description "disable the IPv6cp extension!";
         }
       }
       default disable ;
       description 'Ipv6cp extension flag';
     }

     leaf ipv6cp-aftr {

       type uint8 {
         range 1..255 ;
       }
       description 'AFTR option type value';
     }
     leaf ipv6cp-ipv6-address {

       type uint8 {
         range 1..255 ;
       }
       description 'Ipv6 address option type value';
     }
     leaf ipv6cp-ipv6-prefix {
       type uint8 {
         range 1..255 ;
       }
       description 'Ipv6 prefix option type value';
     }
     container ipv6-dns {
       presence ipv6-dns ;
       leaf ipv6cp-ipv6-dns-secondary {
         type uint8 {
           range 1..255 ;
         }
         mandatory true ;
         description 'IPV6 primary DNS option type value';
       }
       leaf ipv6cp-ipv6-dns-primary {
         type uint8 {
           range 1..255 ;
         }
         mandatory true ;
         description 'IPV6 secondary DNS option type value';
       }
       description 'Ipv6 DNS option type value';
     }
     container ipv4-dns {
       presence ipv4-dns ;
       leaf ipv6cp-ipv4-dns-primary {

         type uint8 {
           range 1..255 ;
         }
         mandatory true ;
         description 'IPV4 primary DNS option type value';
       }
       leaf ipv6cp-ipv4-dns-secondary {

         type uint8 {
           range 1..255 ;
         }
         mandatory true ;
         description 'IPV4 secondary DNS option type value';
       }
       description 'Ipv4 DNS option type value';
     }
     description 'Configuration about IPV6CP extension.';
   }

   container pppox-ipcp-cfg {
     leaf ipcp-flag {
       type enumeration {
         enum enable {
           value 1 ;
                       description "enable ipcp extension flag";
         }
         enum disable {
           value 0 ;
                       description "disable ipcp extension flag";
         }
       }
       default disable ;
       description 'Ipcp extension flag';
     }

     leaf option-type {
       type uint8 {
         range 1..255 ;
       }
       description 'Ipcp 6rd option type';
     }

     leaf br-address {
       type inet:ipv4-address {
         pattern '^((1[0-9]{0,2}|2[0-9]{0,1}|2[0-4][0-9]|25[0-4]|[3-9][0-9]{'
               + '0,1})\.){3}(0|1[0-9]{0,2}|2[0-9]{0,1}|2[0-4][0-9]|25[0-4]|'
               + '[3-9][0-9]{0,1})$|^0\.((1[0-9]{0,2}|2[0-9]{0,1}|2[0-4][0-9'
               + ']|25[0-5]|[3-9][0-9]{0,1})\.){2}(1[0-9]{0,2}|2[0-9]{0,1}|2'
               + '[0-4][0-9]|25[0-5]|[3-9][0-9]{0,1})$|^((1[0-9]{0,2}|2[0-9]'
               + '{0,1}|2[0-4][0-9]|25[0-5]|[3-9][0-9]{0,1})\.)0\.((1[0-9]{0'
               + ',2}|2[0-9]{0,1}|2[0-4][0-9]|25[0-5]|[3-9][0-9]{0,1})\.)(1['
               + '0-9]{0,2}|2[0-9]{0,1}|2[0-4][0-9]|25[0-5]|[3-9][0-9]{0,1})'
               + '$|^((1[0-9]{0,2}|2[0-9]{0,1}|2[0-4][0-9]|25[0-5]|[3-9][0-9'
               + ']{0,1})\.){2}0\.(1[0-9]{0,2}|2[0-9]{0,1}|2[0-4][0-9]|25[0-'
               + '5]|[3-9][0-9]{0,1})$|^((1[0-9]{0,2}|2[0-9]{0,1}|2[0-4][0-9'
               + ']|25[0-5]|[3-9][0-9]{0,1})\.){3}0$|255\.((0|1[0-9]{0,2}|2['
               + '0-9]{0,1}|2[0-4][0-9]|25[0-4]|[3-9][0-9]{0,1})\.){2}(0|1[0'
               + '-9]{0,2}|2[0-9]{0,1}|2[0-4][0-9]|25[0-4]|[3-9][0-9]{0,1})$'
               + '|^((0|1[0-9]{0,2}|2[0-9]{0,1}|2[0-4][0-9]|25[0-4]|[3-9][0-'
               + '9]{0,1})\.)255\.((0|1[0-9]{0,2}|2[0-9]{0,1}|2[0-4][0-9]|25'
               + '[0-4]|[3-9][0-9]{0,1})\.)(0|1[0-9]{0,2}|2[0-9]{0,1}|2[0-4]'
               + '[0-9]|25[0-4]|[3-9][0-9]{0,1})$|^((0|1[0-9]{0,2}|2[0-9]{0,'
               + '1}|2[0-4][0-9]|25[0-4]|[3-9][0-9]{0,1})\.){2}255\.(0|1[0-9'
               + ']{0,2}|2[0-9]{0,1}|2[0-4][0-9]|25[0-4]|[3-9][0-9]{0,1})$|^'
               + '((0|1[0-9]{0,2}|2[0-9]{0,1}|2[0-4][0-9]|25[0-4]|[3-9][0-9]'
               + '{0,1})\.){3}255$'
                 ;
       }
       description '6RD BR IPv4 address';
     }
     container ipv6-rapid-deployment {
       presence ipv6-rapid-deployment ;
       leaf v4-mask-len {
         type uint8 {
           range 0..32 ;
         }
         mandatory true ;
         description 'IPv4 address mask length';
       }
       leaf v6-pref {
         type inet:ipv6-address ;
         mandatory true ;
         description 'IPv6 prefix';
       }
       leaf v6-mask-len {
         type uint8 {
           range 1..128 ;
         }
         mandatory true ;
                     description 'IPv6 prefix length';
       }
       description 'Ipv6 rapid deployment';
     }
     description 'Configuration about IPCP extension.';
   }
   container pppoe-switch {
     leaf delay-time {
       type uint16 {
         range 1..300 ;
       }
       description 'Trigger user offline when VCC phys-interface down';
     }
     leaf keepalive-timer {
       type enumeration {
         enum start {
           value 1 ;
                       description "start keepalive timer";
         }
         enum stop {
           value 0 ;
                       description "stop keepalive timer";
         }
       }
       default start ;
       description 'Start or stop send keepalive packet';
     }
     leaf ppp-max-payload {
       type enumeration {
         enum disable {
           value 0 ;
                       description "disable ppp max payload";
         }
         enum enable {
           value 1 ;
                       description "enable ppp max payload";
         }
       }
       default disable ;
       description 'Enable or disable pppoe ppp-max-payload';
     }
     leaf service {
       type enumeration {
         enum advertise{
           value 1 ;
                       description "enable ppp service!";
         }
         enum disable {
           value 0 ;
                       description "disable ppp service!";
         }
       }
       default advertise ;
               description 'Open or close pppoe service';
     }
     leaf ppp-mru-verify {
       type enumeration {
         enum open {
           value 1 ;
                       description "enable ppp mru verify!";
         }
         enum close {
           value 0 ;
                       description "disable ppp mru!";
         }
       }
       default close ;
               description 'set ppp lcp mru verify when mru over 1492';
     }

     leaf keepalive-fast-reply {
       type enumeration {
         enum enable {
           value 1 ;
           description 'Enable keepalive fast reply!';
         }
         enum disable {
           value 0 ;
           description 'Disable keepalive fast reply!';
         }
       }
       description 'Set keepalive fast reply flag.';
     }
     description 'Configuration about pppoe switch.';
   }
   list pppoe-cfg {
     key template ;
     leaf template {
       type uint32 {
         range 1..1000 ;
       }
       description 'PPPoX template number';
     }
     leaf ppp-authentication {
       type enumeration {
         enum pap {
           value 1 ;
                       description "configure pap authentication!";
         }
         enum chap {
           value 2 ;
                       description "configure chap authentication!";
         }
         enum mschapv1 {
           value 6 ;
                       description "configure mschapv1 authentication!";
         }
         enum mschapv2 {
           value 7 ;
                       description "configure mschapv2 authentication!";
         }
         enum pap-chap {
           value 21 ;
                       description "configure pap-chap authentication!";
         }
       }
       default pap-chap ;
               description 'Set ppp authentication';
     }
     leaf ppp-check-magic-num {
       type enumeration {
         enum disable {
           value 0 ;
                       description 'disable ppp magic check';
         }
         enum enable {
           value 1 ;
                       description 'enable ppp magic check';
         }
       }
       default enable ;
               description 'Check magic number or not';
     }
     leaf ppp-mru {

       type uint32 {
         range 320..9000 ;
       }
       default 1492 ;
               description 'Set mru value';
     }
     leaf pppoe-ac-name {
       type string ;
               description 'Set ac-name';
     }
     leaf pppoe-service-name-omit {
       type enumeration {
         enum disable {
           value 0 ;
                       description "disable pppoe service name omit";
         }
         enum enable {
           value 1 ;
                       description "enable pppoe service name omit";
         }
       }
       default disable ;
               description 'Check service-name value';
     }
     leaf pppoe-ac-cookie-check {
       type enumeration {
         enum disable {
           value 0 ;
                       description "disable pppoe ac cookie check";
         }
         enum enable {
           value 1 ;
                       description "enable pppoe ac cookie check";
         }
       }
       default enable ;
               description 'Check options';
     }
     leaf pppoe-password-string {
       type string ;
               description 'Set authen fail password error string';
     }
     leaf pppoe-username-string {
       type string ;
               description 'Set authen fail username error string';
     }

     choice ppp-quick-redial {
       case quick-redial-disable {
         leaf ppp-quick-redial-disable {
           type enumeration {
             enum disable {
               value 0 ;
                               description "disable ppp quick redial";
             }
           }
           default disable ;
                       description 'disable quick-redial';
         }
                     description 'disable quick-redial';
       }
       case fast-response {
         leaf ppp-fast-response {
           type enumeration {
             enum diable {
               value 0 ;
                                description "disable ppp fast response";
             }
             enum enable {
               value 1 ;
                               description "enable ppp fast response";
             }
           }
           description 'set Response the access request immediately';
         }
         leaf ppp-quick-redial-enable {
           type enumeration {
             enum enable {
               value 1 ;
                               description "enable ppp quick redial";
             }
           }
           default enable ;
                       description 'Enable quick-redial';
         }
                     description 'set quick-redial or Response the access request immediately';
       }
               default quick-redial-disable ;
       description 'Enable or disable quick-redial';
     }
     container ppp-keepalive {
       leaf ppp-keepalive-timer {
         type uint32 {
           range 10..14400 ;
         }
         default 60 ;
         description 'Set keepalive time(unit:seconds)';
       }
       leaf ppp-keepalive-count {
         type uint16 {
           range 1..10 ;
         }
         default 3 ;
                     description 'Set keepalive counter';
       }
              description 'Set keepalive time and counter';
     }
     container ppp-timeout {
       leaf ppp-timeout-negtimeoutsec {
         type uint8 {
           range 1..10 ;
         }
         default 3 ;
                 description 'Set ppp negtimeoutsec timeout(unit:seconds)';
       }
       leaf ppp-timeout-authentication {
         type uint8 {
           range 1..10 ;
         }
         default 3 ;
                     description 'Set ppp authentication timeout(unit:seconds)';
       }
              description 'Set ppp negtimeoutsec and authentication timeout';
     }
             description 'Configuration pppoe template';
   }
       description 'Configuration vBRAS PPPoX.';
 }
     description "ietf-bng configuration!";
}
description "augment lne model";
}
}
