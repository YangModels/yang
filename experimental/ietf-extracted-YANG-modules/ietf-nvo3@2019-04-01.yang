module ietf-nvo3 {
  yang-version 1.1;  
  namespace "urn:ietf:params:xml:ns:yang:ietf-nvo3";
  prefix "nvo3";

  import ietf-network-instance {
    prefix "ni";
  }

  import ietf-interfaces {
    prefix "if";
  }

  import ietf-inet-types {
    prefix "inet";
  }

  import ietf-l2vpn {
    prefix "l2vpn";
  }  

  import ietf-bgp-l3vpn {
    prefix "l3vpn";
  }

  organization  "ietf";
  contact       "ietf";
  description   "Yang model for NVO3";

  revision 2019-04-01 {
    description
      "Init revision";
    reference
      "";
  }

  typedef vni-status-type {
    type enumeration {
      enum "up" {
        description
          "Vni status up.";
      }
      enum "down" {
        description
          "Vni status down.";
      }
    }
    description
      "Vni status";
  }

  typedef vni-type {
    type enumeration {
      enum "l2" {
        description
          "layer 2 mode";
      }
      enum "l3" {
        description
          "layer 3 mode";
      }
    }
    description
      "vni type";
  }

  typedef peer-type {
    type enumeration {
      enum "static" {
        description
          "Static.";
      }
      enum "dynamic" {
        description
          "Dynamic.";
      }
    }
    description
      "Peer type";
  }

  typedef tunnel-status {
    type enumeration {
      enum "up" {
        description
          "The tunnel is up.";
      }      
      enum "down" {
        description
          "The tunnel is down.";
      }
    }
    description
      "Tunnel status";
  }
  typedef tunnel-type {
    type enumeration {
      enum "dynamic" {
        description
          "The tunnel is dynamic.";
      }
      enum "static" {
        description
          "The tunnel is static.";
      }
      enum "invalid" {
        description
          "The tunnel is invalid.";
      }
    }
    description
      "Tunnel type";
  }

  typedef direction-type {
    type enumeration {
      enum "inbound" {
        description
          "Inbound.";
      }
      enum "outbound" {
        description
          "Outbound.";
      }
      enum "bidirection" {
        description
          "Bidirection.";
      }      
    }
    description
      "Bound direction";
  }

  typedef vni-bind-type {
    type enumeration {
      enum "hub-mode" {
        description
          "Hub mode.";
      }
      enum "spoke-mode" {
        description
          "Spoke mode.";
      }
    }
    description
      "bdBindVniType";
  }  

  container nvo3 {
    description
      "Management of NVO3.";

    container vni-instances {
      description
        "The confiuration and information table of the VNI.";
      list vni-instance {
        key "vni-id";
        must "(/if:interfaces/if:interface[if:name = current()/source_nve]/if:type = 'Nve')";
        description
          "The confiuration and information of the VNI.";
        leaf vni-id {
          type uint32 {
            range "1..16777215";
          }
          description
            "The id of VNI.";
        }
        leaf vni-mode {
	 type enumeration {
	   enum "Local" {
	     description
	       "Local mode";
            }
	   enum "Global" {
	     description
	       "Global mode";
            }
           }
           description
             "The mode of the VNI instance.";
        }
        leaf source-nve {
          type if:interface-ref;          
          mandatory true;
          description
            "The name of the nve interface .";
        }
        leaf protocol-bgp {
          type boolean;
          default "false";
          description
            "Whether use bgp as vxlan's protocol.";            
        }         
        leaf status {
          type vni-status-type;
          config false;
          description
            "The status of the VNI.";
        }
        container static-ipv4-peers {
          description
            "The remote NVE address table in a same VNI.";
          list static-peer {
            key "peer-ip";
            description
              "The remote NVE address in a same VNI.";
            leaf peer-ip {
              type inet:ipv4-address-no-zone;
              description
                "The address of the NVE.";
            }
            leaf out-vni-id {
              type uint32 {
                range "1..16777215";
              }
              description
                "The ID of the out VNI. Do not support separate deletion.";                
            }
          }
        }
        container static-ipv6-peers {
          description
            "The remote NVE ipv6 address table in a same VNI.";
          list static-ipv6-peer {
            key "peer-ip";
            description
              "The remote NVE ipv6 address in a same VNI.";
            leaf peer-ip {
              type inet:ipv6-address-no-zone;
              description
                "The ipv6 address of the NVE.";
            }
          }
        }
        container flood-proxys {
          description
            "The flood proxys for this VNI";
          list flood-proxy {
            key "peer-ip";
            leaf peer-ip {
              type inet:ipv4-address-no-zone;
              description
                "peer ip address"; 
            }
            description
              "List of the flood proxys";
          }
        }
        container mcast-groups {
          description
            "The mcast address table.";
          list mcast-group {
            key "mcast-ip";
            description
              "The mcast address.";
            leaf mcast-ip {
              type inet:ipv4-address-no-zone;
              description
                "The mcast address of NVO3.";
            }
          }
        }
        container statistic {
          description
            "The VNI member in a same NVE.";
          leaf statistic-enable {
            type boolean;
            default "false";
            description
              "To determine whether to enable the statistics for a VNI.";
          }
          container statistic-info {
            config false;
            description
              "The vni instance traffic statistics information.";
            leaf rx-bits-per-sec {
              type uint64;
              config false;
              description
                "Number of bits received per second.";
            }
            leaf rx-pkt-per-sec {
              type uint64;
              config false;
              description
                "Number of packets received per second.";
            }
            leaf tx-bits-per-sec {
              type uint64;
              config false;
              description
                "Number of bits sent per second.";
            }
            leaf tx-pkt-per-sec {
              type uint64;
              config false;
              description
                "Number of packets sent per second.";
            }
            leaf rx-pkts {
              type uint64;
              config false;
              description
                "Total number of received packets.";
            }
            leaf rx-bytes {
              type uint64;
              config false;
              description
                "Total number of received bytes.";
            }
            leaf tx-pkts {
              type uint64;
              config false;
              description
                "Total number of sent packets.";
            }
            leaf tx-bytes {
              type uint64;
              config false;
              description
                "Total number of sent bytes.";
            }
            leaf rx-unicast-pkts {
              type uint64;
              config false;
              description
                "Number of received unicast packets.";
            }
            leaf rx-multicast-pkts {
              type uint64;
              config false;
              description
                "Number of received multicast packets.";
            }
            leaf rx-broadcast-pkts {
              type uint64;
              config false;
              description
                "Number of received broadcast packets.";
            }
            leaf drop-unicast-pkts {
              type uint64;
              config false;
              description
                "Number of discarded unicast packets.";
            }
            leaf drop-multicast-pkts {
              type uint64;
              config false;
              description
                "Number of discarded multicast packets.";
            }
            leaf drop-broadcast-pkts {
              type uint64;
              config false;
              description
                "Number of discarded broadcast packets.";
            }
            leaf tx-unicast-pkts {
              type uint64;
              config false;
              description
                "Number of sent unicast packets.";
            }
            leaf tx-multicast-pkts {
              type uint64;
              config false;
              description
                "Number of sent multicast packets.";
            }
            leaf tx-broadcast-pkts {
              type uint64;
              config false;
              description
                "Number of sent broadcast packets.";
            }
          }
        }

      }
    }
  }
  container vni-peer-infos {
      config false;
      description
        "The information table of vni members.";
      container peers {
        config false;
        description
          "The remote nve address in a same VNI.";
        list peer {
          key "vni-id source-ip peer-ip";
          config false;
          description
            "The remote nve address list in a same VNI.";
          leaf vni-id {
            type uint32 {
              range "1..16777215";
            }
            config false;
            description
              "The ID of VNI.";
          }
          leaf source-ip {
            type inet:ip-address-no-zone;
            config false;
            description
              "The source address of the NVE interface.";
          }
          leaf peer-ip {
            type inet:ip-address-no-zone;
            config false;
            description
              "The remote NVE address.";
          }
          leaf tunnel-type {
            type peer-type;
            config false;
            description
              "Tunnel type.";
          }
          leaf out-vni-id {
            type uint32 {
              range "1..16777215";
            }
            config false;
            description
              "The ID of the out VNI.";
          }        
        }
      }
    }

  container tunnel-infos {
    config false;
    description
      "VxLAN tunnel information.";
    list tunnel-info {
      key "tunnel-id";
      config false;
      description
        "VxLAN tunnel information list.";
      leaf tunnel-id {
        type uint32 {
          range "1..4294967295";
        }
        config false;
        description
          "The ID of Vxlan tunnel.";
      }
      leaf source-ip {
        type inet:ip-address-no-zone;
        config false;
        description
          "Local NVE interface address.";        
      }
      leaf peer-ip {
        type inet:ip-address-no-zone;
        config false;
        description
          "Remote NVE interface address.";        
      }
      leaf status {
        type tunnel-status;
        config false;
        description
          "Tunnel status.";
      }
      leaf type {
        type tunnel-type;
        config false;
        description
          "Tunnel type.";
      }
      leaf up-time {
        type string {
          length "1..10";
        }
        config false;
        description
          "Vxlan tunnel up time.";
      }
      leaf vrf-name {
        type leafref {
          path "/ni:network-instances/ni:network-instance/ni:name";
        }
        default "_public_";
        config false;
        description
          "The name of VPN instance.";
      }
    }
  }

  augment "/if:interfaces/if:interface" {
    description
      "Augment the interface, NVE as an interface.";
    container nvo3-nve {
      when "if:interfaces/if:interface/if:type = 'Nve'";
      description
        "Network virtualization edge.";      
      leaf source-vtep-ip {
        type inet:ipv4-address-no-zone;
        description
          "The source address of the NVE interface.";        
      }
      leaf source-vtep-ipv6 {
        type inet:ipv6-address-no-zone;
        description
          "The source ipv6 address of the NVE interface.";        
      }
      leaf bypass-vtep-ip {
        type inet:ipv4-address-no-zone;
        description
          "The source address of bypass VXLAN tunnel.";        
      }
      container statistics {
        description
          "VXLAN Tunnel Traffic Statistical Configuration Table.";
        list statistic {
          key "vni-id mode peer-ip direction";
          description
            "VXLAN Tunnel Traffic Statistics Configuration.";
          leaf vni-id {
            type uint32 {
              range "1..16777215";
            }
            description
              "ID of the VNI.";
          }
          leaf mode {
              type vni-type;
              description
              "The type of the NVE interface.";
          }
          leaf peer-ip {
            type inet:ipv4-address-no-zone;
            description
              "IP address of the remote VTEP.";
          }
          leaf direction {
            type direction-type;
            must "(./mode='l3' and ./bound!='bidirection')";
            description
              "Traffic statistics type about the VXLAN tunnel.";
          }
          container info {
            config false;
            description
              "Traffic statistics about the peer.";
            leaf rx-pkts {
              type uint64;
              config false;
              description
                "Total number of received packets.";
            }
            leaf rx-bytes {
              type uint64;
              config false;
              description
                "Total number of received bytes.";
            }
            leaf tx-pkts {
              type uint64;
              config false;
              description
                "Total number of sent packets.";
            }
            leaf tx-bytes {
              type uint64;
              config false;
              description
                "Total number of sent bytes.";
            }
            leaf rx-unicast-pkts {
              type uint64;
              config false;
              description
                "Number of received unicast packets.";
            }
            leaf rx-multicast-pkts {
              type uint64;
              config false;
              description
                "Number of received multicast packets.";
            }
            leaf rx-broadcast-pkts {
              type uint64;
              config false;
              description
                "Number of received broadcast packets.";
            }
            leaf tx-unicast-pkts {
              type uint64;
              config false;
              description
                "Number of sent unicast packets.";
            }
            leaf tx-multicast-pkts {
              type uint64;
              config false;
              description
                "Number of sent multicast packets.";
            }
            leaf tx-broadcast-pkts {
              type uint64;
              config false;
              description
                "Number of sent broadcast packets.";
            }
            leaf drop-unicast-pkts {
              type uint64;
              config false;
              description
                "Number of discarded unicast packets.";
            }
            leaf drop-multicast-pkts {
              type uint64;
              config false;
              description
                "Number of discarded multicast packets.";
            }
            leaf drop-broadcast-pkts {
              type uint64;
              config false;
              description
                "Number of discarded broadcast packets.";
            }
            leaf rx-bits-per-sec {
              type uint64;
              config false;
              description
                "Number of bits received per second.";
            }
            leaf rx-pkt-per-sec {
              type uint64;
              config false;
              description
                "Number of packets received per second.";
            }
            leaf tx-bits-per-sec {
              type uint64;
              config false;
              description
                "Number of bits sent per second.";
            }
            leaf tx-pkt-per-sec {
              type uint64;
              config false;
              description
                "Number of packets sent per second.";
            }
          }
        }
      }

    }
    container nvo3-gateway {
      when "if:interfaces/if:interface/if:type = 'Vbdif'";
      description
        "Enable anycast gateway.";
      leaf vxlan-anycast-gateway {
        type boolean;
        default "false";
        description
          "Enable vxlan anycast gateway.";
      }
    }
  }

  augment "/ni:network-instances/ni:network-instance/ni:ni-type" +
          "/l3vpn:l3vpn/l3vpn:l3vpn" {
    description "Augment for l3vpn instance";
    container vni-lists {
      description "Vni list for l3vpn";
      list vni {
        key "vni-id";
        description 
          "Vni for current l3vpn instance";
        leaf vni-id {
          type uint32 {
            range "1..16777215";
          }
          description
            "The id of VNI.";
        }       
      }
    }
  }

  augment "/ni:network-instances/ni:network-instance/ni:ni-type" +
          "/l2vpn:l2vpn" {
    description "Augment for l2vpn instance";
    container vni-lists {
      description "Vni list for l2vpn";
      list vni {
        key "vni-id";
        description 
          "Vni for current l2vpn instance";
        leaf vni-id {
          type uint32 {
            range "1..16777215";
          }
          description
            "The id of VNI.";
        }
        leaf split-horizon-mode {
          type vni-bind-type;
          default "hub-mode";
          description
            "Split horizon mode.";          
        }
        leaf split-group {
          type string {
            length "1..31";
          }
          description
            "Split group name.";          
        }        
      }
    }
  }

  rpc reset-vni-instance-statistic {
    description
      "Clear traffic statistics about the VNI.";
    input {
      leaf vni-id {
        type uint32 {
          range "1..16777215";
        }
        mandatory true;
        description
          "ID of the VNI.";
      }
    }
  }
  rpc reset-vni-peer-statistic {
    description
      "Clear traffic statistics about the VXLAN tunnel.";
    input {
      leaf vni-id {
        type uint32 {
          range "1..16777215";
        }
        mandatory true;
        description
          "ID of the VNI.";
      }
      leaf mode {
        type vni-type;
        mandatory true;
        description
          "The type of vni memeber statistic.";
      }
      leaf peer-ip {
        type inet:ipv4-address-no-zone;
        mandatory true;
        description
          "IP address of the remote NVE interface.";
      }
      leaf direction{
        type direction-type;
        must "(./mode='mode-l3' and ./bound!='bidirection')";
        mandatory true;
        description
          "Traffic statistics type about the VXLAN tunnel.";
      }
    }
  }  
}
