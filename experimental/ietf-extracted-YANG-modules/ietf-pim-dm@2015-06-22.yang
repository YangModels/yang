module ietf-pim-dm {
  namespace "urn:ietf:params:xml:ns:yang:ietf-pim-dm";
  // replace with IANA namespace when assigned
  prefix pim-dm;

  import ietf-routing {
    prefix "rt";
  }

  import ietf-pim-base {
    prefix "pim-base";
  }

  organization
    "IETF PIM Working Group";

  contact
    "WG Web:   <http://tools.ietf.org/wg/pim/>
     WG List:  <mailto:pim@ietf.org>

     WG Chair: Stig Venaas
               <mailto:stig@venaas.com>

     WG Chair: Mike McBride
               <mailto:mmcbride7@gmail.com>

     Editors:   ";
  description
    "The YANG module defines a DM (Dense Mode) PIM model.";

  revision 2015-06-22 {
    description
      "Initial revision.";
    reference
      "RFC XXXX: A YANG Data Model for PIM";
  }

  /*
   * Features
   */

  /*
   * Identities
   */

  /*
   * Groupings
   */

  /*
   * Configuration data nodes
   */

  augment "/rt:routing/rt:routing-instance/"
    + "rt:routing-protocols/pim-base:pim/"
    + "pim-base:address-family" {
    description "PIM DM augmentation.";

    container dm {
      presence "Present to enable dense-mode.";
      description
        "PIM DM configuration data.";
    } // Dm
  } // augment

  augment "/rt:routing/rt:routing-instance/"
    + "rt:routing-protocols/pim-base:pim/"
    + "pim-base:address-family/pim-base:interfaces/"
    + "pim-base:interface" {
    description "PIM DM augmentation to PIM base interface.";

    container dm {
      presence "Present to enable dense-mode.";
      description
        "PIM DM configuration data.";
    } // sm
  } // augment

  /*
   * Operational state data nodes
   */

  augment "/rt:routing-state/rt:routing-instance/"
    + "rt:routing-protocols/pim-base:pim/"
    + "pim-base:address-family" {
    description
      "PIM DM state.";
    container dm {
      description
        "PIM DM state data.";
    } // dm
  } // augment

  /*
   * RPCs
   */

  /*
   * Notifications
   */
}
