module ietf-mpls {
  yang-version 1.1;
  namespace "urn:ietf:params:xml:ns:yang:ietf-mpls";

  /* Replace with IANA when assigned */

  prefix mpls;

  import ietf-routing {
    prefix rt;
    reference
      "RFC8349: A YANG Data Model for Routing Management";
  }
  import ietf-routing-types {
    prefix rt-types;
    reference
      "RFC8294:Common YANG Data Types for the Routing Area";
  }
  import ietf-yang-types {
    prefix yang;
    reference
      "RFC6991: Common YANG Data Types";
  }
  import ietf-interfaces {
    prefix if;
    reference
      "RFC8343: A YANG Data Model for Interface Management";
  }

  organization
    "IETF MPLS Working Group";
  contact
    "WG Web:   <http://tools.ietf.org/wg/mpls/>

     WG List:  <mailto:mpls@ietf.org>

     Editor:   Tarek Saad
               <mailto:tsaad@juniper.net>

     Editor:   Kamran Raza
               <mailto:skraza@cisco.com>

     Editor:   Rakesh Gandhi
               <mailto:rgandhi@cisco.com>

     Editor:   Xufeng Liu
               <mailto: xufeng.liu.ietf@gmail.com>

     Editor:   Vishnu Pavan Beeram
               <mailto:vbeeram@juniper.net>";
  description
    "This YANG module defines the essential components for the
     management of the MPLS subsystem. The model fully conforms
     to the Network Management Datastore Architecture (NMDA).

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  // RFC Ed.: replace XXXX with actual RFC number and remove this
  // note.
  // RFC Ed.: update the date below with the date of RFC publication
  // and remove this note.

  revision 2020-10-26 {
    description
      "Initial revision.";
    reference
      "RFC XXXX: A YANG Data Model for base MPLS";
  }

  /* Identities */

  identity mpls {
    base rt:address-family;
    description
      "This identity represents the MPLS address family.";
  }

  identity mpls-unicast {
    base mpls:mpls;
    description
      "This identity represents the MPLS unicast address family.";
  }

  identity label-block-alloc-mode {
    description
      "Base identity for label-block allocation mode.";
  }

  identity label-block-alloc-mode-manager {
    base label-block-alloc-mode;
    description
      "Label block allocation on reserved block
       is managed by label manager.";
  }

  identity label-block-alloc-mode-application {
    base label-block-alloc-mode;
    description
      "Label block allocation on reserved block
       is managed by application.";
  }

  /**
   * Typedefs
   */

  typedef mpls-operations-type {
    type enumeration {
      enum impose-and-forward {
        description
          "Operation impose outgoing label(s) and forward to
           next-hop.";
      }
      enum pop-and-forward {
        description
          "Operation pop incoming label and forward to next-hop.";
      }
      enum pop-impose-and-forward {
        description
          "Operation pop incoming label, impose one or more
           outgoing label(s) and forward to next-hop.";
      }
      enum swap-and-forward {
        description
          "Operation swap incoming label, with outgoing label and
           forward to next-hop.";
      }
      enum pop-and-lookup {
        description
          "Operation pop incoming label and perform a lookup.";
      }
    }
    description
      "MPLS operations types.";
  }

  typedef nhlfe-role {
    type enumeration {
      enum primary {
        description
          "Next-hop acts as primary for carrying traffic.";
      }
      enum backup {
        description
          "Next-hop acts as backup.";
      }
      enum primary-and-backup {
        description
          "Next-hop acts as primary and backup simultaneously
           for carry traffic.";
      }
    }
    description
      "The next-hop role.";
  }

  grouping nhlfe-single-contents {
    description
      "A grouping that describes single Next Hop Label Forwarding
       Entry (NHLFE) and its associated parameters as described in
       the MPLS architecture. This grouping is specific to the case
       when a single next-hop is associated with the route.";
    uses rt-types:mpls-label-stack;
  }

  grouping nhlfe-multiple-contents {
    description
      "A grouping that describes a set of NHLFE(s) and their
       associated parameters as described in the MPLS architecture.
       This grouping is used when multiple next-hops are associated
       with the route.";
    leaf index {
      type string;
      description
        "A user-specified identifier utilised to uniquely
         reference the next-hop entry in the next-hop list.
         The value of this index has no semantic meaning
         other than for referencing the entry.";
    }
    leaf backup-index {
      type string;
      description
        "A user-specified identifier utilised to uniquely
         reference the backup next-hop entry in the NHLFE list.
         The value of this index has no semantic meaning
         other than for referencing the entry.";
      reference
        "RFC4090 and RFC5714";
    }
    leaf loadshare {
      type uint16;
      default "1";
      description
        "This value is used to compute a loadshare to perform un-equal
         load balancing when multiple outgoing next-hop(s) are
         specified. A share is computed as a ratio of this number to the
         total under all next-hops(s).";
      reference
        "RFC7424, section 5.4,
         RFC3031, section 3.11 and 3.12.";
    }
    leaf role {
      type nhlfe-role;
      description
        "NHLFE role.";
    }
    uses nhlfe-single-contents;
  }

  grouping interfaces-mpls {
    description
      "List of MPLS interfaces.";
    container interfaces {
      description
        "List of MPLS enabled interaces.";
      list interface {
        key "name";
        description
          "MPLS enabled interface entry.";
        leaf name {
          type if:interface-ref;
          description
            "A reference to the name of a interface in the system that
             is to be enabled for MPLS.";
        }
        leaf mpls-enabled {
          type boolean;
          default "false";
          description
            "'true' if mpls encapsulation is enabled on the interface.
             'false' if mpls encapsulation is disabled on the
             interface.";
        }
        leaf maximum-labeled-packet {
          type uint32;
          units "octets";
          description
            "Maximum labeled packet size.";
          reference
            "RFC3032, section 3.2.";
        }
      }
    }
  }

  grouping globals {
    description
      "MPLS global configuration grouping.";
    leaf ttl-propagate {
      type boolean;
      default "true";
      description
        "Propagate TTL between IP and MPLS.";
    }
  }

  grouping label-blocks {
    description
      "Label-block allocation grouping.";
    container mpls-label-blocks {
      description
        "Label-block allocation container.";
      list mpls-label-block {
        key "index";
        description
          "List of MPLS label-blocks.";
        leaf index {
          type string;
          description
            "A user-specified identifier utilised to uniquely
             reference an MPLS label block.";
        }
        leaf start-label {
          type rt-types:mpls-label;
          must '. <= ../end-label' {
            error-message
              "The start-label must be less than or equal "
            + "to end-label";
          }
          description
            "Label-block start.";
        }
        leaf end-label {
          type rt-types:mpls-label;
          must '. >= ../start-label' {
            error-message
              "The end-label must be greater than or equal "
            + "to start-label";
          }
          description
            "Label-block end.";
        }
        leaf block-allocation-mode {
          type identityref {
            base label-block-alloc-mode;
          }
          description
            "Label-block allocation mode.";
        }
        leaf inuse-labels-count {
          when "derived-from-or-self(../block-allocation-mode, "
             + "'mpls:label-block-alloc-mode-manager')";
          type yang:gauge32;
          config false;
          description
            "Label-block inuse labels count.";
        }
      }
    }
  }

  grouping rib-mpls-properties {
    description
      "A grouping of native MPLS RIB properties.";
    leaf destination-prefix {
      type leafref {
        path "../mpls-local-label";
      }
      description
        "MPLS destination prefix.";
    }
    leaf route-context {
      type string;
      description
        "A context associated with the native MPLS route.";
    }
  }

  grouping rib-active-route-mpls-input {
    description
      "A grouping applicable to native MPLS RIB 'active-route'
       RPC input augmentation.";
    leaf destination-address {
      type leafref {
        path "../mpls-local-label";
      }
      description
        "MPLS native active route destination.";
    }
    leaf mpls-local-label {
      type rt-types:mpls-label;
      description
        "MPLS local label.";
    }
  }

  augment "/rt:routing" {
    description
      "MPLS augmentation.";
    container mpls {
      description
        "MPLS container, to be used as an augmentation target node
         other MPLS sub-features config, e.g. MPLS static LSP, MPLS
         LDP LSPs, and Trafic Engineering MPLS LSP Tunnels, etc.";
      uses globals;
      uses label-blocks;
      uses interfaces-mpls;
    }
  }

  /* MPLS routes augmentation */

  augment "/rt:routing/rt:ribs/rt:rib/rt:routes/rt:route" {
    description
      "This augmentation is applicable to all MPLS routes.";
    leaf mpls-enabled {
      type boolean;
      default "false";
      description
        "Indicates whether MPLS is enabled for this route.";
    }
    leaf mpls-local-label {
      when "../mpls-enabled = 'true'";
      type rt-types:mpls-label;
      description
        "MPLS local label associated with the route.";
    }
    uses rib-mpls-properties {
      /* MPLS AF augmentation to native MPLS RIB */
      when "derived-from-or-self(../../rt:address-family, "
         + "'mpls:mpls')" {
        description
          "This augment is valid only for routes of native MPLS
           RIB.";
      }
    }
  }

  /* MPLS simple-next-hop augmentation */

  augment "/rt:routing/rt:ribs/rt:rib/rt:routes/rt:route/"
        + "rt:next-hop/rt:next-hop-options/rt:simple-next-hop" {
    description
      "Augment 'simple-next-hop' case in IP unicast routes.";
    uses nhlfe-single-contents {
      when "/rt:routing/rt:ribs/rt:rib/rt:routes/rt:route"
         + "/mpls:mpls-enabled = 'true'";
    }
  }

  /* MPLS next-hop-list augmentation */

  augment "/rt:routing/rt:ribs/rt:rib/rt:routes/rt:route/"
        + "rt:next-hop/rt:next-hop-options/rt:next-hop-list/"
        + "rt:next-hop-list/rt:next-hop" {
    description
      "This leaf augments the 'next-hop-list' case of IP unicast
       routes.";
    uses nhlfe-multiple-contents {
      when "/rt:routing/rt:ribs/rt:rib/rt:routes/rt:route"
         + "/mpls:mpls-enabled = 'true'";
    }
  }

  /* MPLS RPC input augmentation */

  augment "/rt:routing/rt:ribs/rt:rib/rt:active-route/rt:input" {
    description
      "Input MPLS augmentation for the 'active-route' action
       statement.";
    uses rib-active-route-mpls-input {
      /* MPLS AF augmentation to native MPLS RIB */
      when "derived-from-or-self(../rt:address-family, "
         + "'mpls:mpls')" {
        description
          "This augment is valid only for routes of native MPLS
           RIB.";
      }
    }
  }

  /* MPLS RPC output augmentation */

  augment "/rt:routing/rt:ribs/rt:rib/rt:active-route/"
        + "rt:output/rt:route/"
        + "rt:next-hop/rt:next-hop-options/rt:simple-next-hop" {
    description
      "Output MPLS augmentation for the 'active-route' action
       statement.";
    uses nhlfe-single-contents;
  }

  augment "/rt:routing/rt:ribs/rt:rib/rt:active-route/"
        + "rt:output/rt:route/"
        + "rt:next-hop/rt:next-hop-options/rt:next-hop-list/"
        + "rt:next-hop-list/rt:next-hop" {
    description
      "Output MPLS augmentation for the 'active-route' action
       statement.";
    uses nhlfe-multiple-contents;
  }
}
