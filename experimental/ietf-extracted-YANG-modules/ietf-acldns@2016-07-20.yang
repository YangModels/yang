module ietf-acldns {
  yang-version 1.1;
  namespace "urn:ietf:params:xml:ns:yang:ietf-acldns";
  prefix "ietf-acldns";

  import ietf-access-control-list {
    prefix "acl";
  }

  import ietf-inet-types {
    prefix "inet";
  }

  organization
    "IETF OPSAWG (Ops Area) Working Group";

  contact
       "WG Web: http://tools.ietf.org/wg/opsawg/
       WG List: opsawg@ietf.org
       WG Chair: Warren Kumari
       warren@kumari.net
       WG Chair: Zhou Tianran
       zhoutianran@huawei.com
       Editor: Eliot Lear
       lear@cisco.com
       Editor: Ralph Droms
       rdroms@cisco.com
    ";

  description
    "This YANG module defines a component that augments the
     IETF description of an access list to allow dns names
     as matching criteria.";

  revision "2016-07-20" {
    description "Base version of dnsname extension of ACL model";
    reference "RFC XXXX: Manufacturer Usage Description Specification";
  }

  augment "/acl:access-lists/acl:acl/" +
     "acl:access-list-entries/acl:ace/" +
     "acl:matches/acl:ace-type/acl:ace-ip" {
    description "adding domain names to matching";

    leaf src-dnsname {
      type inet:host;
      description "domain name to be matched against";
    }
    leaf dst-dnsname {
      type inet:host;
      description "domain name to be matched against";
    }
  }
}
