module ietf-utunnel  {
    namespace "urn:ietf:params:xml:ns:yang:ietf-utunnel";
    // replace with IANA namespace when assigned
    prefix "utunnel";

    import ietf-inet-types {
        prefix "inet";
    }

    import ietf-routing {
        prefix "rt";
    }

    organization "huawei";
    contact
       "lizhenbin@huawei.com
        xiachen@huawei.com
        vinods.kumar@huawei.com";

    description "unified tunnel model";
    revision "2015-12-16" {
        description "2015-07-05:Initial revision"+
                    "2015-12-16:Add the description in the yang module.";
        reference "TBD";
    }

    typedef tunnel-id {
        type uint32;
        description
            "An identifier for a tunnel.";
    }

    typedef tunnel-name {
        type string {
            length "1..64";
        }
        description
            "The name of a tunnel.";
    }

    typedef tunnel-protocol{
        type enumeration {
            enum ldp {
                value "0";
                description "LDP";
            }
            enum rsvp-te {
                value "1";
                description "RSVP-TE";
            }
            enum bgp {
                value "2";
                description "Labeled BGP";
            }
            enum cr-static-lsp {
                value "3";
                description "Static LSP with TE constraints";
            }
            enum gre {
                value "4";
                description "GRE";
            }
            enum ipsec {
                value "5";
                description "IPSec";
            }
            enum vxlan {
                value "6";
                description "VXLAN";
            }
            enum segment-routing-best-effort {
                value "7";
                description "Segment Routing BE";
            }
            enum segment-routing-te {
                value "8";
                description "Segment Routing TE";
            }
        }
        description
            "The protocol which is used to set up a tunnel.";
    }

    typedef tunnel-status {
        type enumeration {
            enum up {
                value "0";
                description
                "The status of tunnel is up.";
            }
            enum down {
                value "1";
                description
                "The status of tunnel is down.";
            }
        }
        description
            "The status of a tunnel.";
    }

    container utunnel{
        config false;
        description "The information of unified tunnel. The tunnels include P2P, MP2P and P2MP tunnel.
         P2P and MP2P tunnel use the same container with name P2P tunnels. P2MP tunnel is defined later.";

        container p2ptunnels{
            description "The information of unified P2P tunnel.";

            list tunnel {
                key "vrf-name tunnel-protocol tunnel-id";
                description "List of unified P2P tunnels.";

                leaf vrf-name {
                    type rt:routing-instance-ref;
                    description "The name of vrf. Some tunnels like LDP can be from specific VRF or default VRF.
                                 And some tunnels like RSVP-TE are only from the default VRF.";
                }
                leaf tunnel-protocol {
                    type tunnel-protocol;
                    description "The type of tunnel protocol which can be LDP, GRE, BGP etc.";
                }
                leaf tunnel-id {
                    type tunnel-id;
                    description "The identifier of tunnel which can be uniquely represented a tunnel with vrf-name and tunnel-protocol.";
                }
                leaf tunnel-name {
                    type tunnel-name;
                    description "The name of tunnel.";
                }
                leaf oper-status {
                    type tunnel-status;
                    description "The status of tunnel which can be up or down.";
                }
                container address-family {
                    description "IPv4 or IPv6 address family.";

                    container ipv4 {
                        description "IPv4 address family.";
                        leaf destination {
                            type inet:ipv4-address;
                            description "The destination is IPv4 address.";
                        }
                    }  // ipv4
                    container ipv6 {
                        description "IPv6 address family.";
                        leaf destination {
                            type inet:ipv6-address;
                            description "The destination is ipv6 address.";
                        }
                    }  // ipv6
                }
            }
        }
    }
}
