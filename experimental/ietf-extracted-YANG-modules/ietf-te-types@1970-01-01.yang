module ietf-te-types {

    namespace "urn:cisco:params:xml:ns:yang:ietf-te-types";

    /* Replace with IANA when assigned */
    prefix "te-types";

    import ietf-inet-types { prefix inet; }

    organization
      "IETF TEAS Working Group";

    description
        "This module contains a collection of generally
         useful TE specific YANG data type defintions.";
    identity tunnel-type {
        description
            "Base identity from which specific tunnel types are
            derived.";
    }

    identity tunnel-p2p {
        base tunnel-type;
        description
            "TE point-to-point tunnel type.";
    }

    identity tunnel-p2mp {
        base tunnel-type;
        description
            "TE point-to-multipoint tunnel type.";
    }

    identity state-type {
        description
            "Base identity for TE states";
    }

    identity state-up {
        base state-type;
        description
            "State up";
    }

    identity state-down {
        base state-type;
        description
            "State down";
    }

    identity switching-capabilities {
        description
            "Base identity for interface switching capabilities";
    }

    identity switching-psc1 {
        base switching-capabilities;
        description
          "Packet-Switch Capable-1 (PSC-1)";
    }

    identity switching-l2sc {
        base switching-capabilities;
        description
          "Packet-Switch Capable-1 (PSC-1)";
    }

    identity switching-evpl {
        base switching-capabilities;
        description
            "Ethernet Virtual Private Line (EVPL)";
    }

    identity switching-l2sc {
        base switching-capabilities;
        description
            "Layer-2 Switch Capable (L2SC)";
    }

    identity switching-tdm {
        base switching-capabilities;
        description
            "Time-Division-Multiplex Capable (TDM)";
    }

    identity switching-otn {
        base switching-capabilities;
        description
            "OTN-TDM capable";
    }

    identity switching-dcsc {
        base switching-capabilities;
        description
            "Data Channel Switching Capable (DCSC)";
    }

    identity switching-lsc {
        base switching-capabilities;
        description
            "Lambda-Switch Capable (LSC)";
    }

    identity switching-dcsc {
        base switching-capabilities;
        description
            "Data Channel Switching Capable (DCSC)";
    }

    identity switching-fsc {
        base switching-capabilities;
        description
            "Fiber-Switch Capable (FSC)";
    }

    identity lsp-encoding-types {
        description
            "Base identity for encoding types";
    }

    identity lsp-encoding-packet {
        base lsp-encoding-types;
        description
            "Packet LSP encoding";
    }

    identity lsp-encoding-ethernet {
        base lsp-encoding-types;
        description
            "Ethernet LSP encoding";
    }

    identity lsp-encoding-pdh {
        base lsp-encoding-types;
        description
            "ANSI/ETSI LSP encoding";
    }

    identity lsp-encoding-sdh {
        base lsp-encoding-types;
        description
            "SDH ITU-T G.707 / SONET ANSI T1.105 LSP encoding";
    }

    identity lsp-encoding-digital-wrapper {
        base lsp-encoding-types;
        description
            "Digital Wrapper LSP encoding";
    }

    identity lsp-encoding-lambda {
        base lsp-encoding-types;
        description
            "Lambda (photonic) LSP encoding";
    }

    identity lsp-encoding-fiber {
        base lsp-encoding-types;
        description
            "Fiber LSP encoding";
    }

    identity lsp-encoding-fiber-channel {
        base lsp-encoding-types;
        description
            "FiberChannel LSP encoding";
    }

    identity lsp-encoding-oduk {
        base lsp-encoding-types;
        description
            "G.709 ODUk (Digital Path)LSP encoding";
    }

    identity lsp-encoding-optical-channel {
        base lsp-encoding-types;
        description
            "Line (e.g., 8B/10B) LSP encoding";
    }

    identity lsp-encoding-line {
        base lsp-encoding-types;
        description
            "Line (e.g., 8B/10B) LSP encoding";
    }

    /* TE basic features */
    feature p2mp-te {
        description
            "Indicates support for P2MP-TE";
    }

    feature frr-te {
        description
            "Indicates support for TE FastReroute (FRR)";
    }

    feature extended-admin-groups {
        description
            "Indicates support for TE link extended admin
            groups.";
    }

    feature named-path-affinities {
        description
            "Indicates support for named path affinities";
    }
    feature named-extended-admin-groups {
        description
            "Indicates support for named extended admin groups";
    }

    feature named-srlg-groups {
        description
            "Indicates support for named SRLG groups";
    }

    feature named-path-constraints {
        description
            "Indicates support for named path constraints";
    }

    grouping explicit-route-object {
        container explicit-route-object {
            description
                "An explicit route describes as a list of groups of
                nodes along the explicit route.";
            reference "RFC3209: Extensions to RSVP for LSP Tunnels";

            choice type {
                case ipv4-address {
                    description
                        "IPv4 address Explicit Route Object";
                    leaf v4-address {
                        description
                            "An IPv4 address.  This address is treated
                            as a prefix based on the prefix length
                            value below.
                            Bits beyond the prefix are ignored on
                            receipt and
                            SHOULD be set to zero on transmission.";
                        type inet:ipv4-address;
                    }
                    leaf v4-prefix-length {
                        description
                            "Length in bits of the IPv4 prefix";
                        type uint8;
                    }
                    leaf v4-loose {
                        description
                            "Describes whether the object is loose
                            if set, or otherwise strict";
                        type boolean;
                    }
                }
                case ipv6-address {
                    description
                        "IPv6 address Explicit Route Object";
                    leaf v6-address {
                        description
                            "An IPv6 address.  This address is treated
                            as a prefix based on the prefix length
                            value below.
                            Bits beyond the prefix are ignored on
                            receipt and
                            SHOULD be set to zero on transmission.";
                        type inet:ipv6-address;
                    }
                    leaf v6-prefix-length {
                        description
                            "Length in bits of the IPv4 prefix";
                        type uint8;
                    }
                    leaf v6-loose {
                        description
                            "Describes whether the object is loose if
                            set, or otherwise strict";
                        type boolean;
                    }
                }
                case as-number {
                    description
                        "Autonomous System Explicit Route Object";
                    leaf as-number {
                        type uint16;
                    }
                }
                case unnumbered-link {
                    description
                        "Unnumbered link Explicit Route Object";
                    reference
                        "RFC3477: Signalling Unnumbered Links in
                        RSVP-TE";
                    leaf router-id {
                        type inet:ip-address;
                    }
                    leaf interface-id {
                        type uint32;
                    }
                }
                case label {
                    description
                        "The Label ERO subobject";
                    leaf label_value {
                        type uint32;
                    }
                }
                /* AS domain sequence..? */
            }
        }
    }

    grouping record-route-object {
        container record-route-object {
            description
                "Describes a record route object";
            choice type {
                case ipv4-address {
                    leaf address {
                        description
                            "An IPv4 address.  This address is treated
                            as a prefix based on the prefix length
                            value below.
                            Bits beyond the prefix are ignored on
                            receipt and
                            SHOULD be set to zero on transmission.";
                        type inet:ipv4-address;
                    }
                    leaf prefix-length {
                        description
                            "Length in bits of the IPv4 prefix";
                        type uint8;
                    }
                }
                case ipv6-address {
                    leaf address {
                        description
                            "An IPv6 address.  This address is treated
                            as a prefix based on the prefix length
                            value below.
                            Bits beyond the prefix are ignored on
                            receipt and
                            SHOULD be set to zero on transmission.";
                        type inet:ipv6-address;
                    }
                    leaf prefix-length {
                        description
                            "Length in bits of the IPv4 prefix";
                        type uint8;
                    }
                }
                case label {
                }
            }
        }
    }

    identity route-usage-type {
        description
            "Base identity for route usage";
    }

    identity route-include-ero {
        base route-usage-type;
        description
            "Include ERO from route";
    }

    identity route-exclude-ero {
        base route-usage-type;
        description
            "Exclude ERO from route";
    }

    identity route-exclude-srlg {
        base route-usage-type;
        description
            "Exclude SRLG from route";
    }

    identity path-metric-type {
        description
            "Base identity for path metric type";
    }

    identity path-metric-te {
        base path-metric-type;
        description
            "TE path metric";
    }

    identity path-metric-igp {
        base path-metric-type;
        description
            "IGP path metric";
    }

    identity path-tiebreaker-type {
        description
            "Base identity for path tie-breaker type";
    }

    identity path-tiebreaker-minfill {
        base path-tiebreaker-type;
        description
            "Min-Fill LSP path placement";
    }

    identity path-tiebreaker-maxfill {
        base path-tiebreaker-type;
        description
            "Max-Fill LSP path placement";
    }

    identity path-tiebreaker-randoom {
        base path-tiebreaker-type;
        description
            "Random LSP path placement";
    }

    identity bidir-provisioning-mode {
        description
            "Base identity for bidirectional provisioning
            mode.";
    }

    identity bidir-provisioning-single-sided {
        base bidir-provisioning-mode;
        description
            "Single-sided bidirectional provioning mode";
    }

    identity bidir-provisioning-double-sided {
        base bidir-provisioning-mode;
        description
            "Double-sided bidirectional provioning mode";
    }

    identity bidir-association-type {
        description
            "Base identity for bidirectional association type";
    }

    identity bidir-assoc-corouted {
        base bidir-association-type;
        description
            "Co-routed bidirectional association type";
    }

    identity bidir-assoc-non-corouted {
        base bidir-association-type;
        description
            "Non co-routed bidirectional association type";
    }

    identity resource-affinities-type {
        description
            "Base identity for resource affinities";
    }

    identity resource-aff-include-all {
        base resource-affinities-type;
        description
            "The set of attribute filters associated with a
            tunnel all of which must be present for a link
            to be acceptable";
    }

    identity resource-aff-include-any {
        base resource-affinities-type;
        description
            "The set of attribute filters associated with a
            tunnel any of which must be present for a link
            to be acceptable";
    }

    identity resource-aff-exclude-any {
        base resource-affinities-type;
        description
            "The set of attribute filters associated with a
            tunnel any of which renders a link unacceptable";
    }

    typedef admin-group {
        description
            "Administrative group/Resource class/Color.";
        type uint32;
    }

    typedef extended-admin-group {
        description
            "Extended administrative group/Resource class/Color.";
        type binary;
    }

    typedef admin-groups {
        type union {
            type admin-group;
            type extended-admin-group;
        }
    }

    typedef srlg {
        type uin32;
    }

    identity path-computation-srlg-type {
        description
            "Base identity for SRLG path computation";
    }

    identity srlg-ignore {
        base path-computation-srlg-type;
        description
            "Ignores SRLGs in path computation";
    }

    identity srlg-strict {
        base path-computation-srlg-type;
        description
            "Include strict SRLG check in path computation";
    }

    identity srlg-preferred {
        base path-computation-srlg-type;
        description
            "Include preferred SRLG check in path computation";
    }

    identity srlg-weighted {
        base path-computation-srlg-type;
        description
            "Include weighted SRLG check in path computation";
    }

    typedef te-metric {
        type uint32;
    }

    typedef topology-id {
        description
            "An identifier for a topology.";
        type string {
            pattern '/?([a-zA-Z0-9\-_.]+)(/[a-zA-Z0-9\-_.]+)*';
        }
    }

    grouping tunnel-path-selection {
        container path-selection {
            leaf topology {
                description
                    "The tunnel path is computed using the specific
                     topology identified by this identifier";
                type topology-id;
            }
            leaf cost-limit {
                description
                    "The tunnel path cost limit.";
                type uint32 {
                    range "1..4294967295";
                }
            }
            leaf hop-limit {
                description
                    "The tunnel path hop limit.";
                type uint8 {
                     range "1..255";
                }
            }
            leaf metric-type {
                description
                    "The tunnel path metric type.";
                type identityref {
                    base path-metric-type;
                }
                default path-metric-te;
            }
            leaf tiebreaker-type {
                description
                    "The tunnel path computation tie breakers.";
                type identityref {
                    base path-tiebreaker-type;
                }
                default path-tiebreaker-maxfill;
            }
            leaf ignore-overload {
                description
                    "The tunnel path can traverse overloaded node.";
                type boolean;
            }
            uses path-affinities;
            uses path-srlgs;
        }
    }

    grouping path-affinities {
        container path-affinities {
            if-feature ietf-te-types:named-path-affinities;
            choice style {
                case values {
                    leaf value {
                        type uint32 {
                            range "0..4294967295";
                        }
                    }
                    leaf mask {
                        type uint32 {
                            range "0..4294967295";
                        }
                    }
                }
                case named {
                    list constraints {
                        key "usage";
                        leaf usage {
                            type identityref {
                                base resource-affinities-type;
                            }
                        }
                        container constraint {
                            list affinity-names {
                                key "name";
                                leaf name {
                                     type string;
                                }
                            }
                        }
                    }
                }
            }
        }
    }

    grouping path-srlgs {
        container path-srlgs {
            choice style {
                case values {
                    leaf usage {
                        type constraint-usage-type;
                    }
                    leaf-list values {
                        type srlg;
                    }
                }
                case named {
                    list constraints {
                        key "usage";
                        leaf usage {
                            type constraint-usage-type;
                        }
                        container constraint {
                            list srlg-names {
                                key "name";
                                leaf name {
                                     type string;
                                }
                            }
                        }
                    }
                }
            }
        }
    }

    grouping tunnel-forwarding-properties {
        description "Properties for using tunnel in forwarding.";
        container forwarding {
            leaf load-share {
                 description "ECMP tunnel forwarding
                              load-share factor.";
                 type uint32 {
                    range "1..4294967295";
                 }
            }
            choice policy-type {
                container class {
                    leaf class {
                        type uint8 {
                            range "1..7";
                        }
                    }
                }
                container group {
                    leaf-list classes {
                        type uint8 {
                            range "1..7";
                        }
                    }
                }
            }
        }
    }

    grouping tunnel-routing-properties {
        choice routing-choice {
            description
                "Announces the tunnel to IGP as either
                 autoroute or forwarding adjacency.";
            case autoroute {
                container autoroute-announce {
                    presence "Enable autoroute announce.";
                    description
                        "Announce the TE tunnel as autoroute to
                         IGP for use as IGP shortcut.";
                    leaf-list routing-afs {
                         type inet:ip-version;
                    }
                    choice metric-type {
                        leaf metric {
                            type uint32 {
                                 range "1..2147483647";
                            }
                        }
                        leaf relative-metric {
                            type int32 {
                                 range "-10..10";
                            }
                        }
                        leaf absolute-metric {
                            type uint32 {
                                 range "1..2147483647";
                            }
                        }
                    }
                }
            }
            case forwarding-adjacency {
                container forwarding-adjacency {
                    presence "Enable forwarding adjacency
                              on the tunnel.";
                    description
                        "Announce the TE tunnel
                         as forwarding adjacency.";
                    leaf holdtime {
                        description
                            "Holdtime in seconds after
                             tunnel becomes UP.";
                        type uint32 {
                             range "0..4294967295";
                        }
                    }
                    leaf-list routing-afs {
                        type inet:ip-version;
                    }
                }
            }
        }
    }

    grouping tunnel-bidir-assoc-properties {
        container bidirectional {
            description
                "TE tunnel associated bidirectional attributes.";
            container association {
                leaf id {
                     description
                         "The TE tunnel association identifier.";
                     type uint16;
                }
                leaf source {
                     description
                            "The TE tunnel association source.";
                     type inet:ip-address;
                }
                leaf global-source {
                     description
                            "The TE tunnel association global
                             source.";
                     type inet:ip-address;
                }
                leaf type {
                    description
                        "The TE tunnel association type.";
                    type identityref {
                        base bidir-association-type;
                    }
                    default bidir-assoc-non-corouted;
                }
                leaf provisioing {
                    description
                        "Describes the provisioning model of the
                        associated bidirectional LSP";
                    reference
                        "draft-ietf-teas-mpls-tp-rsvpte-ext-
                        associated-lsp, section-3.2";
                    type identityref {
                        base bidir-provisioning-mode;
                    }
                }
            }
        }
    }

    /* TE interface attribute properties */
    grouping interface-switching-cap {
        list switching-capabilities {
            key "switching-capability";
            description
                "List of interface capabilities for this interface";
            leaf capability {
                type identityref {
                    base te-types:switching-capabilities;
                }
                default switching-psc1;
                description
                    "Switching Capability for this interface";
            }
            leaf encoding {
                type identityref {
                    base lsp-encoding-types;
                }
                description
                    "Encoding supported by this interface";
            }
        }
    }

    grouping interface-affinities {
        container affinities {
            choice type {
                case admin-groups {
                    description
                        "Administrative group/Resource class/Color.";
                    leaf admin-group {
                        type admin-group;
                    }
                }
                case extended-admin-groups {
                    if-feature extended-admin-groups;
                    description
                        "Extended administrative group/Resource
                        class/Color.";
                    leaf extended-admin-group {
                        type extended-admin-group;
                    }
                }
            }
        }
    }

    grouping interface-srlgs {
        container srlgs {
            choice type {
                case srlg-name {
                    list names {
                        key "name";
                        description "List of SRLG names that
                            this link is part of.";
                        leaf name {
                             type string;
                        }
                    }
                }
                case srlg-value {
                    list values {
                        key "value";
                        description "List of SRLG values that
                            this link is part of.";
                        leaf value {
                             type uint32 {
                                  range "0..4294967295";
                             }
                        }
                    }
                }
            }
        }
    }
}
