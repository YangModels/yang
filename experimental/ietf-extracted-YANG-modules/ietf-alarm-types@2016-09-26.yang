module ietf-alarm-types {
    namespace "urn:ietf:params:xml:ns:yang:ietf-alarm-types";
    prefix flt-types;

    organization
        "IETF NETMOD (NETCONF Data Modeling Language) Working
        Group";

    contact
        "WG Web: <http://tools.ietf.org/wg/netmod/>
        WG List: <mailto:netmod@ietf.org>

        Editor: Anurag Sharma
                <mailto:AnSharma@infinera.com>

        Editor: Rajan Rao
                <mailto:rrao@infinera.com>

        Editor: Xian Zhang
                <mailto:zhang.xian@huawei.com>";

    description
        "This module contains Alarm data type definitions.";

    revision 2016-09-26 {
        description
                "Revision 0.2";
        reference
                "TBD";
    }

    identity event-type {
        description
           "Base identity from which specific alarm types are
                derived.";
    }

    identity other-event-type {
        base event-type;
        description
                "Alarm type other than the ";
        reference "RFC 3877";
    }

    identity communication-event-type {
        base event-type;
        description
           "Alarm of this type is principally associated with the
                procedures and/or processes required to convey
                information from one point to another.";
        reference "ITU Recommendation X.733";
    }

    identity QoS-event-type {
        base event-type;
        description
           "Alarm of this type is principally associated with a
                degradation in the quality of a service.";
        reference "ITU Recommendation X.733";
    }
    identity processing-event-type {
        base event-type;
        description
           "Alarm of this type is principally associated with a
                software or processing alarm.";
        reference "ITU Recommendation X.733";
    }

    identity equipment-event-type {
        base event-type;
        description
           "Alarm of this type is principally associated with an
                equipment alarm.";
        reference "ITU Recommendation X.733";
    }

    identity environmental-event-type {
        base event-type;
        description
           "Alarm of this type is principally associated with a
                condition relating to an enclosure in which the
                equipment resides.";
        reference "ITU Recommendation X.733";
    }

    identity integrity-violation-event-type {
        base event-type;
        description
                "Integrity Violation Event Type";
        reference "RFC 3877";
    }

    identity operation-violation-event-type {
        base event-type;
        description
                "Operation Violation Event Type";
        reference "RFC 3877";
    }

    identity physical-violation-event-type {
        base event-type;
        description
                "Physical Violation Event Type";
        reference "RFC 3877";
    }

    identity security-service-or-mechanism-violation-event-type {
        base event-type;
        description
                "Security Service or Mechanism Violation Event Type";
        reference "RFC 3877";
    }

    identity time-domain-violation-event-type {
        base event-type;
        description
                "Time domain Violation Event Type";
        reference "RFC 3877";
    }

    identity probable-cause-type {
        description
           "Base identity from which specific probable cause types
                are derived.";
    }

    /* Probable cause definitions from RFC 3877*/
    identity aIS {
         base probable-cause-type;
         description "aIS";
   }
   identity callSetUpFailure {
         base probable-cause-type;
         description "callSetUpFailure";
   }
   identity degradedSignal {
         base probable-cause-type;
         description "degradedSignal";
   }
   identity farEndReceiverFailure {
         base probable-cause-type;
         description "farEndReceiverFailure";
   }
   identity framingError {
         base probable-cause-type;
         description "framingError";
   }
   identity lossOfFrame {
         base probable-cause-type;
         description "lossOfFrame";
   }
   identity lossOfPointer {
         base probable-cause-type;
         description "lossOfPointer";
   }
   identity lossOfSignal {
         base probable-cause-type;
         description "lossOfSignal";
   }
   identity payloadTypeMismatch {
         base probable-cause-type;
         description "payloadTypeMismatch";
   }
   identity transmissionError {
         base probable-cause-type;
         description "transmissionError";
   }
   identity remoteAlarmInterface {
         base probable-cause-type;
         description "remoteAlarmInterface";
   }
   identity excessiveBER {
         base probable-cause-type;
         description "excessiveBER";
   }
   identity pathTraceMismatch {
         base probable-cause-type;
         description "pathTraceMismatch";
   }
   identity unavailable {
         base probable-cause-type;
         description "unavailable";
   }
   identity signalLabelMismatch {
         base probable-cause-type;
         description "signalLabelMismatch";
   }
   identity lossOfMultiFrame {
         base probable-cause-type;
         description "lossOfMultiFrame";
   }
   identity receiveFailure {
         base probable-cause-type;
         description "receiveFailure";
   }
   identity transmitFailure {
         base probable-cause-type;
         description "transmitFailure";
   }
   identity modulationFailure {
         base probable-cause-type;
         description "modulationFailure";
   }
   identity demodulationFailure {
         base probable-cause-type;
         description "demodulationFailure";
   }
   identity broadcastChannelFailure {
         base probable-cause-type;
         description "broadcastChannelFailure";
   }
   identity connectionEstablishmentError {
         base probable-cause-type;
         description "connectionEstablishmentError";
   }
   identity invalidMessageReceived {
         base probable-cause-type;
         description "invalidMessageReceived";
   }
   identity localNodeTransmissionError {
         base probable-cause-type;
         description "localNodeTransmissionError";
   }
   identity remoteNodeTransmissionError {
         base probable-cause-type;
         description "remoteNodeTransmissionError";
   }
   identity routingFailure {
         base probable-cause-type;
         description "routingFailure";
   }
   identity backplaneFailure {
         base probable-cause-type;
         description "backplaneFailure";
   }
   identity dataSetProblem {
         base probable-cause-type;
         description "dataSetProblem";
   }
   identity equipmentIdentifierDuplication {
         base probable-cause-type;
         description "equipmentIdentifierDuplication";
   }
   identity externalIFDeviceProblem {
         base probable-cause-type;
         description "externalIFDeviceProblem";
   }
   identity lineCardProblem {
         base probable-cause-type;
         description "lineCardProblem";
   }
   identity multiplexerProblem {
         base probable-cause-type;
         description "multiplexerProblem";
   }
   identity nEIdentifierDuplication {
         base probable-cause-type;
         description "nEIdentifierDuplication";
   }
   identity powerProblem {
         base probable-cause-type;
         description "powerProblem";
   }
   identity processorProblem {
         base probable-cause-type;
         description "processorProblem";
   }
   identity protectionPathFailure {
         base probable-cause-type;
         description "protectionPathFailure";
   }
   identity receiverFailure {
         base probable-cause-type;
         description "receiverFailure";
   }
   identity replaceableUnitMissing {
         base probable-cause-type;
         description "replaceableUnitMissing";
   }
   identity replaceableUnitTypeMismatch {
         base probable-cause-type;
         description "replaceableUnitTypeMismatch";
   }
   identity synchronizationSourceMismatch {
         base probable-cause-type;
         description "synchronizationSourceMismatch";
   }
   identity terminalProblem {
         base probable-cause-type;
         description "terminalProblem";
   }
   identity timingProblem {
         base probable-cause-type;
         description "timingProblem";
   }
   identity transmitterFailure {
         base probable-cause-type;
         description "transmitterFailure";
   }
   identity trunkCardProblem {
         base probable-cause-type;
         description "trunkCardProblem";
   }
   identity replaceableUnitProblem {
         base probable-cause-type;
         description "replaceableUnitProblem";
   }
   identity realTimeClockFailure {
         base probable-cause-type;
         description "realTimeClockFailure";
   }
   identity antennaFailure {
         base probable-cause-type;
         description "antennaFailure";
   }
   identity batteryChargingFailure {
         base probable-cause-type;
         description "batteryChargingFailure";
   }
   identity diskFailure {
         base probable-cause-type;
         description "diskFailure";
   }
   identity frequencyHoppingFailure {
         base probable-cause-type;
         description "frequencyHoppingFailure";
   }
   identity iODeviceError {
         base probable-cause-type;
         description "iODeviceError";
   }
   identity lossOfSynchronisation {
         base probable-cause-type;
         description "lossOfSynchronisation";
   }
   identity lossOfRedundancy {
         base probable-cause-type;
         description "lossOfRedundancy";
   }
   identity powerSupplyFailure {
         base probable-cause-type;
         description "powerSupplyFailure";
   }
   identity signalQualityEvaluationFailure {
         base probable-cause-type;
         description "signalQualityEvaluationFailure";
   }
   identity tranceiverFailure {
         base probable-cause-type;
         description "tranceiverFailure";
   }
   identity protectionMechanismFailure {
         base probable-cause-type;
         description "protectionMechanismFailure";
   }
   identity protectingResourceFailure {
         base probable-cause-type;
         description "protectingResourceFailure";
   }
   identity airConditioningFailure {
         base probable-cause-type;
         description "airConditioningFailure";
   }
   identity airDryerFailure {
         base probable-cause-type;
         description "airDryerFailure";
   }
   identity batteryDischarging {
         base probable-cause-type;
         description "batteryDischarging";
   }
   identity batteryFailure {
         base probable-cause-type;
         description "batteryFailure";
   }
   identity commercialPowerFailure {
         base probable-cause-type;
         description "commercialPowerFailure";
   }
   identity coolingFanFailure {
         base probable-cause-type;
         description "coolingFanFailure";
   }
   identity engineFailure {
         base probable-cause-type;
         description "engineFailure";
   }
   identity fireDetectorFailure {
         base probable-cause-type;
         description "fireDetectorFailure";
   }
   identity fuseFailure {
         base probable-cause-type;
         description "fuseFailure";
   }
   identity generatorFailure {
         base probable-cause-type;
         description "generatorFailure";
   }
   identity lowBatteryThreshold {
         base probable-cause-type;
         description "lowBatteryThreshold";
   }
   identity pumpFailure {
         base probable-cause-type;
         description "pumpFailure";
   }
   identity rectifierFailure {
         base probable-cause-type;
         description "rectifierFailure";
   }
   identity rectifierHighVoltage {
         base probable-cause-type;
         description "rectifierHighVoltage";
   }
   identity rectifierLowFVoltage {
         base probable-cause-type;
         description "rectifierLowFVoltage";
   }
   identity ventilationsSystemFailure {
         base probable-cause-type;
         description "ventilationsSystemFailure";
   }
   identity enclosureDoorOpen {
         base probable-cause-type;
         description "enclosureDoorOpen";
   }
   identity explosiveGas {
         base probable-cause-type;
         description "explosiveGas";
   }
   identity fire {
         base probable-cause-type;
         description "fire";
   }
   identity flood {
         base probable-cause-type;
         description "flood";
   }
   identity highHumidity {
         base probable-cause-type;
         description "highHumidity";
   }
   identity highTemperature {
         base probable-cause-type;
         description "highTemperature";
   }
   identity highWind {
         base probable-cause-type;
         description "highWind";
   }
   identity iceBuildUp {
         base probable-cause-type;
         description "iceBuildUp";
   }
   identity intrusionDetection {
         base probable-cause-type;
         description "intrusionDetection";
   }
   identity lowFuel {
         base probable-cause-type;
         description "lowFuel";
   }
   identity lowHumidity {
         base probable-cause-type;
         description "lowHumidity";
   }
   identity lowCablePressure {
         base probable-cause-type;
         description "lowCablePressure";
   }
   identity lowTemperatue {
         base probable-cause-type;
         description "lowTemperatue";
   }
   identity lowWater {
         base probable-cause-type;
         description "lowWater";
   }
   identity smoke {
         base probable-cause-type;
         description "smoke";
   }
   identity toxicGas {
         base probable-cause-type;
         description "toxicGas";
   }
   identity coolingSystemFailure {
         base probable-cause-type;
         description "coolingSystemFailure";
   }
   identity externalEquipmentFailure {
         base probable-cause-type;
         description "externalEquipmentFailure";
   }
   identity externalPointFailure {
         base probable-cause-type;
         description "externalPointFailure";
   }
   identity storageCapacityProblem {
         base probable-cause-type;
         description "storageCapacityProblem";
   }
   identity memoryMismatch {
         base probable-cause-type;
         description "memoryMismatch";
   }
   identity corruptData {
         base probable-cause-type;
         description "corruptData";
   }
   identity outOfCPUCycles {
         base probable-cause-type;
         description "outOfCPUCycles";
   }
   identity sfwrEnvironmentProblem {
         base probable-cause-type;
         description "sfwrEnvironmentProblem";
   }
   identity sfwrDownloadFailure {
         base probable-cause-type;
         description "sfwrDownloadFailure";
   }
   identity lossOfRealTimel {
         base probable-cause-type;
         description "lossOfRealTimel";
   }
   identity applicationSubsystemFailure {
         base probable-cause-type;
         description "applicationSubsystemFailure";
   }
   identity configurationOrCustomisationError {
         base probable-cause-type;
         description "configurationOrCustomisationError";
   }
   identity databaseInconsistency {
         base probable-cause-type;
         description "databaseInconsistency";
   }
   identity fileError {
         base probable-cause-type;
         description "fileError";
   }
   identity outOfMemory {
         base probable-cause-type;
         description "outOfMemory";
   }
   identity softwareError {
         base probable-cause-type;
         description "softwareError";
   }
   identity timeoutExpired {
         base probable-cause-type;
         description "timeoutExpired";
   }
   identity underlayingResourceUnavailable {
         base probable-cause-type;
         description "underlayingResourceUnavailable";
   }
   identity versionMismatch {
         base probable-cause-type;
         description "versionMismatch";
   }
   identity bandwidthReduced {
         base probable-cause-type;
         description "bandwidthReduced";
   }
   identity congestion {
         base probable-cause-type;
         description "congestion";
   }
   identity excessiveErrorRate {
         base probable-cause-type;
         description "excessiveErrorRate";
   }
   identity excessiveResponseTime {
         base probable-cause-type;
         description "excessiveResponseTime";
   }
   identity excessiveRetransmissionRate {
         base probable-cause-type;
         description "excessiveRetransmissionRate";
   }
   identity reducedLoggingCapability {
         base probable-cause-type;
         description "reducedLoggingCapability";
   }
   identity systemResourcesOverload {
         base probable-cause-type;
         description "systemResourcesOverload";
   }
   identity adapterError {
         base probable-cause-type;
         description "adapterError";
   }
   identity applicationSubsystemFailture {
         base probable-cause-type;
         description "applicationSubsystemFailture";
   }
   identity bandwidthReducedX733 {
         base probable-cause-type;
         description "bandwidthReducedX733";
   }
   identity callEstablishmentError {
         base probable-cause-type;
         description "callEstablishmentError";
   }
   identity communicationsProtocolError {
         base probable-cause-type;
         description "communicationsProtocolError";
   }
   identity communicationsSubsystemFailure {
         base probable-cause-type;
         description "communicationsSubsystemFailure";
   }
   identity configurationOrCustomizationError {
         base probable-cause-type;
         description "configurationOrCustomizationError";
   }
   identity congestionX733 {
         base probable-cause-type;
         description "congestionX733";
   }
   identity coruptData {
         base probable-cause-type;
         description "coruptData";
   }
   identity cpuCyclesLimitExceeded {
         base probable-cause-type;
         description "cpuCyclesLimitExceeded";
   }
   identity dataSetOrModemError {
         base probable-cause-type;
         description "dataSetOrModemError";
   }
   identity degradedSignalX733 {
         base probable-cause-type;
         description "degradedSignalX733";
   }
   identity dteDceInterfaceError {
         base probable-cause-type;
         description "dteDceInterfaceError";
   }
   identity enclosureDoorOpenX733 {
         base probable-cause-type;
         description "enclosureDoorOpenX733";
   }
   identity equipmentMalfunction {
         base probable-cause-type;
         description "equipmentMalfunction";
   }
   identity excessiveVibration {
         base probable-cause-type;
         description "excessiveVibration";
   }
   identity fileErrorX733 {
         base probable-cause-type;
         description "fileErrorX733";
   }
   identity fireDetected {
         base probable-cause-type;
         description "fireDetected";
   }
   identity framingErrorX733 {
         base probable-cause-type;
         description "framingErrorX733";
   }
   identity heatingVentCoolingSystemProblem {
         base probable-cause-type;
         description "heatingVentCoolingSystemProblem";
   }
   identity humidityUnacceptable {
         base probable-cause-type;
         description "humidityUnacceptable";
   }
   identity inputOutputDeviceError {
         base probable-cause-type;
         description "inputOutputDeviceError";
   }
   identity inputDeviceError {
         base probable-cause-type;
         description "inputDeviceError";
   }
   identity lanError {
         base probable-cause-type;
         description "lanError";
   }
   identity leakDetected {
         base probable-cause-type;
         description "leakDetected";
   }
   identity localNodeTransmissionErrorX733 {
         base probable-cause-type;
         description "localNodeTransmissionErrorX733";
   }
   identity lossOfFrameX733 {
         base probable-cause-type;
         description "lossOfFrameX733";
   }
   identity lossOfSignalX733 {
         base probable-cause-type;
         description "lossOfSignalX733";
   }
   identity materialSupplyExhausted {
         base probable-cause-type;
         description "materialSupplyExhausted";
   }
   identity multiplexerProblemX733 {
         base probable-cause-type;
         description "multiplexerProblemX733";
   }
   identity outOfMemoryX733 {
         base probable-cause-type;
         description "outOfMemoryX733";
   }
   identity ouputDeviceError {
         base probable-cause-type;
         description "ouputDeviceError";
   }
   identity performanceDegraded {
         base probable-cause-type;
         description "performanceDegraded";
   }
   identity powerProblems {
         base probable-cause-type;
         description "powerProblems";
   }
   identity pressureUnacceptable {
         base probable-cause-type;
         description "pressureUnacceptable";
   }
   identity processorProblems {
         base probable-cause-type;
         description "processorProblems";
   }
   identity pumpFailureX733 {
         base probable-cause-type;
         description "pumpFailureX733";
   }
   identity queueSizeExceeded {
         base probable-cause-type;
         description "queueSizeExceeded";
   }
   identity receiveFailureX733 {
         base probable-cause-type;
         description "receiveFailureX733";
   }
   identity receiverFailureX733 {
         base probable-cause-type;
         description "receiverFailureX733";
   }
   identity remoteNodeTransmissionErrorX733 {
         base probable-cause-type;
         description "remoteNodeTransmissionErrorX733";
   }
   identity resourceAtOrNearingCapacity {
         base probable-cause-type;
         description "resourceAtOrNearingCapacity";
   }
   identity responseTimeExecessive {
         base probable-cause-type;
         description "responseTimeExecessive";
   }
   identity retransmissionRateExcessive {
         base probable-cause-type;
         description "retransmissionRateExcessive";
   }
   identity softwareErrorX733 {
         base probable-cause-type;
         description "softwareErrorX733";
   }
   identity softwareProgramAbnormallyTerminated {
         base probable-cause-type;
         description "softwareProgramAbnormallyTerminated";
   }
   identity softwareProgramError {
         base probable-cause-type;
         description "softwareProgramError";
   }
   identity storageCapacityProblemX733 {
         base probable-cause-type;
         description "storageCapacityProblemX733";
   }
   identity temperatureUnacceptable {
         base probable-cause-type;
         description "temperatureUnacceptable";
   }
   identity thresholdCrossed {
         base probable-cause-type;
         description "thresholdCrossed";
   }
   identity timingProblemX733 {
         base probable-cause-type;
         description "timingProblemX733";
   }
   identity toxicLeakDetected {
         base probable-cause-type;
         description "toxicLeakDetected";
   }
   identity transmitFailureX733 {
         base probable-cause-type;
         description "transmitFailureX733";
   }
   identity transmiterFailure {
         base probable-cause-type;
         description "transmiterFailure";
   }
   identity underlyingResourceUnavailable {
         base probable-cause-type;
         description "underlyingResourceUnavailable";
   }
   identity versionMismatchX733 {
         base probable-cause-type;
         description "versionMismatchX733";
   }
   identity authenticationFailure {
         base probable-cause-type;
         description "authenticationFailure";
   }
   identity breachOfConfidentiality {
         base probable-cause-type;
         description "breachOfConfidentiality";
   }
   identity cableTamper {
         base probable-cause-type;
         description "cableTamper";
   }
   identity delayedInformation {
         base probable-cause-type;
         description "delayedInformation";
   }
   identity denialOfService {
         base probable-cause-type;
         description "denialOfService";
   }
   identity duplicateInformation {
         base probable-cause-type;
         description "duplicateInformation";
   }
   identity informationMissing {
         base probable-cause-type;
         description "informationMissing";
   }
   identity informationModificationDetected {
         base probable-cause-type;
         description "informationModificationDetected";
   }
   identity informationOutOfSequence {
         base probable-cause-type;
         description "informationOutOfSequence";
   }
   identity keyExpired {
         base probable-cause-type;
         description "keyExpired";
   }
   identity nonRepudiationFailure {
         base probable-cause-type;
         description "nonRepudiationFailure";
   }
   identity outOfHoursActivity {
         base probable-cause-type;
         description "outOfHoursActivity";
   }
   identity outOfService {
         base probable-cause-type;
         description "outOfService";
   }
   identity proceduralError {
         base probable-cause-type;
         description "proceduralError";
   }
   identity unauthorizedAccessAttempt {
         base probable-cause-type;
         description "unauthorizedAccessAttempt";
   }
   identity unexpectedInformation {
         base probable-cause-type;
         description "unexpectedInformation";
   }
   identity other {
         base probable-cause-type;
         description "other";
   }
}
