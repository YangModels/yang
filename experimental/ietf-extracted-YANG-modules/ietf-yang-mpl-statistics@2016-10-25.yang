module ietf-yang-mpl-statistics {

  yang-version 1;

  namespace
      "urn:ietf:params:xml:ns:yang:ietf-yang-mpl-statistics";

  prefix mpl;

  organization
    "IETF ROLL (Routing over Low power and lossy networks)
 Working Group";

  contact
     "WG Web:   http://tools.ietf.org/wg/roll/
     WG List:  mailto:roll@ietf.org

     WG Chair: Peter van der Stok
               mailto:consultancy@vanderstok.org

     WG Chair: Ines Robles
               mailto:maria.ines.robles@ericsson.com

     Editor:   Peter van der Stok
               mailto:consultancy@vanderstok.org";

  description
    "This module contains information about the operation
of the MPL protocol.

     Copyright (c) 2016 IETF Trust and the persons identified as
     authors of the code.  All rights reserved.

     Redistribution and use in source and binary forms, with or

     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

revision "2016-10-25" {
      description "Initial revision.";
      reference
        "I-D:draft-ietf-roll-mpl-yang: A YANG model for Multicast
 Protocol for Low power and lossy Networks (MPL)";
    }

     list mpl-statistics{
     key "seedID domainID";

     config false;

     description
        "List describes performance statistics integrated over
 the messages identified by seed and domain identifiers. A
forwarder can receive and forward multiple copies of a message
 uniquely identified by seqno, domain, and seed.";

      leaf seedID{
      type uint64;
      description
          "value uniquely identifies the MPL Seed within a MPL
           domain.";
      }

      leaf domainID{
      type uint16;
      description
         "together with seed-ID uniquely identifies buffer set.";
      }

      leaf c-too-high {
      type uint64;
      description
          "Number of times that a copy was not forwarded
             because c > k.";
      }

      leaf nr-forwarded {
      type uint64;
      description
          "number of times copies are forwarded, while c <= k.";
      }

      leaf nr-of-messages-received{
      type uint64;
      description
          "number of messages (one or more copies) received,
must be smaller than or equal to seqno.";
      }

      leaf nr-of-copies-received{
      type uint64;
      description
          "total number of message copies received.";
      }

      leaf nr-of-messages-forwarded{
      type uint64;
      description
          "number of forwarded messages, must be smaller than or
 equal to nr-of-messages-received.";
      }

      leaf nr-of-copies-forwarded{
      type uint64;
      description
          "number of forwarded copies, can be larger than
number-of-copies-received.";
      }

      leaf nr-of-refused{
      type uint64;
      description
           "number of refused copies because seqno too small.";
      }

      leaf nr-of-missed{
      type uint64;
      description
           "number of messages that were not received
(derived from gaps in received seqno's.)";
      }

      leaf nr-of-notreceived{
      type uint64;
      description
            "number of messages that were not received
             according to control message.";
      }

      leaf nr-of-inconsistent-data{
      type uint64;
      description
           "number of inconsistent data messages.";
      }

      leaf nr-of-consistent-data{
      type uint64;
      description
           "number of consistent data messages.";
      }

      leaf nr-of-consistent-control{
      type uint64;
      description
           "number of consistent control messages.";
      }

      leaf nr-of-inconsistent-control{
      type uint64;
      description
           "number of inconsistent control messages.";
      }
    }  // list mpl statistics
} // module  ietf-yang-mpl-statistics
