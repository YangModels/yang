module   ietf-wson-topology {
   namespace "urn:ietf:params:xml:ns:yang:ietf-wson-topology";

   prefix wson;

   import ietf-network {
   prefix "nd";
   }

   import ietf-network-topology {
   prefix "lnk";
   }

   import ietf-inet-types {
   prefix "inet";
   }

   import ietf-te-topology {
   prefix "tet";
   }

   organization
      "IETF CCAMP Working Group";

   contact
      "Editor:   Young Lee  <leeyoung@huawei.com>";
   description
      "This module contains a collection of YANG definitions for
      RWA WSON.

      Copyright (c) 2016 IETF Trust and the persons identified as
      authors of the code.  All rights reserved.

      Redistribution and use in source and binary forms, with or
      without modification, is permitted pursuant to, and subject
      to the license terms contained in, the Simplified BSD
      License set forth in Section 4.c of the IETF Trust's Legal
      Provisions Relating to IETF Documents
      (http://trustee.ietf.org/license-info).";

   revision 2016-07-09 {
      description
         "Version 3";

   reference
      "RFC XXX: A Yang Data Model for WSON Optical Networks ";
   }

   typedef wson-topology-id {
      type inet:uri;
      description
         "The WSON Topology ID";
   }

   typedef wson-node-id {
      type inet:ip-address;
      description
         "The WSON Node ID";
   }

   typedef devicetype {
      type enumeration {
         enum adm {
            value 1;
            description
               "Device is ADM";
         }

         enum roadm {
            value 2;
            description
               "Device is ROAMD/OXC";
         }
      }
      description
         "device type: fixed (ADM) or switched (ROADM/OXC)";
   }

   typedef directionality {
      type enumeration {
         enum bidir {
            value 0;
            description
               "bi-directional";
         }
         enum input {
            value 1;
            description
               "input direction";
         }
         enum output {
            value 2;
            description
               "output direction";
         }
      }
      description
         "The directionality of link set";
   }

   typedef wson-interface-ref {
      type leafref {
      path "/nd:networks/nd:network/lnk:link/lnk:link-id";
      }
      description
         "This type is used by data models that need to
         reference WSON interface.";
   }

    grouping wson-topology-type {
       description
         "Identifies the wson topology type.";
       container wson-topology {
         presence "Indicates WSON topology.";
         description
           "Its presence identifies the WSON topology type.";
       }
     } // wson-topology-type

   augment "/nd:networks/nd:network/nd:network-types"
         + "/tet:te-topology" {

      description "Augment network-types to include WSON topology";
      uses wson-topology-type {
         description
            "An empty WSON container to identify
            the topology type.";
      }
   }

   augment "/nd:networks/nd:network/nd:node/tet:te/tet:config"
         +"/tet:te-node-attributes"
         +"/tet:connectivity-matrix" {
      when "nd:network-types/tet:te-topology/wson-topology" {
         description
            "This augment is only valid for WSON.";
      }
      description "WSON Connectivity Matrix augmentation.";
      container wson-matrix{
         description "WSON specific Matrix.";
         leaf device-type {
            type devicetype;
            description
               "device type: fixed (ADM) or switched
               (ROADM/OXC)";
         }
         leaf dir {
            type directionality;
            description
               "bi-directionality or input or output
               of link set";
         }
         list matrix-interface {
            key "in-port-id";

            description
               "matrix-interface describes input-ports
               and out-ports around a connectivity
               matrix";

            leaf in-port-id {
               type wson-interface-ref;
               description
                  "The reference to in-port";
            }

            leaf out-port-id {
               type wson-interface-ref;
               description
                  "The reference to out-port";
            }
         }
      }
   }

   augment "/nd:networks/nd:network/lnk:link/tet:te/tet:config" {

      when "nd:network-types/tet:te-topology/wson-topology" {

      description
         "This augment is only valid for WSON.";
      }
      description "WSON Link augmentation.";

      leaf-list wavelength-available-bitmap {
         type boolean;
         description
            "array of bits (i.e., bitmap) that indicates
            if a wavelength is available or not on each
            channel.";
      }
   }
   augment "/nd:networks/nd:network/nd:node/tet:te/tet:config" {
      when "nd:network-types/tet:te-topology/wson-topology" {
      description
         "This augment is only valid for WSON.";
      }
      description "WSON Node augmentation.";

      list resource-pool {
         key "resource-pool-id";
         description
            "The resource pool list";

         leaf resource-pool-id {
            type uint32;
            description
               "The resource pool ID";
         }

         leaf pool-state {
            type boolean;
            description
               "TRUE is state UP; FALSE is state down";
         }

         list matrix-interface {
            key "in-port-id";

            description
               "pool is described as matrix-interface
               with input-ports and output-ports
               around the pool";

            leaf in-port-id {
               type wson-interface-ref;
               description
                  "The reference to in-interface";
            }

            leaf out-port-id {
               type wson-interface-ref;
               description
                  "The reference to out-interface";
            }
         }
      }
   }
}
