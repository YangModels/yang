module ietf-nvo3-base {
  yang-version 1.1;
  namespace "urn:ietf:params:xml:ns:yang:ietf-nvo3-base";
  prefix "nvo3";

  import ietf-network-instance {
    prefix "ni";
  }

  import ietf-interfaces {
    prefix "if";
  }

  import ietf-inet-types {
    prefix "inet";
  }

  import ietf-l2vpn {
    prefix "l2vpn";
  }

  import ietf-bgp-l3vpn {
    prefix "l3vpn";
  }

  import iana-if-type {
    prefix ianaift;
  }

  organization
    "IETF NVO3(Network Virtualization Overlays) Working Group";
  contact
    "WG Web:   &lt;https://datatracker.ietf.org/wg/nvo3&gt;
     WG List:  &lt;mailto:nvo3@ietf.org&gt;

     WG Chair: Matthew Bocci
                   &lt;mailto:matthew.bocci@nokia.com&gt;

     WG Chair: Sam Aldrin
                   &lt;mailto:aldrin.ietf@gmail.com&gt;

     Editor:  Ran Chen
                   &lt;mailto:chen.ran@zte.com.cn&gt;
     Editor:  Kunding Zhao
                   &lt;mailto:zhaokun.ding@huawei.com&gt;
     Editor:  Fengwei Qin
                   &lt;mailto:qinfengwei@chinamobile.com&gt;
     Editor:  Reshad Rahman
                   &lt;mailto:reshad@yahoo.com&gt;
     Editor:  Bing Liu
                   &lt;mailto:remy.liubing@huawei.com&gt;
    ";
  description
        "This model is focused on the common configuration
        requirement of various encapsulation options,
        such as VXLAN, NVGRE, GENEVE and VXLAN-GPE.

        Copyright (c) 2025 IETF Trust and the persons identified as
        authors of the code.  All rights reserved.

        Redistribution and use in source and binary forms, with or
        without modification, is permitted pursuant to, and subject
                to the license terms contained in, the Revised BSD License
                set forth in Section 4.c of the IETF Trust's Legal
                Provisions Relating to IETF Documents
        (https://trustee.ietf.org/license-info).
        This version of this YANG module is part of RFC 9719
        (https://www.rfc-editor.org/info/rfc9719); see the RFC
                itself for full legal notices.

        The key words 'MUST', 'MUST NOT', 'REQUIRED', 'SHALL',
                'SHALL NOT', 'SHOULD', 'SHOULD NOT', 'RECOMMENDED',
                'NOT RECOMMENDED','MAY', and 'OPTIONAL' in this document
                are to be interpreted as described in BCP 14 (RFC 2119)
                (RFC 8174) when, and only when, they appear in all capitals,
                as shown here.";

    revision 2025-10-16 {
      description
        "initial version.";
      reference
        "RFC XXXX: Base YANG Data Model for NVO3 Protocols";
    }
  typedef vni-status-type {
    type enumeration {
      enum "up" {
        description
          "The state is up.";
      }
      enum "down" {
        description
          "The state is down.";
      }
    }
    description
      "The state for VNI.";
  }

  typedef tunnel-status {
    type enumeration {
      enum "up" {
        description
          "The tunnel is up.";
}
      enum "down" {
        description
          "The tunnel is down.";
      }
    }
    description
      "The status of NVO3 Tunnel.";
  }
  typedef tunnel-type {
    type enumeration {
      enum "dynamic" {
        description
          "The tunnel is dynamic.";
      }
      enum "static" {
        description
          "The tunnel is static.";
      }
      enum "invalid" {
        description
          "The tunnel is invalid.";
      }
    }
    description
      "The type of NVO3 Tunnel.";
  }

  typedef direction-type {
    type enumeration {
      enum "inbound" {
        description
          "Inbound.";
      }
      enum "outbound" {
        description
          "Outbound.";
      }
      enum "bidirection" {
        description
          "Bidirection.";
      }
    }
    description
      "Bound direction.";
  }
  typedef vni-bind-type {
    type enumeration {
      enum "hub-mode" {
        description
          "Hub mode. The vni instance can't communicate
                  with other hub mode vni instances.";
      }
      enum "spoke-mode" {
        description
          "Spoke mode.";
      }
      enum "split-group-mode" {
        description
          "Split group mode.";
      }
    }
    description
      "The binding type of VNI.";
  }

  typedef vni-mode {
    type enumeration {
      enum "local" {
        description
          "Local mode.";
      }
      enum "global" {
        description
          "Global mode.";
      }
    }
    description
      "The mode of VNI.";
  }

  grouping nvo3-traffic-statistics {
    description
      "NVO3 tunnel traffic statistics collection.";
    leaf send-bits-rate {
      type uint64;
      units bit/s;
      description
        "Number of send bits per second.";
    }
    leaf send-pkts-rate {
      type uint64;
      units pps;
      description
        "Number of send packets per second.";
    }
    leaf send-unicast-pkts {
      type uint64;
      units packet;
      description
        "Number of send unicast packets.";
    }
    leaf send-multicast-pkts {
      type uint64;
      units packet;
      description
        "Number of send multicast packets.";
    }
    leaf send-broadcast-pkts {
      type uint64;
      units packet;
      description
        "Number of send broadcast packets.";
    }
    leaf send-total-bytes {
      type uint64;
      units Byte;
      description
        "Total number of send bytes.";
    }
    leaf send-total-pkts {
      type uint64;
      units packet;
      description
        "Total number of send packets.";
    }
    leaf receive-bits-rate {
      type uint64;
      units bit/s;
      description
        "Number of receive bits per second.";
    }
    leaf receive-pkts-rate {
      type uint64;
      units pps;
      description
        "Number of receive packets per second.";
    }
    leaf receive-unicast-pkts {
      type uint64;
      units packet;
      description
        "Number of receive unicast packets.";
    }
    leaf receive-multicast-pkts {
      type uint64;
      units packet;
      description
        "Number of receive multicast packets.";
    }
    leaf receive-broadcast-pkts {
      type uint64;
      units packet;
      description
        "Number of receive broadcast packets.";
    }
    leaf receive-total-bytes {
      type uint64;
      units Byte;
      description
        "Total number of receive bytes.";
    }
    leaf receive-total-pkts {
      type uint64;
      units packet;
      description
        "Total number of receive packets.";
    }
    leaf drop-unicast-pkts {
      type uint64;
      units packet;
      description
        "Number of discarded unicast packets.";
    }
    leaf drop-multicast-pkts {
      type uint64;
      units packet;
      description
        "Number of discarded multicast packets.";
    }
    leaf drop-broadcast-pkts {
      type uint64;
      units packet;
      description
        "Number of discarded broadcast packets.";
    }
  }

  container nvo3 {
    description
      "Management of NVO3.";
    container vni-instances {
      description
        "List of virtual network instances.";
      list vni-instance {
        key "vni-id";
        description
          "Configure the information of VNI.";
        leaf vni-id {
          type uint32 {
            range "1..16777215";
          }
          description
            "The id of VNI.";
        }
        leaf vni-mode {
          type vni-mode;
          default "local";
          description
            "The mode of VNI.";
        }
        leaf source-nve {
          type if:interface-ref;
          must "(/if:interfaces/if:interface
                  [if:name=current()]/if:type='Nve')";
          mandatory true;
          description
            "The name of the local NVE.";
        }
        leaf protocol-bgp {
          type boolean;
          default "false";
          description
            "Learn remote NVEs in the same VNI via BGP.";
        }
        leaf status {
          type vni-status-type;
          config false;
          description
            "The status of the VNI.";
        }
        container static-ipv4-peers {
          description
            "List of remote NVE address created by users in a VNI.";
          list static-peer {
            key "peer-ip";
            description
              "Configure remote NVE address in a same VNI.";
            leaf peer-ip {
              type inet:ipv4-address-no-zone;
              description
                "The address of the remote NVE.";
            }
            leaf out-vni-id {
              type uint32 {
                range "1..16777215";
              }
              description
                "The ID of VNI for outbound.
                                Do not support separate deletion.";
            }
          }
        }
        container static-ipv6-peers {
          description
            "List of remote NVE IPv6 address created by users
                        in a VNI.";
          list static-ipv6-peer {
            key "peer-ip";
            description
              "Configure remote NVE IPv6 address in a same VNI.";
            leaf peer-ip {
              type inet:ipv6-address-no-zone;
              description
                "The IPv6 address of the remote NVE.";
            }
            leaf out-vni-id {
              type uint32 {
                range "1..16777215";
              }
              description
                "The ID of VNI for outbound. Do not support separate
                                deletion.";
            }
          }
        }
        container flood-proxys {
          description
            "List of flood proxys for the VNI.";
          list flood-proxy {
            key "peer-ip";
            description
              "Configure flood proxys for the VNI.";
            leaf peer-ip {
              type inet:ip-address-no-zone;
              description
                "The address of flood proxy.";
            }
          }
        }
        container mcast-groups {
          description
            "List of multicast address for the VNI.";
          list mcast-group {
            key "mcast-ip";
            description
              "Configure multicast address in a same VNI.";
            leaf mcast-ip {
              type inet:ip-address-no-zone;
              description
                "The mcast address of NVO3.";
            }
          }
        }
        container statistic {
          description
            "Configure VNI traffic statistics.";
          leaf enable {
            type boolean;
            default "false";
            description
              "Enable/disable VNI traffic statistics.";
          }
          container info {
            when "../enable='true'";
            config false;
            description
              "The information of vni instance traffic statistics.";
            uses nvo3-traffic-statistics;
          }
        }
      }
    }
  }
  container vni-peer-infos {
      config false;
      description
        "List of remote NVE addresses.";
      container peers {
        config false;
        description
          "Operational data of remote NVE address in a VNI.";
        list peer {
          key "vni-id source-ip peer-ip";
          config false;
          description
            "Operational data of remote NVE addresses in a VNI.";
          leaf vni-id {
            type uint32 {
              range "1..16777215";
            }
            config false;
            description
              "The ID of VNI.";
          }
          leaf source-ip {
            type inet:ip-address-no-zone;
            config false;
            description
              "Local NVE address, as NVO3 tunnel source point.";
          }
          leaf peer-ip {
            type inet:ip-address-no-zone;
            config false;
            description
              "Remote NVE address, as NVO3 tunnel end point.";
          }
          leaf type {
            type tunnel-type;
            config false;
            description
              "Tunnel type.";
          }
          leaf out-vni-id {
            type uint32 {
              range "1..16777215";
            }
            config false;
            description
              "The ID of VNI for outbound.";
          }
        }
      }
    }

  container tunnel-infos {
    config false;
    description
      "List of NVO3 tunnel information.";
    list tunnel-info {
      key "tunnel-id";
      config false;
      description
        "Operational data of NVO3 tunnel information.";
      leaf tunnel-id {
        type uint32 {
          range "1..4294967295";
        }
        config false;
        description
          "The ID of NVO3 tunnel.";
      }
      leaf source-ip {
        type inet:ip-address-no-zone;
        config false;
        description
          "Local NVE address, as NVO3 tunnel source point.";
      }
      leaf peer-ip {
        type inet:ip-address-no-zone;
        config false;
        description
          "Remote NVE address, as NVO3 tunnel end point.";
      }
      leaf status {
        type tunnel-status;
        config false;
        description
          "Tunnel status.";
      }
      leaf type {
        type tunnel-type;
        config false;
        description
          "Tunnel type.";
      }
      leaf up-time {
        type string {
          length "1..10";
        }
        config false;
        description
          "The continuous time as NVO3 tunnel is reachable.";
      }
      leaf vrf-name {
        type leafref {
          path "/ni:network-instances/ni:network-instance/ni:name";
        }
        default "_public_";
        config false;
        description
          "The name of VPN instance.";
      }
    }
  }

  identity Nve {
    base ianaift:iana-interface-type;
    description "A new interface type to be registered to IANA";
  }

  augment "/if:interfaces/if:interface" {
    when "(/if:interfaces/if:interface/if:type = 'nvo3:Nve')";
    description
      "Augment the interface, NVE as an interface.";
    container nvo3-nve {
      description
        "Local NVE.";
      leaf nve-ip {
        type inet:ipv4-address-no-zone;
        description
          "The address of local NVE.";
      }
      leaf nve-ipv6 {
        type inet:ipv6-address-no-zone;
        description
          "The IPv6 address of the local NVE.";
      }
      leaf bypass-nve-ip {
        type inet:ipv4-address-no-zone;
        description
          "The address of local NVE as bypass.";
      }
      leaf bypass-nve-ipv6 {
        type inet:ipv6-address-no-zone;
        description
          "The IPv6 address of local NVE as bypass.";
      }
      container statistics {
        description
          "List of NVO3 tunnel statistics.";
        list statistic {
          key "vni-id peer-ip direction";
          description
            "Configure NVO3 tunnel statistics information.";
          leaf vni-id {
            type uint32 {
              range "1..16777215";
            }
            description
              "The ID of the VNI.";
          }
          leaf peer-ip {
            type inet:ip-address-no-zone;
            description
              "The address of remote NVE.";
          }
          leaf direction {
            type direction-type;
            description
              "Traffic statistics direction for the tunnel.";
          }
          container info {
            config false;
            description
              "The information of tunnel traffic statistics.";
            uses nvo3-traffic-statistics;
          }
        }
      }
    }
  }

  augment "/ni:network-instances/ni:network-instance/ni:ni-type" +
          "/l3vpn:l3vpn/l3vpn:l3vpn" {
    description "Augment for l3vpn instance";
    container vnis {
      description "Vni list for l3vpn.";
      list vni {
        key "vni-id";
        description
          "Vni for current l3vpn instance.";
        leaf vni-id {
          type uint32 {
            range "1..16777215";
          }
          description
            "The ID of the VNI.";
        }
      }
    }
  }

  augment "/ni:network-instances/ni:network-instance/ni:ni-type" +
          "/l2vpn:l2vpn" {
    description "Augment for l2vpn instance.";
    container vnis {
      description "Vni list for l2vpn.";
      list vni {
        key "vni-id";
        description
          "Vni for current l2vpn instance.";
        leaf vni-id {
          type uint32 {
            range "1..16777215";
          }
          description
            "The ID of the VNI.";
        }
        container split-horizon {
          description "Configure NVO3 split-horizon information.";
          leaf split-horizon-mode {
            type vni-bind-type;
            default "hub-mode";
            description
              "Split horizon mode.";
          }
          leaf split-group {
            when "(../split-horizon-mode='split-group-mode')";
            type string {
              length "1..31";
            }
            description
              "Split group name.";
          }
        }
      }
    }
  }

  rpc reset-vni-instance-statistic {
    description
      "Clear traffic statistics about the VNI.";
    input {
      leaf vni-id {
        type uint32 {
          range "1..16777215";
        }
        mandatory true;
        description
          "The ID of the VNI.";
      }
    }
  }
  rpc reset-vni-peer-statistic {
    description
      "Clear traffic statistics about the VXLAN tunnel.";
    input {
      leaf vni-id {
        type uint32 {
          range "1..16777215";
        }
        mandatory true;
        description
          "The ID of the VNI.";
      }
      leaf peer-ip {
        type inet:ip-address-no-zone;
        mandatory true;
        description
          "The address of the remote NVE.";
      }
      leaf direction{
        type direction-type;
        mandatory true;
        description
          "Traffic statistics direction for the tunnel.";
      }
    }
  }
}
