module ietf-arp {
  namespace "urn:ietf:params:xml:ns:yang:ietf-arp";
  prefix arp;

  import ietf-inet-types {
    prefix inet;
  }
  import ietf-yang-types {
    prefix yang;
  }

  organization
    "IETF Routing Area Working Group (rtgwg)";
  contact
    "WG Web: <http://tools.ietf.org/wg/rtgwg/>
     WG List: <mailto: rtgwg@ietf.org>
     Editor: Xiaojian Ding
         dingxiaojian1@huawei.com
     Editor: Feng Zheng
         habby.zheng@huawei.com
     Editor: Robert Wilton
         rwilton@cisco.com";
  description
    "Address Resolution Protocol (ARP) management, which includes
     static ARP configuration, dynamic ARP learning, ARP entry query,
     and packet statistics collection.";

  revision 2017-10-18 {
    description
      "Init revision";
    reference "RFC XXX: ARP (Address Resolution Protocol) YANG data model.";
  }

  feature global-static-table {
    description
      "This feature indicates that the device allows static entries
       to be configured globally.";
  }

  container arp {
    description
      "Address Resolution Protocol (ARP) management, which includes
        static ARP configuration, dynamic ARP learning, ARP entry
        query, and packet statistics collection.";
    container global-static-table {
      if-feature "global-static-table";
      description
        "Set a global static ARP entry, which is independent of the interface.";
      list static-entry {
        key "ip-address";
        description
          "List of ARP static entries that can be configured globally.";
        leaf ip-address {
          type inet:ipv4-address-no-zone;
          description
            "IP address, in dotted decimal notation.";
        }
        leaf mac-address {
          type yang:mac-address;
          mandatory true;
          description
            "MAC address in the format of H-H-H, in which H is
                        a hexadecimal number of 1 to 4 bits.";
        }
      }
    }
    container statistics {
      config false;
      description
        "List of ARP packet statistics.";
      leaf in-requests-pkts {
        type uint64;
        description
          "Total ARP requests received";
      }
      leaf in-replies-pkts {
        type uint64;
        description
          "Total ARP replies received";
      }
      leaf in-gratuitous-pkts {
        type uint64;
        description
          "Total gratuitous ARP received";
      }
      leaf out-requests-pkts {
        type uint64;
        description
          "Total ARP requests sent";
      }
      leaf out-replies-pkts {
        type uint64;
        description
          "Total ARP replies sent";
      }
      leaf out-gratuitous-pkts {
        type uint64;
        description
          "Total gratuitous ARP sent";
      }
      leaf in-drops {
        type uint64 {
          range "0..4294967294";
        }
        description
          "Number of ARP packets discarded.";
      }
      leaf in-total {
        type uint64 {
          range "0..4294967294";
        }
        description
          "Total number of ARP received packets.";
      }
      leaf out-total {
        type uint64 {
          range "0..4294967294";
        }
        description
          "Total number of ARP sent packets.";
      }
      leaf all-dynamic-pkts {
        type uint64 {
          range "0..4294967294";
        }
        description
          "Number of dynamic ARP packets count.";
      }
      leaf all-static-pkts {
        type uint64 {
          range "0..4294967294";
        }
        description
          "Number of static ARP packets count.";
      }
    }
  }
}
