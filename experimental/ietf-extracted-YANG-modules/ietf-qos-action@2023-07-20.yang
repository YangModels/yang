module ietf-qos-action {
  yang-version 1.1;
  namespace "urn:ietf:params:xml:ns:yang:ietf-qos-action";
  prefix qos-action;

  import ietf-inet-types {
    prefix inet;
    reference
      "RFC 6991: Common YANG Data Types";
  }
  import iana-qos-types {
    prefix qos-types;
    reference
      "RFC XXXX: YANG Model for QoS";
  }

  organization
    "IETF Routing Area Working Group";

  contact
    "WG Web:   <https://datatracker.ietf.org/wg/rtgwg/>
     WG List:  <mailto:rtgwg@ietf.org>

     Editor:   Aseem Choudhary
               <mailto:achoudhary@aviatrix.com>
     Editor:   Mahesh Jethanandani
               <mailto:mjethanandani@gmail.com>";

  description
    "This module contains a collection of YANG definitions for
     configuring QoS actions.

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2023-07-20 {
    description
      "Initial version";
    reference
      "RFC XXXX: YANG Models for Quality of Service (QoS).";
  }

  grouping rate-value-unit {
    leaf value {
      type uint64;
      description
        "Value for the rate that is configured, either in
         bits-per-second or percentage.";
    }

    leaf unit {
      type identityref {
        base qos-types:rate-unit-type;
      }
      default qos-types:bits-per-second;
      description
        "The unit for the value above, either in bits-per-second or
         percentage.";
    }
    description
      "Grouping for configuration of value and unit.";
  }

  grouping meter-action {
    description
      "Configuration of meter actions.";

    leaf action-type {
      type identityref {
        base qos-types:meter-action-type;
      }
      description
        "Action type for metering.";
    }

    leaf dscp-mark {
      type inet:dscp;
      must "../action-type = 'qos-types:action-mark'" {
        error-message
          "DSCP must be marked when action-type is action-mark.";
      }
      description
        "DSCP marking";
    }
    leaf traffic-group-mark {
      type string;
      must "../action-type = 'qos-types:action-mark'" {
        error-message
          "Traffic-group must be marked when action-type is
           action-mark.";
      }
      description
        "A unique name to mark as a traffic group.";
    }
  }

  grouping single-rate-two-color-meter {
    container single-rate-two-color-meter {
      description
        "A container for Basic Single Rate Two Color Marker.";

      leaf committed-information-rate {
        type uint64;
        units "bytes-per-second";
        description
          "The value for Committed Information Rate (CIR).";
      }

      leaf committed-burst-size {
        type uint64;
        units "bytes";
        description
          "The value for Committed Burst Size (CBS).";
      }

      container conform-action {
        uses meter-action;
        description
          "A packet is marked conforming, or green if it does not
           exceed CIR.";
      }

      container exceed-action {
        uses meter-action;
        description
          "A packet is marked exceeding, or yellow if it does
           exceed CIR.";
      }
    }
    description
      "A Basic Single Rate Two Color Meter.";
  }
  grouping single-rate-three-color-meter {
    container single-rate-three-color-meter {
      description
        "Container that defines the Single Rate Three Color Meter
         (srTCM).";

      leaf committed-information-rate {
        type uint64;
        units "bytes-per-second";
        description
          "The value for Committed Information Rate (CIR).";
        reference
          "RFC 2697: A Single Rate Three Color Marker.";
      }

      leaf committed-burst-size {
        type uint64;
        units "bytes";
        description
          "The value for Committed Burst Size (CBS).";
        reference
          "RFC 2697: A Single Rate Three Color Marker.";
      }

      leaf excess-burst-size {
        type uint64;
        units "bytes";
        description
          "The value for Excess Burst Size (EBS).";
        reference
          "RFC 2697: A Single Rate Three Color Marker.";
      }

      container conform-action {
        uses meter-action;
        description
          "A packet is marked conforming, or green if it does not
           exceed CBS.";
        reference
          "RFC 2697: A Single Rate Three Color Marker.";
      }

      container exceed-action {
        uses meter-action;
        description
          "A packet is marked exceeding, or yellow if it does
           exceed CBS, but not the EBS.";
        reference
          "RFC 2697: A Single Rate Three Color Marker.";
      }

      container violate-action {
        uses meter-action;
        description
          "A packet is marked violating, or red if it is exceeds
           both CBS and EBS.";
        reference
          "RFC 2697: A Single Rate Three Color Marker.";
      }
    }
    description
      "Singe Rate Three Color Meter (srTCM).";
    reference
      "RFC 2697: A Single Rate Three Color Marker.";
  }

  grouping two-rate-three-color-meter {
    container two-rate-three-color-meter {
      description
        "A container that defines A Two Rate Three Color Meter
         (trTCM).";

      leaf committed-information-rate {
        type uint64;
        units "bytes-per-second";
        description
          "The value for Committed Information Rate (CIR).";
        reference
          "RFC 2698: A Two Rate Three Color Marker.";
      }

      leaf committed-burst-size {
        type uint64;
        units "bytes";
        description
          "The value for Committed Burst Size (CBS).";
        reference
          "RFC 2698: A Two Rate Three Color Marker.";
      }

      leaf peak-information-rate {
        type uint64;
        units "bytes-per-second";
        description
          "The value for Peak Information Rate (PIR).";
        reference
          "RFC 2698: A Two Rate Three Color Marker.";
      }

      leaf peak-burst-size {
        type uint64;
        units "bytes";
        description
          "The value for Peak Burst Size (PBS).";
        reference
          "RFC 2698: A Two Rate Three Color Marker.";
      }

      container conform-action {
        uses meter-action;
        description
          "A packet is marked conforming, or green, if it does not
           exceed CIR.";
        reference
          "RFC 2698: A Two Rate Three Color Marker.";
      }

      container exceed-action {
        uses meter-action;
        description
          "A packet is marked exceeding, or yellow, if it exceeds
           CIR but not PIR.";
        reference
          "RFC 2698: A Two Rate Three Color Marker.";
      }

      container violate-action {
        uses meter-action;
        description
          "A packet is marked as violating, or red, if it exceeds
           both CIR and PIR.";
        reference
          "RFC 2698: A Two Rate Three Color Marker.";
      }
    }
    description
      "Container for a Two Rate Three Color Marker.";
  }

  grouping meter {
    choice meter-types {
      case single-rate-two-color-meter-type {
        uses single-rate-two-color-meter;
      }
      case single-rate-three-color-meter-type {
        uses single-rate-three-color-meter;
      }

      case two-rate-three-color-meter-type {
        uses two-rate-three-color-meter;
      }
      description
        "A meter action based on choice of meter action type.";
    }
    description
      "Meter attributes.";
  }

  container meters {
    description
      "List of meter templates.";

    list meter {
      key "name";
      description
        "Meter entry template.";

      leaf name {
        type string;
        description
          "A unique string to identify the meter.";
      }
      uses meter;
    }
  }

  grouping meter-reference {
    container meter {
      leaf name {
        type string ;
        mandatory true;
        description
          "This leaf defines name of the meter referenced.";
      }

      leaf type {
        type identityref {
          base qos-types:meter-type;
        }
        mandatory true;
        description
          "This leaf defines type of the meter.";
      }
      description
        "The name and type for meter reference.";
    }
    description
      "Grouping to define meter reference.";
  }

  grouping count {
    container count {
    if-feature qos-types:count;

      leaf count-action {
        type empty;
        description
          "Take an action if this is defined.";
      }
      description
        "Container for whether to take an action for count.";
    }
    description
      "The count action grouping.";
  }

  grouping named-counter {
    container named-counter {
    if-feature qos-types:named-counter;
      leaf count-name-action {
        type string;
        description
          "A unique name for named counter.";
      }
      description
        "The named counter action.";
    }
    description
      "The named counter action grouping.";
  }

  grouping discard {
    container discard {
      leaf discard {
        type empty;
        description
          "If defined this enables discard action.";
      }
      description
        "Container for discard action.";
    }
    description
      "Grouping for discard action.";
  }

  grouping priority {
    container priority {
      leaf level {
        type uint8;
        description
          "Priority level.";
      }
      description
        "Container for priority.";
    }
    description
      "Grouping for priority.";
  }

  grouping min-rate {
    container min-rate {
      uses rate-value-unit;
      description
        "Minimum guaranteed bandwidth.";
    }
    description
      "Grouping for minimum rate.";
  }

  grouping dscp-marking {
    container dscp {
      leaf dscp {
        type inet:dscp;
        description
          "DSCP marking.";
      }
      description
        "Container for DSCP marking.";
    }
    description
      "Grouping for DSCP marking.";
  }

  grouping traffic-group-marking {
    container traffic-group {
      leaf traffic-group {
        type string;
        description
          "A unique name for traffic group.";
      }
      description
        "Container for traffic group marking container.";
    }
    description
      "Grouping for traffic group marking.";
  }

  grouping child-policy {
    container child-policy {
      if-feature qos-types:child-policy;
      leaf name {
        type string;
        description
          "A unique name for hierarchical policy.";
      }
      description
        "Hierarchical Policy configuration container.";
    }
    description
      "Grouping of Hierarchical Policy configuration.";
  }

  grouping max-rate {
    container max-rate {
      uses rate-value-unit;

      leaf burst-value {
        type uint64;
        description
          "Burst value in bytes.";
      }

      leaf burst-unit {
        type identityref {
          base qos-types:burst-unit-type;
        }
        default qos-types:bytes;
        description
          "Burst value in bytes or milliseconds, with a default
           of bytes.";
      }
      description
        "Maximum rate attributes container.";
    }
    description
      "Grouping for maximum rate attributes.";
  }

  grouping red-config-parameters {
    leaf min-threshold-val {
      type uint64;
      description
        "Minimum value of RED threshold.";
    }

    leaf min-threshold-unit {
      type identityref {
        base qos-types:red-threshold-unit;
      }
      default qos-types:red-threshold-bytes;
      description
        "The unit for minimum RED threshold value, with the default
         of bytes.";
    }

    leaf max-threshold-val {
      type uint64;
      description
        "Maximum value of RED threshold.";
    }

    leaf max-threshold-unit {
      type identityref {
        base qos-types:red-threshold-unit;
      }
      default qos-types:red-threshold-bytes;
      description
        "The unit for maximum RED threshold value, with the default
         of bytes.";
    }

    leaf weight {
      type uint8;
      description
        "The decay factor for the average queue size
         calculation. The numbers is a 2's exponent.";
    }

    leaf max-probability-val {
      type uint64;
      description
        "Value of maximum probability value. This value need
         be interpreted along with max-probability-unit";
    }
    leaf max-probability-unit {
      type identityref {
        base qos-types:probability-unit;
      }
      default qos-types:probability-pc;
      description
       "Probability unit type, with a default of percentage.";
    }
    description
      "Random Early Detect (RED) configuration parameters.";
  }

  grouping queue {
    container queue {
      uses priority;
      uses min-rate;
      uses max-rate;
      container algorithmic-drop {
        choice drop-algorithm {
          case tail-drop {
            container tail-drop {
              leaf tail-drop {
                type empty;
                description
                  "When defined, tail drop algorithm is enabled.";
              }
              description
                "Tail Drop configuration container.";
            }
            description
              "Tail Drop choice.";
          }

          case red {
            container red {
              uses red-config-parameters;
              leaf ecn-enabled {
                type boolean;
                default "false";
                description
                  "ECN is enabled on the queue.";
              }
              description
                "Random Early Detect (RED) configuration.";
            }
          }

          case wred {
            container wred {
              list wred {
                key "profile";

                leaf profile {
                  type uint8;
                  description
                    "Profile id of each WRED profile.";
                }

                leaf color-type {
                  type identityref {
                    base qos-types:wred-color-type;
                  }
                  default qos-types:wred-color-dscp;
                  description
                    "WRED color-type of each profile.";
                }

                list color-val {
                  key "min max";

                  leaf min {
                    type uint8;
                    description
                      "Minimum value of color types.";
                  }

                  leaf max {
                    type uint8;
                    description
                      "Maximum value of color types.";
                  }
                  description
                    "List of color markings which constitute
                     a traffic profile.";
                }
                uses red-config-parameters;
                description
                  "List of RED profiles each with its own
                   threshold values.";
              }

              leaf ecn-enabled {
                type boolean;
                default "false";
                description
                  "ECN is enabled on the queue.";
              }
              description
                "Weighted Random Early Detect (WRED) configuration.";
            }
          }
          description
            "Choice of Drop Algorithm.";
        }
        description
          "Algorithmic Drop configuration container.";
      }
      description
        "Queue configuration container.";
    }
    description
      "Queue grouping.";
  }

  container queues {
    description
      "List of queue templates.";

    list queue {
      key "name";
      description
        "Queue entry template.";

      leaf name {
        type string;
        description
          "A unique name identifying this queue template";
      }
      uses queue;
    }
  }

  grouping queue-reference {
    container queue-reference {
      leaf queue-name {
        type string;
        mandatory true;
        description
          "This leaf defines name of the  queue template
           referenced.";
      }
      description
        "Queue template reference.";
    }
    description
      "Queue template reference grouping.";
  }

  grouping scheduler {
    container scheduler {
      uses min-rate;
      uses max-rate;
      description
        "Scheduler configuration container.";
    }
    description
      "Scheduler configuration grouping.";
  }
}
