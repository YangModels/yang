module ietf-network-inventory-topology {
  yang-version 1.1;
  namespace
    "urn:ietf:params:xml:ns:yang:ietf-network-inventory-topology";
  prefix nwit;

  import ietf-network {
    prefix nw;
    reference
      "RFC 8345: A YANG Data Model for Network Topologies,
                 Section 4.1";
  }
  import ietf-network-topology {
    prefix nt;
    reference
      "RFC 8345: A YANG Data Model for Network Topologies,
                 Section 4.2";
  }
  import ietf-network-inventory {
    prefix nwi;
    reference
      "RFC AAAA: A YANG Data Model for Network Inventory";
  }

  organization
    "IETF Network Inventory YANG (ivy) Working Group";
  contact
    "WG Web:   <https://datatracker.ietf.org/wg/ivy>
     WG List:  IVY <mailto:inventory-yang@ietf.org>

     Editor: Bo Wu
             <lana.wubo@huawei.com>
     Editor: Mohamed Boucadair
             <mohamed.boucadair@orange.com>
     Author: Cheng Zhou
             <zhouchengyjy@chinamobile.com>
     Author: Qin Wu
             <bill.wu@huawei.com>";
  description
    "This YANG module defines a YANG module for network
     topology and inventory mapping.

     Copyright (c) 2026 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-02-28 {
    description
      "Initial revision.";
    reference
      "RFC XXXX: A Network Data Model for Inventory Topology
                 Mapping";
  }

  // Groupings
  // Node Grouping with 1:1 mapping to NE

  grouping node-inventory-mapping-attributes {
    description
      "Attributes for mapping a topology node to a Network Element
       (NE) in the physical inventory.";
    container inventory-mapping-attributes {
      description
        "Container for inventory mapping attributes of a node.";
      leaf ne-ref {
        type nwi:ne-ref;
        description
          "Reference to the NE in the inventory that corresponds to
           this topology node.

           This reference establishes a 1:1 mapping between the
           logical node and its physical NE.";
      }
    }
  }

  // TP Grouping with 1:1 mapping to physical port

  grouping tp-inventory-mapping-attributes {
    description
      "Attributes for mapping a topology termination point (TP)
       to a physical port in the network inventory.";
    container inventory-mapping-attributes {
      description
        "Container for inventory mapping attributes of a TP.";
      uses nwi:port-ref {
        refine "port-ref" {
          description
            "Reference to the physical port component in the
             network inventory. This reference establishes a 1:1
             mapping between the logical TP and its physical port
             component.";
        }
      }
      // breakout channels (lightweight, per physical port)
      container port-breakout {
        presence "Indicates the port supports channel breakout.";
        config false;
        description
          "Breakout capability of the physical port represented by
           this TP. One TP maps to one physical port; channels are
           listed here. This container is present only when the
           underlying hardware supports partitioning the port into
           multiple independent channels (e.g., 400G to 4x100G).";
        list breakout-channel {
          key "channel-id";
          description
            "List of breakout channels available on this port.
             Each entry represents an independent lane or sub-port
             that can be used for channelized interfaces.";
          leaf channel-id {
            type uint16;
            description
              "Unique identifier for the breakout channel within the
               scope of the parent port.";
          }
        } // breakout-channel
      } // port-breakout
    }
  }

  // Link Grouping  with placeholder for future augumentation

  grouping link-inventory-mapping-attributes {
    description
      "Attributes for classifying link media type.
       Detailed inventory reference is intentionally omitted from
       this model; implementations should use the appropriate
       specialized inventory modules based on the indicated
       link-type.";
    container inventory-mapping-attributes {
      description
        "Container for inventory-related attributes of a link.

         This container provides lightweight media classification.
         The link-type indicates which specialized inventory model
         contains detailed resource information:

         - Wired media (fiber, copper): passive network inventory
         - Wireless media (microwave, Wi-Fi): wireless-specific
           inventory

           Detailed inventory references may be added in future
           modules.";
      leaf link-type {
        type string;
        description
          "Classification of the link media type at the topology
           layer. Example values include 'copper', 'fiber',
           'microwave', or 'wifi'.";
      }
    }
  }

  // Main blocks

  augment "/nw:networks/nw:network/nw:node" {
    description
      "Augments the network topology node with inventory mapping
       attributes. This enables correlation between the logical node
       and its physical network element.";
    uses node-inventory-mapping-attributes;
  }

  augment "/nw:networks/nw:network/nt:link" {
    description
      "Augments the network topology link with inventory-related
       attributes.";
    uses link-inventory-mapping-attributes;
  }

  augment "/nw:networks/nw:network/nw:node/nt:termination-point" {
    description
      "Augments the TP with inventory mapping attributes for
       physical port correlation and breakout capability reporting.";
    uses tp-inventory-mapping-attributes;
  }
}
