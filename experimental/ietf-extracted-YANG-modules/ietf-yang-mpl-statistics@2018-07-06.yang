module ietf-yang-mpl-statistics {

  yang-version 1.1;

  namespace
      "urn:ietf:params:xml:ns:yang:ietf-yang-mpl-statistics";

  prefix "mplst";

  import ietf-yang-mpl-domain{
     prefix "mpl";
  }

  organization
    "IETF ROLL (Routing over Low power and lossy networks)
     Working Group";

  contact
    "WG Web:   http://tools.ietf.org/wg/roll/
     WG List:  mailto:roll@ietf.org

     WG Chair: Peter van der Stok
               mailto:consultancy@vanderstok.org

     WG Chair: Ines Robles
               mailto:maria.ines.robles@ericsson.com

     Editor:   Peter van der Stok
               mailto:consultancy@vanderstok.org";

  description
    "This module contains information about the operation
     of the MPL protocol.

     Copyright (c) 2018 IETF Trust and the persons identified as
     authors of the code.  All rights reserved.

     Redistribution and use in source and binary forms, with or

     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

revision "2018-07-06" {
      description "revision 3";
      reference
        "I-D:draft-ietf-roll-mpl-yang: A YANG model for Multicast
 Protocol for Low power and lossy Networks (MPL)";
    }

 augment "/mpl:domain" {
       description "additional MPL message statistics to MPL
       domains";

     list mpl-statistics{
     key "seedID domainID";

     config false;

     description
        "List describes performance statistics integrated over
         the messages identified by seed and domain identifiers.
         A forwarder can receive and forward multiple copies of
         a message uniquely identified by seqno, domain, and
         seed.";

      leaf seedID{
         type uint64;
         description
            "value uniquely identifies the MPL Seed within a MPL
             domain.";
      }

      leaf domainID{
         type uint16;
         description
            "together with seed-ID uniquely identifies buffer
             set.";
      }

      leaf c-too-high {
         type uint64;
         description
            "Number of times that a copy was not forwarded
             because c > k.";
      }

      leaf nr-forwarded {
         type uint64;
         description
            "number of times copies are forwarded,
             while c <= k.";
      }

      leaf nr-of-messages-received{
         type uint64;
         description
            "number of messages received,
             must be smaller than or equal to seqno.";
      }

         leaf nr-of-messages-forwarded{
         type uint64;
         description
            "number of forwarded messages, must be smaller
             than or equal to nr-of-messages-received.";
      }

      leaf nr-of-copies-received{
         type uint64;
         description
            "total number of message copies received.";
      }

      leaf nr-of-copies-forwarded{
         type uint64;
         description
            "number of forwarded copies, can be larger than
             number-of-copies-received.";
      }
      leaf nr-of-refused-copies{
         type uint64;
         description
            "number of refused copies because seqno too small.";
      }

      leaf nr-of-missed-messages{
         type uint64;
         description
            "number of messages that were not received
             because seqno < min-seqno.";
      }

      leaf nr-of-notreceived-messages{
         type uint64;
         description
            "number of messages that were not received
             according to control message.";
      }

      leaf nr-of-inconsistent-data{
         type uint64;
         description
            "number of inconsistent data messages.";
      }

      leaf nr-of-consistent-data{
         type uint64;
         description
            "number of consistent data messages.";
      }

      leaf nr-of-consistent-control{
         type uint64;
         description
            "number of consistent control messages.";
      }

      leaf nr-of-inconsistent-control{
         type uint64;
         description
            "number of inconsistent control messages.";
      }

      leaf statistics-interval{
         type uint64;
         description
            "Interval, expressed in seconds, during which
             the statistics are collected.";
      }

      action reset-buffer-statistics{
         description
            "set all statistics counters and
             statistics-interval of buffer[seedID domainID}
             to zero.";
      }

   }  // list mpl statistics

   action reset-all-statistics{
      description
         "set all statistics counters and
          statistics-interval of all buffers to zero.";
   }

  }  //  augment
} // module  ietf-yang-mpl-statistics
