module ietf-i2nsf-capability {
  namespace
    "urn:ietf:params:xml:ns:yang:ietf-i2nsf-capability";
  prefix
    i2nsf-capability;

  import ietf-inet-types{
    prefix inet;
  }

  organization
    "IETF I2NSF (Interface to Network Security Functions)
     Working Group";

  contact
    "WG Web: <http://tools.ietf.org/wg/i2nsf>
     WG List: <mailto:i2nsf@ietf.org>

     WG Chair: Adrian Farrel
     <mailto:Adrain@olddog.co.uk>

     WG Chair: Linda Dunbar
     <mailto:Linda.duhbar@huawei.com>

     Editor: Susan Hares
     <mailto:shares@ndzh.com>

     Editor: Jaehoon Paul Jeong
     <mailto:pauljeong@skku.edu>

     Editor: Jinyong Tim Kim
     <mailto:timkim@skku.edu>";

  description
    "This module describes a capability model
    for I2NSF devices.";

  revision "2017-07-03"{
    description "The second revision";
    reference
      "draft-xibassnez-i2nsf-capability-01
       draft-hares-i2nsf-capability-data-model-02";
  }

  container sec-ctl-capabilities {
    description
      "sec-ctl-capabilities";
  }

  grouping i2nsf-nsf-location {
    description
      "This provides a location for capabilities.";
    container nsf-address {
      description
       "This is location information for capabilities.";
      choice nsf-address-type {
        description
          "nsf address type: ipv4 and ipv4";
        case ipv4-address {
          description
            "ipv4 case";
          leaf ipv4-address {
            type inet:ipv4-address;
            mandatory true;
            description
              "nsf address type is ipv4";
          }
        }
        case ipv6-address {
          description
            "ipv6 case";
          leaf ipv6-address {
            type inet:ipv6-address;
            mandatory true;
            description
              "nsf address type is ipv6";
          }
        }
      }
    }
  }

  grouping i2nsf-it-resources {
    description
      "This provides a link between capabilities
       and IT resources. This has a list of IT resources
       by name.";
    list it-resources {
      key "it-resource-id";
      description
        "it-resource";
      leaf it-resource-id {
        type uint64;
        mandatory true;
        description
          "it-resource-id";
      }
      leaf it-resource-name {
        type string;
        mandatory true;
        description
          "it-resource-name";
      }
    }
  }

  grouping capabilities-information {
    description
      "This includes information of capabilities.";
    uses i2nsf-nsf-location;
    uses i2nsf-it-resources;
  }

  grouping i2nsf-net-sec-control-caps {
    description
      "i2nsf-net-sec-control-caps";
    container network-security-control {
      description
        "i2nsf-net-sec-control-caps";
      leaf nsc-support {
        type boolean;
        mandatory true;
        description
          "nsc-support";
      }
      list nsc-fcn {
        key "nsc-fcn-name";
        description
          "nsc-fcn";
        leaf nsc-fcn-name {
          type string;
          mandatory true;
          description
            "nsc-fcn-name";
        }
        uses capabilities-information;
      }
    }
  }

  grouping i2nsf-con-sec-control-caps {
    description
      "i2nsf-con-sec-control-caps";

    container content-security-control {
      description
        "content-security-control";

      container antivirus {
        description
          "antivirus";

        leaf antivirus-support {
          type boolean;
          mandatory true;
          description
            "antivirus-support";
        }
        list antivirus-fcn-name {
          key "antivirus-fcn-name";
          description
            "antivirus-fcn-name";

          leaf antivirus-fcn-name {
            type string;
            mandatory true;
            description
              "antivirus-fcn-name";
          }
          uses capabilities-information;
        }
      }

      container ips {
        description
          "ips";

        leaf ips-support {
          type boolean;
          mandatory true;
          description
            "ips-support";
        }
        list ips-fcn {
          key "ips-fcn-name";
          description
            "ips-fcn";

          leaf ips-fcn-name {
            type string;
            mandatory true;
            description
              "ips-fcn-name";
          }
          uses capabilities-information;
        }
      }

      container ids {
        description
          "ids";

        leaf ids-support {
          type boolean;
          mandatory true;
          description
            "ids-support";
        }
        list ids-fcn {
          key "ids-fcn-name";
          description
            "ids-fcn";

          leaf ids-fcn-name {
            type string;
            mandatory true;
            description
              "ids-fcn-name";
          }
          uses capabilities-information;
        }
      }

      container url-filter {
        description
          "url-filter";

        leaf url-filter-support {
          type boolean;
          mandatory true;
          description
            "url-filter-support";
        }
        list url-filter-fcn {
          key "url-filter-fcn-name";
          description
            "url-filter-fcn";

          leaf url-filter-fcn-name {
            type string;
            mandatory true;
            description
              "url-filter-fcn-name";
          }
          uses capabilities-information;
        }
      }

      container data-filter {
        description
          "data-filter";

        leaf data-filter-support {
          type boolean;
          mandatory true;
          description
            "data-filter-support";
        }
        list data-filter-fcn {
          key "data-filter-fcn-name";
          description
            "data-filter-fcn";

          leaf data-filter-fcn-name {
            type string;
            mandatory true;
            description
              "data-filter-fcn-name";
          }
          uses capabilities-information;
        }
      }

      container mail-filter {
        description
          "mail-filter";

        leaf mail-filter-support {
          type boolean;
          mandatory true;
          description
            "mail-filter-support";
        }
        list mail-filter-fcn {
          key "mail-filter-fcn-name";
          description
            "mail-filter-fcn";

          leaf mail-filter-fcn-name {
            type string;
            mandatory true;
            description
              "mail-filter-fcn-name";
          }
          uses capabilities-information;
        }
      }

      container dns-filter {
        description
          "dns-filter";

        leaf dns-filter-support {
          type boolean;
          mandatory true;
          description
            "dns-filter-support";
        }
        list dns-filter-fcn {
          key "dns-filter-fcn-name";
          description
            "dns-filter-fcn";

          leaf dns-filter-fcn-name {
            type string;
            mandatory true;
            description
              "dns-filter-fcn-name";
          }
          uses capabilities-information;
        }
      }

      container ftp-filter {
        description
          "ftp-filter";

        leaf ftp-filter-support {
          type boolean;
          mandatory true;
          description
            "ftp-filter-support";
        }
        list ftp-filter-fcn {
          key "ftp-filter-fcn-name";
          description
            "ftp-filter-fcn";

          leaf ftp-filter-fcn-name {
            type string;
            mandatory true;
            description
              "ftp-filter-fcn-name";
          }
          uses capabilities-information;
        }
      }

      container games-filter {
        description
          "games-filter";

        leaf games-filter-support {
          type boolean;
          mandatory true;
          description
            "games-filter-support";
        }
        list games-filter-fcn {
          key "games-filter-fcn-name";
          description
            "games-filter-fcn";

          leaf games-filter-fcn-name {
            type string;
            mandatory true;
            description
              "games-filter-fcn-name";
          }
          uses capabilities-information;
        }
      }

      container p2p-filter {
        description
          "p2p-filter";

        leaf p2p-filter-support {
          type boolean;
          mandatory true;
          description
            "p2p-filter-support";
        }
        list p2p-filter-fcn {
          key "p2p-filter-fcn-name";
          description
            "p2p-filter-fcn";

          leaf p2p-filter-fcn-name {
            type string;
            mandatory true;
            description
              "p2p-filter-fcn-name";
          }
          uses capabilities-information;
        }
      }

      container rpc-filter {
        description
          "rpc-filter";

        leaf rpc-filter-support {
          type boolean;
          mandatory true;
          description
            "rpc-filter-support";
        }
        list rpc-filter-fcn {
          key "rpc-filter-fcn-name";
          description
            "rpc-filter-fcn";

          leaf rpc-filter-fcn-name {
            type string;
            mandatory true;
            description
              "rpc-filter-fcn-name";
          }
          uses capabilities-information;
        }
      }

      container sql-filter {
        description
          "sql-filter";

        leaf sql-filter-support {
          type boolean;
          mandatory true;
          description
            "sql-filter-support";
        }
        list sql-filter-fcn {
          key "sql-filter-fcn-name";
          description
            "sql-filter-fcn";

          leaf sql-filter-fcn-name {
            type string;
            mandatory true;
            description
              "sql-filter-fcn-name";
          }
          uses capabilities-information;
        }
      }

      container telent-filter {
        description
          "telent-filter";

        leaf telent-filter-support {
          type boolean;
          mandatory true;
          description
            "telent-filter-support";
        }
        list telent-filter-fcn {
          key "telent-filter-fcn-name";
          description
            "telent-filter-fcn";

          leaf telent-filter-fcn-name {
            type string;
            mandatory true;
            description
              "telent-filter-fcn-name";
          }
          uses capabilities-information;
        }
      }

      container tftp-filter {
        description
          "tftp-filter";

        leaf tftp-filter-support {
          type boolean;
          mandatory true;
          description
            "tftp-filter-support";
        }
        list tftp-filter-fcn {
          key "tftp-filter-fcn-name";
          description
            "tftp-filter-fcn";

          leaf tftp-filter-fcn-name {
            type string;
            mandatory true;
            description
              "tftp-filter-fcn-name";
          }
          uses capabilities-information;
        }
      }

      container file-blocking {
        description
          "file-blocking";
        leaf file-blocking-support {
          type boolean;
          mandatory true;
          description
            "file-blocking-support";
        }
        list file-blocking-fcn {
          key "file-blocking-fcn-name";
          description
            "file-blocking-fcn";

          leaf file-blocking-fcn-name {
            type string;
            mandatory true;
            description
              "file-blocking-fcn-name";
          }
          uses capabilities-information;
        }
      }

      container file-isolate {
        description
          "file-isolate";

        leaf file-isolate-support {
          type boolean;
          mandatory true;
          description
            "file-isolate-support";
        }
        list file-isolate-fcn {
          key "file-isolate-fcn-name";
          description
            "file-isolate-fcn";

          leaf file-isolate-fcn-name {
            type string;
            mandatory true;
            description
              "file-isolate-fcn-name";
          }
          uses capabilities-information;
        }
      }

      container pkt-capture {
        description
          "pkt-capture";

        leaf pkt-capture-support {
          type boolean;
          mandatory true;
          description
            "pkt-capture-support";
        }
        list pkt-capture-fcn {
          key "pkt-capture-fcn-name";
          description
            "pkt-capture-fcn";

          leaf pkt-capture-fcn-name {
            type string;
            mandatory true;
            description
              "pkt-capture-fcn-name";
          }
          uses capabilities-information;
        }
      }

      container app-control {
        description
          "app-control";

        leaf app-control-support {
          type boolean;
          mandatory true;
          description
            "app-control-support";
        }
        list app-control-fcn {
          key "app-control-fcn-name";
          description
            "app-control-fcn";

          leaf app-control-fcn-name {
            type string;
            mandatory true;
            description
              "app-control-fcn-name";
          }
          uses capabilities-information;
        }
      }

      container voip-volte {
        description
          "voip-volte";

        leaf voip-volte-support {
          type boolean;
          mandatory true;
          description
            "voip-volte-support";
        }
        list voip-volte-fcn {
          key "voip-volte-fcn-name";
          description
            "voip-volte-fcn";

          leaf voip-volte-fcn-name {
            type string;
            mandatory true;
            description
              "voip-volte-fcn-name";
          }
          uses capabilities-information;
        }
      }
    }
  }

  grouping i2nsf-attack-mitigation-control-caps {
    description
      "i2nsf-attack-mitigation-control-caps";

    container attack-mitigation-control {
      description
        "attack-mitigation-control";
      choice attack-mitigation-control-type {
        description
          "attack-mitigation-control-type";
        case ddos-attack {
          description
            "ddos-attack";
          choice ddos-attack-type {
            description
              "ddos-attack-type";
            case network-layer-ddos-attack {
              description
                "network-layer-ddos-attack";
              container network-layer-ddos-attack-types {
                description
                  "network-layer-ddos-attack-type";
                container syn-flood-attack {
                  description
                    "syn-flood-attack";
                  leaf syn-flood-attack-support {
                    type boolean;
                    mandatory true;
                    description
                      "syn-flood-attack-support";
                  }
                  list syn-flood-fcn {
                    key "syn-flood-fcn-name";
                    description
                      "syn-flood-fcn";
                    leaf syn-flood-fcn-name {
                      type string;
                      mandatory true;
                      description
                        "syn-flood-fcn-name";
                    }
                    uses capabilities-information;
                  }
                }
                container udp-flood-attack {
                  description
                    "udp-flood-attack";
                  leaf udp-flood-attack-support {
                    type boolean;
                    mandatory true;
                    description
                      "udp-flood-attack-support";
                  }
                  list udp-flood-fcn {
                    key "udp-flood-fcn-name";
                    description
                      "udp-flood-fcn";
                    leaf udp-flood-fcn-name {
                      type string;
                      mandatory true;
                      description
                        "udp-flood-fcn-name";
                    }
                    uses capabilities-information;
                  }
                }
                container icmp-flood-attack {
                  description
                    "icmp-flood-attack";
                  leaf icmp-flood-attack-support {
                    type boolean;
                    mandatory true;
                    description
                      "icmp-flood-attack-support";
                  }
                  list icmp-flood-fcn {
                    key "icmp-flood-fcn-name";
                    description
                      "icmp-flood-fcn";
                    leaf icmp-flood-fcn-name {
                      type string;
                      mandatory true;
                      description
                        "icmp-flood-fcn-name";
                    }
                    uses capabilities-information;
                  }
                }
                container ip-fragment-flood-attack {
                  description
                    "ip-fragment-flood-attack";
                  leaf ip-fragment-flood-attack-support {
                    type boolean;
                    mandatory true;
                    description
                      "ip-fragment-flood-attack-support";
                  }
                  list frag-flood-fcn {
                    key "ip-frag-flood-fcn-name";
                    description
                      "frag-flood-fcn";
                    leaf ip-frag-flood-fcn-name {
                      type string;
                      mandatory true;
                      description
                        "ip-frag-flood-fcn-name";
                    }
                    uses capabilities-information;
                  }
                }
                container ipv6-related-attack {
                  description
                    "ipv6-related-attack";
                  leaf ipv6-related-attack-support {
                    type boolean;
                    mandatory true;
                    description
                      "ipv6-related-attack-support";
                  }
                  list ipv6-related-fcn {
                    key "ipv6-related-fcn-name";
                    description
                      "ipv6-related-fcn";
                    leaf ipv6-related-fcn-name {
                      type string;
                      mandatory true;
                      description
                        "ipv6-related-fcn-name";
                    }
                    uses capabilities-information;
                  }
                }
              }
            }
            case app-layer-ddos-attack {
              description
                "app-layer-ddos-attack";
              container app-layer-ddos-attack-types {
                description
                  "app-layer-ddos-attack-types";
                container http-flood-attack {
                  description
                    "http-flood-attack";
                  leaf http-flood-attack-support {
                    type boolean;
                    mandatory true;
                    description
                      "http-flood-attack-support";
                  }
                  list http-flood-fcn {
                    key "http-flood-fcn-name";
                    description
                      "http-flood-fcn";
                    leaf http-flood-fcn-name {
                      type string;
                      mandatory true;
                      description
                        "http-flood-fcn-name";
                    }
                    uses capabilities-information;
                  }
                }
                container https-flood-attack {
                  description
                    "https-flood-attack";
                  leaf https-flood-attack-support {
                    type boolean;
                    mandatory true;
                    description
                      "https-flood-attack-support";
                  }
                  list https-flood-fcn {
                    key "https-flood-fcn-name";
                    description
                      "https-flood-fcn";
                    leaf https-flood-fcn-name {
                      type string;
                      mandatory true;
                      description
                        "https-flood-fcn-name";
                    }
                    uses capabilities-information;
                  }
                }
                container dns-flood-attack {
                  description
                    "dns-flood-attack";
                  leaf dns-flood-attack-support {
                    type boolean;
                    mandatory true;
                    description
                      "dns-flood-attack-support";
                  }
                  list dns-flood-fcn {
                    key "dns-flood-fcn-name";
                    description
                      "dns-flood-fcn";
                    leaf dns-flood-fcn-name {
                      type string;
                      mandatory true;
                      description
                        "dns-flood-fcn-name";
                    }
                    uses capabilities-information;
                  }
                }
                container dns-amp-flood-attack {
                  description
                    "dns-amp-flood-attack";
                  leaf dns-flood-attack-support {
                    type boolean;
                    mandatory true;
                    description
                      "dns-flood-attack-support";
                  }
                  list dns-amp-flood-fcn {
                    key "dns-amp-flood-fcn-name";
                    description
                      "dns-amp-flood-fcn";
                    leaf dns-amp-flood-fcn-name {
                      type string;
                      mandatory true;
                      description
                        "dns-amp-flood-fcn-name";
                    }
                    uses capabilities-information;
                  }
                }
                container ssl-ddos-attack {
                  description
                    "ssl-ddos-attack";
                  leaf ssl-ddos-attack-support {
                    type boolean;
                    mandatory true;
                    description
                      "ssl-ddos-attack-support";
                  }
                  list ssl-ddos-fcn {
                    key "ssl-ddos-fcn-name";
                    description
                      "ssl-ddos-fcn";
                    leaf ssl-ddos-fcn-name {
                      type string;
                      mandatory true;
                      description
                        "ssl-ddos-fcn-name";
                    }
                    uses capabilities-information;
                  }
                }
              }
            }
          }
        }

        case single-packet-attack {
          description
            "single-packet-attack";
          choice single-packet-attack-type {
            description
              "single-packet-attack-type";
            case scan-and-sniff-attack {
              description
                "scan-and-sniff-attack";
              container ip-sweep-attack {
                description
                  "ip-sweep-attack";
                leaf ip-sweep-attack-suppor {
                  type boolean;
                  mandatory true;
                  description
                    "ip-sweep-attack-suppor";
                }
                list ip-sweep-fcn {
                  key "ip-sweep-fcn-name";
                  description
                    "ip-sweep-fcn";
                  leaf ip-sweep-fcn-name {
                    type string;
                    mandatory true;
                    description
                      "ip-sweep-fcn-name";
                  }
                  uses capabilities-information;
                }
              }
              container port-scanning-attack {
                description
                  "port-scanning-attack";
                leaf port-scanning-attack-support {
                  type boolean;
                  mandatory true;
                  description
                    "port-scanning-attack-support";
                  }
                list port-scanning-fcn {
                  key "port-scanning-fcn-name";
                  description
                    "port-scanning-fcn";
                  leaf port-scanning-fcn-name {
                    type string;
                    mandatory true;
                    description
                      "port-scanning-fcn-name";
                  }
                  uses capabilities-information;
                }
              }
            }
            case malformed-packet-attack {
              description
                "malformed-packet-attack";
              container ping-of-death-attack {
                description
                  "ping-of-death-attack";
                leaf ping-of-death-attack-support {
                  type boolean;
                  mandatory true;
                  description
                    "ping-of-death-attack-support";
                }
                list ping-of-death-fcn {
                  key "ping-of-death-fcn-name";
                  description
                    "ping-of-death-fcn";
                  leaf ping-of-death-fcn-name {
                    type string;
                    mandatory true;
                    description
                      "ping-of-death-fcn-name";
                  }
                  uses capabilities-information;
                }
              }
              container teardrop-attack {
                description
                  "teardrop-attack";
                leaf teardrop-attack-support {
                  type boolean;
                  mandatory true;
                  description
                    "teardrop-attack-support";
                }
                list tear-drop-fcn {
                  key "tear-drop-fcn-name";
                  description
                    "tear-drop-fcn";
                  leaf tear-drop-fcn-name {
                    type string;
                    mandatory true;
                    description
                      "tear-drop-fcn-name";
                  }
                  uses capabilities-information;
                }
              }
            }
            case special-packet-attack {
              description
                "special-packet-attack";
              container oversized-icmp-attack {
                description
                  "oversized-icmp-attack";
                leaf oversized-icmp-attack-support {
                  type boolean;
                  mandatory true;
                  description
                    "oversized-icmp-attack-support";
                }
                list oversized-icmp-fcn {
                  key "oversized-icmp-fcn-name";
                  description
                    "oversized-icmp-fcn";
                  leaf oversized-icmp-fcn-name {
                    type string;
                    mandatory true;
                    description
                      "oversized-icmp-fcn-name";
                  }
                  uses capabilities-information;
                }
              }
              container tracert-attack {
                description
                  "tracert-attack";
                leaf tracert-attack-support {
                  type boolean;
                  mandatory true;
                  description
                    "tracert-attack-support";
                }
                list tracert-fcn {
                  key "tracert-fcn-name";
                  description
                    "tracert-fcn";
                  leaf tracert-fcn-name {
                    type string;
                    mandatory true;
                    description
                      "tracert-fcn-name";
                  }
                  uses capabilities-information;
                }
              }
            }
          }
        }
      }
    }
  }

  list nsf-capabilities {
    key "nsf-capabilities-id";
    description
      "nsf-capabilities";
    leaf nsf-capabilities-id {
      type uint8;
      mandatory true;
      description
        "nsf-capabilities-id";
    }

      container net-sec-control-capabilities {
        uses i2nsf-net-sec-control-caps;
        description
          "net-sec-control-capabilities";
      }
      container con-sec-control-capabilities {
        uses i2nsf-con-sec-control-caps;
        description
          "con-sec-control-capabilities";
      }
      container attack-mitigation-capabilities {
        uses i2nsf-attack-mitigation-control-caps;
        description
          "attack-mitigation-capabilities";
      }
  }
}
