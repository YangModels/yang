module ietf-lmo-support-case-management {
  yang-version 1.1;
  namespace "urn:ietf:params:xml:ns:yang:ietf-lmo-support-case-management";
  prefix lmoscm;

  import ietf-yang-types {
    prefix yang;
  }
  import ietf-lmo-common {
    prefix lmocom;
  }
  import ietf-lmo-assets-inventory {
    prefix lmoasset;
  }

  organization
    "IETF OPSA (Operations and Management Area) Working Group";
  contact
    "WG Web:   <https://datatracker.ietf.org/wg/opsawg/>
     WG List:  <mailto:opsawg@ietf.org>
     Editor:  Marisol Palmero
              <mailto:mpalmero@cisco.com>
     Editor:  Josh Suhr
              <mailto:josuhr@cisco.com>
     Editor:  Sudhendu Kumar
              <mailto:skumar23@ncsu.edu>";
  description
    "This YANG module includes the support case management attributes
     to handle incidents.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.";
  revision 2021-08-23 {
    description
      "Initial revision for Support Case Management as part of
       the LMO YANG Model";
    reference
      "RFC XXXX: LMO YANG Model";
  }

  container tracking-number {
    config false;
    description
      "Support Tracking Support Management Case Number";
    list tracking-number {
      key "id";
      description
        "Support Tracking Support Management Case Number List,
        internal to Developer, ie. INCxxxxx";
      leaf id {
        type string;
        description
          "Technical Support Center Case Number id";
      }
      leaf title {
        type string;
        description
          "headline Support Case";
      }
      leaf summary {
        type string;
        description
          "Problem description summary";
      }
      leaf severity {
        type string;
        description
        "severity, in some cases also defined as priority";
        // NEED to define different levels of severity, from
        // severity 1 to 6, i.e. Sev1: network down, Sev6: enhacement
      }
      leaf status {
        type string;
        description
        "case status, i.e. Customer-Pending, Customer
        Engineer-Pending, Developer-Pending, Closed, Open, etc.";
        // NEED to define different status
      }
      leaf created {
        type yang:date-and-time;
        description
        "created date-and-time";
      }
      leaf last_updated {
        type yang:date-and-time;
        description
        "last updated date-and-time";
      }
      leaf capability {
        type string;
        description
        "i.e. to reveal associated RMA items";
      }
      leaf technology{
        type string;
        description
        "Technology related";
      }
      leaf subtechnology{
        type string;
        description
        "Subtechnology related";
      }
      leaf problem-type{
        type string;
        description
        "Problem type definition, i.e. network, faulty hardware,
        performance, security, etc. ";
      }
      leaf resolution{
        type string;
        description
        "code (closed cases only)";
      }
      leaf owner{
        type string;
        description
        "Customer in charge of the case";
      // NEED to add contact information: email and phone number
      }
      leaf support-engineer{
        type string;
        description
        "Customer Support Engineer in charge of the case";
      // NEED to add contact information: email and phone number
      }
      leaf asset {
        type leafref {
          path "/lmoasset:assets/lmoasset:asset/lmoasset:id";
        }
        description
        "Asset to which this support case is attached";
      }
      leaf serial-number {
        type leafref {
            path "/lmoasset:assets/lmoasset:asset/lmoasset:serial-number";
        }
        description
          "Serial-number to which this support case is attached";
      }
      leaf software-version {
        type leafref {
          path "/lmoasset:assets/lmoasset:asset/lmoasset:software-version";
        }
        description
        "Software version running in the asset to which this support
        case is attached";
      }
      leaf contract-number {
        type string;
        description
        "Support contract number";
      // NEED to evaluate if it should be independent container. It
      // should be associated to asset and license
      }
    }
  }
}
