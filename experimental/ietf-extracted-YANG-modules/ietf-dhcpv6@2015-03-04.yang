module ietf-dhcpv6 {
    namespace "urn:ietf:params:xml:ns:yang:dhcpv6";
    prefix "dhcpv6";

        import ietf-inet-types { prefix inet; revision-date "2013-07-15"; }
    import ietf-yang-types { prefix yang; revision-date "2013-07-15"; }

        organization "dhc wg";
    contact "yong@csnet1.cs.tsinghua.edu.cn
                 wangh13@mails.tsinghua.edu.cn
                         lh.sunlinh@gmail.com
                         ";

        description "This model defines a YANG data model that can be used to configure
        and manage DHCPv6 server, DHCPv6 relay and DHCPv6 client.";

    revision 2015-03-04 {
        description "Initial revision.";
    }

/*
 * Data Nodes
 */

    container dhcpv6-server {
        description "";
        grouping bindinginfo {
            description "";
            list bindinginfo {
                config "false";
                description "A list records a binding information for each DHCPv6 client that
                    has already been allocated IPv6 addresses.";
                key cliduid;
                leaf cliduid {
                    description "";
                    type uint32;
                }
                list cliia {
                    description "";
                    key iaid;
                    leaf iaid {
                        description "";
                        type uint8;
                    }
                    leaf iatype {
                        description "";
                        type string;
                    }
                    leaf-list cliaddr {
                        description "";
                        type inet:ipv6-address;
                    }
                    leaf pool-name {
                        description "";
                        type string;
                    }
                }
            }
        }
        container servattributes {
            description "This container contains basic attributes of a DHCPv6 server
                such as DUID, server name and so on. Some optional functions that
                can be provided by the server is also included.";
            leaf duid {
                description "Each server and client has only one DUID (DHCP Unique Identifier).
                    The DUID here identifies a unique DHCPv6 server for clients.";
                type uint32;
            }
            leaf enable {
                description "";
                type boolean;
            }
            leaf name {
                description "";
                type string;
            }
            leaf description {
                description "";
                type string;
            }
            leaf pd-function {
                description "Whether the server can act as a delegating router to perform
                    prefix delegation ([RFC3633]).";
                type boolean;
            }
            leaf two-step-interaction {
                description "A boolean value specifies whether the server support client-server
                    exchanges involving two messages defined in ([RFC3315]).";
                type boolean;
            }
            leaf rapidcommit {
                description "A boolean value specifies whether the server support client-server
                    exchanges involving two messages defined in ([RFC3315]).";
                type boolean;
            }
        }
        container address-pools {
            description "A container describes the DHCPv6 server's address pools.";
            list address-pool {
                description "A DHCPv6 server can be configured with several address pools.
                    This list defines such address pools which are distinguish by
                    the key called 'pool-name'.";
                key pool-name;
                leaf pool-name {
                    description "";
                    type string;
                }
                leaf pool-prefix {
                    description "";
                    type inet:ipv6-prefix;
                }
                leaf start-address {
                    description "";
                    type inet:ipv6-address-no-zone;
                }
                leaf end-address {
                    description "";
                    type inet:ipv6-address-no-zone;
                }
                leaf preferred-lifetime {
                    description "";
                    type yang:timeticks;
                }
                leaf valid-lifetime {
                    description "";
                    type yang:timeticks;
                }
                leaf used-ipv6-count {
                    config "false";
                    description "";
                    type uint32;
                }
                leaf idle-ipv6-count {
                    config "false";
                    description "";
                    type uint32;
                }
            }
            uses bindinginfo;

        }
        container prefix-pools {
            description "If a server supports prefix delegation function, this container
                will be used to define the delegating router's refix pools.";
            list prefix-pool {
                description "Similar to server's address pools, a delegating router can also
                    be configured with multiple prefix pools specified by a list called
                                        'prefix-pool'.";
                key pool-name;
                leaf pool-name {
                    description "";
                    type string;
                }
                leaf  prefix {
                    description "";
                    type inet:ipv6-prefix;
                }
                leaf prefix-length {
                    description "";
                    type uint8;
                }
                leaf preferred-lifetime {
                    description "";
                    type yang:timeticks;
                }
                leaf valid-lifetime {
                    description "";
                    type yang:timeticks;
                }
            }
            uses bindinginfo;
        }
        container otherparas {
            description "This container defines extra configuration parameters provided
                by the DHCPv6 server apart from the address and prefix information.
                Such parameters may include DNS servers, SIP servers, SNTP servers,
                etc.";
            list dnsserver {
                description "";
                key dnsname;
                leaf dnsname {
                    description "";
                    type string;
                }
                leaf dnsservaddr {
                    description "";
                    type inet:ipv6-address;
                }
            }
            leaf domainsearchlist {
                description "";
                type string;
            }
            list sipserver {
                description "";
                key sipservdomainname;
                leaf sipserverdomainname {
                    description "";
                    type string;
                }
                leaf sipservaddr {
                    description "";
                    type inet:ipv6-address;
                }
            }
            list sntpserver {
                description "";
                key sntpservname;
                leaf sntpservname {
                    description "";
                    type string;
                }
                leaf sntpservaddr {
                    description "";
                    type inet:ipv6-address;
                }
            }
            list ntpservparas {
                description "";
                key ntpname;
                leaf ntpname {
                    description "";
                    type string;
                }
                leaf ntpservaddr {
                    description "";
                    type inet:ipv6-address;
                }
                leaf ntpservmuladdr {
                    description "";
                    type inet:ipv6-address;
                }
                leaf ntpservfqdn {
                    description "";
                    type string;
                }
            }
            container nisparas {
                description "";
                leaf nisservaddr {
                    description "";
                    type inet:ipv6-address;
                }
                list niscli {
                    description "";
                    key cliduid;
                    leaf cliduid {
                        description "";
                        type uint32;
                    }
                    leaf clidomainname {
                        description "";
                        type string;
                    }
                }
            }
            container nispparas {
                description "";
                leaf nispservaddr {
                    description "";
                    type inet:ipv6-address;
                }
                list nispcli {
                    description "";
                    key cliduid;
                    leaf cliduid {
                        description "";
                        type uint32;
                    }
                    leaf clidomainname {
                        description "";
                        type string;
                    }
                }
            }

        }
        container relayopaqueparas {
            description "This container contains some opaque values in Relay Agent options
                that need to be configured on the server side only for value match.
                Such Relay Agent options include Interface-Id option, Remote-Id
                option and Subscriber-Id option.";
            list relaysif {
                description "";
                key ifname;
                leaf ifname {
                    description "";
                    type string;
                }
                leaf interface-id {
                    description "";
                    type string;
                }
                list subscribers {
                    description "";
                    key subscribername;
                    leaf subscribername {
                        description "";
                        type string;
                    }
                    leaf subscribernameid {
                        description "";
                        type string;
                    }
                }
                list remotehost {
                    description "";
                    key entnum;
                    leaf entnum {
                        description "";
                        type uint8;
                    }
                    leaf remote-id {
                        description "";
                        type string;
                    }
                }
            }
        }
        container packetstats {
            config "false";
            description "A container presents the packet statistics related to the DHCPv6
                server.";
            leaf solicit-count {
                description "";
                type uint32;
            }
            leaf request-count {
                description "";
                type uint32;
            }
            leaf renew-count {
                description "";
                type uint32;
            }
            leaf rebind-count {
                description "";
                type uint32;
            }
            leaf decline-count {
                description "";
                type uint32;
            }
            leaf release-count {
                description "";
                type uint32;
            }
            leaf inforeq-count {
                description "";
                type uint32;
            }
            leaf advertise-count {
                description "";
                type uint32;
            }
            leaf confirm-count {
                description "";
                type uint32;
            }
            leaf reply-count {
                description "";
                type uint32;
            }
            leaf reconfigure-count {
                description "";
                type uint32;
            }
            leaf relay-forward-count {
                description "";
                type uint32;
            }
            leaf relay-reply-count {
                description "";
                type uint32;
            }
        }

    }
    container dhcpv6-relay {
        description "";
        container relayinterfaces {
            description "It is a container that defines common configuration and state
                parameters in the interfaces of a DHCPv6 relay agent. In this
                YANG data model for DHCPv6 relay agent, the parameters are configured
                in a per-interface manner.";
            list relayif {
                description "A list describes a specific interface and its corresponding parameters.
                    Here we use a string called 'ifName' as the key of list.";
                key ifname;
                leaf ifname {
                    description "";
                    type string;
                }
                leaf enable {
                    description "";
                    type boolean;
                }
                leaf interface-id {
                    description "";
                    type string;
                }
                list subscribers {
                    description "";
                    key subscribername;
                    leaf subscribername {
                        description "";
                        type string;
                    }
                    leaf subscriber-id {
                        description "";
                        type string;
                    }
                }
                list remotehost {
                    description "";
                    key entnum;
                    leaf entnum {
                        description "";
                        type uint8;
                    }
                    leaf remote-id {
                        description "";
                        type string;
                    }
                }
                leaf-list destaddrs {
                    description "Each DHCPv6 relay agent may be configured with a list of destination
                        addresses. This node defines such a list of IPv6 addresses that
                        may include unicast addresses, multicast addresses or other addresses.";
                    type inet:ipv6-address;
                }
                list nextentity {
                    description "This node defines a list that is used to describe the next hop
                        entity of this relay distinguished by their addresses.";
                    key destaddr;
                    leaf destaddr {

                        type inet:ipv6-address;
                    }
                    leaf available {
                        description "";
                        type boolean;
                    }
                    leaf multicast {
                        description "";
                        type boolean;
                    }
                    leaf server {
                        description "";
                        type boolean;
                    }
                }
                container packetstats {
                    config "false";
                    description "A container shows packet state information of a specific interface.
                        It is a sub-container of the 'relayInterfaces' container.";
                    leaf clipacketrvd-count {
                        description "";
                        type uint32;
                    }
                    leaf solicitrvd-count {
                        description "";
                        type uint32;
                    }
                    leaf requestrvd-count {
                        description "";
                        type uint32;
                    }
                    leaf renewrvd-count {
                        description "";
                        type uint32;
                    }
                    leaf rebindrvd-count {
                        description "";
                        type uint32;
                    }
                    leaf declinervd-count {
                        description "";
                        type uint32;
                    }
                    leaf releaservd-count {
                        description "";
                        type uint32;
                    }
                    leaf inforeqrvd-count {
                        description "";
                        type uint32;
                    }
                    leaf servpacketrvd-count {
                        description "";
                        type uint32;
                    }
                    leaf advertiservd-count {
                        description "";
                        type uint32;
                    }
                    leaf confirmrvd-count {
                        description "";
                        type uint32;
                    }
                    leaf replyrvd-count {
                        description "";
                        type uint32;
                    }
                    leaf reconfigurervd-count {
                        description "";
                        type uint32;
                    }
                    leaf relayforvd-count {
                        description "";
                        type uint32;
                    }
                    leaf relayreprvd-count {
                        description "";
                        type uint32;
                    }
                    leaf packettocli-count {
                        description "";
                        type uint32;
                    }
                    leaf advertisesent-count {
                        description "";
                        type uint32;
                    }
                    leaf confirmsent-count {
                        description "";
                        type uint32;
                    }
                    leaf replysent-count {
                        description "";
                        type uint32;
                    }
                    leaf reconfiguresent-count {
                        description "";
                        type uint32;
                    }
                    leaf packettoserv-count {
                        description "";
                        type uint32;
                    }
                    leaf solicitsent-count {
                        description "";
                        type uint32;
                    }
                    leaf requestsent-count {
                        description "";
                        type uint32;
                    }
                    leaf renewsent-count {
                        description "";
                        type uint32;
                    }
                    leaf rebindsent-count {
                        description "";
                        type uint32;
                    }
                    leaf declinesent-count {
                        description "";
                        type uint32;
                    }
                    leaf releasesent-count {
                        description "";
                        type uint32;
                    }
                    leaf inforeqsent-count {
                        description "";
                        type uint32;
                    }
                    leaf relayforsent-count {
                        description "";
                        type uint32;
                    }
                    leaf relayrepsent-count {
                        description "";
                        type uint32;
                    }
                }

            }
        }
        container relaystats {
            config "false";
            description "The container records and presents the overall packet statistics
                of the relay agent.";
            leaf clipacketrvd-count {
                description "";
                type uint32;
            }
            leaf serpacketrvd-count {
                description "";
                type uint32;
            }
            leaf relayforrvd-count {
                description "";
                type uint32;
            }
            leaf relayreprvd-count {
                description "";
                type uint32;
            }
            leaf discardedpacket-count {
                description "";
                type uint32;
            }
            leaf packettocli-count {
                description "";
                type uint32;
            }
            leaf packettoserv-count {
                description "";
                type uint32;
            }
            leaf packettorelay-count {
                description "";
                type uint32;
            }
        }
    }
    container dhcpv6-client {
        description "";
        container clientinterfaces {
            description "A client may have several interfaces, it is more reasonable to
                configure and manage parameters on the interface-level. This container
                includes configuration and state data of a DHCPv6 client in a
                per-interface manner.";
            list clientif {
                description "The list defines a specific client interface and its data. Different
                    interfaces are distinguished by the key which is a configurable string
                        value.";
                key ifname;
                leaf ifname {
                    description "";
                    type string;
                }
                leaf duid {
                    description "Each server and client has only one DUID (DHCP Unique Identifier).
                        The DUID here will be carried in the Client ID option to identify
                        a specific DHCPv6 client.";
                    type uint32;
                }
                leaf enable {
                    description "";
                    type boolean;
                }
                leaf clifqdn {
                    description "A DHCPv6 server needs to know the Fully Qualified Domain Name
                        (FQDN) of the client to achieve the DNS update.";
                    type string;
                }
                leaf pd-function {
                    description "Whether the client can act as a requesting router to request
                        prefixes using prefix delegation ([RFC3633]).";
                    type boolean;
                }
                leaf rapidcommit {
                    description "'1' indicates a client can initiate a Solicit-Reply message exchange
                        by adding a Rapid Commit option in Solicit message. '0' means
                        the client is not allowed to add a Rapid Commit option to request
                        addresses in a two-message exchange pattern.";
                    type boolean;
                }
                leaf dual-stack {
                    description "";
                    type boolean;
                }
                container mo-tab {
                    config "false";
                    description "The management tab label indicates the operation mode of the
                        DHCPv6 client. 'm'=1 and 'o'=1 indicate the client will use DHCPv6
                        to obtain all the configuration data. 'm'=1 and 'o'=0 are a meaningless
                        combination. 'm'=0 and 'o'=1 indicate the client will use stateless
                        DHCPv6 to obtain configuration data apart from addresses/prefixes
                        data. 'm'=0 and 'o'=0 represent the client will not use DHCPv6
                        but use SLAAC to achieve configuration.";
                    leaf m-tab {
                        description "";
                        type boolean;
                    }
                    leaf o-tab {
                        description "";
                        type boolean;
                    }
                }
                container identity-associations {
                    config "false";
                    description "IA is a construct through which a server and a client can identify,
                        group, and manage a set of related IPv6 addresses. The key of
                        the list is a 4-byte number IAID defined in [RFC3315] .";
                    list identity-association {
                        description "";
                        key iaid;
                        leaf iaid {
                            description "";
                            type uint8;
                        }
                        leaf iatype {
                            description "";
                            type string;
                        }
                        leaf-list ipv6addr {
                            description "";
                            type inet:ipv6-address;
                        }
                        leaf-list ipv6prefix {
                            description "";
                            type inet:ipv6-prefix;
                        }
                        leaf-list prefix-length {
                            description "";
                            type uint8;
                        }
                        leaf t1-time {
                            description "";
                            type yang:date-and-time;
                        }
                        leaf t2-time {
                            description "";
                            type yang:date-and-time;
                        }
                        leaf preferred-lifetime {
                            description "";
                            type yang:timeticks;
                        }
                        leaf valid-lifetime {
                            description "";
                            type yang:timeticks;
                        }
                    }
                }
                container ifotherparas {
                    config "false";
                    description "A client can obtain extra configuration data other than address
                        and prefix information through DHCPv6. This container describes
                        such data the client was configured. The potential configuration
                        data may include DNS server addresses, SIP server domain names, etc.";
                    leaf-list dnsservaddr {
                        description "";
                        type inet:ipv6-address;
                    }
                    leaf domainsearchlist {
                        description "";
                        type string;
                    }
                    leaf-list sipservaddr {
                        description "";
                        type inet:ipv6-address;
                    }
                    leaf sipservdomainnamelist {
                        description "";
                        type string;
                    }
                    leaf unidhcpv6servaddr {
                        description "";
                        type inet:ipv6-address;
                    }
                    leaf-list sntpservaddr {
                        description "";
                        type inet:ipv6-address;
                    }
                    container ntpservparas {
                        description "";
                        leaf ntpservaddr {
                            description "";
                            type inet:ipv6-address;
                        }
                        leaf ntpservmuladdr {
                            description "";
                            type inet:ipv6-address;
                        }
                        leaf ntpservfqdn {
                            description "";
                            type string;
                        }
                    }
                    container nisparas {
                        description "";
                        leaf nisservaddr {
                            description "";
                            type inet:ipv6-address;
                        }
                        leaf nisclidomainname {
                            description "";
                            type string;
                        }
                    }
                    container nispparas {
                        description "";
                        leaf nispservaddr {
                            description "";
                            type inet:ipv6-address;
                        }
                        leaf nispclidomainname {
                            description "";
                            type string;
                        }
                    }
                }
                container packetstats {
                    config "false";
                    description "A container records all the packet status information of a specific
                        interface.";
                    leaf solicit-count {
                        description "";
                        type uint32;
                    }
                    leaf request-count {
                        description "";
                        type uint32;
                    }
                    leaf renew-count {
                        description "";
                        type uint32;
                    }
                    leaf rebind-count {
                        description "";
                        type uint32;
                    }
                    leaf decline-count {
                        description "";
                        type uint32;
                    }
                    leaf release-count {
                        description "";
                        type uint32;
                    }
                    leaf inforeq-count {
                        description "";
                        type uint32;
                    }
                    leaf advertise-count {
                        description "";
                        type uint32;
                    }
                    leaf confirm-count {
                        description "";
                        type uint32;
                    }
                    leaf reply-count {
                        description "";
                        type uint32;
                    }
                    leaf reconfigure-count {
                        description "";
                        type uint32;
                    }
                }
            }
        }
    }
}
