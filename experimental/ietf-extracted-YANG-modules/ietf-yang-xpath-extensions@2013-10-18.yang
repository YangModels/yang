module ietf-yang-xpath-extensions {

  namespace "urn:ietf:params:xml:ns:yang:ietf-yang-xpath-extensions";
  prefix "yangxp";

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Martin Bjorklund
               <mailto:mbj@tail-f.com>";

  description
    "This module contains a collection of YANG extensions
     for defining XPath functions to be used in XPath
     expressions in YANG modules and NETCONF filters.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.
  // RFC Ed.: update the date below with the date of RFC publication
  // and remove this note.
  revision 2013-10-18 {
    description
      "Initial revision.";
    reference
      "RFC XXXX: YANG XPath Extensions";
  }

  /*
   * Extensions
   */

  extension xpath-function {
    argument name;
    description
      "This statement introduces an XPath function that can be
       used in 'must' and 'when' XPath expression in YANG modules,
       and in NETCONF filters.

       The statement's argument specifies the name of the XPath
       function.

       When the function is used in a YANG module, the module where
       the function is defined MUST be imported.  The function is
       referred to using the syntax '<prefix>:<name>', where <prefix>
       is the prefix of the module, and <name> is the name of the
       XPath function.

       The following substatements are used:

         +-----------------------+-------------+
         | substatement          | cardinality |
         +-----------------------+-------------+
         | yangxp:xpath-argument | 0..n        |
         | yangxp:xpath-result   | 1           |
         | description           | 0..1        |
         | reference             | 0..1        |
         +-----------------------+-------------+

       The yangxp:xpath-argument statement defines the arguments to
       the XPath function.  The functions takes the arguments in the
       order they are defined in the YANG module.";
  }

  extension xpath-argument {
    argument name;
    description
      "This statement defines an argument to an XPath function.

       The statement's argument specifies the name of the XPath
       function's argument.  The mandatory substatement
       yangxp:xpath-type defines the type of the argument.

       The following substatements are used:

         +-----------------------+-------------+
         | substatement          | cardinality |
         +-----------------------+-------------+
         | yangxp:xpath-type     | 1           |
         +-----------------------+-------------+";
  }

  extension xpath-type {
    argument type-name;
    description
      "This statement defines the type of the parent statement's
       XPath object.

       The statement's argument is one of the strings:
       'node-set', 'number', 'string', or 'boolean'.";
  }

  extension xpath-result {
    argument type;
    description
      "This statement defines the type of the XPath function's
       return value.

       The statement's argument is one of the strings:
       'node-set', 'number', 'string', or 'boolean'.";
  }

  /*
   * XPath functions
   */

  /* Function for leafref and instance-identifier */

  yangxp:xpath-function deref {
    yangxp:xpath-argument nodes {
      yangxp:xpath-type node-set;
    }
    yangxp:xpath-result node-set;
    description
      "The deref() function follows the reference defined by the
       first node in document order in the argument 'nodes', and
       returns the nodes it refers to.

       If the first argument node is of type instance-identifier,
       the function returns a node-set that contains the single node
       that the instance identifier refers to, if it exists. If no
       such node exists, an empty node-set is returned.

       If the first argument node is of type leafref, the function
       returns a node-set that contains the nodes that the leafref
       refers to.

       If the first argument node is of any other type, an empty
       node-set is returned.";
    reference
      "RFC 6020: YANG, Section 9.9 and Section 9.13.";
  }

  /* Function for identityref */

  yangxp:xpath-function derived-from {
    yangxp:xpath-argument nodes {
      yangxp:xpath-type node-set;
    }
    yangxp:xpath-argument module-name {
      yangxp:xpath-type string;
    }
    yangxp:xpath-argument identity-name {
      yangxp:xpath-type string;
    }
    yangxp:xpath-result boolean;
    description
      "The derived-from() function returns true if the first node in
       document order in the argument 'nodes' is a node of type
       identityref, and its value is an identity that is derived from
       the identity 'identity-name' defined in the YANG
       'module-name'; otherwise it returns false.";
    reference
      "RFC 6020: YANG, Section 9.10.";
  }

  /* Function for enumeration */

  yangxp:xpath-function enum-value {
    yangxp:xpath-argument nodes {
      yangxp:xpath-type node-set;
    }
    yangxp:xpath-result number;
    description
      "The enum-value() function checks if the first node in
       document order in the argument 'nodes' is a node of type
       enumeration, and returns the enum's integer value.  If the
       'nodes' node-set is empty, or if the first node 'nodes' is
       not of type enumeration, it returns NaN.";
    reference
      "RFC 6020: YANG, Section 9.6.4.2.";
  }

  /* Function for bits */

  yangxp:xpath-function bit-is-set {
    yangxp:xpath-argument nodes {
      yangxp:xpath-type node-set;
    }
    yangxp:xpath-argument bit-name {
      yangxp:xpath-type string;
    }
    yangxp:xpath-result boolean;
    description
      "The bit-is-set() function returns true if the first node in
       document order in the argument 'nodes' is a node of type
       bits, and its value has the bit 'bit-name' set; otherwise
       it returns false.";
    reference
      "RFC 6020: YANG, Section 9.7.4.";
  }

  /* String function */

  yangxp:xpath-function re-match {
    yangxp:xpath-argument subject {
      yangxp:xpath-type string;
    }
    yangxp:xpath-argument pattern {
      yangxp:xpath-type string;
    }
    yangxp:xpath-result boolean;
    description
      "The re-match() function returns true if the 'subject' string
       matches the regular expression 'pattern'; otherwise it
       returns false.

       The regular expressions used are the XML Schema regular
       expressions.";

    reference
      "http://www.w3.org/TR/xmlschema-2/#regexs";
  }

}
