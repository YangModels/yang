module draft-extended-example {
  yang-version 1.1;
  namespace "urn:ietf:params:xml:ns:yang:draft-extended-example";
  prefix dr-ext-exp;

  import draft-template {
    prefix dr-tmp;
  }

  organization
    "INSA Lyon";
  contact
    "Editor:   Vivekananda Boudia
     <mailto:vivekananda.boudia@insa-lyon.fr>";
  description
    "add external references to RFC8345";
  revision 2025-03-09 {
    description
      "Initial revision.";
    reference
      "";
  }

  identity AUGMENT-EXAMPLE-TEMPLATE-TYPE {
    base dr-tmp:template-type;
    description
      "augment example for template type";
  }

  identity AUGMENT-EXAMPLE-EXTRA-LABEL {
    base dr-tmp:extra-label;
    description
      "augment example for extra label";
  }

  identity AUGMENT-EXAMPLE-REQUEST-TYPE {
    base dr-tmp:request-type;
    description
      "augment example for request type";
  }

  grouping augment-example-request {
    description
      "augment example for a request";
    leaf foo {
      type string;
      description
        "leaf example";
    }
  }

  augment "/dr-tmp:template/dr-tmp:template/dr-tmp:request/dr-tmp:request-builder" {
    when "derived-from-or-self(../dr-tmp:request-type, 'AUGMENT-EXAMPLE-REQUEST-TYPE')";
    uses augment-example-request;
    description
      "we add our example to the possible request type";
  }
}
