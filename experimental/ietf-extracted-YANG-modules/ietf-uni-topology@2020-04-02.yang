module ietf-uni-topology {
  yang-version 1.1;
  namespace "urn:ietf:params:xml:ns:yang:ietf-uni-topology";
  prefix uni;

  import ietf-interfaces {
    prefix if;
    reference
      "RFC 8343: A YANG Data Model for Interface Management";
  }
  import ietf-network-topology {
    prefix nt;
    reference
      "Section 6.2 of RFC 8345: A YANG Data Model for Network
        Topologies";
  }
  import ietf-network {
    prefix nw;
    reference
      "Section 6.1 of RFC 8345: A YANG Data Model for Network
          Topologies";
  }

  organization
    "IETF OPSA (Operations and Management Area) Working Group ";
  contact
   "   Editor:    Oscar Gonzalez de Dios
                 <mailto:oscar.gonzalezdedios@telefonica.com>
       Editor:   Samier Barguil
                 <mailto:alejandro.aguado_martin@nokia.com>
       Editor:    Qin Wu
                 <mailto:victor.lopezalvarez@telefonica.com>
       Editor:   Mohamed Boucadair
                 <mailto:daniel.voyer@bell.ca>
   ";
  description
    "This YANG module defines a model for representing, managing
     and controlling the User Network Interface (UNI) topology.
     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2020-04-02 {
    description
      "Initial version";
    reference
      "RFC XXXX: A YANG Model for User-Network Interface (UNI)
                 Topologies";
  }

  grouping uni-information-group {
    description
      "User-Network Interface Information";
    list service-attachment-point {
      key "attachment-id";
      description
        "The service attachment points are abstraction of
         the points where network services such as L3 VPNs
         or L2 VPNs can be attached.";
      leaf attachment-id {
        type nt:tp-id;
        description
          "Name of the interface";
      }
      leaf type {
        type identityref {
          base if:interface-type;
        }
        config false;
        description
          "The type of the interface.";
        reference
          "RFC 8343: A YANG Data Model for Interface Management";
      }
      leaf admin-status {
        type boolean;
        description
          "Administrative Status UP/DOWN";
      }
      leaf oper-status {
        type boolean;
        description
          "Operational Status UP/DOWN";
      }
      leaf encapsulation-type {
        type string;
        description
          "Encapsulation type.  By default, the
           encapsulation type is set to 'untagged'.";
      }
    }
  }

  augment "/nw:networks/nw:network/nw:network-types" {
    description
      "Introduces new network type for UNI Unicast topology";
    container uni-topology {
      presence "indicates UNI Unicast topology";
      description
        "The presence of the container node indicates UNI
         topology";
    }
  }

  augment "/nw:networks/nw:network/nw:node" {
    description
      "Parameters for the service edge point level.";
    uses uni-information-group;
  }
}
