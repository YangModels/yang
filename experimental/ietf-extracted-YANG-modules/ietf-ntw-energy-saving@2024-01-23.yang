module ietf-ntw-energy-saving {
  yang-version 1.1;
  namespace "urn:ietf:params:xml:ns:yang:ietf-ntw-energy-saving";
  prefix esm-ntw;

  import ietf-energy-efficiency-common {
    prefix esm-common;
    reference
      "RFC XXXX: YANG Data Models for Energy Saving Management";
  }
  import ietf-network {
    prefix nw;
    reference
      "RFC 8345: A YANG Data Model for Network Topologies";
  }
  import ietf-yang-types {
    prefix yang;
    reference
      "RFC 6991: Common YANG Types";
  }
  import iana-hardware {
   prefix ianahw;
   reference
     "https://www.iana.org/assignments/iana-hardware/iana-hardware.xhtml";
  }
  organization
    "IETF XXX Working Group.";
  contact
    "WG Web:   <https://datatracker.ietf.org/wg/xxx/>;
     WG List:  <mailto:xxxx@ietf.org>

     Author:   Gen Chen
               <mailto:chengen@huawei.com>
     Editor:   Qin Wu
               <mailto:bill.wu@huawei.com>
     Editor:   XXX XXXX
               <mailto:xxx.xxx@orange.com>
     Author:   Carlos Pignataro
               <mailto:cpignata@gmail.com>";
  description
    "This module contains a collection of YANG definitions for power
     and energy management of devices. It also augments both the
     network topology and inventory models.

     Copyright (c) 2024 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2024-01-23 {
    description
      "Initial revision.";
    reference
      "RFC XXXX: YANG Data Models for Energy Saving Management";
  }

  augment "/nw:networks/nw:network/nw:node" {
    if-feature "esm-common:energy-saving";
    description
      "Energy monitoring data for network elements.";
    container energy-power-consumption {
      config false;
      description
        "Statistics data about energy and power monitoring.";
      uses esm-common:energy-power-consumption-stats;
      leaf start-time {
        type yang:date-and-time;
        description
          "The time (in hundredths of a second) since the
          network management portion of the system was last
          re-initialized. It corresponds to the sysUpTime MIB object.
          It specifies the start time of the energy measurement
          results collection.";
      reference
        "RFC 3418:   Management Information Base (MIB) for the
                     Simple Network Management Protocol (SNMP)";
      }
    }
    container energy-saving-modes {
      description
        "List of the energy saving mode.";
      uses esm-common:energy-saving-modes;
    }
    list component {
      key name;
      config false;
      description
      "List of components.";
      leaf name {
        type string;
        description
          "The name assigned to this component.
           This name is not required to be the same as
           entPhysicalName.";
      }
      leaf class {
        type identityref {
          base ianahw:hardware-class;
        }
        mandatory true;
        description
          "An indication of the general hardware type of the
           component.";
        reference
          "RFC 6933: Entity MIB (Version 4) - entPhysicalClass";
        }
      container energy-monitoring {
        description
          "Energy monitoring data for components.";
        container energy-consumption {
          description
          "Statistics of component about energy monitoring.";
          uses esm-common:energy-consumption-data;
        }
       container energy-saving {
        description
        "Controls energy saving parameters of a component.";
         leaf enabled {
          type boolean;
          default "true";
           description
             "Controls whether the energy-saving
             of the component is enabled (when set to true)
              or disabled (set to false).";
         }
         leaf power-state {
          type identityref {
            base esm-common:energy-saving-power-state;
          }
          description
            "The device energy saving operator state.";
         }
       }
     }
   }
  }
}
