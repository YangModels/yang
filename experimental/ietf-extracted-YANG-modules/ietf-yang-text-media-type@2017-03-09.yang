module ietf-yang-text-media-type {

  namespace "urn:ietf:params:xml:ns:yang:ietf-yang-text-media-type";

  prefix ymt;

  ymt:text-media-type "text/markdown; charset=UTF-8";

  organization
    "IETF NETMOD (NETCONF Data Modeling Language) Working Group";

  contact
    "WG Web:   <https://tools.ietf.org/wg/netmod/>
     WG List:  <mailto:netmod@ietf.org>

     WG Chair: Lou Berger
               <mailto:lberger@labn.net>

     WG Chair: Kent Watsen
               <mailto:kwatsen@juniper.net>

     Editor:   Ladislav Lhotka
               <mailto:lhotka@nic.cz>";

  description
    "This module defines the *text-media-type* extension that allows
     for specifying media-type for markup that is used in arguments
     of these YANG statements: contact, description, error-message,
     organization, and reference.

     Copyright (c) 2016 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     The key words 'MUST', 'MUST NOT', 'REQUIRED', 'SHALL', 'SHALL
     NOT', 'SHOULD', 'SHOULD NOT', 'RECOMMENDED', 'MAY', and
     'OPTIONAL' in the module text are to be interpreted as described
     in RFC 2119 (https://tools.ietf.org/html/rfc2119).

     This version of this YANG module is part of RFC XXXX
     (https://tools.ietf.org/html/rfcXXXX); see the RFC itself for
     full legal notices.";

  revision 2017-03-09 {
    description
      "Initial revision.";
    reference
      "RFC XXXX: Using Markup in YANG Text Arguments";
  }

  extension text-media-type {
    argument type;
    description
      "This extension allows for specifying a media type that is used
       for markup in the arguments of the following YANG statements:

       - contact

       - description

       - error-message

       - organization
       - reference

       The *text-media-type* extension statement MAY be used at the
       top level of a module or submodule, i.e., as a substatement of
       *module* or *submodule*, and no more than once. The declared
       media type applies throughout the module or submodule.

       The argument SHOULD be a media type registered by IANA in the
       *text* registry. Media type parameters MAY be present.

       This YANG extension is only indicative and optional to
       implement. Tools MAY ignore it completely or support just a
       subset of markup directives that are available for a given
       media type.";
    reference
      "- IANA: Media Types, 2016-12-21. Available [online]
         (http://www.iana.org/assignments/media-types/media-types.xhtml)

       - [RFC 6838](https://tools.ietf.org/html/rfc6838): Media Type
         Specifications and Registration Procedures";
  }
}
