submodule snmp-target-params {

  belongs-to snmp {
    prefix snmp;
  }

  include snmp-common;
  include snmp-community;
  include snmp-target;

  reference
    "RFC3413: Simple Network Management Protocol (SNMP) Applications
     SNMP-TARGET-MIB";

  revision 2010-10-17 {
    description
      "Initial revision.";
  }

  augment /snmp:snmp/snmp:target {

    /* By including the params directly in the target entry we
       lose some flexibility, but we get a simpler model with less
       cross-references.  In SNMP, two addrEntries can point to the
       same paramsEntry.
    */
    choice params {
      mandatory true;
      reference "SNMP-TARGET-MIB.snmpTargetParamsTable";
      container v1 {
        description "SNMPv1 parameters type";
        // mp-model is v1, sec-level is noAuthNoPriv
        leaf community {
          type leafref {
            path "/snmp/community/index";
          }
          mandatory true;
          reference "SNMP-TARGET-MIB.snmpTargetParamsSecurityName";
        }
      }
      container v2c {
        description "SNMPv2 community parameters type";
        // mp-model is v2c, sec-level is noAuthNoPriv
        leaf community {
          type leafref {
            path "/snmp/community/index";
          }
          mandatory true;
          reference "SNMP-TARGET-MIB.snmpTargetParamsSecurityName";
        }
      }
      container usm {
        description "User based SNMPv3 parameters type";
        // mp-model is v3
        leaf user-name {
          type leafref {
            path "/snmp/usm/local/user/name";
          }
          mandatory true;
          reference "SNMP-TARGET-MIB.snmpTargetParamsSecurityName";
        }
        leaf sec-level {
          type sec-level;
          mandatory true;
          reference "SNMP-TARGET-MIB.snmpTargetParamsSecurityLevel";
        }
      }
    }
  }

}
