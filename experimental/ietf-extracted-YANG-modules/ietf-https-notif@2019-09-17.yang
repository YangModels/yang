module ietf-https-notif {
  yang-version 1.1;
  namespace "urn:ietf:params:xml:ns:yang:ietf-https-notif";
  prefix "hsn";

  import ietf-subscribed-notifications {
    prefix sn;
    reference
      "I-D.ietf-netconf-subscribed-notifications";
  }

  import ietf-tcp-client {
    prefix tcpc;
  }

  import ietf-tls-client {
    prefix tlsc;
  }

  import ietf-http-client {
    prefix httpc;
  }

  organization
    "IETF NETCONF Working Group";

  contact
    "WG Web:   <http://tools.ietf.org/wg/netconf>
     WG List:  <netconf@ietf.org>

     Authors: Mahesh Jethanandani (mjethanandani at gmail dot com)
              Kent Watsen (kent plus ietf at watsen dot net)";
  description
    "YANG module for configuring HTTPS base configuration.

     Copyright (c) 2018 IETF Trust and the persons identified as
     the document authors.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).

     This version of this YANG module is part of RFC XXXX; see
     the RFC itself for full legal notices.";

  revision "2019-09-17" {
    description
      "Initial Version.";
    reference
      "RFC XXXX, YANG Data Module for HTTPS Notifications.";
  }

  identity https {
    base sn:transport;
    description
      "HTTPS transport for notifications.";
  }

  container receivers {
    list receiver {
      key "name";

      leaf name {
        type string;
        description
          "A name that uniquely identifies this receiver.";
      }

      container tcp-params {
        uses tcpc:tcp-client-grouping;
        description
          "TCP client parameters.";
      }

      container tls-params {
        uses tlsc:tls-client-grouping;
        description
          "TLS client parameters.";
      }

      container http-params {
        uses httpc:http-client-grouping;
        description
          "HTTP client parameters.";
      }
      description
        "All receivers interested in this notification.";
    }
    description
      "HTTPS based notifications.";
  }

  augment "/sn:subscriptions/sn:subscription/sn:receivers/sn:receiver" {
    leaf receiver-ref {
      type leafref {
        path "/receivers/receiver/name";
      }
      description
        "Reference to a receiver.";
    }
    description
      "Augment the subscriptions container to define the receiver.";
  }
}
