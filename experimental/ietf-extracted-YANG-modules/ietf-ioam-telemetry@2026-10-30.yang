module ietf-ioam-telemetry {
  yang-version 1.1;
  namespace "urn:ietf:params:xml:ns:yang:ietf-ioam-telemetry";
  prefix "ioam-telemetry";

  import ietf-interfaces {
    prefix if;
    reference
      "RFC 8343: A YANG Data Model for Interface Management";
  }

  import ietf-ioam {
    prefix ioam;
    reference
      "RFC 9617";
  }

  organization
    "IETF BPM (Benchmarking & Performance Measurements) Working Group";

  contact
    "WG Web: <https://datatracker.ietf.org/wg/bpm>
     WG List: <bpm@ietf.org>
     Author: giuseppe.fioccola@huawei.com
     Author: zhoutianran@huawei.com
     Author: zhuyq8@chinatelecom.cn
     Author: zhangwq@chinatelecom.cn
     Author: alex.huang-feng@t-systems.com
     Author: zhukeyi@huawei.com";

  description
    "This YANG module specifies vendor-independent data model
     for IOAM Telemetry.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-10-30 {
    description "First revision.";
    reference "RFC XXXX: YANG Data Models for On-path Telemetry";
  }

 /*
  * FEATURES
  */

  feature pathdelay {
    description
      "This feature indicates that the Path Delay is
       supported.";
    reference
      "RFC 9951: Export of Delay Performance Metrics in IPFIX";
  }

 /*
  * IDENTITIES
  */

  identity trace-data {
    description
      "IOAM trace data as defined in RFC 9197.";
  }

  identity pot-data {
    description
      "IOAM pot data as defined in RFC 9197.";
  }

  identity e2e-data {
    description
      "IOAM edge-to-edge data as defined in RFC 9197.";
  }

 /*
  * TYPE DEFINITIONS
  */

  typedef ioam-trace-data {
    type identityref {
      base trace-data;
    }
    description
      "It specifies the trace data.";
  }

  typedef ioam-pot-data {
    type identityref {
      base pot-data;
    }
    description
      "It specifies the pot data.";
  }
  typedef ioam-e2e-data {
    type identityref {
      base e2e-data;
    }
    description
      "It specifies the edge-to-edge data.";
  }

 /*
  * GROUP DEFINITIONS
  */

  grouping path-delay-metrics {
    description
      "It indicates the path delay measurements.";

    leaf path-delay-mean {
      type uint32;
      units "microseconds";
      config false;
      description
        "mean path delay as per RFC 9951";
    }
    leaf path-delay-min {
      type uint32;
      units "microseconds";
      config false;
      description
        "min path delay as per RFC 9951";
    }

    leaf path-delay-max {
      type uint32;
      units "microseconds";
      config false;
      description
        "max path delay as per RFC 9951";
    }

    leaf path-delay-sum {
      type uint64;
      units "microseconds";
      config false;
      description
        "sum of the path delay as per RFC 9951";
    }
  }

  grouping ioam-incremental-tracing-data-list {
    description
      "A grouping for incremental tracing data.";

    leaf-list incremental-tracing {
      type ioam-trace-data;
      config false;
      description
        "This object indicates the incremental tracing data.";
    }
  }

  grouping ioam-preallocated-tracing-data-list {
    description
      "A grouping for the list of pre-allocated tracing data.";

    leaf-list preallocated-tracing {
      type ioam-trace-data;
      config false;
      description
        "This object indicates the preallocated tracing data.";
    }
  }

  grouping ioam-direct-export-tracing-data-list {
    description
      "A grouping for the list of direct export data.";

    leaf-list direct-export {
      type ioam-trace-data;
      config false;
      description
        "This object indicates the direct export data.";
    }
  }

  grouping ioam-proof-of-transit-data-list {
    description
      "A grouping for the list of proof of transit data.";

    leaf-list proof-of-transit {
      type ioam-pot-data;
      config false;
      description
        "This object indicates the proof of transit data.";
    }
  }

  grouping ioam-edge-to-edge-data-list {
    description
      "A grouping for the list of edge-to-edge data.";

    leaf-list edge-to-edge {
      type ioam-e2e-data;
      config false;
      description
        "This object indicates the edge to edge data.";
    }
  }

 /*
  * DATA NODES
  */

  augment "/ioam:ioam/ioam:profiles/ioam:profile" {
    description "Augments the AltMark with the On-path Telemetry data";

    list available-interface {
      key "if-name";
      description
        "It contains the list of the interfaces activated for
         Telemetry";
      leaf if-name {
        type if:interface-ref;
        description "This is a reference to the Interface name.";
      }

      container ioam-incremental-tracing {
        if-feature ioam:incremental-trace;
        presence
          "Present when incremental tracing option is available.";
        description
          "It reports the incremental tracing option data.";

        uses ioam-incremental-tracing-data-list;
      }

      container ioam-preallocated-tracing {
        if-feature ioam:preallocated-trace;
        presence
          "Present when preallocated tracing option is available.";
        description
          "It reports the preallocated tracing option data.";

        uses ioam-preallocated-tracing-data-list;
      }
      container ioam-direct-export {
        if-feature ioam:direct-export;
        presence
          "Present when direct-export option is available.";
        description
          "It reports the direct-export option data";

        uses ioam-direct-export-tracing-data-list;
      }

      container ioam-proof-of-transit {
        if-feature ioam:proof-of-transit;
        presence
          "Present when proof of transit option is available.";
        description
          "It reports the PoT option data.";

        uses ioam-proof-of-transit-data-list;
      }

      container ioam-edge-to-edge {
        if-feature ioam:edge-to-edge;
        presence
          "Present when edge-to-edge option is available.";
        description
          "It reports the edge-to-edge option data.";

        uses ioam-edge-to-edge-data-list;
      }

      container path-delay-measurement {
        if-feature pathdelay;
        description
          "It reports the path delay measurement data.";

        uses path-delay-metrics;
      }
    }
  }
}
