module ietf-yang-rev-annotations {
  yang-version 1.1;
  namespace "urn:ietf:params:xml:ns:yang:ietf-yang-rev-annotations";
  prefix rev-ext;

  import ietf-yang-revisions {
    prefix rev;
  }

  organization
    "IETF NETMOD (Network Modeling) Working Group";
  contact
    "WG Web:   <https://datatracker.ietf.org/wg/netmod/>
     WG List:  <mailto:netmod@ietf.org>

     Author:   Robert Wilton
               <mailto:rwilton@cisco.com>";

  description
    "This YANG 1.1 module contains extensions to annotation to YANG
     module with additional metadata information on the nature of
     changes between two YANG module revisions.

     XXX, maybe these annotations could also be included in
     ietf-yang-revisions?

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.
  // RFC Ed.: replace XXXX (inc above) with actual RFC number and
  // remove this note.

  revision 2023-03-11 {
    rev:revision-label 1.0.0-draft-ietf-netmod-yang-schema-comparison-02;
    description
      "Draft revision";
    reference
      "XXXX: YANG Schema Comparison";
  }

  extension nbc-change-at {
    argument revision-date-or-label;
    description
      "A node compatibility statement that identifies a revision
      (by revision-label, or revision date if a revision-label is
      not available) where a non-backwards-compatible change has
      occurred in a particular YANG statement relative to the
      previous revision listed in the revision history.

      The format of the revision-label argument MUST conform to the
      pattern defined for the ietf-yang-revisions
      revision-date-or-label typedef.

      The following YANG statements MAY have zero or more
      nbc-change-at substatements:
        - all schema node statements (leaf, rpc, choice, etc)
        - 'feature' statements
        - 'grouping' statements
        - 'identity' statements
        - 'must' statements
        - 'refine' statements
        - 'typedef' statements
        - YANG extensions

      Each YANG statement MUST only a have a single node
      compatibilty statement (one of nbc-change-at, bc-change-at,
      or editorial-change-at) for a particular revision. When a node
      has more than one of the node compatibilty statements (for
      different revisions), they must be ordered from most recent
      to least recent.

      An nbc-change-at statement can have 0 or 1 'description'
      substatements.

      The nbc-change-at statement in not inherited by descendants
      in the schema tree. It only applies to the specific YANG
      statement with which it is associated.
      ";

    reference
      "XXXX: YANG Schema Comparison;
       Section XXX, XXX";

  }

  extension bc-change-at {
    argument revision-date-or-label;
    description
      "A node compatibility statement that identifies a revision
      (by revision-label, or revision date if a revision-label is
      not available) where a backwards-compatible change has
      occurred in a particular YANG statement relative to the
      previous revision listed in the revision history.

      The format of the revision-label argument MUST conform to the
      pattern defined for the ietf-yang-revisions
      revision-date-or-label typedef.

      The following YANG statements MAY have zero or more
      bc-change-at substatements:
        - all schema node statements (leaf, rpc, choice, etc)
        - 'feature' statements
        - 'grouping' statements
        - 'identity' statements
        - 'must' statements
        - 'refine' statements
        - 'typedef' statements
        - YANG extensions

      Each YANG statement MUST only a have a single node
      compatibilty statement (one of nbc-change-at, bc-change-at,
      or editorial-change-at) for a particular revision. When a node
      has more than one of the node compatibilty statements (for
      different revisions), they must be ordered from most recent
      to least recent.

      An bc-change-at statement can have 0 or 1 'description'
      substatements.

      The bc-change-at statement in not inherited by descendants
      in the schema tree. It only applies to the specific YANG
      statement with which it is associated.
      ";

    reference
      "XXXX: YANG Schema Comparison;
       Section XXX, XXX";

  }

  extension editorial-change-at {
    argument revision-date-or-label;
    description
      "A node compatibility statement that identifies a revision
      (by revision-label, or revision date if a revision-label is
      not available) where an editorial change has
      occurred in a particular YANG statement relative to the
      previous revision listed in the revision history.

      The format of the revision-label argument MUST conform to the
      pattern defined for the ietf-yang-revisions
      revision-date-or-label typedef.

      The following YANG statements MAY have zero or more
      editorial-change-at substatements:
        - all schema node statements (leaf, rpc, choice, etc)
        - 'feature' statements
        - 'grouping' statements
        - 'identity' statements
        - 'must' statements
        - 'refine' statements
        - 'typedef' statements
        - YANG extensions

      Each YANG statement MUST only a have a single node
      compatibilty statement (one of nbc-change-at, bc-change-at,
      or editorial-change-at) for a particular revision. When a node
      has more than one of the node compatibilty statements (for
      different revisions), they must be ordered from most recent
      to least recent.

      An editorial-change-at statement can have 0 or 1 'description'
      substatements.

      The editorial-change-at statement in not inherited by descendants
      in the schema tree. It only applies to the specific YANG
      statement with which it is associated.
      ";

    reference
      "XXXX: YANG Schema Comparison;
       Section XXX, XXX";

  }

  extension backwards-compatible {
    argument revision-date-or-label;
    description
      "Identifies a revision (by revision-label, or revision date if
       a revision-label is not available) where a
       backwards-compatible change has occurred relative to the
       previous revision listed in the revision history.

       The format of the revision-label argument MUST conform to the
       pattern defined for the ietf-yang-revisions
       revision-date-or-label typedef.

       The following YANG statements MAY have zero or more
       'rev-ext:non-backwards-compatible' statements:
           description
           must
           when

       Each YANG statement MUST only a have a single
       non-backwards-compatible, backwards-compatible, or editorial
       extension statement for a particular revision-label, or
       corresponding revision-date.";

    reference
      "XXXX: YANG Schema Comparison;
       Section XXX, XXX";
  }

  extension editorial {
    argument revision-date-or-label;
    description
      "Identifies a revision (by revision-label, or revision date if
       a revision-label is not available) where an editorial change
       has occurred relative to the previous revision listed in the
       revision history.

       The format of the revision-label argument MUST conform to the
       pattern defined for the ietf-yang-revisions
       revision-date-or-label typedef.

       The following YANG statements MAY have zero or more
       'rev-ext:non-backwards-compatible' statements:
           description

       Each YANG statement MUST only a have a single
       non-backwards-compatible, backwards-compatible, or editorial
       extension statement for a particular revision-label, or
       corresponding revision-date.";

    reference
      "XXXX: YANG Schema Comparison;
       Section XXX, XXX";
  }

  extension renamed-from {
    argument yang-identifier;
    description
      "Specifies a previous name for this identifier.

       This can be used when comparing schema to optimize handling
       for data nodes that have been renamed rather than naively
       treated them as data nodes that have been deleted and
       recreated.

       The argument 'yang-identifier' MUST take the form of a YANG
       identifier, as defined in section 6.2 of RFC 7950.

       Any YANG statement that takes a YANG identifier as its
       argument MAY have a single 'rev-ext:renamed-from'
       sub-statement.

       TODO, we should also facilitate identifiers being moved into
       other modules, e.g. by supporting a module-name qualified
       identifier.";

    reference
      "XXXX: YANG Schema Comparison;
       Section XXX, XXX";
  }
}
