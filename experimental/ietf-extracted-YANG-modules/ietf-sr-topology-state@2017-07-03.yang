module ietf-sr-topology-state {
  yang-version 1.1;
  namespace "urn:ietf:params:xml:ns:yang:ietf-sr-topology-state";
  prefix "srt-s";

  import ietf-sr-topology {
    prefix "srt";
  }
  import ietf-network-state {
    prefix "nd-s";
  }
  import ietf-network-topology-state {
    prefix "lnk-s";
  }
  import ietf-l3-unicast-topology-state {
    prefix "l3t-s";
  }
  import ietf-segment-routing-common {
    prefix "sr-cmn";
  }

  organization "TBD";
  contact "TBD";
  description "L3 TE Topology model";
  revision 2017-07-03 {
    description "Initial revision";
    reference "TBD";
  }

  augment "/nd-s:networks/nd-s:network/nd-s:network-types/"
    + "l3t-s:l3-unicast-topology" {
    description
      "Defines the SR topology type.";
    uses srt:sr-topology-type;
  }

  augment "/nd-s:networks/nd-s:network/"
    + "l3t-s:l3-topology-attributes" {
    when "../nd-s:network-types/l3t-s:l3-unicast-topology/sr" {
      description "Augment only for SR topology.";
    }
    description "Augment topology configuration";
    uses srt:sr-topology-attributes;
  }

  augment "/nd-s:networks/nd-s:network/nd-s:node/"
    + "l3t-s:l3-node-attributes" {
    when "../../nd-s:network-types/l3t-s:l3-unicast-topology/sr" {
      description "Augment only for SR topology.";
    }
    description "Augment node configuration.";
    uses srt:sr-node-attributes;
  }

  augment "/nd-s:networks/nd-s:network/nd-s:node/"
    + "l3t-s:l3-node-attributes/l3t-s:prefix" {
    when "../../../nd-s:network-types/l3t-s:l3-unicast-topology/sr" {
      description "Augment only for SR topology.";
    }
    description "Augment node prefix.";
    uses srt:sr-node-prefix-attributes;
  }

  augment "/nd-s:networks/nd-s:network/nd-s:node/"
    + "lnk-s:termination-point/"
    + "l3t-s:l3-termination-point-attributes" {
    when "../../../nd-s:network-types/l3t-s:l3-unicast-topology/"
      + "sr" {
      description "Augment only for SR topology.";
    }
    description "Augment termination point configuration";
    uses srt:sr-tp-attributes;
  }

  augment "/nd-s:networks/nd-s:network/lnk-s:link/"
    + "l3t-s:l3-link-attributes" {
    when "../../nd-s:network-types/l3t-s:l3-unicast-topology/sr" {
      description "Augment only for SR topology.";
    }
    description "Augment link configuration.";
    uses srt:sr-link-attributes;
  }

  grouping sr-topology-attributes {
    description "SR topology scope attributes.";
    container sr {
      description
        "Containing SR attributes.";
      uses sr-cmn:srgb-cfg;
    } // sr
  } // sr-topology-attributes
}
