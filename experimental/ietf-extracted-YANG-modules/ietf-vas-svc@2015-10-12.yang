module ietf-vas-svc {
      namespace "urn:ietf:params:xml:ns:yang:ietf-vas-svc";

      prefix vas-svc;

      import ietf-inet-types {
          prefix inet;
      }

      import ietf-yang-types {
          prefix yang;
      }

      organization
       "IETF L3SM Working Group";

      contact
          "TBD";

      description
          "The YANG module defines a generic value added service configuration
          model.";

      revision 2015-10-12 {
          description
           "TBD";
                   reference
      "draft-gu-l3sm-vas-service-model-00";}

    identity vas-service-types{
  description
  "Base identity for vas service component type.";
 }
 identity firewall{
  base vas-service-types;
  description
  "identity for firewall service component type.";
 }
 identity loadbalance{
  base vas-service-types;
  description
  "identity for firewall service component type.";
 }

 identity vas-operation-type{
  description
  "Base identity for vas operation type.";
 }

 identity create{
  base vas-operation-type;
  description
  "Identity for create service.";
 }

 identity delete{
  base vas-operation-type;
  description
  "Identity for delete service.";
 }

 identity update{
  base vas-operation-type;

  description
  "Identity for update service.";
 }

      identity service-availability {
          description
           "Base identity for site availability.";
      }

      identity loadsharing {
              base service-availability;
              description
               "Identity for loadsharing.";
      }

      identity primary  {
              base service-availability;
              description
               "Identity for primary.";
      }
      identity backup  {
              base service-availability;
              description
               "Identity for backup.";
      }

       grouping vas-availability {
          container availability {
                      leaf service-type {
                          type identityref {
                              base service-availability;
                          }
                          description
                           "Type of service availability";
                      }
                  description
                   "Service availability parameters.";
              }
          description
           "This grouping defines service availability
            parameters";
      }

 container vas-service-components{
  description

  "this container contains several value-added-service components.";

  list service-component{
   key "name";
   description
   "this container present a value-added-service component.";

   leaf name{
    type string;
    description
    "the name of value added service.";
   }

   leaf id{
    type uint32;
    description
    "the vas id";
   }

   leaf admin-status{
       type enumeration {
        enum up {
         value 1;
                 description
                 "admin status up.";
   }
        enum down {
   value 2;
                 description
                 "admin status down.";
         }
  enum testing {
         value 3;
                 description
                 "testing.";
         }
        }
        description
    "admin status";
   }

   leaf enable{
    type boolean;
    description
    "enable this vas service.";
   }

   leaf isvirtual{
    type boolean;
    description
    "if it is set to true, it indicate the vas
    is a virtual service";
   }

   leaf tenant-id{
    type string;

    description
    "tenant id";
   }

   leaf provider{
    type string;
    description
    "provider name";
   }

   leaf service-component-type{
    type identityref{
     base vas-service-types;
    }
    description
    "indicate the service component type.";
   }

   container vas-policy{
    description
        "vas policy container.";
    container vas-classification-policy{
     description
         "container of classification policy";
  list rules{
   key "id";
   description
   "list of rules";
   leaf id{
    type uint16;
    description
    "rule id";
   }

 container match-flow{
    description
    "match flow.";

    choice type{
     description
     "match flow type";

     case ip{
      choice ip-version{
    case ipv4{
     leaf src-ipv4-network{
      type inet:ipv4-prefix;
               description
               "source ip.";
             }
     leaf dst-ipv4-network{

      type inet:ipv4-prefix;
      description
      "destination ip.";
     }
         description
         "ipv4";
    }
    case ipv6{
     leaf src-ipv6-network{
      type inet:ipv6-prefix;
               description
               "source ip.";
             }
     leaf dst-ipv6-network{
      type inet:ipv6-prefix;
      description
      "destination ip.";
     }
     leaf flow-label{
      type inet:ipv6-flow-label;
      description
      "flow label.";
     }
     leaf dscp{
      type inet:dscp;
      description
      "Differentiated Services Code Point";
     }
     leaf protocol{
      type uint8;
      description
      "Internet Protocol number.";
     }
     container source-port-range {
               description
               "Inclusive range representing source ports to be used.
                When only lower-port is present, it represents a single port.";
              leaf lower-port {
               type inet:port-number;
               description
               "Lower boundary for port.";
               }
      leaf upper-port {
        type inet:port-number;
        must ". >= ../lower-port" {
          error-message
          "The upper-port must be greater than or equal to lower-port";
                  description
                  "must statement.";
        }
        description
          "Upper boundary for port . If existing, the upper port
          must be greater or equal to lower-port.";
      }

             }
             container destination-port-range {
              description
              "Inclusive range representing destination ports to be used. When
               only lower-port is present, it represents a single port.";
              leaf lower-port {
               type inet:port-number;
               mandatory true;
               description
               "Lower boundary for port.";
               }
      leaf upper-port {
        type inet:port-number;
        must ". >= ../lower-port" {
          error-message
          "The upper-port must be greater than or equal to lower-port";
                  description
                  "must statement.";
        }
        description
          "Upper boundary for port . If existing, the upper port
          must be greater or equal to lower-port.";
      }
              }
     description
         "ipv6 case";
    }
        description
        "choice of ip version.";
   }
     }
     case eth{
      leaf src-mac-address{
    type yang:mac-address;
    description
    "source mac address.";
   }

   leaf dst-mac-address{
    type yang:mac-address;
    description
    "destination mac address.";
   }

   leaf src-mac-address-mask{
    type yang:mac-address;
    description
    "source mac address mask.";
   }

   leaf dst-mac-address-mask{
    type yang:mac-address;

    description
    "destination mac address mask.";
   }

     }
    }
   }
  }
    }
    leaf std-vas-profile{
  type string;
  description
  "standard vas profile.";
    }
   }
   leaf service-component-redundancy{
    type boolean;
        description
        "service component redundancy.";
   }
   uses vas-availability;
   container management{
    description
    "vas management.";
    leaf management-url{
     type string;
  description
  "management url.";
     }
    leaf vas-instance-id{
     type uint32;
  description
  "vas instance id";
    }
    leaf vlan-id{
     type uint32;
  description
  "vlan id";
    }
   }
  }
 }

  rpc vas-component-management{
   description
   "vas component management.";
   input{
    container service-component{
  description
  "service component.";

  leaf name{
   type string;
   description
   "name of service component.";
  }
   leaf admin-status{
       type enumeration {
        enum up {
         value 1;
                 description
                 "admin status up.";
   }
        enum down {
   value 2;
   description
   "admin status down.";
         }
  enum testing {
         value 3;
                 description
                 "testing";
         }
        }
                description
                "admin status.";
   }
   leaf operation-type{
    type identityref{
     base vas-operation-type;
    }
    description
    "operation type such as create, delete, update, etc.";
   }
   leaf isvirtual{
    type boolean;
    description
    "if it is set to true, it indicate the vas
    is a virtual service";
   }
   leaf tenant-id{
    type string;
    description
    "tenant identity";
   }
   leaf provider{
    type string;
    description
    "provider name";
   }
   leaf service-component-type{
    type identityref{
     base vas-service-types;
    }
    description
    "service component type.";
   }

   container vas-policy{
    description
    "value added service policy.";
    leaf id{
     type string;
  description
  "policy id.";
    }
   }
 }
   }
   output{
    container service-component{
  description
  "service component.";
  leaf name{
   type string;
   description
   "name of service component.";
  }
    leaf admin-status{
       type enumeration {
        enum up {
         value 1;
                 description
                 "admin status up.";
   }
        enum down {
   value 2;
   description
   "admin status down.";
         }
  enum testing {
         value 3;
                 description
                 "testing";
         }
        }
                description
                "admin status.";
   }
   leaf operation-type{
    type identityref{
     base vas-operation-type;
    }
    description
    "operation type such as create, delete, update, etc.";
   }
   leaf isvirtual{
    type boolean;
    description
    "if it is set to true, it indicate the vas
    is a virtual service";
   }
   leaf tenant-id{
    type string;

    description
    "tenant identity";
   }
   leaf provider{
    type string;
    description
    "provider name";
   }
   leaf service-component-type{
    type identityref{
     base vas-service-types;
    }
    description
    "service component type.";
   }
   container vas-policy{
    description
    "value added service policy.";
    leaf id{
     type string;
  description
  "policy id.";
    }
   }
   container management{
    description
    "vas management.";
    leaf management-url{
     type string;
  description
  "management url.";
     }
    leaf vas-instance-id{
     type uint32;
  description
  "vas instance id";
    }
   }
  }
 }
   }

   rpc vas-policy-management{
    description
 "vas policy management.";
 input{
  container service-component{
   description

   "service component.";
   leaf name{
    type string;
    description
    "name of service-component.";
   }
   leaf isvirtual{
    type boolean;
    description
    "if it is set to true, it indicate the vas
    is a virtual service";
   }

   leaf tenant-id{
    type string;
    description
    "tenant id";
   }

   leaf provider{
    type string;
    description
    "provider name";
   }

   leaf service-component-type{
    type identityref{
     base vas-service-types;
    }
    description
    "indicate the service component type.";
   }
   container vas-policy{
    description
    "value added service policy.";
    leaf id{
     type string;
  description
  "policy id.";
    }
   }
  }
 }
 output{
  container service-component{
   description
   "service component.";
   leaf name{

    type string;
    description
    "name of service-component.";
   }
   leaf isvirtual{
    type boolean;
    description
    "if it is set to true, it indicate the vas
    is a virtual service";
   }

   leaf tenant-id{
    type string;
    description
    "tenant id";
   }

   leaf provider{
    type string;
    description
    "provider name";
   }

   leaf service-component-type{
    type identityref{
     base vas-service-types;
    }
    description
    "indicate the service component type.";
   }
   container vas-policy{
    description
        "vas policy.";
    container vas-classification-policy{
    description
        "vas classification policy";
  list rules{
   key "id";
   description
   "list of rules.";
   leaf id{
    type string;
    description
    "rule id";
   }

         container match-flow{
    description
    "match flow.";

    choice type{

     description
     "match flow type";

     case ip{
      choice ip-version{
    case ipv4{
     leaf src-ipv4-network{
      type inet:ipv4-prefix;
               description
               "source ip.";
             }
     leaf dst-ipv4-network{
      type inet:ipv4-prefix;
      description
      "destination ip.";
     }
         description
         "case of ipv4";
    }
    case ipv6{
     leaf src-ipv6-network{
      type inet:ipv6-prefix;
               description
               "source ip.";
             }
     leaf dst-ipv6-network{
      type inet:ipv6-prefix;
      description
      "destination ip.";
     }
     leaf flow-label{
      type inet:ipv6-flow-label;
      description
      "flow label.";
     }
     leaf dscp{
      type inet:dscp;
      description
      "Differentiated Services Code Point";
     }
     leaf protocol{
      type uint8;
      description
      "Internet Protocol number.";
     }
     container source-port-range {
               description
               "Inclusive range representing source ports to be used.
                When only lower-port is present, it represents a single port.";
              leaf lower-port {

               type inet:port-number;
               description
               "Lower boundary for port.";
               }
                  leaf upper-port {
        type inet:port-number;
        must ". >= ../lower-port" {
          error-message
          "The upper-port must be greater than or equal to lower-port";
                  description
                  "must statement.";
        }
        description
          "Upper boundary for port . If existing, the upper port
          must be greater or equal to lower-port.";
      }
             }
             container destination-port-range {
              description
              "Inclusive range representing destination ports to be used. When
               only lower-port is present, it represents a single port.";
              leaf lower-port {
               type inet:port-number;
               mandatory true;
               description
               "Lower boundary for port.";
               }
     leaf upper-port {
        type inet:port-number;
        must ". >= ../lower-port" {
          error-message
          "The upper-port must be greater than or equal to lower-port";
                  description
                  "must statement.";
        }
        description
          "Upper boundary for port . If existing, the upper port
          must be greater or equal to lower-port.";
      }
              }
         description
         "case of ipv6";
    }
        description
        "choice of ip version.";
   }
   description
   "case of ip.";
     }
     case eth{
      leaf src-mac-address{
    type yang:mac-address;
    description
    "source mac address.";
   }

   leaf dst-mac-address{
    type yang:mac-address;

    description
    "destination mac address.";
   }

   leaf src-mac-address-mask{
    type yang:mac-address;
    description
    "source mac address mask.";
   }

   leaf dst-mac-address-mask{
    type yang:mac-address;
    description
    "destination mac address mask.";
   }
    description
        "case of ethernet";
     }
    }
   }
  }
    }
    leaf std-vas-profile{
  type string;
  description
  "standard vas profile.";
    }
   }
   container management{
    description
    "vas management.";
    leaf management-url{
     type string;
  description
  "management url.";
     }
    leaf vas-instance-id{
     type uint32;
  description
  "vas instance id";
    }
   }
   }
  }
 }
}
