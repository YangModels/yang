module ietf-nrp-device {
  yang-version 1.1;
  namespace "urn:ietf:params:xml:ns:yang:ietf-nrp-device";
  prefix nrp-dev;

  /* Import IETF Network module */

  import ietf-network {
    prefix nw;
    reference
      "RFC 8345: A YANG Data Model for Network Topologies,
                 Section 6.1";
  }

  /* Import IETF interface module */

  import ietf-interfaces {
    prefix if;
    reference
      "RFC8343: A YANG Data Model for Interface Management";
  }

  /* Import NRPs module */

  import ietf-nrp {
    prefix nrp;
    reference
      "RFCXXXX: YANG Data Models for Network Resource
                Partitions (NRPs)";
  }

  organization
    "IETF Traffic Engineering Architecture and Signaling (TEAS)
     Working Group";
  contact
    "WG Web:   <https://datatracker.ietf.org/wg/teas/>
     WG List:  <mailto:teas@ietf.org>

     Editor:   Bo Wu
               <mailto:lana.wubo@huawei.com>

     Editor:   Dhruv Dhody
               <mailto:dhruv.ietf@gmail.com>

     Editor:   Vishnu Pavan Beeram
               <mailto:vbeeram@juniper.net>

     Editor:   Tarek Saad
               <mailto:tsaad.net@gmail.com>

     Editor:   Shaofu Peng
               <mailto:peng.shaofu@zte.com.cn>";
  description
    "This YANG module defines a data model for Network Resource
     Partitions (NRPs) device configurations and states. The model
     fully conforms to the Network Management Datastore
     Architecture (NMDA).

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  // RFC Ed.: replace XXXX with actual RFC number and remove this
  // note.
  // RFC Ed.: update the date below with the date of RFC publication
  // and remove this note.

  revision 2024-07-05 {
    description
      "Initial revision.";
    reference
      "RFCXXXX: YANG Data Models for Network Resource
                Partitions (NRPs)";
  }

  /* NRP device configuraiton */

  augment "/nw:networks/nrp:nrp-policies/nrp:nrp-policy" {
    description
      "NRP policy list.";
    /* NRP Interface Configuration Data */
    container interfaces {
      description
        "NRP interfaces global configuration.";
      list interface {
        key "interface";
        description
          "The list of interfaces enabled for NRP.";
        leaf interface {
          type if:interface-ref;
          description
            "NRP interface name.";
        }
        uses nrp:nrp-resource-reservation;
        uses nrp:nrp-selector-config;
        uses nrp:nrp-qos-phb-profile;
      }
    }
  }
}
