module ietf-lisp-pitr {
  namespace "urn:ietf:params:xml:ns:yang:ietf-lisp-pitr";
  prefix lisp-pitr;
  import ietf-lisp {
    prefix lisp;
  }
  import ietf-lisp-address-types {
   prefix lcaf;
  }
  import ietf-inet-types {
    prefix inet;
  }
  organization
   "IETF LISP (Locator/ID Separation Protocol) Working Group";
  contact
    "lisp@ietf.org";
  description
    "This YANG module defines the generic configuration
     data for a LISP PITR. The module can be extended by vendors
     to define vendor-specific configuration parameters and
     policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";
  revision 2015-07-02 {
    description
      "Initial revision.";
    reference
      "https://tools.ietf.org/html/rfc6832";
  }
  identity pitr {
    base lisp:lisp-device;
    description
      "LISP PITR.";
  }
  augment "/lisp:lisp/lisp:devices/lisp:device" {
    when "lisp:type = lisp-pitr:pitr" {
      description
        "Augment is valid when LISP device type is PITR.";
    }
    description
      "This augments LISP devices list with PITR specific
       parameters.";
    container proxy-itr-cfg {
      presence "LISP PITR operation enabled";
      description
        "Proxy-ITR configuration parameters.";
      container servicing-eids {
        description
          "EIDs serviced by the PITR.";
        list eid {
          key "id";
          description
            "List of EIDs serviced by the PITR.";
          leaf id {
            type lisp:eid-id;
            description
              "Id of serviced EID.";
          }
          container eid-address {
            uses lcaf:lisp-address;
            description
              "Serviced EID address in generic LISP address format.";
          }
        }
      }

      container map-resolvers {
        description
          "Map-Resolvers configured for PITR.";
        list map-resolver {
          key "id";
          description
            "List of Map-Resolvers configured for PITR.";
          leaf id {
            type lisp:eid-id;
            description
              "Id of EID for which the Map-Resolver is used.";
          }
          container eid {
            uses lcaf:lisp-address;
            description
              "EID for which the Map-Resolver is used.";
          }
          leaf-list address {
            type inet:ip-address;
            min-elements 1;
            description
              "List of Map-Resolver's addresses.";
          }
        }
      }
      container static-mappings{
        uses lisp:mappings;
        description
          "EID to RLOCs mappings cache.";
      }
    }
  }
  augment "/lisp:lisp-state/lisp:devices/lisp:device" {
    when "lisp:type = lisp-pitr:pitr" {
      description
        "Augment is valid when LISP device type is PITR.";
    }
    description
      "This augments LISP devices list state with PITR specific
       parameters.";
    container pitr-state {
      config false;
      description
        "ITR state.";
      container learned-mappings {
        uses lisp:mappings;
        description
          "EID to RLOCs mappings cache.";
      }
    }
  }
}
