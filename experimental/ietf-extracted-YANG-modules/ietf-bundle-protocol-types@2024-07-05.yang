module ietf-bundle-protocol-types {
  yang-version 1.1;
  namespace "urn:ietf:params:xml:ns:yang:ietf-bundle-protocol-types";
  prefix bundle-types;

  import ietf-inet-types {
    prefix inet;
    reference
      "RFC 6991: Common YANG Data Types";
  }
  import ietf-yang-types {
    prefix yang;
    reference
      "RFC 6991: Common YANG Data Types";
  }

  organization
    "IETF DTN: Delay-Tolerant Networking Working Group";
  contact
    "WG Web:   <http://datatracker.ietf.org/wg/dtn>
     WG List:  <mailto:dtn@ietf.org>

     Author:   Marc Blanchet
               <mailto:marc.blanchet@viagenie.ca>
     Author:    Yingzhen Qu
               <mailto:yingzhen.ietf@gmail.com>";
  description
    "This module contains Bundle Protocol (RFC5050, RFC9171) types.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC TBD; see
    the RFC itself for full legal notices.";

  revision 2024-07-05 {
    description
      "Initial revision. date TBD";
    reference
      "RFC 5050 Bundle Protocol Specification
       RFC 9171 Bundle Protocol Version 7
       IANA Bundle Protocol Registry,
       https://www.iana.org/assignments/bundle/bundle.xhtml";
  }

  /* Bundle Block Types */
  identity bundle-block-types {
    description
      "Base identity for bundle block types. The Bundle Block Types
       are defined in IANA Bundle Protocol registry.";
  }

  identity bundle-payload-block {
    base bundle-block-types;
    description
      "Bundle payload block type";
  }

  identity bundle-authentication-block {
    base bundle-block-types;
    description
      "Bundle authentication block type";
  }

  identity payload-integrity-block {
    base bundle-block-types;
    description
      "Payload integrity block type";
  }

  identity payload-confidentiality-block {
    base bundle-block-types;
    description
      "Payload confidentiality block type";
  }

  identity previous-hop-insertion-block {
    base bundle-block-types;
    description
      "Previous-hop insertion block type";
  }

  identity previous-node {
    base bundle-block-types;
    description
      "Previous node type";
  }

  identity bundle-age {
    base bundle-block-types;
    description
      "Bundle age type";
  }

  identity metadata-extension-block {
    base bundle-block-types;
    description
      "Metadata extension type";
  }

  identity extension-security-block {
    base bundle-block-types;
    description
      "Extension security block type";
  }

  identity hop-count {
    base bundle-block-types;
    description
      "Hop count type";
  }

  identity block-integrity {
    base bundle-block-types;
    description
      "Block integrity type";
  }

  identity block-confidentially {
    base bundle-block-types;
    description
      "Block confidentiality type";
  }

  /* Primary Bundle Protocol Version */
  identity bundle-protocol-version {
    description
      "Base identity for primary bundle protocol version. The
       Primary Bundle Protocol Version is defined in IANA
       Bundle Protocol registry.";
  }

  identity version6 {
    base bundle-protocol-version;
    description
      "The Bundle protocol version 6 as defined in RFC5050";
  }

  identity version7 {
    base bundle-protocol-version;
    description
      "The Bundle protocol version 7 as defined in RFC9171";
  }

  /* Block Processing Control Flags */
  identity block-processing-control-flag {
    description
      "Base identity for bundle processing control flags";
  }

  identity block-replicated-every-fragment {
    base block-processing-control-flag;
    description
      "Block must be replicated in every fragment";
  }

  identity transmit-status-report-block-not-processed {
    base block-processing-control-flag;
    description
      "Transmit status report if block can't be processed";
  }

  identity delete-bundle-block-not-processed {
    base block-processing-control-flag;
    description
      "Delete bundle if block can't be processed";
  }

  identity last-block {
    base block-processing-control-flag;
    description
      "Last block";
  }

  identity discard-block-not-processed {
    base block-processing-control-flag;
    description
      "Discard block if it can't be processed";
  }

  identity block-forwarded-not-processed {
    base block-processing-control-flag;
    description
      "Block was forwarded without being processed";
  }

  identity block-contains-eid-reference {
    base block-processing-control-flag;
    description
      "Block contains an EID-reference field";
  }

  typedef convergence-layer-adapter-type {
    type enumeration {
      enum tcpcl {
        description
          "TCP convergence layer";
        reference
          "RFC7242: Delay-Tolerant Networking TCP
           Convergence-Layer Protocol";
      }
      enum tcpclv4 {
        description
          "TCPv4 convergence layer";
        reference
          "RFC9174: Delay-Tolerant Networking TCP Convergence-Layer
           Protocol Version 4";
      }
      enum udpcl {
        description
          "UDP convergence layer";
        reference
          "RFC7122: Datagram Convergence Layers for the Delay- and
           Disruption-Tolerant Networking (DTN) Bundle Protocol and
           Licklider Transmission Protocol (LTP)";
      }
      enum ltp {
        description
          "Licklider Transmission Protocol";
        reference
          "RFC 5326: Licklider Transmission Protocol - Specification";
      }
    }
    description
      "Types of convergence layers of Bundle protocol";
  }

  typedef bundle-endpoint-identifier {
    type inet:uri;
    description
      "Bundle protocol Endpoint Identifier type";
  }

  grouping address-port {
    leaf host {
      type inet:host;
      description
        "The IPv4, IPv6 address or hostname";
    }
    leaf port {
      type inet:port-number;
      description
        "The tranport port number";
    }
    description
      "IP address or hostname and port";
  }

  grouping convergence-layer-adapter {
    leaf id {
      type yang:yang-identifier;
      description
        "Unique id of this CLA. Local to the implementation. Enables referencing it for
         management purposes";
    }
    leaf type {
      type bundle-types:convergence-layer-adapter-type;
      description
        "Type of the convergence layer of this neighbor";
    }
    choice transport {
      case udp-and-tcp {
        uses address-port;
      }
      /* other cla */
      description
        "Convergence layer adapter specific transport information";
    }
    description
      "The convergence layer adapter used to communicate
       with this neighbor";
  }

  grouping bundle {
    leaf id {
      type yang:yang-identifier;
      description
        "Unique id of a bundle. Local to the implementation. Enables referencing it for
         management purposes";
    }
    leaf version {
      type identityref {
        base bundle-protocol-version;
      }
      description
        "Bundle protocol version";
    }
    leaf-list processing-control-flags {
      type identityref {
        base block-processing-control-flag;
      }
      description
        "List of bundle processing control flags";
    }
    leaf destination-endpoint-identifier {
      type bundle-endpoint-identifier;
      description
        "Endpoint identifier of the destination";
    }
    leaf source-node-endpoint-identifier {
      type bundle-endpoint-identifier;
      description
        "Endpoint identifier of the source node";
    }
    leaf report-to-endpoint-identifier {
      type bundle-endpoint-identifier;
      description
        "Endpoint identifier of the node to send reports to";
    }
    leaf creation-timestamp {
      type yang:timestamp;
      description
        "Creation timestamp";
    }
    leaf lifetime {
      type uint32;
      units "seconds";
      description
        "Lifetime of the bundle in seconds";
    }
    leaf application-data-unit-length {
      type uint32;
      units "octets";
      description
        "Application data unit (aka bundle payload) length in octets";
    }
    /* TBD: additional fields: fragmentoffset, crc-type, ... */
    description
      "A bundle";
    reference
      "RFC 5050 Bundle Protocol Specification
       RFC 9171 Bundle Protocol Version 7";
  }
}
