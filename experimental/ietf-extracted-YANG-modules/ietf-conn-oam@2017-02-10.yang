module ietf-conn-oam {
  namespace "urn:ietf:params:xml:ns:yang:ietf-conn-oam";
  prefix goam;

  import ietf-yang-types {
    prefix yang;
  }
  import ietf-inet-types {
    prefix inet;
  }
  import ietf-interfaces {
    prefix if;
  }
  organization "IETF LIME Working Group";
  contact
    "WG Web:    http://tools.ietf.org/wg/lime
     WG List:   mailto:lime@ietf.org
     WG Chair:  Carlos Pignataro cpignata@cisco.com
     WG Chair:  Ron Bonica rbonica@juniper.net
     Editor:    Deepak Kumar dekumar@cisco.com
     Editor:    Qin Wu bill.wu@huawei.com
     Editor:    Zitao Wang wangzitao@huawei.com";
  description
    "This YANG module defines the generic configuration,
  statistics and rpc for connection oriented OAM
  to be used within IETF in a protocol indpendent manner.
  Functional level abstraction is indendent
  with YANG modeling. It is assumed that each protocol
  maps corresponding abstracts to its native format.
  Each protocol may extend the YANG model defined
  here to include protocol specific extensions";

  revision 2017-02-10 {
    description
      "Initial revision. - 07 version";

    reference "draft-ietf-lime-yang-oam-model";
  }

  /* features */
  feature connectivity-verification {
    description
      "This feature indicates that the server supports
    executing connectivity verification OAM command and
    returning a response. Servers that do not advertise
    this feature will not support executing
    connectivity verification command or rpc model for
    connectivity verification command.";
  }
  feature continuity-check{
    description
      "This feature indicates that the server supports
    executing continuity check OAM command and
    returning a response. Servers that do not advertise
    this feature will not support executing
    continuity check command or rpc model for
    continuity check command.";
  }

  feature traceroute{
    description
      "This feature indicates that the server supports
    executing traceroute OAM command and
    returning a response. Servers that do not advertise
    this feature will not support executing
    traceroute command or rpc model for
    traceroute command.";
   }
  feature mip {
   description
   "This feature indicates that the MIP (Maintenance Intermediate Point)
   need to
   be explicit configured";
  }
  /* Identities */

  identity technology-types {
    description
      "This is the base identy of technology types which are
    TRILL,MPLS-TP,vpls etc";
  }

  identity command-sub-type {
    description
      "Defines different rpc command subtypes,
    e.g rfc6905 trill OAM, this is optional for most cases";
  }

  identity on-demand {
   base command-sub-type;
   description
   "On demand activation - indicates that the tool is activated
    manually to detect a specific anomaly.";
  }

  identity proactive {
   base command-sub-type;
   description
   "Proactive activation - indicates that the tool is activated on a
    continual basis, where messages are sent periodically, and errors
    are detected when a certain number of expected messages are not
    received.";
  }

  identity name-format {

    description
      "This defines the name format, IEEE 8021ag CFM defines varying
      styles of names. It is expected name format as an identity ref
      to be extended with new types.";
  }

  identity name-format-null {
    base name-format;
    description
      "Defines name format as null";
  }

  identity identifier-format {
    description
      "Identifier-format identity can be augmented to define other
     format identifiers used in MEP-ID etc";
  }

  identity identifier-format-integer {
    base identifier-format;
    description
      "Defines identifier-format to be integer";

  }

  identity defect-types {
    description
      "Defines different defect types, e.g. remote rdi,
       mis-connection defect, loss of continuity";
  }
  identity rdi {
    base defect-types;
    description
      "Indicates the aggregate health of the remote MEPs. ";
  }

  identity remote-mep-defect{
    base defect-types;
    description
      "Indicates that one or more of the remote MEPs is
       reporting a failure ";
  }

  identity loss-of-continuity{
    base defect-types;
    description
    "If no proactive CC OAM packets from the source
     MEP (and in the case of CV, this includes the
     requirement to have the expected globally unique
     Source MEP identifier) are received within the interval. ";
   }
  identity invalid-oam-defect{
    base defect-types;
    description
    "Indicates that one or more invalid OAM messages has been
    received and that 3.5 times that OAM message transmission
    interval has not yet expired.";
  }

  identity cross-connect-defect{
    base defect-types;
    description
    "Indicates that one or more cross-connect defect
    (for example, a service ID does not match the VLAN.)
     messages has been received and that 3.5 times that OAM message
     transmission interval has not yet expired.";
  }

  /* typedefs */

  typedef MEP-name {
    type string;
    description
      "Generic administrative name for a MEP";
  }

  typedef Interval{
    type decimal64{
    fraction-digits 2;
   }
   units "milliseconds";
    description
    "Interval between packets in milliseconds.
    0 means no packets are sent.";
  }

  typedef MD-name-string {
    type string;
    description
      "Generic administrative name for an MD";
  }

  typedef MA-name-string {
    type string;
    description
      "Generic administrative name for an MA";
  }

  typedef oam-counter32 {
    type yang:zero-based-counter32;
    description
      "Defines 32 bit counter for OAM";
  }

  typedef MD-level {
    type uint32 {

      range "0..255";
    }
    description
      "Maintenance Domain level.  The level may be restricted in
       certain protocols (eg to 0-7)";
  }

  /* groupings */

  grouping maintenance-domain-reference {
  description
     "This grouping uniquely identifies a maintenance domain.";

  leaf maintenance-domain {
     type leafref {
       path "/goam:domains/goam:domain/goam:MD-name-string";
    }
  description
    "A reference to a specific Maintenance Domain.";
}
}

grouping maintenance-association-reference {
  description
    "This grouping uniquely identifies a
        maintenance association. It consists
     of a maintence-domain-reference and
         a maintenance-association leafref";
  uses maintenance-domain-reference;
  leaf maintenance-association {
    type leafref {
      path "/goam:domains/goam:domain"
          +"[goam:MD-name-string = current()/"
          +"../maintenance-domain]/goam:MAs"
          +"/goam:MA/goam:MA-name-string";
    }
  description
      "A reference to a specific Maintenance Association.";
  }
}
grouping maintenance-association-end-point-reference {
  description
  "This grouping uniquely identifies
  a maintenance association. It consists
   of a maintence-association-reference and
   a maintenance-association-end-point leafref";
  uses maintenance-association-reference;
  leaf maintenance-association-end-point {
    type leafref {
      path "/goam:domains/goam:domain"
          +"[goam:MD-name-string = current()/"
          +"../maintenance-domain]/goam:MAs"
          +"/goam:MA[goam:MA-name-string = "
          +"current()/../maintenance-association]"
          +"/goam:MEP/goam:mep-name";
     }
    description
      "A reference to a specific Maintenance
          association End Point.";
  }
 }

  grouping time-to-live {
    choice ttl{
      case ip-ttl{
        leaf ip-ttl{
        type uint8;
        default "255";
        description
          "Time to live";
        }
      }
     case mpls-ttl{
       leaf mpls-ttl{

       type uint8;
       description
         "Time to live. When an IP packet is imposed with a label,
        the IP TTL value is first decremented then copied into
        the MPLS TTL. As each LSR the MPLS frame's TTL is
        decremented.This behavior can be modified with no
        mpls ip ttl. When a MPLS label is popped, the MPLS
        TTL value is decremented then copied in the IP TTL
        field. If the MPLS TTL value is great than IP TTL,
        that values is not copied over. This is to prevent
        a possible condition of forwarding loop and TTL
        never reaching 0. When two MPLS labels are swapped,
        decrement by 1 and copy over the result into the new label.
        When a new MPLS labels is pushed, decrement by 1 and copy
        over the result into the new label. When a new MPLS labels
        is popped, decrement by 1 and copy over the result into
        the label below.[RFC3443]";

       }
     }
     description
       "Time to Live.";
    }
    description
      "Time to Live grouping.";
  }
  grouping defect-message {
    choice defect {
      case defect-null {
        description

          "This is a placeholder when no defect status is needed";
        leaf defect-null {
           type empty;
           description
             "there is no defect define, it will be defined in
              technology specific model.";
        }
      }
      case defect-code {
        description
          "This is a placeholder to display defect code.";
        leaf defect-code {
           type int32;
           description
             "Defect code is integer value specific to technology.";
        }
      }

      description
        "Defect Message choices.";
    }

    description
      "Defect Message.";
  }

  grouping mep-address {
    choice mep-address {
      case mac-address {
        leaf mac-address {
          type yang:mac-address;
          description
          "MAC Address";
        }
      description
      "MAC Address based MEP Addressing.";
      }
      case ipv4-address {
        leaf ipv4-address {
          type inet:ipv4-address;
          description
          "IPv4 Address";
        }
      description
      "IP Address based MEP Addressing.";
      }
      case ipv6-address {
        leaf ipv6-address {
          type inet:ipv6-address;
          description
          "IPv6 Address";
        }
        description
        "IPv6 Address based MEP Addressing.";
      }
      description
       "MEP Addressing.";
    }
    description
     "MEP Address";
  }
  grouping mip-address {
    choice mip-address {
      case mac-address {
        leaf mac-address {
          type yang:mac-address;
          description
          "MAC Address";
        }
      description
      "MAC Address based MIP Addressing.";
      }
      case ipv4-address {
        leaf ipv4-address {
          type inet:ipv4-address;
          description
          "IPv4 Address";
        }
      description
      "IP Address based MIP Addressing.";
      }
      case ipv6-address {
        leaf ipv6-address {
          type inet:ipv6-address;
          description
          "IPv6 Address";
        }
        description
        "IPv6 Address based MIP Addressing.";
      }
      description
       "MIP Addressing.";
    }
    description
     "MIP Address";
  }
  grouping maintenance-domain-id {
    description
      "Grouping containing leaves sufficient to identify an MD";
    leaf technology {

      type identityref {
        base technology-types;
      }
      mandatory true;

      description
        "Defines the technology";
    }
    leaf MD-name-string {
      type MD-name-string;
      mandatory true;
      description
        "Defines the generic administrative maintenance domain name";
    }
  }

  grouping MD-name {
    leaf MD-name-format {
      type identityref {
        base name-format;
      }
      description
        "Name format.";
    }
    choice MD-name {
      case MD-name-null {
        leaf MD-name-null {
        when "'../../../MD-name-format' = 'name-format-null'" {
        description
        "MD name format is equal to null format.";
        }
        type empty;
        description
        "MD name Null.";
        }
      }
      description
        "MD name.";
    }
    description
      "MD name";
  }

  grouping ma-identifier {
    description
      "Grouping containing leaves sufficient to identify an MA";
    leaf MA-name-string {
      type MA-name-string;

      description

        "MA name string.";
    }
  }

  grouping MA-name {
    description
      "MA name";
    leaf MA-name-format {
      type identityref {
        base name-format;
      }
      description
        "Ma name format";
    }
    choice MA-name {
     case MA-name-null {
      leaf MA-name-null {
       when "'../../../MA-name-format' = 'name-format-null'" {
       description
         "MA";
      }
        type empty;
        description
        "Empty";
        }
      }
      description
        "MA name";
    }
  }

  grouping MEP-ID {
    choice MEP-ID {
      default "MEP-ID-int";
      case MEP-ID-int {
        leaf MEP-ID-int {
          type int32;
  description
    "MEP ID in integer format";
        }
      }
      description
        "MEP-ID";
    }

    leaf MEP-ID-format {

      type identityref {
        base identifier-format;
      }
      description
        "MEP ID format.";
    }
    description
      "MEP-ID";
  }

  grouping MEP {
    description
      "Defines elements within the MEP";
    leaf mep-name {
      type MEP-name;
      mandatory true;
      description
        "Generic administrative name of the MEP";
    }
    uses MEP-ID;
    uses mep-address;
  }

 grouping monitor-stats {
   description
    "grouping for monitoring statistics, this will be augmented
    by others who use this component";
    choice monitor-stats {

     default "monitor-null";
      case monitor-null {
       description
        "This is a place holder when
         no monitoring statistics is needed";
         leaf monitor-null {
          type empty;
          description
          "There is no monitoring statistics to be defined";
              }
            }
          description
          "Define the monitor stats";
          }
        }

  grouping connectivity-context {
    description
      "Grouping defining the connectivity context for an MA; for
       example, a VRF for VPLS, or an LSP for MPLS-TP.  This will be
       augmented by each protocol who use this component";
    choice connectivity-context {
      default "context-null";
      case context-null {
        description
          "This is a place holder when no context is needed";
        leaf context-null {
          type empty;
          description
            "There is no context define";
        }
      }
      description
        "Connectivity context";
    }
  }
  grouping cos {
    description

      "Priority used in transmitted packets; for example, in the
       EXP field in MPLS-TP.";
    leaf cos-id {
      type uint8;
      description
        "Class of service";
    }
  }
  grouping MIP-grouping {
   uses mip-address;
   leaf level {
    type MD-level;
        description
        "Configure a level of maintenance intermediate point (MIP)
        for the interface. The MIP level range is 0 to 7.";
   }
   description
   "Grouping for MIP configuration";
  }

  container domains {
    description
      "Contains configuration related data. Within the container
       is list of fault domains. Wihin each domian has List of MA.";
    list domain {
      key "technology MD-name-string";

      ordered-by system;
      description

        "Define the list of Domains within the IETF-OAM";
      uses maintenance-domain-id;
      uses MD-name;
      leaf md-level {
        type MD-level;
        description
          "Defines the MD-Level";
      }
      container MAs {
        description
          "This container defines MA, within that have multiple MA
           and within MA have MEP";
        list MA {
          key "MA-name-string";
          ordered-by system;
          uses ma-identifier;
          uses MA-name;
          uses connectivity-context;
          uses cos {
            description
              "Default class of service for this MA,
                          which may be overridden
               for particular MEPs,
                           sessions or operations.";
          }
             leaf cc-enable{
              type boolean;
              description
              "Indicate whether the CC enable.";
             }
          list MEP {
            key "mep-name";

            ordered-by system;
            description
            "Contain list of MEPS";
            uses MEP;
            uses cos;
                    leaf cc-enable{
                     type boolean;
                     description
                     "Indicate whether the CC enable.";
                    }
            list session {
              key "session-cookie";
              ordered-by user;
              description
                "Monitoring session to/from a particular remote MEP.
                 Depending on the protocol, this could represent CC
                 messages received from a single remote MEP (if the
                 protocol uses multicast CCs) or a target to which
                 unicast echo request CCs are sent and from which
                 responses are received (if the protocol uses a
                 unicast request/response mechanism).";
              leaf session-cookie {
                type uint32;
                description
                  "Cookie to identify different sessions, when there
                   are multiple remote MEPs or multiple sessions to
                   the same remote MEP.";
              }
              container destination-mep {
                uses MEP-ID;
                description
                "Destination MEP";
              }
              container destination-mep-address {
                uses mep-address;
                description
                "Destination MEP Address";
              }
              uses cos;
            }
          }
                  list MIP {
                   if-feature mip;
                   key "interface";
                   leaf interface {
                    type if:interface-ref;
                        description
                        "Interface";
                   }
                   uses MIP-grouping;
                   description
                   "List for MIP";
                  }

          description
          "Maintenance Association list";
         }
                }
      }

  }

  notification defect-condition-notification {
    description
      "When defect condition is met this notification is sent";
    leaf technology {
      type identityref {
        base technology-types;
      }
      description
        "The technology";
    }
    leaf MD-name-string {
      type leafref{
           path "/domains/domain/MD-name-string";
          }
      mandatory true;
      description
      "Indicate which MD is seeing the defect";
    }
    leaf MA-name-string{
          type leafref{
           path "/domains/domain/MAs/MA/MA-name-string";
          }
      mandatory true;
      description
      "Indicate which MA is seeing the defect";
        }
    leaf mep-name {
      type leafref{
           path "/domains/domain/MAs/MA/MEP/mep-name";
          }
      description
        "Indicate which MEP is seeing the defect";
    }
    leaf defect-type {
      type identityref {
        base defect-types;
      }
      description

        "The currently active defects on the specific MEP.";
    }
    container generating-mepid {

      uses MEP-ID;
      description
        "Who is generating the defect (if known) if
         unknown make it 0.";
    }
    uses defect-message {
      description
         "Defect message to indicate more details.";
    }
  }

  notification defect-cleared-notification {
    description
      "When defect cleared is met this notification is sent";
    leaf technology {
      type identityref {
        base technology-types;
      }
      description
        "The technology";
    }
    leaf MD-name-string {
      type leafref{
           path "/domains/domain/MD-name-string";
          }
      mandatory true;
      description
      "Indicate which MD is seeing the defect";
    }
    leaf MA-name-string{
          type leafref{
           path "/domains/domain/MAs/MA/MA-name-string";
          }
      mandatory true;
      description
      "Indicate which MA is seeing the defect";
        }
    leaf mep-name {
      type leafref{
           path "/domains/domain/MAs/MA/MEP/mep-name";
          }
      description
        "Indicate which MEP is seeing the defect";
    }

    leaf defect-type {
      type identityref {
        base defect-types;

      }
      description

        "The currently active defects on the specific MEP.";
    }
    container generating-mepid {
      uses MEP-ID;
      description
        "Who is generating the defect (if known) if
         unknown make it 0.";
    }
    uses defect-message {
      description
         "Defect message to indicate more details.";
    }
  }

  rpc continuity-check {
    if-feature "continuity-check";
    description
      "Generates continuity-check as per RFC7276 Table 4.";
    input {
    leaf technology {
      type identityref {
        base technology-types;
      }
      description
        "The technology";
    }
    leaf MD-name-string {
      type leafref{
           path "/domains/domain/MD-name-string";
          }
      mandatory true;
      description
      "Indicate which MD is seeing the defect";
    }
    leaf MA-name-string{
          type leafref{
           path "/domains/domain/MAs/MA/MA-name-string";
          }
      mandatory true;
      description
      "Indicate which MA is seeing the defect";
        }
      uses cos;
      uses time-to-live;
      leaf sub-type {

        type identityref {
          base command-sub-type;
        }
        description
          "Defines different command types";
      }
      leaf source-mep {
       type leafref{
           path "/domains/domain/MAs/MA/MEP/mep-name";
           }
       description
       "Source MEP";
      }
      container destination-mep {
        uses mep-address;
        uses MEP-ID {
          description
                  "Only applicable if the destination is a MEP";
        }
        description
        "Destination MEP";

      }
      leaf count {
        type uint32;
        default "3";
        description
         "Number of continuity-check message to send";
      }
      leaf cc-transmit-interval {
        type Interval;
        description

          "Interval between echo requests";
      }
      leaf packet-size {
        type uint32 {
          range "0..10000";
        }
        default "64";
        description
          "Size of continuity-check packets, in octets";
      }
    }
    output {
      uses monitor-stats {
        description
          "Stats of continuity check.";
      }

    }
  }

  rpc continuity-verification {
    if-feature connectivity-verification;
    description
      "Generates continuity-verification as per RFC7276 Table 4.";
    input {
     leaf MD-name-string {
      type leafref{
           path "/domains/domain/MD-name-string";
          }
      mandatory true;
      description
      "Indicate which MD is seeing the defect";
     }
     leaf MA-name-string{
          type leafref{
           path "/domains/domain/MAs/MA/MA-name-string";
          }
      mandatory true;
      description
      "Indicate which MA is seeing the defect";
         }
      uses cos;
      uses time-to-live;
      leaf sub-type {

        type identityref {
          base command-sub-type;
        }
        description
          "Defines different command types";
      }
      leaf source-mep {
       type leafref{
           path "/domains/domain/MAs/MA/MEP/mep-name";
           }
       description
       "Source MEP";
      }
      container destination-mep {
        uses mep-address;
        uses MEP-ID {
          description "Only applicable if the destination is a MEP";
        }
        description
        "Destination MEP";

      }
      leaf count {
        type uint32;
        default "3";
        description
          "Number of continuity-verification message to send";
      }
      leaf interval {
        type Interval;
        description
          "Interval between echo requests";
      }
      leaf packet-size {
        type uint32 {
          range "64..10000";
        }
        default "64";
        description
          "Size of continuity-verification packets, in octets";
      }
    }
    output {
      uses monitor-stats {
        description
          "Stats of continuity check.";
      }
    }
  }
  rpc traceroute {
    if-feature traceroute;
    description
      "Generates Traceroute or Path Trace and return response.
       Referencing RFC7276 for common Toolset name, for
       MPLS-TP OAM it's Route Tracing, and for TRILL OAM It's
       Path Tracing tool. Starts with TTL of one and increment
       by one at each hop. Untill destination reached or TTL
       reach max value";
    input {
     leaf MD-name-string {
      type leafref{
           path "/domains/domain/MD-name-string";
          }
      mandatory true;
      description
      "Indicate which MD is seeing the defect";
     }
     leaf MA-name-string{
          type leafref{

           path "/domains/domain/MAs/MA/MA-name-string";
          }
      mandatory true;
      description
      "Indicate which MA is seeing the defect";
         }
      uses cos;
      uses time-to-live;
      leaf command-sub-type {
        type identityref {

          base command-sub-type;
        }
        description
          "Defines different command types";
      }
      leaf source-mep {
       type leafref{
           path "/domains/domain/MAs/MA/MEP/mep-name";
           }
       description
       "Source MEP";
      }
      container destination-mep {
        uses mep-address;
        uses MEP-ID {
          description
                  "Only applicable if the destination is a MEP";
        }
        description
        "Destination MEP";
      }
      leaf count {
        type uint32;
        default "1";
        description
          "Number of traceroute probes to send.  In protocols where a
           separate message is sent at each TTL, this is the number
           of packets to send at each TTL.";
      }
      leaf interval {
        type Interval;
        description
          "Interval between echo requests";
      }
    }
    output {
      list response {
        key "response-index";

        leaf response-index {
         type uint8;
          description
            "Arbitrary index for the response.  In protocols that
             guarantee there is only a single response at each TTL
             , the TTL can be used as the response
             index.";
        }
        uses time-to-live;
        container destination-mep {
          description "MEP from which the response has been received";
          uses mep-address;
          uses MEP-ID {
            description
              "Only applicable if the destination is a MEP";
          }
        }
                container mip {
                 if-feature mip;
                 leaf interface {
                  type if:interface-ref;
                  description
                  "MIP interface";
                 }
         uses mip-address;
                 description
                 "MIP responding with traceroute";
                }
        uses monitor-stats {
          description
            "Stats of traceroute.";
        }
      description
        "List of response.";
      }
    }
  }
}
