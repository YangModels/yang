module ietf-l1csm-te-service-mapping {

    namespace "urn:ietf:params:xml:ns:yang:ietf-l1csm-te-service-mapping";

    prefix "tm";

    import ietf-te-service-mapping-types {
       prefix "tsm-types";
   }

   import ietf-l1csm {
        prefix "l1";
    }

    organization
        "IETF Traffic Engineering Architecture and Signaling (TEAS)
        Working Group";
    contact
        "Editor: Young Lee <leeyoung@huawei.com>
                 Dhruv Dhody <dhruv.ietf@gmail.com>
       Qin Wu <bill.wu@huawei.com>";
    description
        "This module contains a YANG module for the mapping of
        Layer 1 Connectivity Service Module (L1CSM) to the TE and VN ";

    revision 2019-03-05 {
        description
            "initial version.";
        reference
            "TBD";
    }

    /*
     * Configuration data nodes
     */
    augment "/l1:l1-connectivity/l1:services/l1:service" {
      description
        "l1csm augmented to include TE parameters and mapping";
      container te-service-mapping {
         presence "indicates l1 service to te mapping";
         description
           "Container to augment l1csm to TE parameters and mapping";
       }
    }

    augment "/l1:l1-connectivity/l1:services/l1:service" {
       description
         "This augment is only valid for TE mapping --
         te mapping is added";
       uses tsm-types:te-mapping;
    }

    augment "/l1:l1-connectivity/l1:services/l1:service/l1:endpoint-1" {
      description
         "This augment is only valid for TE mapping --
          endpoint-1 te-reference is added";
      uses tsm-types:te-endpoint-ref;
    }

    augment "/l1:l1-connectivity/l1:services/l1:service/l1:endpoint-2" {
      description
        "This augment is only valid for TE mapping --
        endpoint-2 te-reference is added";
      uses tsm-types:te-endpoint-ref;
    }
}
