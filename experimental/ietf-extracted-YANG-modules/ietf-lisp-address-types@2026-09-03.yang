module ietf-lisp-address-types {
  yang-version 1.1;
  namespace "urn:ietf:params:xml:ns:yang:ietf-lisp-address-types";
  prefix laddr;

  import ietf-inet-types {
    prefix inet;
    reference
      "RFC 6991: Common YANG Data Types";
  }
  import ietf-yang-types {
    prefix yang;
    reference
      "RFC 6991: Common YANG Data Types";
  }

  organization
    "IETF LISP (Locator/ID Separation Protocol) Working Group";
  contact
    "WG Web:   <http://tools.ietf.org/wg/lisp/>
      WG List:  <mailto:lisp@ietf.org>

      Editor:   Vina Ermagan
                <mailto:ermagan@gmail.com>

      Editor:   Alberto Rodriguez-Natal
                <mailto:natal@cisco.com>

      Editor:   Reshad Rahman
                <mailto:reshad@yahoo.com>";
  description
    "This YANG module defines the LISP Canonical Address Formats
      (LCAF) for LISP. The module can be extended by vendors to
      define vendor-specific parameters.

      Copyright (c) 2026 IETF Trust and the persons identified as
      authors of the code.  All rights reserved.

      Redistribution and use in source and binary forms, with or
      without modification, is permitted pursuant to, and subject to
      the license terms contained in, the Revised BSD License set
      forth in Section 4.c of the IETF Trust's Legal Provisions
      Relating to IETF Documents
      (https://trustee.ietf.org/license-info).

      This version of this YANG module is part of RFC XXXX; see
      the RFC itself for full legal notices.

    ";

  // RFC Ed.: replace XXXX with actual RFC number and remove
  // this note

  reference
    "RFC XXXX";

  revision 2026-09-03 {
    description
      "Initial revision.";
    reference
      "RFC XXXX";
  }

  identity lisp-address-family {
    description
      "Base identity from which identities describing LISP address
        families are derived.";
  }

  identity no-address-afi {
    base lisp-address-family;
    description
      "IANA Reserved.";
  }

  identity ipv4-afi {
    base lisp-address-family;
    description
      "IANA IPv4 address family.";
  }

  identity ipv4-prefix-afi {
    base lisp-address-family;
    description
      "IANA IPv4 address family prefix.";
  }

  identity ipv6-afi {
    base lisp-address-family;
    description
      "IANA IPv6 address family.";
  }

  identity ipv6-prefix-afi {
    base lisp-address-family;
    description
      "IANA IPv6 address family prefix.";
  }

  identity mac-afi {
    base lisp-address-family;
    description
      "IANA MAC address family.";
  }

  identity distinguished-name-afi {
    base lisp-address-family;
    description
      "IANA Distinguished Name address family.";
  }

  identity as-number-afi {
    base lisp-address-family;
    description
      "IANA AS Number address family.";
  }

  identity lcaf {
    base lisp-address-family;
    description
      "IANA LISP Canonical Address Format address family.";
  }

  identity null-address-lcaf {
    base lcaf;
    description
      "Null body LCAF type.";
  }

  identity afi-list-lcaf {
    base lcaf;
    description
      "AFI-List LCAF type.";
  }

  identity instance-id-lcaf {
    base lcaf;
    description
      "Instance-ID LCAF type.";
  }

  identity as-number-lcaf {
    base lcaf;
    description
      "AS Number LCAF type.";
  }

  identity application-data-lcaf {
    base lcaf;
    description
      "Application Data LCAF type.";
  }

  identity opaque-key-lcaf {
    base lcaf;
    description
      "Opaque Key LCAF type.";
  }

  identity nat-traversal-lcaf {
    base lcaf;
    description
      "NAT-Traversal LCAF type.";
  }

  identity nonce-locator-lcaf {
    base lcaf;
    description
      "Nonce-Locator LCAF type.";
  }

  identity multicast-info-lcaf {
    base lcaf;
    description
      "Multicast Info LCAF type.";
  }

  identity explicit-locator-path-lcaf {
    base lcaf;
    description
      "Explicit Locator Path LCAF type.";
  }

  identity security-key-lcaf {
    base lcaf;
    description
      "Security Key LCAF type.";
  }

  identity source-dest-key-lcaf {
    base lcaf;
    description
      "Source/Dest LCAF type.";
  }

  identity replication-list-lcaf {
    base lcaf;
    description
      "Replication-List LCAF type.";
  }

  identity json-data-model-lcaf {
    base lcaf;
    description
      "JSON Data Model LCAF type.";
  }

  identity key-value-address-lcaf {
    base lcaf;
    description
      "Key/Value Address LCAF type.";
  }

  identity encapsulation-format-lcaf {
    base lcaf;
    description
      "Encapsulation Format LCAF type.";
  }

  identity vendor-specific-lcaf {
    base lcaf;
    description
      "Vendor-Specific LCAF type.";
  }

  typedef instance-id-type {
    type uint32 {
      range "0..16777215";
    }
    description
      "Defines the range of values for an Instance ID.";
  }

  typedef distinguished-name-type {
    type string;
    description
      "Distinguished Name address.";
    reference
      "http://www.iana.org/assignments/address-family-numbers/
        address-family-numbers.xhtml";
  }

  typedef simple-address {
    type union {
      type inet:ip-address;
      type inet:ip-prefix;
      type yang:mac-address;
      type distinguished-name-type;
      type inet:as-number;
    }
    description
      "Union of address types that can be part of LCAFs.";
  }
  typedef lisp-address-family-ref {
    type identityref {
      base lisp-address-family;
    }
    description
      "LISP address family reference.";
  }

  typedef lcaf-ref {
    type identityref {
      base lcaf;
    }
    description
      "LCAF types reference.";
  }

  typedef id-type {
    type string {
      length "1..64";
      pattern '[a-zA-Z0-9][a-zA-Z0-9\-_.:]*';
    }
    description
      "Pattern and length for general ids.";
  }

  grouping lisp-address {
    description
      "Generic LISP address.";
    leaf address-type {
      type lisp-address-family-ref;
      mandatory true;
      description
        "Type of the LISP address.";
    }
    choice address {
      description
        "Various LISP address types, including IP, MAC, and LCAF.";
      leaf no-address {
        when "../address-type = 'laddr:no-address-afi'" {
          description
            "When AFI is 0.";
        }
        type empty;
        description
          "No address.";
      }
      leaf ipv4 {
        when "../address-type = 'laddr:ipv4-afi'" {
          description
            "When AFI is IPv4.";
        }
        type inet:ipv4-address;
        description
          "IPv4 address.";
      }
      leaf ipv4-prefix {
        when "../address-type = 'laddr:ipv4-prefix-afi'" {
          description
            "When AFI is IPv4.";
        }
        type inet:ipv4-prefix;
        description
          "IPv4 prefix.";
      }
      leaf ipv6 {
        when "../address-type = 'laddr:ipv6-afi'" {
          description
            "When AFI is IPv6.";
        }
        type inet:ipv6-address;
        description
          "IPv6 address.";
      }
      leaf ipv6-prefix {
        when "../address-type = 'laddr:ipv6-prefix-afi'" {
          description
            "When AFI is IPv6.";
        }
        type inet:ipv6-prefix;
        description
          "IPv6 address.";
      }
      leaf mac {
        when "../address-type = 'laddr:mac-afi'" {
          description
            "When AFI is MAC.";
        }
        type yang:mac-address;
        description
          "MAC address.";
      }
      leaf distinguished-name {
        when "../address-type = 'laddr:distinguished-name-afi'" {
          description
            "When AFI is distinguished-name.";
        }
        type distinguished-name-type;
        description
          "Distinguished Name address.";
      }
      leaf as-number {
        when "../address-type = 'laddr:as-number-afi'" {
          description
            "When AFI is as-number.";
        }
        type inet:as-number;
        description
          "AS Number.";
      }
      container null-address {
        when "../address-type = 'laddr:null-address-lcaf'" {
          description
            "When LCAF type is null.";
        }
        description
          "Null body LCAF type";
        leaf address {
          type empty;
          description
            "AFI address.";
        }
      }
      container afi-list {
        when "../address-type = 'laddr:afi-list-lcaf'" {
          description
            "When LCAF type is AFI-List.";
        }
        description
          "AFI-List LCAF type.";
        reference
          "RC8060: LISP Canonical Address Format (LCAF)
            #section-4.10";
        leaf-list address-list {
          type simple-address;
          description
            "List of AFI addresses.";
        }
      }
      container instance-id {
        when "../address-type = 'laddr:instance-id-lcaf'" {
          description
            "When LCAF type is Instance ID as per RFC8060.";
        }
        description
          "Instance ID LCAF type.";
        reference
          "RC8060: LISP Canonical Address Format (LCAF)
            #section-4.1";
        leaf instance-id {
          type instance-id-type;
          description
            "Instance ID value.";
        }
        leaf mask-length {
          type uint8;
          description
            "Mask length.";
        }
        leaf address {
          type simple-address;
          description
            "AFI address.";
        }
      }
      container as-number-lcaf {
        when "../address-type = 'laddr:as-number-lcaf'" {
          description
            "When LCAF type is AS-Number.";
        }
        description
          "AS Number LCAF type.";
        reference
          "RC8060: LISP Canonical Address Format (LCAF)
            #section-4.2";
        leaf as {
          type inet:as-number;
          description
            "AS number.";
        }
        leaf address {
          type simple-address;
          description
            "AFI address.";
        }
      }
      container application-data {
        when "../address-type = 'laddr:application-data-lcaf'" {
          description
            "When LCAF type is Application Data.";
        }
        description
          "Application Data LCAF type.";
        reference
          "RC8060: LISP Canonical Address Format (LCAF)
            #section-5.1";
        leaf address {
          type simple-address;
          description
            "AFI address.";
        }
        leaf protocol {
          type uint8;
          description
            "Protocol number.";
        }
        leaf ip-tos {
          type int32;
          description
            "IP TOS, IPv6 TC, or Flow Label field.";
        }
        leaf local-port-low {
          type inet:port-number;
          description
            "Low end of local port range.";
        }
        leaf local-port-high {
          type inet:port-number;
          must '. >= ../local-port-low';
          description
            "High end of local port range.";
        }
        leaf remote-port-low {
          type inet:port-number;
          description
            "Low end of remote port range.";
        }
        leaf remote-port-high {
          type inet:port-number;
          must '. >= ../remote-port-low';
          description
            "High end of remote port range.";
        }
      }
      container opaque-key {
        when "../address-type = 'laddr:opaque-key-lcaf'" {
          description
            "When LCAF type is Opaque Key.";
        }
        description
          "Opaque Key LCAF type. The key fields are encoded in user
            order and MUST all have the same decoded-octet length.";
        reference
          "draft-ietf-lisp-rfc8060bis: LISP Canonical Address Format
            (LCAF), Section 4.5.";
        list key-field {
          key "key-field-id";
          min-elements 1;
          max-elements 16;
          ordered-by user;
          description
            "Ordered key subfields. The list size and wildcard leaves
              determine the Key Field Num and Key Wildcard Fields wire
              values.";
          leaf key-field-id {
            type id-type;
            description
              "Management identifier for the key field; it is not
                transmitted on the wire.";
          }
          leaf wildcard {
            type boolean;
            default "false";
            description
              "Indicates that this key field is not used in a lookup.";
          }
          leaf value {
            type binary;
            mandatory true;
            description
              "Opaque key-field value.";
          }
        }
      }
      container nat-traversal {
        when "../address-type = 'laddr:nat-traversal-lcaf'" {
          description
            "When LCAF type is NAT-Traversal.";
        }
        description
          "NAT-Traversal LCAF type.";
        reference
          "RC8060: LISP Canonical Address Format (LCAF)
            #section-4.4";
        leaf ms-udp-port {
          type uint16;
          default "4342";
          description
            "Map-Server UDP port.";
        }
        leaf etr-udp-port {
          type uint16;
          description
            "ETR UDP port.";
        }
        leaf global-etr-rloc {
          type simple-address;
          description
            "Global ETR RLOC address.";
        }
        leaf ms-rloc {
          type simple-address;
          description
            "Map-Server RLOC address.";
        }
        leaf private-etr-rloc {
          type simple-address;
          description
            "Private ETR RLOC address.";
        }
        leaf-list rtr-rlocs {
          type simple-address;
          description
            "List of RTR RLOC addresses.";
        }
      }
      container nonce-locator {
        when "../address-type = 'laddr:nonce-locator-lcaf'" {
          description
            "When LCAF type is Nonce Locator.";
        }
        description
          "Nonce Locator LCAF type.";
        reference
          "draft-ietf-lisp-rfc8060bis: LISP Canonical Address Format
            (LCAF), Section 4.7.";
        leaf nonce {
          type uint32 {
            range "0..16777215";
          }
          mandatory true;
          description
            "24-bit nonce value.";
        }
        leaf address {
          type inet:ip-address;
          mandatory true;
          description
            "IPv4 or IPv6 locator address.";
        }
      }
      container multicast-info {
        when "../address-type = 'laddr:multicast-info-lcaf'" {
          description
            "When LCAF type is Multicast Info.";
        }
        must "not(source-ipv4) or "
           + "(source-mask-length <= 32 and "
           + "group-mask-length <= 32)" {
          error-message
            "IPv4 source and group masks cannot exceed 32 bits.";
        }
        must "not(source-mac) or "
           + "(source-mask-length <= 48 and "
           + "group-mask-length <= 48)" {
          error-message
            "MAC source and group masks cannot exceed 48 bits.";
        }
        description
          "Multicast Info LCAF type. Source and group addresses use
            the same address family. The group address MUST be a
            multicast or broadcast address.";
        reference
          "draft-ietf-lisp-rfc8060bis: LISP Canonical Address Format
            (LCAF), Section 4.8.";
        leaf instance-id {
          type uint32;
          mandatory true;
          description
            "32-bit LCAF Instance ID.";
        }
        leaf source-mask-length {
          type uint8 {
            range "0..128";
          }
          mandatory true;
          description
            "Source mask length. The maximum is 32 for IPv4, 128 for
              IPv6, and 48 for a MAC address.";
        }
        leaf group-mask-length {
          type uint8 {
            range "0..128";
          }
          mandatory true;
          description
            "Group mask length. The maximum is 32 for IPv4, 128 for
              IPv6, and 48 for a MAC address.";
        }
        choice address-family {
          mandatory true;
          description
            "Address family shared by the source and group.";
          case ipv4 {
            leaf source-ipv4 {
              type inet:ipv4-address;
              mandatory true;
              description
                "IPv4 source or subnet address. An all-zero value is
                  the wildcard source.";
            }
            leaf group-ipv4 {
              type inet:ipv4-address;
              mandatory true;
              description
                "IPv4 multicast or broadcast group address.";
            }
          }
          case ipv6 {
            leaf source-ipv6 {
              type inet:ipv6-address;
              mandatory true;
              description
                "IPv6 source or subnet address. An all-zero value is
                  the wildcard source.";
            }
            leaf group-ipv6 {
              type inet:ipv6-address;
              mandatory true;
              description
                "IPv6 multicast group address.";
            }
          }
          case mac {
            leaf source-mac {
              type yang:mac-address;
              mandatory true;
              description
                "MAC source or subnet address. An all-zero value is
                  the wildcard source.";
            }
            leaf group-mac {
              type yang:mac-address;
              mandatory true;
              description
                "Multicast or broadcast MAC group address.";
            }
          }
        }
      }
      container explicit-locator-path {
        when "../address-type = 'laddr:explicit-locator-path-lcaf'" {
          description
            "When LCAF type type is Explicit Locator Path.";
        }
        description
          "Explicit Locator Path LCAF type.";
        reference
          "RC8060: LISP Canonical Address Format (LCAF)
            #section-4.6";
        list hop {
          key "hop-id";
          ordered-by user;
          description
            "List of locator hops forming the explicit path.";
          leaf hop-id {
            type id-type;
            description
              "Unique identifier for the hop.";
          }
          leaf address {
            type simple-address;
            description
              "AFI address.";
          }
          leaf lrs-bits {
            type bits {
              bit lookup {
                description
                  "Lookup bit.";
              }
              bit rloc-probe {
                description
                  "RLOC-probe bit.";
              }
              bit strict {
                description
                  "Strict bit.";
              }
            }
            description
              "Flag bits per hop.";
          }
        }
      }
      container security-key {
        when "../address-type = 'laddr:security-key-lcaf'" {
          description
            "When LCAF type is Security Key.";
        }
        description
          "Security Key LCAF type. Key Count and each Key Length are
            derived from the key-section list.";
        reference
          "draft-ietf-lisp-rfc8060bis: LISP Canonical Address Format
            (LCAF), Section 4.10.";
        leaf key-algorithm {
          type uint8;
          mandatory true;
          description
            "Algorithm that determines the key-material format.";
        }
        leaf revoke {
          type boolean;
          default "false";
          description
            "Indicates that the key is being revoked.";
        }
        list key-section {
          key "key-id";
          max-elements 255;
          ordered-by user;
          description
            "Ordered key sections.";
          leaf key-id {
            type uint8 {
              range "1..255";
            }
            description
              "Management identifier for the key section; it is not
                transmitted on the wire.";
          }
          leaf key-material {
            type binary {
              length "0..65535";
            }
            mandatory true;
            description
              "Key material for this section.";
          }
        }
        leaf address {
          type inet:ip-address;
          mandatory true;
          description
            "IPv4 or IPv6 locator that owns the security key.";
        }
      }
      container source-dest-key {
        when "../address-type = 'laddr:source-dest-key-lcaf'" {
          description
            "When LCAF type type is Source/Dest.";
        }
        description
          "Source/Dest LCAF type.";
        reference
          "RC8060: LISP Canonical Address Format (LCAF)
            #section-4.8";
        leaf source {
          type simple-address;
          description
            "Source address.";
        }
        leaf dest {
          type simple-address;
          description
            "Destination address.";
        }
      }
      container replication-list {
        when "../address-type = 'laddr:replication-list-lcaf'" {
          description
            "When LCAF type is Replication List.";
        }
        description
          "Replication List LCAF type. All entries use the address
            family selected by the enclosing choice.";
        reference
          "draft-ietf-lisp-rfc8060bis: LISP Canonical Address Format
            (LCAF), Section 4.12.";
        choice address-family {
          mandatory true;
          description
            "Address family shared by all replication entries.";
          case ipv4 {
            list ipv4-entry {
              key "entry-id";
              min-elements 1;
              ordered-by user;
              description
                "Ordered IPv4 replication entries.";
              leaf entry-id {
                type id-type;
                description
                  "Management identifier for the entry; it is not
                    transmitted on the wire.";
              }
              leaf level {
                type uint8;
                mandatory true;
                description
                  "Overlay distribution-tree level.";
              }
              leaf address {
                type inet:ipv4-address;
                mandatory true;
                description
                  "IPv4 RTR or ETR address.";
              }
            }
          }
          case ipv6 {
            list ipv6-entry {
              key "entry-id";
              min-elements 1;
              ordered-by user;
              description
                "Ordered IPv6 replication entries.";
              leaf entry-id {
                type id-type;
                description
                  "Management identifier for the entry; it is not
                    transmitted on the wire.";
              }
              leaf level {
                type uint8;
                mandatory true;
                description
                  "Overlay distribution-tree level.";
              }
              leaf address {
                type inet:ipv6-address;
                mandatory true;
                description
                  "IPv6 RTR or ETR address.";
              }
            }
          }
        }
      }
      container json-data-model {
        when "../address-type = 'laddr:json-data-model-lcaf'" {
          description
            "When LCAF type is JSON Data Model.";
        }
        description
          "JSON Data Model LCAF type. The selected encoding determines
            the B bit, and the encoded value determines JSON Length.";
        reference
          "draft-ietf-lisp-rfc8060bis: LISP Canonical Address Format
            (LCAF), Section 4.13.";
        choice json-encoding {
          mandatory true;
          description
            "JSON encoding carried by this LCAF.";
          leaf json-text {
            type string {
              length "1..65535";
            }
            description
              "RFC 8259 JSON text encoding.";
          }
          leaf json-binary {
            type binary {
              length "1..65535";
            }
            description
              "Universal Binary JSON encoding.";
          }
        }
        leaf address {
          type simple-address;
          description
            "Optional address associated with the JSON data model.";
        }
      }
      container key-value-address {
        when "../address-type = 'laddr:key-value-address-lcaf'" {
          description
            "When LCAF type type is Key/Value Address.";
        }
        description
          "Key/Value Address LCAF type.";
        reference
          "RC8060: LISP Canonical Address Format (LCAF)
            #section-5.5";
        leaf key {
          type simple-address;
          description
            "Address as Key.";
        }
        leaf value {
          type simple-address;
          description
            "Address as Value.";
        }
      }
      container encapsulation-format {
        when "../address-type = 'laddr:encapsulation-format-lcaf'" {
          description
            "When LCAF type is Encapsulation Format.";
        }
        description
          "Encapsulation Format LCAF type.";
        reference
          "draft-ietf-lisp-rfc8060bis: LISP Canonical Address Format
            (LCAF), Section 4.15.";
        leaf encapsulations {
          type bits {
            bit no-encapsulation {
              position 0;
              description
                "No encapsulation.";
            }
            bit gue {
              position 25;
              description
                "Generic UDP Encapsulation.";
            }
            bit geneve {
              position 26;
              description
                "Geneve encapsulation.";
            }
            bit nv-gre {
              position 27;
              description
                "NV-GRE encapsulation.";
            }
            bit vxlan-gpe {
              position 28;
              description
                "VXLAN-GPE encapsulation.";
            }
            bit vxlan {
              position 29;
              description
                "VXLAN encapsulation.";
            }
            bit layer-2-lisp {
              position 30;
              description
                "Layer 2 LISP encapsulation.";
            }
            bit layer-3-lisp {
              position 31;
              description
                "Layer 3 LISP encapsulation.";
            }
          }
          mandatory true;
          description
            "Supported encapsulation formats.";
        }
        leaf address {
          type inet:ip-address;
          mandatory true;
          description
            "IPv4 or IPv6 RLOC address.";
        }
      }
      container vendor-specific {
        when "../address-type = 'laddr:vendor-specific-lcaf'" {
          description
            "When LCAF type is Vendor-Specific.";
        }
        description
          "Vendor-Specific LCAF type.";
        reference
          "draft-ietf-lisp-rfc8060bis: LISP Canonical Address Format
            (LCAF), Section 4.16.";
        leaf oui {
          type yang:hex-string {
            length "8"; // "aa:bb:cc"
          }
          mandatory true;
          description
            "A 24-bit IEEE Organizationally Unique Identifier.";
          reference
            "IEEE Std 802, subclause 8.2.2";
        }
        leaf internal-format {
          type binary;
          mandatory true;
          description
            "Vendor-defined internal-format data.";
        }
      }
    }
  }
}
