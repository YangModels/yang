module ietf-notification-capabilities {
  yang-version 1.1;
  namespace
    "urn:ietf:params:xml:ns:yang:ietf-notification-capabilities";
  prefix notc;

  import ietf-yang-push {
    prefix yp;
    description
      "This module requires ietf-yang-push to be implemented.";
    reference
      "RFC 8641: Subscription to YANG Notifications for Datastore
        Updates";
  }
  import ietf-system-capabilities {
    prefix sysc;
    description
      "This module requires ietf-system-capabilities to be
       implemented.";
    reference
      "RFC XXXX: YANG Modules describing Capabilities for Systems
       and Datastore Update Notifications";
  }

  // RFC Ed.: replace the above XXXX with actual RFC number
  // and remove this note.

  organization
    "IETF NETCONF (Network Configuration) Working Group";
  contact
    "WG Web:   <https://datatracker.ietf.org/wg/netconf/>
     WG List:  <mailto:netconf@ietf.org>

     Editor:   Balazs Lengyel
               <mailto:balazs.lengyel@ericsson.com>";
  description
    "This module specifies YANG-Push [RFC 8641] related publisher
     capabilities.

     The module contains:

     - specification of which data nodes support 'on-change' or
     'periodic' notifications.

     - capabilities related to the throughput of notification data
     that the publisher can support. (Note that for a specific
     subscription, the publisher MAY allow only longer periods
     or smaller updates depending on, e.g., actual load conditions.)

     Capability values can be specified on system/publisher level,
     datastore level or for specific data nodes of a specific
     datastore (and their contained sub-trees), as defined in the
     ietf-system-capabilities module.

     If different data nodes covered by a single subscription
     have different values for a specific capability, then using
     values that are only acceptable for some of these data nodes,
     but not for others, may result in the rejection of the
     subscription.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  // RFC Ed.: replace XXXX with actual RFC number and remove this
  // note.

  revision 2021-04-02 {
    description
      "Initial version";
    reference
      "RFC XXXX: YANG Modules describing Capabilities for Systems
       and Datastore Update Notifications";
  }

  // RFC Ed.: replace XXXX with actual RFC number and remove this
  // note.

  grouping subscription-capabilities {
    description
      "Capabilities related to YANG-Push subscriptions
       and notifications";
    container subscription-capabilities {
      description
        "Capabilities related to YANG-Push subscriptions
         and notifications";
      typedef notification-support {
        type bits {
          bit config-changes {
            description
              "The publisher is capable of sending
               notifications for 'config true' nodes for the
               relevant scope and subscription type.";
          }
          bit state-changes {
            description
              "The publisher is capable of sending
               notifications for 'config false' nodes for the relevant
               scope and subscription type.";
          }
        }
        description
          "Type for defining whether 'on-change' or
           'periodic' notifications are supported for all data nodes,
           'config false' data nodes, 'config true' data nodes, or
           no data nodes.

           If the bit config-changes or state-changes is set
           for a datastore, or a set of nodes that does not contain
           nodes with the indicated config value, this has no
           effect, as if no support was declared. E.g. indicating
           support for state-changes for a candidate datastore has
           no effect.";
      }

      leaf max-nodes-per-update {
        type uint32 {
          range "1..max";
        }
        description
          "Maximum number of data nodes that can be sent
           in an update. The publisher MAY support more data nodes,
           but SHOULD support at least this number.

           May be used to avoid the 'update-too-big' error
           during subscription.";
        reference
          "RFC 8641: Subscription to YANG Notifications for Datastore
           Updates, the 'update-too-big' error/identity";
      }
      leaf periodic-notifications-supported {
        type notification-support;
        description
          "Specifies whether the publisher is capable of
           sending 'periodic' notifications for the selected
           data nodes including any subtrees that may exist
           below them.";
        reference
          "RFC 8641: Subscription to YANG Notifications for Datastore
           Updates, 'periodic' subscription concept";
      }
      choice update-period {
        description
          "Supported update period value or values for
           'periodic' subscriptions.";
        leaf minimum-update-period {
          type uint32;
          units "centiseconds";
          description
            "Indicates the minimal update period that is
             supported for a 'periodic' subscription.

             A subscription request to the selected data nodes with
             a smaller period than what this leaf specifies is
             likely to result in a 'period-unsupported' error.";
          reference
            "RFC 8641: Subscription to YANG Notifications for Datastore
             Updates, the period leaf in the ietf-yang-push YANG
             module";
        }
        leaf-list supported-update-period {
          type uint32;
          units "centiseconds";
          description
            "Supported update period values for a 'periodic'
             subscription.

             A subscription request to the selected data nodes with a
             period not included in the leaf-list will result in a
             'period-unsupported' error.";
          reference
            "RFC 8641: Subscription to YANG Notifications for Datastore
             Updates, the period leaf in the ietf-yang-push YANG
             module";
        }
      }
      leaf on-change-supported {
        if-feature "yp:on-change";
        type notification-support;
        description
          "Specifies whether the publisher is capable of
           sending 'on-change' notifications for the selected
           data nodes and the subtree below them.";
        reference
          "RFC 8641: Subscription to YANG Notifications for Datastore
           Updates, on-change concept";
      }
      leaf minimum-dampening-period {
        if-feature "yp:on-change";
        type uint32;
        units "centiseconds";
        description
          "The minimum dampening-period supported for 'on-change'
           subscriptions for the selected data nodes.

           If this value is present and greater than zero,
           that implies dampening is mandatory.";
        reference
          "RFC 8641: Subscription to YANG Notifications for
           Datastore Updates, the dampening-period leaf in the
           ietf-yang-push YANG module";
      }
      leaf-list supported-excluded-change-type {
        if-feature "yp:on-change";
        type union {
          type enumeration {
            enum none {
              value -2;
              description
                "None of the change types can be excluded.";
            }
            enum all {
              value -1;
              description
                "Any combination of change types can be excluded.";
            }
          }
          type yp:change-type;
        }
        description
          "The change types that can be excluded in
           YANG-Push subscriptions for the selected data nodes.";
        reference
          "RFC 8641: Subscription to YANG Notifications for Datastore
           Updates, the change-type typedef in the ietf-yang-push
           YANG module";
      }
    }
  }

  augment "/sysc:system-capabilities" {
    description
      "Add system level capabilities";
    uses subscription-capabilities {
      refine
        "subscription-capabilities/supported-excluded-change-type" {
        default "none";
      }
    }
  }

  augment "/sysc:system-capabilities/sysc:datastore-capabilities"
        + "/sysc:per-node-capabilities" {
    description
      "Add datastore and node level capabilities";
    uses subscription-capabilities {
      refine
        "subscription-capabilities/supported-excluded-change-type" {
        default "none";
      }
    }
  }
}
