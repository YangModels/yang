submodule ietf-snmp-engine {

  belongs-to ietf-snmp {
    prefix snmp;
  }

  import ietf-inet-types {
    prefix inet;
  }

  include ietf-snmp-common;

  organization
    "IETF NETMOD (NETCONF Data Modeling Language) Working Group";

  contact
    "WG Web:   <http://tools.ietf.org/wg/netmod/>
     WG List:  <mailto:netmod@ietf.org>

     WG Chair: Thomas Nadeau
               <mailto:tnadeau@lucidvision.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";

  description
    "This submodule contains a collection of YANG definitions
     for configuring SNMP engines.

     Copyright (c) 2014 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";

  // RFC Ed.: replace XXXX with actual RFC number and remove this
  // note.

  // RFC Ed.: update the date below with the date of RFC publication
  // and remove this note.

  revision 2014-02-09 {
    description
      "Initial revision.";
    reference
      "RFC XXXX: A YANG Data Model for SNMP Configuration";
  }

  augment /snmp:snmp {

    container engine {

      description
        "Configuration of the SNMP engine.";

      leaf enabled {
        type boolean;
        default "false";
        description
          "Enables the SNMP engine.";
      }

      container listen {
        description
          "Configuration of the transport endpoints on which the
           engine listens. Submodules providing configuration for
           additional transports are expected to augment this
           container.";

        list udp {
          key "ip port";
          description
            "A list of IPv4 and IPv6 addresses and ports to which the
             engine listens.";

          leaf ip {
            type inet:ip-address;
            description
              "The IPv4 or IPv6 address on which the engine
               listens.";
          }
          leaf port {
            type inet:port-number;
            description
              "The UDP port on which the engine listens.";
          }
        }
      }

      container version {
        description
          "SNMP version used by the engine";
        leaf v1 {
          type empty;
        }
        leaf v2c {
          type empty;
        }
        leaf v3 {
          type empty;
        }
      }

      leaf engine-id {
        type snmp:engine-id;
        description
          "The local SNMP engine's administratively-assigned unique
           identifier.

           If this leaf is not set, the device automatically
           calculates an engine id, as described in RFC 3411.  A
           server MAY initialize this leaf with the automatically
           created value.";
        reference "SNMP-FRAMEWORK-MIB.snmpEngineID";
      }

      leaf enable-authen-traps {
        type boolean;
        description
          "Indicates whether the SNMP entity is permitted to
           generate authenticationFailure traps.";
        reference "SNMPv2-MIB.snmpEnableAuthenTraps";
      }
    }
  }
}
