module ietf-schema-version-selection {
  yang-version 1.1;
  namespace
    "urn:ietf:params:xml:ns:yang:ietf-schema-version-selection";
  prefix "ver-sel";

  import ietf-inet-types {
    prefix inet;
    reference "RFC 6991: Common YANG Data Types.";
  }
  import ietf-datastores {
    prefix ds;
    reference
      "RFC 8342: Network Management Datastore Architecture (NMDA)";
  }
  import ietf-yang-library {
    prefix yanglib;
    reference "RFC 8525: YANG Library";
  }
  import ietf-yang-library-packages {
    prefix pkg;
    reference "draft-rwilton-netmod-yang-packages-01";
  }

  organization
    "IETF NETMOD (Network Modeling) Working Group";

  contact
    "WG Web:   <http://tools.ietf.org/wg/netmod/>
     WG List:  <mailto:netmod@ietf.org>

     Author:   Reshad Rahman
               <mailto:rrahman@cisco.com>

     Author:   Rob Wilton
               <mailto:rwilton@cisco.com>";

  description
    "This module provide a data model to advertise and allow the
     selection of schema versions by clients.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: update the date below with the date of RFC publication
  // and remove this note.
  // RFC Ed.: replace XXXX with actual RFC number and remove this
  // note.
  revision 2019-03-11 {
    description
      "Initial revision";
    reference
      "RFC XXXX: YANG Schema Version Selection";
  }

  /*
   * Typedefs
   */

  typedef yang-sem-ver {
    type string {
      pattern '\d+[.]\d+[.]\d+[mM]?';
    }
    description
      "Represents a YANG semantic version number.";
    reference
      "TODO - Should be defined by YANG versioning types module";
  }

  feature "default-schema-set" {
    description
      "Feature that allows clients to choose the default schema set
       to be used for clients that connect using the standard network
       configuration protocol port number or URL.

       Implementations may choose to only support this feature in
       <operational> to report the default-schema-set without
       allowing it to be configured.";
  }
  feature "secondary-schema-set" {
    description
      "Feature to choose if secondary schema sets may be configured
       by clients.

       Implementations may choose to only support this feature in
       <operational> to report secondary schema sets without
       allowing them to be configured.";
  }

  container schema-selection {
      description
        "YANG schema version selection";

    list schema-sets {
      key "name";

      description
        "All schema-sets that are available for client selection.";

      leaf name {
        type "string" {
          length "1..255";
        }
        description
          "The server assigned name of the schema-set.

           This should include the schema family, and appropriate
           versioning or release information";
      }

      container netconf {
        if-feature "secondary-schema-set";

        presence "Make this schema-set available via NETCONF";
        description
          "NETCONF protocol settings for this schema set, if
           available";

        leaf port {
          type inet:port-number;
          description
            "The port numnber to use for interacting with this
             schema-set.  If not configured,then the port number is
             server allocated.";
          reference
            "RFC 6242: Using the NETCONF Protocol over SSH";
        }
      }

      container restconf {
        if-feature "secondary-schema-set";

        presence
          "Make this schema-set available via RESTCONF";
        description
          "RESTCONF protocol settings for this schema set, if
           available";

        leaf port {
          type inet:port-number;
          default "443";
          description
            "The port numnber to use for interacting with this
             schema-set.  If not configured, then the port number
             defaults to the standard RESTCONF https port number of
             443";
          reference
            "RFC 8040: RESTCONF Protocol, section 2.1";
        }

        leaf root-path {
          type inet:uri;
          default "/restconf";
          description
            "The default root path to use to access the RESTCONF
             protocol instance for this schema-set";

        }
      }

      list datastores {
        key "datastore";
        config false;

        description
          "The list of datastores supported for this schema set";

        leaf datastore {
          type ds:datastore-ref;
          description
            "The datastore that this datastore schema is associated
             with";
          reference
            "RFC 8342: Network Management Datastore Architecture
             (NMDA)";
        }

        container package {
          description
            "YANG package associated with this datastore schema";

          leaf name {
            type leafref {
              path "/yanglib:yang-library/pkg:package/pkg:name";
            }
            description
              "The name of the YANG package this schema relates to";
          }
          leaf version {
            type leafref {
              path '/yanglib:yang-library/'
               + 'pkg:package[pkg:name = current()/../name]/'
               + 'pkg:version';
            }

            description
              "The version of the YANG package this schema relates
               to";
          }
        }
      }
    }

    leaf default-schema-set {
      if-feature "default-schema-set";
      type leafref {
        path '/schema-selection/schema-sets/name';
      }
      description
        "Specifies the default schema-set used by this device.  This
         is the set of datastore schema that is used if a client
         connects using the standard protocol port numbers and URLs";
    }
  }
}
