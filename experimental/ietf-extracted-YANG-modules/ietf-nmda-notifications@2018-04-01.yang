module ietf-nmda-notifications {
  namespace "urn:ietf:params:xml:ns:yang:ietf-nmda-notifications";
  prefix nmdan;

  import ietf-datastores {
    prefix ds;
  }
  import ietf-inet-types { prefix inet; }
  organization
    "IETF NETCONF (Network Configuration Protocol) Working Group";
  contact
    "WG Web:   <http://tools.ietf.org/wg/netconf/>
     WG List:  <mailto:netconf@ietf.org>
     WG Chair: Kent Watsen
               <mailto:kwatsen@juniper.net>
     WG Chair: Mahesh Jethanandani
               <mailto:mjethanandani@gmail.com>
     Editor:   Qin Wu
               <mailto:bill.wu@huawei.com>
     Editor:   Rohit R Ranade
               <mailto:rohitrranade@huawei.com>";
  description
    "This module defines a YANG data model for use with the
     NETCONF protocol that allows the NETCONF client to
     receive additional common NETCONF base event notifications
      related to NMDA.
     Copyright (c) 2012 IETF Trust and the persons identified as
     the document authors.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC xxxx; see
     the RFC itself for full legal notices.";

  revision 2018-04-01 {
    description
      "Initial version.";
    reference "RFC xxx: NETCONF Base Notifications for NMDA";
  }
  typedef session-id-or-zero-type {
     type uint32;
     description
       "NETCONF Session Id or Zero to indicate none";
   }

  grouping common-session-parms {
    description
      "Common session parameters to identify a
       management session.";

    leaf username {
      type string;
      mandatory true;
      description
        "Name of the user for the session.";
    }

    leaf session-id {
      type session-id-or-zero-type;
      mandatory true;
      description
        "Identifier of the session.
         A NETCONF session MUST be identified by a non-zero value.
         A non-NETCONF session MAY be identified by the value zero.";
    }

    leaf source-host {
      type inet:ip-address;
      description
        "Address of the remote host for the session.";
    }
  }
  notification nmda-data-validate {
    description
      "Generated when a NETCONF server detects that a
       Data validation event has occurred.  Indicates the event
       and the current state of the data validation procedure
       in progress.";
    reference "RFC 8342, Section 5";
    uses common-session-parms;
    leaf validate-event {
      type enumeration {
        enum "start" {
          description
            "The data validate procedure has started.";
        }
        enum "complete" {
          description
            "The data validation procedure has been completed.";
        }
      }
      mandatory true;
      description
        "Indicates the event that caused the notification.";
    }
    leaf validate-result {
      when "../validate-event = 'complete'";
      type enumeration {
        enum "fail" {
          description
            "The <intended> configuration fails to be validated
             before being applied to <operational>, e.g., resources
             are not available or otherwise not physically present
             leads to the whole set of <intended>are not applied.";
        }
        enum "partial-fail" {
          description
            "The <intended> configuration partially fails to be
             validated before being applied to <operational>,e.g.,
             resources are not available or otherwise not physically
             present leads to parts of <intended>are not applied";
        }
        enum "success" {
          description
            "The <intended> configuration is successfully validated
             before being applied to <operational>.";
        }
      }
      description
        "Result of validate";
    }
    list fail-validate-target {
      leaf datastore {
        type identityref {
          base ds:datastore;
        }
        default "ds:operational";
        description
          "Indicates which datastore has changed or which datastore is
           target of edit-data operation.";
      }
      leaf target {
        type instance-identifier;
        description
          "Topmost node associated with the configuration change.
           A server SHOULD set this object to the node within
           the datastore that is being altered.  A server MAY
           set this object to one of the ancestors of the actual
           node that was changed, or omit this object, if the
           exact node is not known.";
      }
      description
        "List for fail validate targets";
    }
  }
}
