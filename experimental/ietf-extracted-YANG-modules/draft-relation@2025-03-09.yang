module draft-relation {
  yang-version 1.1;
  namespace "urn:ietf:params:xml:ns:yang:draft-relation";
  prefix dr-rel;

  import ietf-inet-types {
    prefix inet;
    reference
      "RFC 6991: Common YANG Data Types";
  }
  import ietf-network {
    prefix nw;
    reference
      "RFC 8345: A YANG Data Model for Network Topologies";
  }
  import ietf-network-topology {
    prefix nt;
    reference
      "RFC 8345: A YANG Data Model for Network Topologies";
  }
  import draft-template {
    prefix dr-tmp;
  }

  organization
    "INSA Lyon";
  contact
    "Editor:   Vivekananda Boudia
     <mailto:vivekananda.boudia@insa-lyon.fr>";
  description
    "relations external of RFC8345";

  revision 2025-03-09 {
    description
      "Initial revision";
    reference
      "";
  }

  container relation {
    description
      "relation container";
    list relation {
      key "relation-id";
      description
        "relation list";
      leaf relation-id {
        type inet:uri;
        description
          "relation id";
      }
      choice network-element-ref {
        description
          "linking to RFC8345";
        leaf network-ref {
          type leafref {
            path "/nw:networks/nw:network/nw:network-id";
          }
          description
            "linking to network";
        }
        leaf node-ref {
          type leafref {
            path "/nw:networks/nw:network/nw:node/nw:node-id";
          }
          description
            "linking to node";
        }
        leaf link-ref {
          type leafref {
            path "/nw:networks/nw:network/nt:link/nt:link-id";
          }
          description
            "linking to link";
        }
        leaf tp-ref {
          type leafref {
            path "/nw:networks/nw:network/nw:node/nt:termination-point/nt:tp-id";
          }
          description
            "linking to termination point";
        }
      }
      leaf template-ref {
        type leafref {
          path "/dr-tmp:template/dr-tmp:template/dr-tmp:template-id";
        }
        description
          "reference to template";
      }
      leaf-list request-type-supported {
        type identityref {
          base dr-tmp:request-type;
        }
        description
          "template is generic and may include requests that are not supported by the network element
           here, we specify the types of requests that the network element supports
           if network element supports all template ALL-REQUEST may be used";
      }
      leaf path {
        type string;
        description
          "network element can be augmented and may contain containers nested within other containers.
           path is used for filtering.";
      }
      list parameter-value {
        key "param-ref request-type";
        description
          "parameter value from network element";
        leaf param-ref {
          type leafref {
            path "/dr-tmp:template/dr-tmp:template/dr-tmp:parameter/dr-tmp:param-id";
          }
          description
            "reference to template parameter";
        }
        leaf request-type {
          type identityref {
            base dr-tmp:request-type;
          }
          description
            "value can be different depending on the request";
        }
        leaf value {
          type string;
          description
            "value of the parameter";
        }
      }
    }
  }
}
