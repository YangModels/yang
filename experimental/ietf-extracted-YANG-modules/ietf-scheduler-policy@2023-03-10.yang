module ietf-scheduler-policy {
  yang-version 1.1;
  namespace "urn:ietf:params:xml:ns:yang:ietf-scheduler-policy";
  prefix scheduler-policy;

  import ietf-qos-action {
    prefix action;
  }
  import ietf-traffic-policy {
    prefix policy;
  }

  organization
    "IETF Routing Area Working Group";

  contact
    "WG Web:   <https://datatracker.ietf.org/wg/rtgwg/>
     WG List:  <mailto:rtgwg@ietf.org>

     Editor:   Aseem Choudhary
               <mailto:achoudhary@aviatrix.com>
     Editor:   Mahesh Jethanandani
               <mailto:mjethanandani@gmail.com>";

  description
    "This module contains a collection of YANG definitions for
     configuring diffserv specification implementations.

     Copyright (c) 2021 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2023-03-10 {
    description
      "Initial version";
    reference
      "RFC XXXX: YANG Models for Quality of Service (QoS).";
  }

  grouping filter-match-all {
    container match-all {
      leaf match-all-action {
        type empty;
        description
          "match all packets";
      }
      description
        "the match-all action";
    }
    description
      "the match-all filter grouping";
  }

  augment "/policy:policies/policy:policy/policy:classifier" +
          "/policy:inline/policy:filter" {
        when "derived-from-or-self(../../../policy:type, " +
             "'scheduler-policy:scheduler-policy-type')" {
            description
               "Only when policy type is scheduler-policy";
        }
    choice filter-params {
      description
        "Choice of action types";
      case filter-match-all {
        uses filter-match-all;
        description
          "filter match-all";
      }
    }
    description
      "Augments Queue policy Classifier with common filter types";
  }

  grouping queue-policy-name {
    container queue-policy-name {
      leaf queue-policy {
        type string ;
        mandatory true;
        description
          "This leaf defines name of the queue-policy";
      }
    description
      "container for queue-policy name";
    }
    description
      "queue-policy name grouping";
  }

  augment "/policy:policies/policy:policy/policy:classifier" +
          "/policy:action/policy:action-params" {
        when "derived-from-or-self(../../policy:type, " +
             "'scheduler-policy:scheduler-policy-type')" {
            description
               "Only when policy type is scheduler-policy";
        }
      case scheduler {
        uses action:scheduler;
      }
      case queue-policy-name {
        uses queue-policy-name;
      }
    description
      "augments scheduler template reference to scheduler policy";
  }
}
