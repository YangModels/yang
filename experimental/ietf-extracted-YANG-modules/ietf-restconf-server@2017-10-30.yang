module ietf-restconf-server {
  yang-version 1.1;

  namespace "urn:ietf:params:xml:ns:yang:ietf-restconf-server";
  prefix "rcs";

  import ietf-inet-types {
    prefix inet;
    reference
      "RFC 6991: Common YANG Data Types";
  }

  import ietf-x509-cert-to-name {
    prefix x509c2n;
    reference
      "RFC 7407: A YANG Data Model for SNMP Configuration";
  }

  import ietf-tls-server {
    prefix ts;
    revision-date 2017-10-30; // stable grouping definitions
    reference
      "RFC ZZZZ: YANG Groupings for TLS Clients and TLS Servers";
  }

  organization
   "IETF NETCONF (Network Configuration) Working Group";

  contact
   "WG Web:   <http://tools.ietf.org/wg/netconf/>
    WG List:  <mailto:netconf@ietf.org>

    Author:   Kent Watsen
              <mailto:kwatsen@juniper.net>

    Author:   Gary Wu
              <mailto:garywu@cisco.com>

    Author:   Juergen Schoenwaelder
              <mailto:j.schoenwaelder@jacobs-university.de>";

  description
   "This module contains a collection of YANG definitions for
    configuring RESTCONF servers.

    Copyright (c) 2017 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2017-10-30" {
    description
     "Initial version";
    reference
     "RFC XXXX: RESTCONF Client and Server Models";
  }

  // Features

  feature listen {
    description
     "The 'listen' feature indicates that the RESTCONF server
      supports opening a port to accept RESTCONF client connections
      using at least one transport (e.g., TLS, etc.).";
  }

  feature tls-listen {
    if-feature listen;
    description
     "The 'tls-listen' feature indicates that the RESTCONF server
      supports opening a port to listen for incoming RESTCONF
      client connections.  This feature exists as TLS might not
      be a mandatory-to-implement transport in the future.";
    reference
     "RFC 8040: RESTCONF Protocol";
  }

  feature call-home {
    description
     "The 'call-home' feature indicates that the RESTCONF server
      supports initiating RESTCONF call home connections to RESTCONF
      clients using at least one transport (e.g., TLS, etc.).";
    reference
     "RFC 8071: NETCONF Call Home and RESTCONF Call Home";
  }

  feature tls-call-home {
    if-feature call-home;
    description
     "The 'tls-call-home' feature indicates that the RESTCONF server
      supports initiating connections to RESTCONF clients.  This
      feature exists as TLS might not be a mandatory-to-implement
      transport in the future.";
    reference
     "RFC 8071: NETCONF Call Home and RESTCONF Call Home";
  }

  container restconf-server {
    uses restconf-server;
    description
      "Top-level container for RESTCONF server configuration.";
  }

  grouping restconf-server {
    description
      "Top-level grouping for RESTCONF server configuration.";

    container listen {
      if-feature listen;
      description
        "Configures listen behavior";
      list endpoint {
        key name;
        description
          "List of endpoints to listen for RESTCONF connections.";
        leaf name {
          type string;
          description
            "An arbitrary name for the RESTCONF listen endpoint.";
        }
        choice transport {
          mandatory true;
          description
            "Selects between available transports. This is a 'choice'
             statement so as to support additional transport options
             to be augmented in.";
          case tls {
            if-feature tls-listen;
            container tls {
              description
                "TLS-specific listening configuration for inbound
                 connections.";
              leaf address {
                type inet:ip-address;
              description
                "The IP address to listen on for incoming connections.
                 The RESTCONF server will listen on all configured
                 interfaces if no value is specified.  INADDR_ANY
                 (0.0.0.0) or INADDR6_ANY (0:0:0:0:0:0:0:0 a.k.a. ::)
                 MUST be used when the server is to listen on all IPv4
                 or IPv6 addresses, respectively.";
              }
              leaf port {
                type inet:port-number;
                default 443;
                description
                 "The local port number to listen on.  If no value is
                  specified, the IANA-assigned port value for 'https'
                  (443) is used.";
              }
              uses ts:tls-server-grouping {
                refine "client-auth" {
                  must 'pinned-ca-certs or pinned-client-certs';
                  description
                    "RESTCONF servers MUST be able to validate
                     clients.";
                }
                augment "client-auth" {
                  description
                    "Augments in the cert-to-name structure,
                     so the RESTCONF server can map TLS-layer
                     client certificates to RESTCONF usernames.";
                  container cert-maps {
                    uses x509c2n:cert-to-name;
                    description
                     "The cert-maps container is used by a TLS-based
                      RESTCONF server to map the RESTCONF client's
                      presented X.509 certificate to a RESTCONF
                      username.  If no matching and valid
                      cert-to-name list entry can be found, then
                      the RESTCONF server MUST close the connection,
                      and MUST NOT accept RESTCONF messages over
                      it.";
                    reference
                      "RFC 7407: A YANG Data Model for SNMP
                                 Configuration.";
                  }
                }
              }
            } // end tls container
          } // end tls case
        } // end transport
      } // end endpoint
    } // end listen

    container call-home {
      if-feature call-home;
      description
        "Configures call-home behavior";
      list restconf-client {
        key name;
        description
          "List of RESTCONF clients the RESTCONF server is to
           initiate call-home connections to in parallel.";
        leaf name {
          type string;
          description
            "An arbitrary name for the remote RESTCONF client.";
        }
        container endpoints {
          description
            "Container for the list of endpoints.";
          list endpoint {
            key name;
            min-elements 1;
            ordered-by user;
            description
              "User-ordered list of endpoints for this RESTCONF
               client.  Defining more than one enables high-
               availability.";
            leaf name {
              type string;
              description
                "An arbitrary name for this endpoint.";
            }
            choice transport {
              mandatory true;
              description
                "Selects between available transports. This is a
                 'choice' statement so as to support additional
                 transport options to be augmented in.";
              case tls {
                if-feature tls-call-home;
                container tls {
                  description
                    "Specifies TLS-specific call-home transport
                     configuration.";
                  leaf address {
                    type inet:host;
                    mandatory true;
                    description
                     "The IP address or hostname of the endpoint.
                      If a domain name is configured, then the DNS
                      resolution should happen on each usage attempt.
                      If the DNS resolution results in multiple IP
                      addresses, the IP addresses will be tried
                      according to local preference order until a
                      connection has been established or until all
                      IP addresses have failed.";
                  }
                  leaf port {
                    type inet:port-number;
                    default 4336;
                    description
                     "The IP port for this endpoint.  The RESTCONF
                      server will use the IANA-assigned well-known
                      port for 'restconf-ch-tls' (4336) if no value
                      is specified.";
                  }
                  uses ts:tls-server-grouping {
                    refine "client-auth" {
                      must 'pinned-ca-certs or pinned-client-certs';
                      description
                        "RESTCONF servers MUST be able to validate
                         clients.";
                    }
                    augment "client-auth" {
                      description
                        "Augments in the cert-to-name structure,
                         so the RESTCONF server can map TLS-layer
                         client certificates to RESTCONF usernames.";
                      container cert-maps {
                        uses x509c2n:cert-to-name;
                        description
                         "The cert-maps container is used by a
                          TLS-based RESTCONF server to map the
                          RESTCONF client's presented X.509
                          certificate to a RESTCONF username. If
                          no matching and valid cert-to-name list
                          entry can be found, then the RESTCONF
                          server MUST close the connection, and
                          MUST NOT accept RESTCONF messages over
                          it.";
                        reference
                          "RFC 7407: A YANG Data Model for SNMP
                           Configuration.";
                      }
                    }
                  }
                }
              }
            } // end transport
          } // end endpoint
        } // end endpoints
        container connection-type {
          description
           "Indicates the RESTCONF client's preference for how the
            RESTCONF server's connection is maintained.";
          choice connection-type {
            description
              "Selects between available connection types.";
            case persistent-connection {
              container persistent {
                presence true;
                description
                 "Maintain a persistent connection to the RESTCONF
                  client. If the connection goes down, immediately
                  start trying to reconnect to it, using the
                  reconnection strategy.

                  This connection type minimizes any RESTCONF client
                  to RESTCONF server data-transfer delay, albeit at
                  the expense of holding resources longer.";
                leaf idle-timeout {
                  type uint32;
                  units "seconds";
                  default 86400;  // one day;
                  description
                    "Specifies the maximum number of seconds that the
                     underlying TLS session may remain idle. A TLS
                     session will be dropped if it is idle for an
                     interval longer than this number of seconds.
                     If set to zero, then the server will never drop
                     a session because it is idle.  Sessions that
                     have a notification subscription active are
                     never dropped.";
                }
                container keep-alives {
                  description
                    "Configures the keep-alive policy, to proactively
                     test the aliveness of the TLS client.  An
                     unresponsive TLS client will be dropped after
                     approximately (max-attempts * max-wait)
                     seconds.";
                  reference
                    "RFC 8071: NETCONF Call Home and RESTCONF Call
                     Home, Section 3.1, item S6";
                  leaf max-wait {
                    type uint16 {
                      range "1..max";
                    }
                    units seconds;
                    default 30;
                    description
                     "Sets the amount of time in seconds after which
                      if no data has been received from the TLS
                      client, a TLS-level message will be sent to
                      test the aliveness of the TLS client.";
                  }
                  leaf max-attempts {
                    type uint8;
                    default 3;
                    description
                     "Sets the maximum number of sequential keep-alive
                      messages that can fail to obtain a response from
                      the TLS client before assuming the TLS client is
                      no longer alive.";
                  }
                }
              }
            }
            case periodic-connection {
              container periodic {
                presence true;
                description
                 "Periodically connect to the RESTCONF client, so that
                  the RESTCONF client may send requests pending for
                  the RESTCONF server.  Once the connection has been
                  closed, for whatever reason, the server will restart
                  its timer until the next connection.";
                leaf idle-timeout {
                  type uint16;
                  units "seconds";
                  default 300; // five minutes
                  description
                    "Specifies the maximum number of seconds that the
                     underlying TLS session may remain idle.  A TLS
                     session will be dropped if it is idle for an
                     interval longer than this number of seconds.
                     If set to zero, then the server will never drop
                     a session because it is idle.  Sessions that
                     have a notification subscription active are
                     never dropped.";
                }
                leaf reconnect-timeout {
                  type uint16 {
                    range "1..max";
                  }
                  units minutes;
                  default 60;
                  description
                   "The maximum amount of unconnected time the
                    RESTCONF server will wait before re-establishing
                    a connection to the RESTCONF client.  The
                    RESTCONF server may initiate a connection to
                    the RESTCONF client before this time if desired
                    (e.g., to deliver a notification).";
                }
              }
            }
          }
        }
        container reconnect-strategy {
          description
           "The reconnection strategy directs how a RESTCONF server
            reconnects to a RESTCONF client after after discovering
            its connection to the client has dropped, even if due to
            a reboot.  The RESTCONF server starts with the specified
            endpoint and tries to connect to it max-attempts times
            before trying the next endpoint in the list (round
            robin).";
          leaf start-with {
            type enumeration {
              enum first-listed {
                description
                  "Indicates that reconnections should start with
                   the first endpoint listed.";
              }
              enum last-connected {
                description
                  "Indicates that reconnections should start with
                   the endpoint last connected to.  If no previous
                   connection has ever been established, then the
                   first endpoint configured is used.   RESTCONF
                   servers SHOULD be able to remember the last
                   endpoint connected to across reboots.";
              }
            }
            default first-listed;
            description
             "Specifies which of the RESTCONF client's endpoints the
              RESTCONF server should start with when trying to connect
              to the RESTCONF client.";
          }
          leaf max-attempts {
            type uint8 {
              range "1..max";
            }
            default 3;
            description
             "Specifies the number times the RESTCONF server tries to
              connect to a specific endpoint before moving on to the
              next endpoint in the list (round robin).";
          }
        }
      }
    }
  }
}
