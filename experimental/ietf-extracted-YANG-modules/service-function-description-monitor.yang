module service-function-description-monitor {
  namespace "urn.intel.params:xml:ns:sf-desc-mon";
  prefix sf-desc-mon;

  import service-function { prefix sfc-sf;}
  import service-function-description-monitor-report { prefix sf-desc-mon-rpt;}

  organization "Intel Inc.";
  contact "honglix.chen@intel.com";
  description
      "Create description and monitoring information of Service
       Function extensions to service-function model";

  revision 2014-12-01 {
      description "Initial revision.";
  }

  augment "/sfc-sf:service-functions-state/sfc-sf:service-function-state" {
    description "Service function description and monitoring information";
    container sfc-sf-desc-mon {
      container description-info {
        uses sf-desc-mon-rpt:SF-description;
      }
      container monitoring-info {
        uses sf-desc-mon-rpt:SF-monitoring-info;
      }
    }
  }
}
