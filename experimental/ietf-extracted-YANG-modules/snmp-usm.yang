submodule snmp-usm {

  belongs-to snmp {
    prefix snmp;
  }

  include snmp-common;

  description
    "This submodule contains a collection of YANG definitions for
    configuring the User-based Security Model (USM) of SNMP.";
  reference
    "RFC3414: User-based Security Model (USM) for version 3 of the
              Simple Network Management Protocol (SNMPv3).";

  revision 2010-10-17 {
    description
      "Initial revision.";
  }

  grouping key {
    choice key-type {
      leaf password {
        /* This must be stored in the config; it cannot be derived from
           the SNMP table.  Also, if SNMP is used to set the key,
           this password will not be used anymore */
        type string;
        description
          "Will be used to create a localized key.";
      }
      leaf key {
        type string {
          pattern '([0-9a-fA-F]){2}(:([0-9a-fA-F]){2})*';
        }
        description
          "Authentication key specified as a list of colon-specified
          hexa-decimal octets";
      }
    }
  }

  grouping user-list {
    list user {
      key "name";
      reference "SNMP-USER-BASED-SM-MIB.usmUserTable";

      leaf name {
        type snmp:identifier;
        reference "SNMP-USER-BASED-SM-MIB.usmUserName
                   SNMP-USER-BASED-SM-MIB.usmUserSecurityName";
      }
      leaf security-name {
        type snmp:identifier;
        description
          "If not set, the value of 'name' is operationally used";
        reference "SNMP-USER-BASED-SM-MIB.usmUserSecurityName";
      }
      container auth {
        presence "enables authentication";
        description "Enables authentication protocol of the user";
        choice protocol {
          mandatory true;
          reference "SNMP-USER-BASED-SM-MIB.usmUserAuthProtocol";
          container md5 {
            presence "md5";
            uses key;
          }
          container sha {
            presence "sha";
            uses key;
          }
        }
      }
      container priv {
        must "../auth" {
          error-message
            "when privacy is used, authentication must also be used";
        }
        presence "enables encryption";
        description
          "Enables encryption for the authentication process.";

        choice protocol {
          mandatory true;
          reference "SNMP-USER-BASED-SM-MIB.usmUserPrivProtocol";
          container des {
            presence "des";
            uses key;
          }
          container aes {
            presence "aes";
            uses key;
          }
        }
      }
    }
  }

  augment /snmp:snmp {

    container usm {
      description
        "Configuration of the User-based Security Model";
      container local {
        uses user-list;
      }

      list remote {
        key "engine-id";

        leaf engine-id {
          type snmp:engine-id;
          reference "SNMP-USER-BASED-SM-MIB.usmUserEngineID";
        }

        uses user-list;
      }
    }
  }
}
