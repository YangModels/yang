module ietf-flexi-grid-media-channel {
   yang-version 1.1;

   namespace
     "urn:ietf:params:xml:ns:yang:ietf-flexi-grid-media-channel";
   prefix "fg-mc";

   import ietf-flexi-grid-ted {
      prefix "fg-ted";
   }

   import ietf-te {
      prefix "te";
   }

   import ietf-network {
      prefix "nd";
   }
   organization
      "IETF CCAMP Working Group";
   contact
      "Editor: Jorge Lopez de Vergara
                 <jorge.lopez_vergara@uam.es>";

   description
      "This module contains a collection of YANG definitions for
      a Flexi-Grid media channel.

      Copyright (c) 2017 IETF Trust and the persons identified as
      authors of the code.  All rights reserved.

      Redistribution and use in source and binary forms, with or
      without modification, is permitted pursuant to, and subject
      to the license terms contained in, the Simplified BSD
      License set forth in Section 4.c of the IETF Trust's Legal
      Provisions Relating to IETF Documents
      (http://trustee.ietf.org/license-info).";

   revision 2017-07-03 {
      description
         "version 0.";

      reference
         "RFC XXX: A Yang Data Model for Flexi-Grid media-channels";
   }
   grouping flexi-grid-media-channel {
         description
            "Media association that represents both the topology
            (i.e., path through the media) and the resource
            (frequency slot) that it occupies.  As a topological
            construct, it represents a (effective) frequency slot
            supported by a concatenation of media elements (fibers,
            amplifiers, filters, switching matrices...).  This term
            is used to identify the end-to-end physical layer entity
            with its corresponding (one or more) frequency slots
            local at each link filters.";
         reference "rfc7698";
         leaf source-port {
            type fg-ted:flexi-grid-node-port-ref;
            description "Source port";
          }
         leaf destination-port {
            type fg-ted:flexi-grid-node-port-ref;
            description "Destination port";
          }
         container effective-freq-slot {
         description "The effective frequency slot is an attribute
            of a media channel and, being a frequency slot, it is
            described by its nominal central frequency and slot
            width";
         reference "rfc7698";
            leaf N {
               type int32;
               description
                  "Is used to determine the Nominal Central
                  Frequency. The set of nominal central frequencies
                  can be built using the following expression:
                     f = 193.1 THz + n x 0.00625 THz,
                  where 193.1 THz is ITU-T ''anchor frequency'' for
                  transmission over the C band, n is a positive or
                  negative integer including 0.";
               reference "rfc7698";
            }
            leaf M {
               type int32;
               description
                  "Is used to determine the slot width. A slot width
                  is constrained to be M x SWG (that is, M x 12.5 GHz),
                  where M is an integer greater than or equal to 1.";
               reference "rfc7698";
         }
      }
   }
   grouping link-channel-attributes {
      description
         "A link channel is one of the concatenated elements of
         the media channel.";
      leaf N {
         type int32;
         description
            "Is used to determine the Nominal Central Frequency.
            The set of nominal central frequencies can be built
            using the following expression:
               f = 193.1 THz + n x 0.00625 THz,
            where 193.1 THz is ITU-T ''anchor frequency'' for
            transmission over the C band, n is a positive or
            negative integer including 0.";
         reference "rfc7698";
      }
      leaf M {
         type int32;
            description
               "Is used to determine the slot width. A slot
               width is constrained to be M x SWG (that is,
               M x 12.5 GHz), where M is an integer greater than
               or equal to 1.";
            reference "rfc7698";
      }
      leaf source-port {
         type fg-ted:flexi-grid-node-port-ref;
         description "Source port of the link channel";
      }
      leaf destination-port {
         type fg-ted:flexi-grid-node-port-ref;
         description "Destination port of the link channel";
      }
      leaf link {
         type fg-ted:flexi-grid-link-ref;
         description "Link of the link channel";
      }
      leaf bidirectional {
         type boolean;
         description
            "Determines whether the link is bidirectional or
            not";
      }
   }
   /* Augment for media-channel */
   augment "/te:te/te:tunnels/te:tunnel/te:config" {
       when "/nd:networks/nd:network/nd:network-types/
     fg-ted:flexi-grid-network"{
          description "Augment only for Flexigrid network.";
       }
       description "Augment tunnel with media-channel config";
       uses flexi-grid-media-channel;

   }

      augment "/te:te/te:tunnels/te:tunnel/te:state" {
       when "/nd:networks/nd:network/nd:network-types/
     fg-ted:flexi-grid-network"{
          description "Augment only for Flexigrid network.";
       }
       uses flexi-grid-media-channel;
       description "Augment tunnel with media-channel state";

   }

   /* Augment for LSP */
   augment "/te:te/te:lsps-state/te:lsp" {
      when "/nd:networks/nd:network/nd:network-types/
     fg-ted:flexi-grid-network"{
          description "Augment only for Flexigrid network.";
      }
      uses link-channel-attributes;
      description "Augment LSP for paths";
   }

}
