module ietf-ipv4-unicast-routing {

  namespace "urn:ietf:params:xml:ns:yang:ietf-ipv4-unicast-routing";

  prefix "v4ur";

  import ietf-routing {
    prefix "rt";
  }

  import ietf-inet-types {
    prefix "inet";
  }

  organization
    "IETF NETMOD (NETCONF Data Modeling Language) Working Group";

  contact
    "WG Web: <http://tools.ietf.org/wg/netmod/>
     WG List: <mailto:netmod@ietf.org>

     WG Chair: David Kessens
     <mailto:david.kessens@nsn.com>

     WG Chair: Juergen Schoenwaelder
     <mailto:j.schoenwaelder@jacobs-university.de>

     Editor: Ladislav Lhotka
     <mailto:lhotka@nic.cz>
    ";

  description
    "This YANG module augments the 'ietf-routing' module with basic
     configuration and operational state data for IPv4 unicast
     routing.

     Copyright (c) 2013 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.
    ";

  revision 2013-07-13 {
    description
      "Initial revision.";
    reference
      "RFC XXXX: A YANG Data Model for Routing Management";
  }

  /* Groupings */

  grouping route-content {
    description
      "Parameters of IPv4 unicast routes.";
    leaf dest-prefix {
      type inet:ipv4-prefix;
      description
        "IPv4 destination prefix.";
    }
    leaf next-hop {
      type inet:ipv4-address;
      description
        "IPv4 address of the next hop.";
    }
  }

  /* RPC Methods */

  augment "/rt:active-route/rt:input/rt:destination-address" {
    when "rt:address-family='ipv4' and rt:safi='nlri-unicast'" {
      description
        "This augment is valid only for IPv4 unicast.";
    }
    description
      "The 'address' leaf augments the 'rt:destination-address'
       parameter of the 'rt:active-route' operation.";
    leaf address {
      type inet:ipv4-address;
      description
        "IPv4 destination address.";
    }
  }

  augment "/rt:active-route/rt:output/rt:route" {
    when "rt:address-family='ipv4' and rt:safi='nlri-unicast'" {
      description
        "This augment is valid only for IPv4 unicast.";
    }
    description
      "Contents of the reply to 'rt:active-route' operation.";
    uses route-content;
  }

  /* Operational state */

  augment "/rt:routing-state/rt:routing-tables/rt:routing-table/"
        + "rt:routes/rt:route" {
    when "../../rt:address-family = 'ipv4' and ../../rt:safi = "
       + "'nlri-unicast'" {
      description
        "This augment is valid only for IPv4 unicast.";
    }
    description
      "This augment defines the content of IPv4 unicast routes.";
    uses route-content;
  }

  /* Configuration */

  augment "/rt:routing/rt:router/rt:routing-protocols/"
        + "rt:routing-protocol/rt:static-routes" {
    description
      "This augment defines the configuration of the 'static'
       pseudo-protocol with data specific for IPv4 unicast.";
    container ipv4 {
      description
        "Configuration of a 'static' pseudo-protocol instance
         consists of a list of routes.";
      list route {
        key "id";
        ordered-by "user";
        description
          "A user-ordered list of static routes.";
        leaf id {
          type uint32 {
            range "1..max";
          }
          description
            "Numeric identifier of the route.

             It is not required that the routes be sorted by their
             'id'.
            ";
        }
        leaf description {
          type string;
          description
            "Textual description of the route.";
        }
        uses rt:route-content;
        uses route-content {
          refine "dest-prefix" {
            mandatory "true";
          }
        }
      }
    }
  }
}
