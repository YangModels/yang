module ietf-hw-inventory-ref-topo {
 yang-version 1.1;
 namespace "urn:ietf:params:xml:ns:yang:ietf-hw-inventory-ref-topo";
 prefix hirt;

  import ietf-network {
    prefix nw;
    reference
      "RFC8345: A YANG Data Model for Network Topologies";
  }

  import ietf-network-topology {
    prefix nt;
    reference
      "RFC8345: A YANG Data Model for Network Topologies";
  }

  import ietf-network-hardware-inventory {
    prefix nhi;
    reference
      "RFC XXXX: A YANG Data Model for Network Hardware Inventory.";
      //RFC Editor: replace XXXX with actual RFC number, update date
      //information and remove this note
  }

 organization
   "IETF CCAMP Working Group";
 contact
   "WG Web:   <https://datatracker.ietf.org/wg/ccamp/>
    WG List:  <mailto:ccamp@ietf.org>

    Editor:   Chaode Yu
              <yuchaode@huawei.com>

    Editor:   Sergio Belotti
              <sergio.belotti@nokia.com>

    Editor:   Jean-Francois Bouquier
              <jeff.bouquier@vodafone.com>

    Editor:   Fabio Peruzzini
              <fabio.peruzzini@telecomitalia.it>

    Editor:   Phil Bedard
              <phbedard@cisco.com>";

 description
   "This module defines a model for navigation between hardware
   inventory data module and network topology module.

   The model fully conforms to the Network Management
   Datastore Architecture (NMDA).

   Copyright (c) 2021 IETF Trust and the persons
   identified as authors of the code.  All rights reserved.

   Redistribution and use in source and binary forms, with or
   without modification, is permitted pursuant to, and subject
   to the license terms contained in, the Simplified BSD License
   set forth in Section 4.c of the IETF Trust's Legal Provisions
   Relating to IETF Documents
   (https://trustee.ietf.org/license-info).
   This version of this YANG module is part of RFC XXXX; see
   the RFC itself for full legal notices.

   The key words 'MUST', 'MUST NOT', 'REQUIRED', 'SHALL', 'SHALL
   NOT', 'SHOULD', 'SHOULD NOT', 'RECOMMENDED', 'NOT RECOMMENDED',
   'MAY', and 'OPTIONAL' in this document are to be interpreted as
   described in BCP 14 (RFC 2119) (RFC 8174) when, and only when,
   they appear in all capitals, as shown here.";

 // RFC Ed.: replace XXXX with actual RFC number and remove this
 // note.
 // RFC Ed.: update the date below with the date of RFC publication
 // and remove this note.

  revision 2023-03-10 {
    description
      "Initial revision.";
     reference
       "RFC XXXX: A YANG Data Model for Network Hardware Inventory.";
       //RFC Editor: replace XXXX with actual RFC number, update date
       //information and remove this note
  }

  augment "/nw:networks/nw:network/nw:node" {
    description
      "Information that allows the relationship between the node in
      the topology and the Network Element (NE) in the network
      hardware inventory model from which the node is abstracted";

    leaf inventory-id {
    type leafref {
      path "/nhi:network-hardware-inventory/nhi:network-elements"
      + "/nhi:network-element/nhi:uuid";
    }
    config false;
    description
      "The identifier of the Network Element (NE) from which this
      node is abstracted";
    }
  }

  augment "/nw:networks/nw:network/nw:node/nt:termination-point" {
    description
      "Information that allows the relationship between the Link
      Termination Point (LTP) and the port component in the network
      hardware inventory model from which this LTP is abstracted.";

    leaf inventory-id {
    type leafref {
      path "/nhi:network-hardware-inventory/nhi:network-elements"
      + "/nhi:network-element/nhi:components/nhi:component"
      + "/nhi:uuid";
    }
    config false;
    description
        "The identifier of the port component from which this Link
        Termination Point (LTP) is abstracted";
    }
  }
}
