module ietf-network-vpn-pm {
  yang-version 1.1;
  namespace "urn:ietf:params:xml:ns:yang:ietf-network-vpn-pm";
  prefix nvp;

  import ietf-yang-types {
    prefix yang;
    reference
      "RFC 6991: Common YANG Types";
  }
  import ietf-vpn-common {
    prefix vpn-common;
    reference
      "RFC CCCC: A Layer 2/3 VPN Common YANG Model.";
    // RFC Ed.: replace CCCC with actual RFC number and remove
    // this note.
  }
  import ietf-network {
    prefix nw;
    reference
      "RFC 8345: A YANG Data Model for Network
       Topologies, Section 6.1";
  }
  import ietf-network-topology {
    prefix nt;
    reference
      "RFC 8345: A YANG Data Model for Network
       Topologies, Section 6.2";
  }
  import ietf-lime-time-types {
    prefix lime;
    reference
      "RFC 8532: Generic YANG Data Model for the Management of
       Operations, Administration, and Maintenance (OAM) Protocols
       That Use Connectionless Communications";
  }

  organization
    "IETF OPSAWG Working Group";
  contact
    "Editor: Qin Wu
             <bill.wu@huawei.com>
     Editor: Bo Wu
             <lana.wubo@huawei.com>
     Editor: Mohamed Boucadair
             <mohamed.boucadair@orange.com>";
  description
    "This module defines a model for Network and VPN Service
     Performance monitoring.

     Copyright (c) 2022 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  // RFC Ed.: update the date below with the date of RFC
  // publication and remove this note.
  // RFC Ed.: replace XXXX with actual RFC number and remove
  // this note.

  revision 2022-01-28 {
    description
      "Initial revision.";
    reference
      "RFC XXXX: A YANG Model for Network and VPN Service
       Performance Monitoring";
  }

  identity node-type {
    description
      "Base identity for node type";
  }

  identity pe {
    base node-type;
    description
      "Provider Edge (PE) node type.";
    reference
      "RFC 4026: Provider Provisioned
       Virtual Private Network (VPN) Terminology";
  }

  identity p {
    base node-type;
    description
      "Provider router node type.";
    reference
      "RFC 4026: Provider Provisioned
       Virtual Private Network (VPN) Terminology";
  }

  identity asbr {
    base node-type;
    description
      "Autonomous System Border Router (ASBR) node type.";
    reference
      "RFC 4364: BGP/MPLS IP Virtual Private Networks (VPNs)";
  }

  identity pm-source-type {
    description
      "Base identity from which specific performance monitoring
       mechanism types are derived.";
  }

  identity pm-source-bgpls {
    base pm-source-type;
    description
      "Indicates BGP-LS as the performance monitoring metric source";
    reference
      "RFC 8571: BGP - Link State (BGP-LS) Advertisement of
        IGP Traffic Engineering Performance Metric Extensions";
  }

  identity pm-source-owamp {
    base pm-source-type;
    description
      "Indicates One-Way Active Measurement Protocol(OWAMP)
       as the performance monitoring metric source.";
    reference
      "RFC 4656: A One-Way Active Measurement Protocol (OWAMP)";
  }

  identity pm-source-twamp {
    base pm-source-type;
    description
      "Indicates Two-Way Active Measurement Protocol(TWAMP)
       as the performance monitoring metric source.";
    reference
      "RFC 5357: A Two-Way Active Measurement Protocol (TWAMP)";
  }

  identity pm-source-y-1731 {
    base pm-source-type;
    description
      "Indicates Ethernet OAM Y.1731 as the performance monitoring
       metric source.";
    reference
      "ITU-T Y.1731: Operations, administration and
       maintenance (OAM) functions and mechanisms
       for Ethernet-based networks";
  }

  typedef percentage {
    type decimal64 {
      fraction-digits 5;
      range "0..100";
    }
    description
      "Percentage.";
  }

  typedef percentile {
    type decimal64 {
      fraction-digits 2;
      range "0..100";
    }
    description
      "The percentile is a value between 0 and 100,
       e.g. 10.00, 99.90 ,99.99 etc..
       For example, for a given one-way delay measurement,
       if the percentile is set to 95.00 and
       the 95th percentile one-way delay is 2 milliseconds,
       then the 95 percent of the sample value
       is less than or equal to 2 milliseconds.";
  }

  grouping vpn-summary-statistics {
    description
      "VPN Statistics grouping used for network topology
       augmentation.";
    container vpn-summary-statistics {
      config false;
      description
        "Container for VPN summary statistics.";
      container ipv4 {
        leaf maximum-routes {
          type uint32;
          description
            "Indicates the maximum number of IPv4 routes
             for the VPN.";
        }
        leaf total-active-routes {
          type uint32;
          description
            "Indicates total active IPv4 routes for the VPN.";
        }
        description
          "IPv4-specific parameters.";
      }
      container ipv6 {
        leaf maximum-routes {
          type uint32;
          description
            "Indicates the maximum number of IPv6 routes
             for the VPN.";
        }
        leaf total-active-routes {
          type uint32;
          description
            "Indicates total active IPv6 routes for the VPN.";
        }
        description
          "IPv6-specific parameters.";
      }
      container mac-num {
        leaf mac-num-limit {
          type uint32;
          description
            "Maximum number of MAC addresses.";
        }
        leaf total-active-mac-num {
          type uint32;
          description
            "Total active MAC entries for the VPN.";
        }
        description
          "MAC statistics.";
      }
    }
  }

  grouping link-loss-statistics {
    description
      "Grouping for per link error statistics.";
    container loss-statistics {
      description
        "Link loss summarized information. By default,
         one way measurement protocol (e.g., OWAMP) is used
         to measure one-way packet loss.";
      reference
        "RFC 4656: A One-way Active Measurement Protocol (OWAMP)";
      leaf packet-loss-count {
        type yang:counter64;
        description
          "Total received packet drops count.";
      }
      leaf loss-ratio {
        type percentage;
        description
          "Loss ratio of the packets. Express as percentage
           of packets lost with respect to packets sent.";
      }
    }
  }

  grouping link-delay-statistics {
    description
      "Grouping for per link delay statistics.";
    container delay-statistics {
      description
        "Link delay summarized information. By default,
         one way measurement protocol (e.g., OWAMP) is used
         to measure delay.";
      reference
        "RFC 4656: A One-way Active Measurement Protocol (OWAMP)";
      leaf unit-value {
        type identityref {
          base lime:time-unit-type;
        }
        default "lime:milliseconds";
        description
          "Time units, where the options are s, ms, ns, etc.";
      }
      leaf min-delay-value {
        type yang:gauge64;
        description
          "Minimum observed one-way delay.";
      }
      leaf max-delay-value {
        type yang:gauge64;
        description
          "Maximum observed one-way delay.";
      }
      leaf low-delay-percentile {
        type yang:gauge64;
        description
          "Low percentile of observed one-way delay with
           specific measurement method.";
      }
      leaf intermediate-delay-percentile {
        type yang:gauge64;
        description
          "Intermediate percentile of observed one-way delay with
           specific measurement method.";
      }
      leaf high-delay-percentile {
        type yang:gauge64;
        description
          "High percentile of observed one-way delay with
           specific measurement method.";
      }
    }
  }

  grouping link-jitter-statistics {
    description
      "Grouping for per link jitter statistics.";
    container jitter-statistics {
      description
        "Link jitter summarized information. By default,
         jitter is measured using one-way IP Packet
         Delay Variation (IPDV).";
      reference
        "RFC 3393: IP Packet Delay Variation Metric
         for IP Performance Metrics (IPPM)";
      leaf unit-value {
        type identityref {
          base lime:time-unit-type;
        }
        default "lime:milliseconds";
        description
          "Time units, where the options are s, ms, ns, etc.";
      }
      leaf min-jitter-value {
        type yang:gauge32;
        description
          "Minimum observed one-way jitter.";
      }
      leaf max-jitter-value {
        type yang:gauge32;
        description
          "Maximum observed one-way jitter.";
      }
      leaf low-jitter-percentile {
        type yang:gauge32;
        description
          "Low percentile of observed one-way jitter.";
      }
      leaf intermediate-jitter-percentile {
        type yang:gauge32;
        description
          "Intermediate percentile of observed one-way jitter.";
      }
      leaf high-jitter-percentile {
        type yang:gauge32;
        description
          "High percentile of observed one-way jitter.";
      }
    }
  }

  grouping tp-svc-telemetry {
    leaf reference-time {
      type yang:date-and-time;
      config false;
      description
        "Indicates the time when the statistics are collected.";
    }
    leaf inbound-octets {
      type yang:counter64;
      description
        "The total number of octets received on the
         interface, including framing characters.";
    }
    leaf inbound-unicast {
      type yang:counter64;
      description
        "The total number of inbound unicast packets.";
    }
    leaf inbound-nunicast {
      type yang:counter64;
      description
        "The total number of non-unicast
         (i.e., broadcast or multicast) packets.";
    }
    leaf inbound-discards {
      type yang:counter32;
      description
        "The number of inbound packets that were chosen to be
         discarded even though no errors had been detected.
         One possible reason for discarding such a
         packet could be to free up buffer space";
    }
    leaf inbound-errors {
      type yang:counter64;
      description
        "The number of inbound packets that contained errors.";
    }
    leaf inbound-unknown-protocol {
      type yang:counter64;
      description
        "The number of packets received via the interface
         which were discarded because of an unknown or
         unsupported protocol.";
    }
    leaf outbound-octets {
      type yang:counter64;
      description
        "The total number of octets transmitted out of the
         interface, including framing characters.";
    }
    leaf outbound-unicast {
      type yang:counter64;
      description
        "The total number of outbound unicast packets.";
    }
    leaf outbound-nunicast {
      type yang:counter64;
      description
        "The total number of outbound non unicast
         (i.e., broadcast or multicast) packets.";
    }
    leaf outbound-discards {
      type yang:counter64;
      description
        "The number of outbound packets which were chosen
         to be discarded even though no errors had been
         detected to prevent their being transmitted.
         One possible reason for discarding such a packet could
         be to free up buffer space.";
    }
    leaf outbound-errors {
      type yang:counter64;
      description
        "The number of outbound packets that contained
         errors.";
    }
    description
      "Grouping for interface service telemetry.";
  }

  augment "/nw:networks/nw:network/nw:network-types" {
    description
      "Defines the service topologies types.";
    container service-type {
      presence "Indicates network service topology.";
      leaf service-type {
        type identityref {
          base vpn-common:service-type;
        }
        description
          "The presence identifies the network service type,
           e.g., L3VPN, VPLS, etc.";
      }
      description
        "Container for VPN service type.";
    }
  }

  augment "/nw:networks/nw:network" {
    when 'nw:network-types/nvp:service-type' {
      description
        "Augments only for VPN Network topology.";
    }
    description
      "Augments the network with service topology attributes";
    container vpn-pm-attributes {
      leaf vpn-id {
        type vpn-common:vpn-id;
        description
          "VPN identifier.";
      }
      leaf vpn-service-topology {
        type identityref {
          base vpn-common:vpn-topology;
        }
        description
          "VPN service topology, e.g., hub-spoke, any-to-any,
           hub-spoke-disjoint.";
      }
      description
        "Container for VPN topology attributes.";
    }
  }

  augment "/nw:networks/nw:network/nw:node" {
    description
      "Augments the network node with other general attributes.";
    container pm-attributes {
      leaf node-type {
        type identityref {
          base node-type;
        }
        description
          "Node type, e.g., PE, P, ASBR.";
      }
      description
        "Container for node attributes.";
    }
  }

  augment "/nw:networks/nw:network/nw:node/pm-attributes" {
    when '../../nw:network-types/nvp:service-type' {
      description
        "Augments only for VPN node attributes.";
    }
    description
      "Augments the network node with VPN specific attributes.";
    leaf role {
      type identityref {
        base vpn-common:role;
      }
      default "vpn-common:any-to-any-role";
      description
        "Role of the node in the VPN.";
    }
    uses vpn-summary-statistics;
  }

  augment "/nw:networks/nw:network/nt:link" {
    description
      "Augments the network topology link with performance
       monitoring attributes.";
    container pm-attributes {
      description
        "Container for PM attributes.";
      leaf low-percentile {
        type percentile;
        default "10.00";
        description
          "Low percentile to report. Setting low-percentile
           into 0.00 indicates the client is not interested
           in receiving low percentile.";
      }
      leaf intermediate-percentile {
        type percentile;
        default "50.00";
        description
          "Intermediate percentile to report. Setting
           intermediate-percentile into 0.00 indicates the client
           is not interested in receiving intermediate percentile.";
      }
      leaf high-percentile {
        type percentile;
        default "95.00";
        description
          "High percentile to report. Setting high-percentile
           into 0.00 indicates the client is not interested in
           receiving high percentile.";
      }
      leaf measurement-interval {
        type uint32;
        units "seconds";
        default "60";
        description
          "Indicates the time interval to perform PM measurement.";
      }
      leaf start-time {
        type yang:date-and-time;
        config false;
        description
          "The time that the current measurement started.";
      }
      leaf end-time {
        type yang:date-and-time;
        config false;
        description
          "The time that the current measurement ended.";
      }
      leaf pm-source {
        type identityref {
          base pm-source-type;
        }
        config false;
        description
          "The OAM tool used to collect the PM data.";
      }
      container one-way-pm-statistics {
        config false;
        description
          "Container for link telemetry attributes.";
        uses link-loss-statistics;
        uses link-delay-statistics;
        uses link-jitter-statistics;
      }
    }
  }

  augment "/nw:networks/nw:network/nt:link/pm-attributes" {
    when '../../nw:network-types/nvp:service-type' {
      description
        "Augments only for VPN Network topology.";
    }
    description
      "Augments the network topology link with VPN service
       performance monitoring attributes.";
    leaf vpn-underlay-transport-type {
      type identityref {
        base vpn-common:protocol-type;
      }
      config false;
      description
        "The leaf indicates the underlay transport type of
         a VPN service, e.g., GRE, LDP, etc.";
    }
    list vpn-one-way-pm-statistics {
      key "class-id";
      config false;
      description
        "The list of PM data based on class of service.";
      leaf class-id {
        type string;
        description
          "The class-id is used to identify the class of service.
           This identifier is internal to the administration.";
      }
      uses link-loss-statistics;
      uses link-delay-statistics;
      uses link-jitter-statistics;
    }
  }

  augment "/nw:networks/nw:network/nw:node/nt:termination-point" {
    description
      "Augments the network topology termination point with
       performance monitoring attributes.";
    container pm-statistics {
      config false;
      description
        "Container for termination point PM attributes.";
      uses tp-svc-telemetry;
    }
  }

  augment "/nw:networks/nw:network/nw:node"
        + "/nt:termination-point/pm-statistics" {
    when '../../../nw:network-types/nvp:service-type' {
      description
        "Augments only for VPN Network topology.";
    }
    description
      "Augments the network topology termination-point with
       VPN service performance monitoring attributes";
    list vpn-network-access {
      key "network-access-id";
      description
        "The list of PM based on VPN network accesses.";
      leaf network-access-id {
        type vpn-common:vpn-id;
        description
          "References to an identifier for the VPN network
           access, e.g. L3VPN or VPLS.";
      }
      uses tp-svc-telemetry;
    }
  }
}
