module ietf-srv6-base {
  yang-version 1.1;

  namespace "urn:ietf:params:xml:ns:yang:ietf-srv6-base";
  prefix srv6;
  import ietf-interfaces {
    prefix "if";
    reference "RFC 8343: A YANG Data Model for Interface Management";
  }

  import ietf-inet-types {
    prefix inet;
    reference "RFC 6991: Common YANG Data Types";
  }

  import ietf-yang-types {
    prefix "yang";
    reference "RFC 6991: Common YANG Data Types";
  }

  import ietf-routing-types {
     prefix "rt-types";
     reference "RFC 8294: Common YANG Data Types for the Routing Area";
  }

  import ietf-routing {
    prefix "rt";
    reference
      "RFC 8349: A YANG Data Model for Routing Management
      (NMDA version)";
  }

  import iana-msd-types {
    prefix iana-msd-types;
    reference "RFC 9702: YANG Data Model for MSD Types";
  }

  import ietf-segment-routing {
    prefix sr;
    reference "RFC 9020: YANG Data Model for Segment Routing";
  }

  import ietf-srv6-types {
    prefix srv6-types;
    reference "RFC XXXX: YANG Data Model for SRv6";
    // RFC Editor: replace XXXX with actual RFC number and remove
    // this note
  }

  organization
    "IETF SPRING Working Group";
  contact
      "WG Web:   <http://tools.ietf.org/wg/spring/>
     WG List:  <mailto:spring@ietf.org>

     Editor:   Kamran Raza
               <mailto:skraza@cisco.com>

     Editor:   Jaganbabu Rajamanickam
               <maito:jrajaman@cisco.com>

     Editor:   Satoru Matsushima
               <mailto:satoru.matsushima@gmail.com>

     Editor:   Pingping Yu
               <mailto:susana.yu@huawei.com>

     Editor:   Xufeng Liu
               <mailto:xufeng.liu.ietf@gmail.com>
     ";

  description
    "This YANG module defines the essential elements for the
     management of Segment-Routing with IPv6 dataplane (SRv6).

     Copyright (c) 2017 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see the
     RFC itself for full legal notices.";
     // RFC Editor: replace XXXX with actual RFC number and remove
     // this note

  revision 2026-05-06 {
    description
      "Re-use MSD types (from iana-msd-types) for SRH";
    reference
      "RFC XXXX: YANG Data Model for SRv6 Base";
    // RFC Editor: replace XXXX with actual RFC number and remove
    // this note
  }

  revision 2025-07-07 {
    description
      "Adding compressed SID and few other missing def";
    reference
      "RFC XXXX: YANG Data Model for SRv6";
    // RFC Editor: replace XXXX with actual RFC number and remove
    // this note
  }

  revision 2022-01-14 {
    description
      "Alignment with SRv6 network programming rev16";
    reference
      "RFC XXXX: YANG Data Model for SRv6";
    // RFC Editor: replace XXXX with actual RFC number and remove
    // this note
  }

  revision 2019-10-30 {
    description
      "Alignment with SRv6 network programming";
    reference
      "RFC XXXX: YANG Data Model for SRv6";
    // RFC Editor: replace XXXX with actual RFC number and remove
    // this note
  }

  revision 2019-07-08 {
    description
      "Alignment with SRv6 network programming";
    reference
      "RFC XXXX: YANG Data Model for SRv6";
    // RFC Editor: replace XXXX with actual RFC number and remove
    // this note
  }

  revision 2018-10-22 {
    description
      "Initial revision.";
    reference
      "RFC XXXX: YANG Data Model for SRv6";
    // RFC Editor: replace XXXX with actual RFC number and remove
    // this note
  }

/*
 * Common
 */

  grouping path-attrs-cmn {
     description
       "Path properties -common for v4/v6";

     leaf weight {
       type uint32;
       description
         "This value is used to compute a loadshare to perform un-equal
          load balancing when multiple outgoing path(s) are specified. A
          share is computed as a ratio of this number to the total under
          all configured path(s).";
     }

     leaf role {
       type enumeration {
         enum PRIMARY { description "Path as primary traffic carrying"; }
         enum BACKUP { description "Path acts as a backup"; }
         enum PRIMARY_AND_BACKUP {
           description "Path acts as primary and backup simultaneously"; }
         }
         description "The path role";
      }

      leaf backup-path-index {
       type uint8;
       description "Index of the protecting (backup) path";
      }
   }

  grouping path-out-sids {
    description "Grouping for path's SID stack";

      list out-sid {
        key "sid";
        description "Out SID";

        leaf sid {
          type srv6-types:srv6-sid;
          description "SID value";
        }
      }
  }

  grouping path-out-labels {
    description "Grouping for path's label stack";

      list out-label {
        key "label";
        description "Out label";

        leaf label {
          type rt-types:mpls-label;
          description "Label value";
        }
      }

  }

 /*
  * Config and State
  */

  grouping srv6-encap {
   description "Grouping for encap param config.";

   container encapsulation {
      description "Configure encapsulation related parameters";
      leaf source-address {
        type inet:ipv6-address;
        description "Specify a source address (for T.Encap).
                     The address must locally exists and be routable";
      }
      container hop-limit {
        description "Configure IPv6 header's Hop-limit options";
        leaf value {
          when "../propagate = 'false'";
          type uint8;
          default 64;
          description "Set encapsulating outer IPv6 header's Hoplimit
                      field to specified value when doing
                      encapsulation";
        }

        leaf propagate {
          type boolean;
          default false;
          description "IP TTL/Hop-limit propagation from encapsulated
                      packet to encapsulating outer IPv6 header's
                      Hoplimit field. When configured on decapsulation
                      side, this refers to propagating Hop-limit from
                      outer IPv6 header to inner header after decap";
        }
      }

      container traffic-class {
        description "Configure IPv6 header's Traffic-class options";
        leaf value {
          when "../propagate = 'false'";
          type uint8;
          default 0;
          description "Set encapsulating outer IPv6 header's
                      Traffic-class field to specified value when
                      doing encapsulation";
        }

        leaf propagate {
          type boolean;
          default false;
          description "Propagate (or map) Traffic-class/CoS/PCP from
                      the incoming packet or L2 Ethernet frame being
                      encapsulated to the encapsulating IPv6 header's
                      Traffic-class field.";
        }
      }

    }
  }

grouping srv6-ucsid16-cfg-grouping {
    description "Uncompressed 16 bit FUNCT SID format config grouping";

   container id-block {
     description "Container for Id allocation corresponding to FUNCT";
     reference "RFC XXXX: YANG Data Model for SRv6 - Section 3.4.1";

     container explicit {
       description "Configure Explicit FUNCT parameters";
       leaf start {
         type uint16;
         description "Start of explicit block";
       }
       leaf size {
         type uint16;
         description "Size of explicit block";
       }
    }
  }
}

grouping srv6-csid-next16-cfg-grouping {
    description "NEXT-CSID (16b uSID) common grouping";

   // CFG

   container local-id-block {
     description "Configure LIB parameters";
     reference "RFC XXXX: YANG Data Model for SRv6 - Section 3.4.2";

     leaf start {
       type uint16;
       description "LIB space follows GIB space. An implementation may chose
                    the default index for the start of LIB - e.g. LIB starting
                    from 0xE000. This configuration item allows to change the start of
                    LIB space as a user wishes to resize (expand or shrink)
                    it";
     }

     container explicit {
       description "Configure Explicit LIB parameters";

       leaf start {
         type uint16;
         description "Start of explicit LIB within LIB space";
       }
       leaf size {
         type uint16;
         description "Size (to shrink or expand) of explicit LIB";
       }
    }
  }
}

  grouping srv6-sid-formats {
   description "SRv6 SID formats grouping";

   container sid-formats {
      description "Container for SRv6 SID formats";

      list format {
        key "type";
        description "SRv6 SID format";

        leaf type {
          type identityref { base srv6-types:srv6-sid-format-type; }
          description "Format type";
        }

        // STATE
        leaf compression-type {
          type srv6-types:srv6-sid-compression-type;
          config false;
          description "Compression type";
        }
        leaf description {
          type string;
          config false;
          description "Format description";
        }

        uses srv6-types:srv6-sid-structure-info-grouping;

        // CFG
        container uncompressed-16 {
          when "derived-from-or-self(../type, 'srv6-sid-fmt-uc-1')" {
               description "This container is valid only when the
                            SID format is one of the uncompressed types";
          }

          description "Configuration specific to uncompressed SID formats with 16b FUNCT";
          uses srv6-ucsid16-cfg-grouping;
        }

        container csid-next-16 {
          when "derived-from-or-self(../type, 'srv6-sid-fmt-cnext-1616') or
                derived-from-or-self(../type, 'srv6-sid-fmt-cnext-3216') or
                derived-from-or-self(../type, 'srv6-sid-fmt-cnext-6416')" {
               description "This container is valid only when the
                            SID format is one of the 16bits NEXT-CSID";
          }

          description "Configuration specific to NEXT-CSID with 16b CSIDs";
          uses srv6-csid-next16-cfg-grouping;
        }
      }
   }
 }

  grouping srv6-locator-state {
   description "SRv6 grouping Locator state";

       leaf operational-status {
         type srv6-types:srv6-status-type;
         config false;
         description "Indicates whether locator state is UP";
       }

       leaf is-in-address-conflict {
         type boolean;
         config false;
         description "Indicates whether locator address conflicts with
                      some other IPv6 address on the box";
       }
    }

 grouping srv6-remote-locator-stats-grouping {
   description "SRv6 Locator prefix accounting grouping";

   container traffic-accounting {
      description "SRv6 remote locator traffic accounting";

      container inbound {
         description "Per-Locator prefix inbound accounting";

         uses srv6-stats-in;
      }

      container outbound {
         description "Per-Locator prefix per-nexthop counters (aka LOC.INT.E)";

         list paths {
           key "interface next-hop";
           description "Forwarding path information";

           leaf interface {
             type if:interface-ref;
             description "The outgoing interface";
           }

           leaf next-hop {
             type inet:ipv6-address;
             description "The IPv6 address of the next-hop";
           }

           uses srv6-stats-out;
         }
     }
   }
}
 grouping srv6-remote-locators-state {

   description "SRv6 Remote Locator state grouping";

   list remote {
      key "prefix";
      config false;
      description "SRv6 remote locators' prefixes";

      leaf prefix {
        type inet:ipv6-prefix;
        description "Locator IPv6 prefix";
      }

      uses srv6-remote-locator-stats-grouping;
    }
  }

  grouping srv6-locators {
   description "SRv6 locator grouping";

   container locators {
      description "SRv6 locators";

      list locator {
        key "name";
        description "Configure a SRv6 locator";

        leaf name {
          type srv6-types:srv6-locator-name-type;
          description "Locator name";
        }

        leaf enable {
          type boolean;
          default false;
          description "Enable a SRv6 locator";
        }

        leaf format {
          type identityref { base srv6-types:srv6-sid-format-type; }
          mandatory true;
          description "SRv6 SID format";
        }

        container prefix {
          description "Specify locator prefix value";
          leaf address {
            type inet:ipv6-address;
            mandatory true;
            description "IPv6 address";
          }
          leaf length {
            type srv6-types:srv6-locator-len;
            mandatory true;
            description "Locator (prefix) length";
          }
        }

        leaf algorithm {
          type uint8 {
            range "128..255";
          }

          description "Algorithm Id (for Flex-Algo)";
        }

        leaf anycast {
          type boolean;
          default false;
          description "Set to true if locator is an Anycast locator";
        }

        container node-sid-auto-allocation {
          description "Container for SID auto allocation";
          leaf behavior {
            type identityref { base srv6-types:srv6-endpoint-type; }

            description "As locator becomes operational, Node SIDs can be
              auto allocated - e.g. in Uncompressed format locator, a reserved
              FUNC value can be used and assigned for END SID; In
              NEXT-CSID, the locator prefix address is used as
              NEXT-CSID's END. These node SID are auto allocated with a
              default variant (e.g. PSP-USD). This item allows a user to specify
              a different variant.";
          }

          leaf disable {
             type boolean;
             default false;
             description "Set to true to disable auto allocation of SIDs";
          }
        }

        uses srv6-locator-state;
      }
      uses srv6-remote-locators-state;
    }
  }

  grouping srv6-stats-in {
    description "Grouping for inbound stats";

      leaf in-pkts {
        type yang:counter64;
        description
          "A cumulative counter of the total number of packets
          received";
      }

      leaf in-octets {
        type yang:counter64;
        description
          "A cumulative counter of the total bytes received.";
      }
  }

  grouping srv6-stats-out {
    description "Grouping for inbound stats";

      leaf out-pkts {
        type yang:counter64;
        description
          "A cumulative counter of the total number of packets
          transmitted";
      }

      leaf out-octets {
        type yang:counter64;
        description
          "A cumulative counter of the total bytes transmitted.";
      }
  }

  grouping path-out-sids-choice {
    description "Grouping for Out-SID choices";
    choice encap-type {
       description "Out-SID encap-based choice";
       case srv6 {
         uses path-out-sids;
       }
       case mpls {
         uses path-out-labels;
       }
    }
  }

  grouping local-sid-fwd-state {
    description "SRv6 local-SID forwarding state grouping";

    container forwarding {
       description "SRv6 local-SID forwarding state";

       leaf is-installed {
         type boolean;
         description "Indicates whether SID is installed in forwarding";
       }

       leaf next-hop-type {
         type srv6-types:srv6-nexthop-type;
         description "Forwarding next-hop types";
       }

       container paths {
         when "../is-installed = 'true'" {
           description "This container is valid only when the
           local-SID is installed in forwarding";
         }

         list path {
          key path-index;
          description "The list of paths associated with the SID";

          leaf path-index {
            type uint8;
            description "Index of the path";
          }

          container l2 {

            leaf interface {
              when "../../../../next-hop-type = 'l2'" {
                description "This leaf is valid only when the nexthop type
                             is l2";
              }
              type if:interface-ref;
               description "The outgoing Layer2 interface";
            }

            leaf lookup-table-id {
              when "../../../../next-hop-type = 'l2_lookup'" {
                description "This leaf is valid only when the nexthop type
                             is L2 lookup (in a table)";
              }
              type uint32;
              description "Lookup Table ID; Applicable to L2 VLAN,
                   L2 Ucast/Mcast table";
            }

            description "L2 information";
           }

          container l3 {
            when "../../../next-hop-type = 'ipv4' or ../../../next-hop-type = 'ipv6'" {
              description "This container is valid only for L3 type
                  of NHs";
            }

            leaf interface {
              type if:interface-ref;
              description "The outgoing Layer3 interface";
            }

            leaf next-hop {
              type inet:ip-address;
              description "The IP address of the next-hop";
            }

            uses path-attrs-cmn;

            leaf lookup-table-id {
              when "../../../../next-hop-type = 'l3_lookup'" {
                description "This leaf is valid only when the nexthop type
                             is L3 lookup (in a table)";
              }
              type uint32;
              description "L3 Lookup Table ID; Applicable to L3 unicast table";
             }

          //leaf vrf-name {
          //    type string;
          //     description " vrf name";
          //}

            description "L3 information";
          }

          uses path-out-sids-choice;
        }

        description "Forwarding paths";
       }
    }
  }

  grouping srv6-sid-alloc-grouping {
   description "SRv6 SID allocation grouping";

   container allocation {
     description "SRv6 SID allocation container.";

     leaf alloc-type {
       type srv6-types:sid-alloc-type;
       description "Type of sid allocation.";
     }

     list owner {
       key "type instance";
       description "SID Owner clients";

       leaf type {
         type identityref { base srv6-types:srv6-sid-owner-type; }
         description "SID owner/client type";
       }

       leaf instance {
         type string;
         description "Client instance";
       }

       leaf is-winner {
         type boolean;
         description "Is this client/owner the winning in terms of forwarding";
       }
     }

     leaf allocated-from-reserved {
       type boolean;
       description "Set to true if SID comes from reserved pool";
     }
  }
}

  grouping srv6-state-sid {
   description "SRv6 SID state grouping";

   container sids {

     description "My SID state";

         leaf sid-holdtime {
           type uint8 {
             range "0..60"; //The range of minutes is from 0 (disabled) to 60 minutes
           }
           units minutes;
           default 30;
           description "The holdtime for a stale or freed SID. The value 0
                        is used for an immediate release of an allocated SID.";
         }

         container counts {
           config false;
           description "Summary/aggregate counts for my SIDs";

           leaf allocated {
             type uint32;
             description "Total number of currently allocated SID";
           }

           leaf stale {
             type uint32;
             description "A stale SID is the a previously allocated SID which
                 is freed by the owner but not fully released due to holdtime";
            }
         }

     list sid {
       key "sid";
       config false;

       description "Per-SID";

       leaf sid {
        type srv6-types:srv6-sid;
        description "My SID value";
       }

       leaf behavior {
           type identityref { base srv6-types:srv6-endpoint-type; }
           description "Type of SRv6 endpoint behavior.";
       }

       uses srv6-locator;

       uses srv6-sid-alloc-grouping;

       uses local-sid-fwd-state;

       container counters {
         description "SRv6 per SID counters";

         container success {
           description "Counts SRv6 traffic received on local-SID
           prefix and processed successfully - see
           srv6-counter-types:CNT-MySID-Success (RFC 8986 section 6)";
           uses srv6-stats-in;
         }
       }
    }
   }
  }

  grouping srv6-support-ends {
    description "SRv6 End behavior support grouping";
   list end-behavior {
     key "type";
     description "End behavior support";

     leaf type {
       type identityref { base srv6-types:srv6-endpoint-type; }
       description "End behavior (End*) type";
     }
     leaf supported {
       type boolean;
       mandatory true;
       description "True if supported";
     }
    }
   }

  grouping srv6-support-headends {
    description "SRv6 Headend behavior support grouping";

    list headend-behavior {
      key "type";
      description "Headend behavior support";
      leaf type {
        type identityref { base srv6-types:srv6-headend-type; }
        description "Headend behavior (H*) type";
      }
     leaf supported {
       type boolean;
       mandatory true;
       description "True if supported";
     }
    }
  }

  grouping srv6-msd-signaled {
    description "SRv6 MSD signaled parameter support grouping";

    container msd {
     description "SRv6 signaled MSD parameter support";

     list msds {
       key "msd-type";
       description "List of MSD types as defined in iana-msd-types";

       leaf msd-type {
         type identityref { base iana-msd-types:msd-base-srh; }
         description "MSD types";
       }

       leaf msd-value {
         type uint8;
         description "MSD value, in the range of 0-255.";
       }
      }
    }
  }

  grouping srv6-support-security-rules {
    description "SRv6 Security rules grouping";

   list security-rule {
     key "type";
     description "Security rule support";

     leaf type {
       type identityref { base srv6-types:srv6-security-type; }
       description "Security rule type";
     }
     leaf supported {
       type boolean;
       mandatory true;
       description "True if supported";
     }
    }
   }

  grouping srv6-support-counters {
    description "SRv6 Counters grouping";

   list counters {
     key "type";
     description "SRv6 counter support";
     leaf type {
       type identityref { base srv6-types:srv6-counter-type; }
       description "Counter type";
     }
     leaf supported {
       type boolean;
       mandatory true;
       description "True if supported";
     }
    }
   }

   grouping srv6-state-capabilities {
     description "SRv6 node capabilities grouping";
     container node-capabilities {
       config false;
       description "Node's SRv6 capabilities";

       uses srv6-support-ends;
       uses srv6-support-headends;
       uses srv6-msd-signaled;
       uses srv6-support-security-rules;
       uses srv6-support-counters;
     }
  }

   augment "/rt:routing/sr:segment-routing" {
      description
        "This augments Segment Routing (SR) with SRv6.";

   container srv6 {
    description "Segment Routing with IPv6 dataplane";

    /* config */
    leaf enable {
      type boolean;
      default false;
      description "Enable SRv6";
    }

    uses srv6-state-capabilities;
    uses srv6-encap;
    uses srv6-sid-formats;
    uses srv6-locators;
    uses srv6-state-sid;
   }
 }
 /* Notifications */

  grouping srv6-locator {
    description
      "An absolute reference to an SRv6 locator";
    leaf locator {
      type leafref {
        path "/rt:routing/sr:segment-routing/srv6:srv6/srv6:locators/srv6:locator/srv6:name";
      }
      description
        "Reference to a SRv6 locator.";
    }
  }

  notification srv6-locator-status-event {
    description
      "Notification event for a change of SRv6 locator operational
      status.";
    leaf operational-status {
      type srv6-types:srv6-status-type;
      description "Operational status";
    }
    uses srv6-locator;
  }

  notification srv6-sid-collision-event {
    description
      "Notification event for an SRv6 SID collision - i.e., attempt
      to bind an already bound SID to a new context";
    leaf sid {
      type srv6-types:srv6-sid;
      description "SRv6 SID";
    }
    container existing {
      description "Current assignment / bind";
      leaf end-behavior-type {
        type identityref { base srv6-types:srv6-endpoint-type; }
        description "End type";
      }

     list owner {
       key "type instance";
       description "SID Owner clients";

       leaf type {
         type identityref { base srv6-types:srv6-sid-owner-type; }
         description "SID owner/client type";
       }

       leaf instance {
         type string;
         description "Client instance";
       }
     }
    }

    container requested {
      description "Requested assignment / bind";

      leaf end-behavior-type {
        type identityref { base srv6-types:srv6-endpoint-type; }
        description "End type";
      }

     container requester {
       description "SID client";

       leaf type {
         type identityref { base srv6-types:srv6-sid-owner-type; }
         description "SID owner/client type";
       }

       leaf instance {
         type string;
         description "Client instance";
       }
     }
    }
  }
} // module
