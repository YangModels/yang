module ietf-nmda-compare {

  yang-version 1.1;
  namespace "urn:ietf:params:xml:ns:yang:ietf-nmda-compare";

  prefix cp;

  import ietf-yang-types {
    prefix yang;
  }
  import ietf-datastores {
    prefix ds;
  }
  import ietf-yang-patch {
    prefix ypatch;
  }
  import ietf-netconf {
    prefix nc;
  }

  organization "IETF";
  contact
    "WG Web:   <http://tools.ietf.org/wg/netconf/>
     WG List:  <mailto:netconf@ietf.org>

     Author: Alexander Clemm
             <mailto:ludwig@clemm.org>

     Author: Yingzhen Qu
             <mailto:yingzhen.qu@huawei.com>

     Author: Jeff Tantsura
             <mailto:jefftant.ietf@gmail.com>";

  description
    "The YANG data model defines a new operation, <compare>, that
     can be used to compare NMDA datastores.";

  revision 2018-02-23 {
    description
      "Initial revision";
    reference
      "RFC XXXX: Discrepancy detection between NMDA datastores";
  }

  feature cmp-dampening {
    description
      "This feature indicates that the ability to only report
       differences that pertain for a certain amount of time,
       as indicated through a dampening period, is supported.";
  }

  /* RPC */
  rpc compare {
    description
      "NMDA compare operation.";
    input {
      leaf source {
        type identityref {
          base ds:datastore;
        }
        mandatory true;
        description
          "The source datastore to be compared.";
      }
      leaf target {
        type identityref {
          base ds:datastore;
        }
        mandatory true;
        description
          "The target datastore to be compared.";
      }
          choice filter-spec {
        description
          "Identifies the portions of the datastores to be
               compared.";

        anydata subtree-filter {
          description
            "This parameter identifies the portions of the
             target datastore to retrieve.";
          reference "RFC 6241, Section 6.";
        }
        leaf xpath-filter {
          if-feature nc:xpath;
          type yang:xpath1.0;
          description
            "This parameter contains an XPath expression
             identifying the portions of the target
             datastore to retrieve.";
        }
      }
      leaf dampening {
        if-feature cmp-dampening;
        type yang:timeticks;
        default "0";
        description
          "The dampening period, in hundredths of a second, for the
                   reporting of differences. Only differences that pertain
                   for at least the dampening time are reported.  Reporting
           of differences may be deferred by the dampening time.
           A value of 0 or omission of the leaf indicates no
           dampening.";
      }
    }
    output {
      container differences {
        uses ypatch:yang-patch;
        description
          "The list of differences, encoded per RFC8072, with
                   a value for patch-id and values for edit-id generated
                   by the server.  If there are no differences, an
                   empty container is returned.";
      }
    }
  }
}
