module service-function-path {

  namespace "urn:cisco:params:xml:ns:yang:sfc-sfp";

  prefix sfc-sfp;

  import ietf-inet-types { prefix inet; }
  import ietf-yang-types { prefix yang; }
  import service-function {prefix sfc-sf; }

  organization "Cisco Systems, Inc.";
  contact "Reinaldo Penno <repenno@cisco.com>";

  description
    "This module contains a collection of YANG definitions for
     managing service function chains.
     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
      "Changes based on Opendaylight Testing and IETF SFC ml.";
  }

  typedef service-function-path-ref {
    type leafref {
      path "/sfc-sfp:service-function-paths/sfc-sfp:service-function-path/sfc-sfp:name";
    }
    description
      "This type is used by data models that need to reference
       configured service functions.";
  }

  // Service Function Path

  container service-function-paths {
    list service-function-path {
      description
        "A Service Function Path is an instantiation of a Service Chain. It
         specifies the actual firewall (say, firewall-3) that will be traversed by
         the packets. The Service Path needs to be known before hand or stitched
         run-time (given the dynamic LB decision) since a forwarding decision need
         to be made regardless.";
      key "name";
      leaf name {
        type string;
        description
          "the name of this service function path";
      }
      list sfp-service-function {
        key "name";
        leaf name {
          type string;
          description
            "Service Function name";
        }
        leaf service-function-forwarder {
          type string;
          description
            "Service Function Forwarder name";
        }
        ordered-by user;
        min-elements 1;
        description
          "A list of service function instances that compose the service path";
      }
      leaf service-chain-name {
        mandatory true;
        type string;
        description
          " The Service Function Chain used as blueprint for this path";
      }
      leaf service_index {
        type uint8;
      }
      leaf path-id {
        type uint32 {
          range "0..16777216";
        }
      }
      leaf path-id-low {
        type uint8;
      }

      leaf path-id-med {
        type uint8;
      }

      leaf path-id-hi {
        type uint8;
      }
    }
  }

/*
   Base Service Header:
      0                   1                   2                   3
      0 1 2 3 4 5 6 7 8 9 0 1 2 3 4 5 6 7 8 9 0 1 2 3 4 5 6 7 8 9 0 1
     +-+-+-+-+-+-+-+-+-+-+-+-+-+-+-+-+-+-+-+-+-+-+-+-+-+-+-+-+-+-+-+-+
     |O|C|R|R|R|R|R|R| Protocol Type                 |Service Index  |
     +-+-+-+-+-+-+-+-+-+-+-+-+-+-+-+-+-+-+-+-+-+-+-+-+-+-+-+-+-+-+-+-+
     |                 Service path  ID              | Reserved      |
     +-+-+-+-+-+-+-+-+-+-+-+-+-+-+-+-+-+-+-+-+-+-+-+-+-+-+-+-+-+-+-+-+

   Flags: 8
   Protocol Type (PT): 16
   Service Index: 8
   Service path: 24
   Reserved: 8
*/

}
