module ietf-bgp-l3vpn {
  namespace "urn:ietf:params:xml:ns:yang:ietf-bgp-l3vpn";
  // replace with IANA namespace when assigned
  prefix l3vpn ;

  import ietf-routing {
    prefix rt;
    revision-date 2015-10-16;
  }

  import ietf-interfaces {
    prefix if;
  }

  import bgp {
    prefix bgp;
  }

  organization
    "Cisco Systems
     170 West Tasman Drive
     San Jose, CA 95134-1706
     USA";

  contact
     "Keyur Patel keyupate@cisco.com
      Dhanendra Jain dhjain@cisco.com
     ";

  description
    "This YANG module defines the configuration for the BGP Layer 3 VPNs.
     It augments the IETF bgp yang model and IETF routing model to add L3VPN specific
     configuration and operational knobs.

     Terms and Acronyms

     AS : Autonomous System

     ASBR : Autonomous Systems Border Router

     BGP (bgp): Border Gateway Protocol

     CE  : Customer Edge

     IP (ip): Internet Protocol

     IPv4 (ipv4):Internet Protocol Version 4

     IPv6 (ipv6): Internet Protocol Version 6

     PE : Provider Edge

     RT : Route Target

     RD : Route Distinguisher

     VPN : Virtual Private Network

    ";

  revision 2015-12-27 {
    description
      "Initial revision.";
    reference
      "RFC XXXX: A YANG Data Model for L3VPN config management";
  }

  grouping bgp-rd-spec {
      description "Route distinguisher specification as per RFC4364";
      leaf rd {
          type string;
          description "Route distinguisher value as per RFC4364";
      }
  }
  grouping bgp-rd {
      description "BGP route distinguisher";
      container route-distinguisher {
         description "Route distinguisher";
         container config {
            description "Configuration parameters for route distinguisher";
            uses bgp-rd-spec ;
         }
         container state {
            config "false" ;
            description "State information for route distinguisher";
            uses bgp-rd-spec ;
         }
      }
  }

  typedef bgp-label-mode {
      type enumeration {
        enum per-ce {
             description "Allocate labels per CE";
        }
        enum per-prefix {
             description "Allocate labels per prefix";
        }
        enum per-vrf {
             description "Allocate labels per VRF";
        }
     }
     description "BGP label allocation mode";
  }

  typedef fwd-mode-type {
      type enumeration {
        enum mpls {
             description "Forwarding mode mpls";
        }
      }
      description "Enable forwarding mode under ASBR facing interface";
  }

  grouping forwarding-mode {
      description "Forwarding mode of interface for ASBR scenario";
      container forwarding-mode {
          description "Forwarding mode of interface for ASBR scenario";
          container config {
              description "Configuration of Forwarding mode";
              leaf forwarding-mode {
                 type  fwd-mode-type;
                 description "Forwarding mode for this interface";
              }
          }
          container state {
              config "false";
              description "State information of Forwarding mode";
              leaf forwarding-mode {
                 type  fwd-mode-type;
                 description "Forwarding mode for this interface";
              }
          }
      }
  }

  grouping label-security {
      description "Mpls label security for ASBR option B scenario";
      container mpls-label-security {
          description "MPLS label secruity";
          container config {
              description "Configuration parameters";
              leaf rpf {
                 type boolean;
                 description "Enable MPLS label security rpf on interface";
              }
          }
          container state {
              config "false";
              description "State information";
              leaf rpf {
                 type boolean;
                 description "MPLS label security rpf on interface";
              }
          }
      }
  }

  grouping route-target-set {
       description
          "Extended community route-target set ";
       container route-targets {
          description
            "Route-target";
          list rt-list {
              key "rt";
              description
                 "List of route-targets" ;
              leaf rt {
                 type string {
                    pattern '([0-9]+:[0-9]+)';
                 }
                 description "Route target extended community as per RFC4360";
              }
          }
       }
       leaf route-policy {
            type string;
            description
              "Reference to the policy containing set of routes.
               TBD: leafref to policy entry in IETF policy model";
       }
  }

  grouping import-from-default {
       description "Import from default VRF";
       leaf from-default-vrf {
           type boolean;
           description "Import from default VRF";
       }
       leaf advertise-as-vpn {
           when "../from-default-vrf == TRUE" {
              description "This option is valid only when importing from default VRF";
           }
           type boolean;
           description "Advertise from-default routes as VPN routes";
       }
  }

  grouping export-to-default {
       description "Export routes to default VRF";
       leaf to-default-vrf {
           type boolean;
           description "Export routes to default VRF";
       }
  }

  grouping route-import-set {
      description "Grouping to specify rules for route import";
      container import-routes {
         description "Set of route-targets to match to import routes into VRF";
         container config {
           description
               "Configuration parameters for import routes";
           uses route-target-set ;
           uses import-from-default;
         }
         container state {
           config "false" ;
           description
               "State information for the import routes";
           uses route-target-set ;
           uses import-from-default;
         }
      }
  }
  grouping route-export-set {
      description "Groupign to specify rules for route export";
      container export-routes {
        description "Set of route-targets to attach with exported routes from VRF";
        container config {
           description
              "Configuration parameters for export routes";
           uses route-target-set ;
           uses export-to-default;
        }
        container state {
           config "false" ;
           description
              "State information for export routes";
           uses route-target-set ;
           uses export-to-default;
        }
      }
  }

  grouping route-import-export-set {
      description "Grouping to specify rules for route import/export both";
      container import-export-routes {
          description "Set of route-targets for import/export both";
          container config {
              description "Both import/export routes";
              uses route-target-set;
          }
          container state {
           config "false" ;
              description "Both import/export routes";
              uses route-target-set;
          }
      }
  }

  grouping route-filter-set {
      description "Specify route filtering rules for import/export";
      uses route-import-set;
      uses route-export-set;
      uses route-import-export-set;
  }

  grouping bgp-label-mode {
       description "MPLS/VPN label allocation mode";
       container config {
         description "Configuration parameters for label allocation mode";
         leaf label-mode {
           type bgp-label-mode;
           description "Label allocation mode";
         }
       }
       container state {
         config "false" ;
         description "State information for label allocation mode";
         leaf label-mode {
           type bgp-label-mode;
           description "Label allocation mode";
         }
       }
  }

  grouping retain-route-targets {
       description "Grouping for route target accept";
    container retain-rts {
      description "Control route target acceptance behavior for ASBRs";
      container config {
         description "Configuration parameters for retaining route targets";
         leaf all {
            type empty;
            description "Disable filtering of all route-targets";
         }
         leaf route-policy {
            type string;
            description "Filter routes as per filter policy name
                         TBD: leafref to IETF routing policy model";
         }
      }
      container state {
         config "false" ;
         description "State information for retaining route targets";
         leaf all {
            type empty;
            description "Disable filtering of all route-targets";
         }
         leaf route-policy {
            type string;
            description "Filter routes as per filter policy name";
         }
      }
    }
  }

  grouping nexthop-opts {
     description "Next hop control options for inter-as route exchange";
     leaf next-hop-self {
        type boolean;
        description "Set nexthop of the route to self when advertising routes";
     }
     leaf next-hop-unchanged {
        type boolean;
        description "Enforce no nexthop change when advertising routes";
     }
  }

  grouping asbr-nexthop-options {
     description "Nexthop parameters for inter-as VPN options ";
     container nexthop-options {
         description "Nexthop related options for inter-as options";
         container config {
             description "Configuration parameters for nexthop options";
             uses nexthop-opts;
         }
         container state {
             description "State information for nexthop options" ;
             uses nexthop-opts;
         }
     }
  }

  // Augmentations of base models.

  // Route-distinguisher is added in BGP global level. BGP is supposed to be
  // under scope of VRF as a routing instance, once BGP model is augmented.
  // Which means rd defined here will be per VPN per BGP instance.
  //
  augment "/bgp:bgp/bgp:global" {
     description "Route distinguisher under BGP global mode";
     uses bgp-rd ;
  }

  // route import/export rules in applicable address families.
  augment "/bgp:bgp/bgp:global/bgp:afi-safis/bgp:afi-safi/bgp:ipv4-unicast" {
     description "Route import/export rules under BGP Address family mode";
     uses route-filter-set;
  }

  augment "/bgp:bgp/bgp:global/bgp:afi-safis/bgp:afi-safi/bgp:ipv6-unicast" {
     description "Route import/export rules under BGP Address family mode";
     uses route-filter-set ;
  }

  /* multicast safi is not in the BGP base model yet.
  augment "/bgp:bgp/bgp:global/bgp:afi-safis/bgp:afi-safi/bgp:ipv6-multicast" {
     description "Route import/export rules under BGP Address family mode";
     uses route-filter-set ;
  }

  augment "/bgp:bgp/bgp:global/bgp:afi-safis/bgp:afi-safi/bgp:ipv4-multicast" {
     description "Route import/export rules under BGP Address family mode";
     uses route-filter-set ;
  }
  */

  // Retain route-target for inter-as option ASBR-B knob.
  // vpnv4/vpnv6/mvpn address-family only.
  augment "/bgp:bgp/bgp:global/bgp:afi-safis/bgp:afi-safi/bgp:l3vpn-ipv4-unicast" {
    description "Retain route targets for ASBR scenario";
    uses retain-route-targets;
  }

  augment "/bgp:bgp/bgp:global/bgp:afi-safis/bgp:afi-safi/bgp:l3vpn-ipv6-unicast" {
    description "Retain route targets for ASBR scenario";
    uses retain-route-targets;
  }

  augment "/bgp:bgp/bgp:global/bgp:afi-safis/bgp:afi-safi/bgp:l3vpn-ipv4-multicast" {
    description "Retain route targets for ASBR scenario";
    uses retain-route-targets;
  }

  /* MPVN address family is not in BASE BGP model yet.
  augment "/bgp:bgp/bgp:global/bgp:afi-safis/bgp:afi-safi/bgp:ipv4-mpvn" {
    description "Retain route targets for ASBR scenario";
    uses retain-route-targets;
  }

  augment "/bgp:bgp/bgp:global/bgp:afi-safis/bgp:afi-safi/bgp:ipv6-mpvn" {
    description "Retain route targets for ASBR scenario";
    uses retain-route-targets;
  }
  */

  // Label allocation mode configuration. Certain AFs only.
  augment "/bgp:bgp/bgp:global/bgp:afi-safis/bgp:afi-safi/bgp:ipv4-unicast" {
     description "Augment BGP global AF mode for label allocation mode configuration";
     uses bgp-label-mode ;
  }

  augment "/bgp:bgp/bgp:global/bgp:afi-safis/bgp:afi-safi/bgp:ipv6-unicast" {
     description "Augment BGP global AF mode for label allocation mode configuration";
     uses bgp-label-mode ;
  }

  //Nexthop options for the inter-as option-B and option-C ASBR peering.
  augment "/bgp:bgp/bgp:neighbors/bgp:neighbor" {
     description "Augment BGP NBR mode with nexthop options for inter-as ASBRs";
     uses asbr-nexthop-options;
  }

  augment "/bgp:bgp/bgp:peer-groups/bgp:peer-group" {
     description "Augment BGP peer-group mode with nexthop options for inter-as ASBRs";
     uses asbr-nexthop-options;
  }

  augment "/bgp:bgp/bgp:neighbors/bgp:neighbor/bgp:afi-safis/bgp:afi-safi" {
     description "Augment BGP NBR AF mode with nexthop options for inter-as ASBRs";
     uses asbr-nexthop-options;
  }

  augment "/bgp:bgp/bgp:peer-groups/bgp:peer-group/bgp:afi-safis/bgp:afi-safi" {
     description "Augment BGP peer-group AF mode with nexthop options for inter-as ASBRs";
     uses asbr-nexthop-options;
  }

  // Add route import-export rules in  VRF level (routing instance container in ietf-routing model).
  augment "/rt:routing/rt:routing-instance" {
     description "Augment routing instance container for per VRF import/export rules configuration";
     uses route-filter-set ;
  }

  // bgp mpls forwarding enable required for inter-as option AB.
  // mpls label secruity for inter-as option-B
  augment "/if:interfaces/if:interface" {
    description "BGP mpls forwarding mode configuration on interface for ASBR scenario";
    uses forwarding-mode ;
    uses label-security;
  }
}
