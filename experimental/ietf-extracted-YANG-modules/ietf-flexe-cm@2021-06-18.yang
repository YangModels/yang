module ietf-flexe-cm {
  yang-version 1.1;
  namespace "urn:ietf:params:xml:ns:yang:ietf-flexe-cm";
  prefix "flexe-cm";

  import iana-if-type {
    prefix ianaift;
  }
  import ietf-interfaces {
    prefix if;
    reference
    "RFC8343: A YANG Data Model for Interface Management";
  }
  organization "IETF CCAMP Working Group";
  contact
   "WG Web:   http://tools.ietf.org/wg/ccamp/
    WG List:  <mailto:ccamp@ietf.org>
    Author:   Minxue Wang
              <mailto: wangminxue@chinamobile.com>
    Author:   Liuyan Han
              <mailto: hanliuyan@chinamobile.com>
    Author:   Fan Yang
              <mailto:shirley.yangfan@huawei.com>
    Author:   Yuanlong Jiang
              <mailto:jiangyuanlong21@yeah.net>";
  description
   "This YANG module defines a data model for the configuration
    of a FlexE network and its clients.";

  revision "2021-06-18" {
    description "Initial version";
    reference
    "draft-wang-ccamp-flexe-yang-cm-00: YANG Data Model for FlexE
     Management";
  }

  typedef negotiation-mode-type {
    type enumeration {
      enum "dynamic" {
        value 1;
        description
          "Dynamic mode.";
      }
      enum "static" {
        value 2;
        description
          "Static mode.";
      }
    }
    description
      "Negotiation mode of a FlexE group.";
  }

  container flexe {
    description
      "Specify FlexE configuration information.";
    container flexe-groups {
      description
        "List of FlexE groups.";
      list flexe-group {
        key "index";
        description
          "Configure FlexE group.";
        leaf index {
          type uint32 {
            range "1..65535";
          }
          description
            "FlexE group index.";
        }
        leaf group-num {
          type uint32 {
            range "1..1048574";
          }
          description
            "FlexE group number, as specified in OIF FlexE 2.1.";
        }
        leaf negotiation-mode {
          type negotiation-mode-type;
          default "dynamic";
          description
            "FlexE group calendar negotiation mode.";
        }
        leaf total-bandwidth {
          type string {
            length "1..9";
          }
          config false;
          description
            "FlexE group total bandwidth in Gbit/s, such as 10.";
        }
        leaf free-bandwidth {
          type string {
            length "1..9";
          }
          config false;
          description
            "FlexE group free bandwidth in Gbit/s, such as 100.";
        }
        leaf sync-phy-number {
          type uint32 {
            range "1..254";
          }
          config false;
          description
            "The FlexE PHY number used for synchronization management
             channel in a FlexE group, which is one of the PHY number
             value in a FlexE group.";
        }
        container flexe-phys {
          description
            "List of physical port information in a FlexE Group.";
          list flexe-phy {
            key "port-name";
            description
              "FlexE PHY port name.";
            leaf port-name {
              type if:interface-ref;
              description
                "Physical port name. ";
            }
            leaf flexe-phy-number {
              type uint32 {
                range "1..254";
              }
              description
                "Number of a FlexE physical port. The PHY number of
              a 100G port is an integer ranging from 1 to 254.
              The PHY number of a 50G port is an integer ranging
              from 1 to 126.";
            }
            leaf free-timeslot-list {
              type string {
                length "1..199";
              }
              config false;
              description
                "Free timeslots.";
            }
            leaf used-timeslot-list {
              type string {
                length "1..199";
              }
              config false;
              description
                "Timeslots that have been used.";
            }
          }
        }
      }
    }
  }

  augment "/if:interfaces/if:interface" {
    when "if:type = 'ianaift:flexEclient'" {
      description "Applies to FlexE client interfaces";
    }
    description
      "Augment interface model with FlexE client interface specific
      configuration nodes. Each flexEclient interface represents a
      FlexE Client configured in a device.";

    container flexe-client {
      description
        "FlexE client.";
      leaf client-index {
        type uint32 {
          range "1..65535";
        }
        description
          "FlexE client index.";
      }
      leaf group-index {
        type leafref {
        path "/flexe-cm:flexe/flexe-cm:flexe-groups/flexe-cm:flexe-group"
         + "/flexe-cm:index";
        }
        description
          "A local FlexE group index configured for a client on one
           equipment for the sake of simplicity on configuration and
           management.";
      }
      leaf client-num {
        type uint32 {
          range "1..65534";
        }
        description
          "FlexE Client number.";
      }
      container timeslot-lists {
        description
          "List of binding timeslots.";
        list timeslot-list {
          key "port-name";
          description
            "Configure binding timeslots.";
          leaf port-name {
            type if:interface-ref;
            description
              "FlexE physical port name.";
          }
          leaf time-slot {
            type string {
              length "1..199";
            }
            description
              "Set timeslot. The string consists of one or more
            numbers separated by commas (,) or hyphens (-).";
          }
        }
      }
    }
  }
}
