module ietf-ip-tunnel{

  namespace "urn:ietf:params:xml:ns:yang:ietf-ip-tunnel";
  prefix "iptnl";

  import ietf-interfaces {
    prefix "if";
  }

  import ietf-inet-types {
    prefix inet;
  }

  import ietf-routing {
    prefix "rt";
  }

  import iana-if-type {
    prefix ianaift;
  }

  organization
    "IETF NETMOD (NETCONF Data Modeling Language) Working Group.";

  contact
    "Mandy.Liu@ericsson.com
     Adam.Foldes@ericsson.com
     zhengguangying@huawei.com";

  description
    "This YANG model defines the configuration data
     and operational state data for generic IPv4/6-in-IPv4 tunnel.
     It includes the IPv4 in IPv4, 6-to-4, and IPv6 over IPv4 manual
     tunnels.";

  revision 2016-04-27 {
    description
      "Made model more generic in order to allow augmentation by e.g.
       GRE tunnels.";
    reference
      "RFC XXXX: A YANG Data Model for IPv4 Tunnel.";
  }
  revision 2016-03-11 {
    description
      "Collapsed all tunnel types into a single subtree based on
       suggestions to more closely follow the IP Tunnel MIB.";
    reference
      "RFC XXXX: A YANG Data Model for IPv4 Tunnel.";
  }
  revision 2015-10-14 {
    description
      "Update model based on comments.";
    reference
      "RFC XXXX: A YANG Data Model for IPv4 Tunnel.";
  }

  revision 2015-07-20 {
    description
      "This version adds the following new items:
        - hop-limit
        - tos
        - tunnel-type
       This version changes 'ipv6to4-auto' to 'ipv6to4'";
    reference
      "RFC XXXX: A YANG Data Model for IPv4 Tunnel.";
  }

  revision 2015-05-27 {
    description
      "Initial revision.";
    reference
      "RFC XXXX: A YANG Data Model for IPv4 Tunnel.";
  }

  /* Identities */
  identity ip-tunnel-type {
    description
      "Base identity from which identities describing
       IP tunnel types are derived.";
  }
  identity ip-ip {
    base ip-tunnel-type;
    description
      "This identity represents IPv4-in-IPv4 tunnel type";
  }
  identity ipv6v4-manual {
    base ip-tunnel-type;
    description
      "This identity represents IPv6-to-IPv4 manual tunnel type";
  }
  identity ipv6-to-v4 {
    base ip-tunnel-type;
    description
      "This identity represents the 6-to-4 tunnel type";
  }

        typedef routing-instance-ref {
        type leafref {
          path "/rt:routing/rt:routing-protocols/rt:routing-protocol/rt:name";
        }
        description
        "This type is used for leafs that reference a routing instance
         configuration.";
      }

  /*Configuration Data*/
  container Tunnels{
    description
     "Configuration data for tunnels.";
    list Tunnel{
      key "name type";
      description
        "Configuration data for tunnels.";
      leaf name {
        type string;
        description
          "Name of the tunnel.";
      }
      leaf type {
        type identityref {
          base ip-tunnel-type;
        }
        description "The encapsulation type of the tunnel.";
      }

      leaf routing-instance {
        type routing-instance-ref;
        description "The routing instance of the local address.";
      }
      uses tunnel-config-components;
    }
  }

  /* Configuration data */
  grouping tunnel-config-components {
      description
        "Configuration data for all tunnels and subtunnels";
      leaf description {
        type string {
          length "1..255";
        }
        description
          "Textual description for a tunnel. Can be any "+
          "alphanumeric string, including spaces, not to exceed "+
          "255 ASCII characters.";
      }
      leaf bind-interface {
        type if:interface-ref;
        description
          "Bind to an interface.";
      }
          leaf local-address {
        type inet:ip-address-no-zone;
        description "IP address of the local end of the tunnel.";
      }
      leaf remote-address {
        when "type != ipv6-to-v4" {
          description
            "6-to-4 tunnels do not have a fixed remote endpoint.";
        }
        type inet:ip-address-no-zone;
        description "IP address of the remote end of the tunnel.";
      }

      leaf clear-df {
        type empty;
        description
          "If clear-df is absent, it means that fragmentation of
           tunnel packets are permitted. If clear-df is present,
           it means that fragmentation of tunnel packets are not
           permitted.";
      }
      leaf shutdown {
        type empty;
        description
          "Disable/enable the tunnel.";
      }
      leaf tmtu {
        type uint16 {
          range "256..16384";
        }
        description
          "Sets the Maximum Transmission Unit (MTU) size for
           packets sent in a tunnel. The default MTU is the MTU
           for the interface to which the tunnel is bound.";
      }
      leaf mirror-destination {
        type string;
        description
          "Designate the name of a tunnel as a circuit
           mirror destination. ";
      }
      leaf hop-limit {
        type uint8 {
          range "0|1..255";
        }
        description
          "The IPv4 TTL or IPv6 Hop Limit which is used in the
           outer IP header. A value of 0 indicates that the value
           is copied from the payload's header.";
      }
      leaf tos {
        type int8 {
          range "-1..63";
        }
        description
          "The method used to set the high 6 bits (the
            differentiated services codepoint) of the IPv4 TOS or
            IPv6 Traffic Class in the outer IP header. A value of -1
            indicates that the bits are copied from the payload\u2019s
            header. A value between 0 and 63 inclusive indicates
            that the bit field is set to the indicated value.";
      }

  }

  /*Operational state data*/
  grouping tunnel-oper-states {
    description "Operational states of tunnels";
    choice state {
      description "Choice of operational states";
      case up {
        leaf up {
          type empty;
          description "The tunnel is up.";
        }
      }
      case down {
        leaf down {
          type empty;
          description "The tunnel is down.";
        }
      }
      case shutdown {
        leaf shutdown {
          type empty;
          description "The tunnel is shut down administratively.";
        }
      }
    }
  }

  grouping tunnel-state-components {
    description
      "The basic tunnel information to be displayed.";

    leaf name {
      type string;
      description
        "Name of the tunnel.";
    }

    leaf type {
      type identityref;
      description
        "The type of the tunnel.";
    }
    leaf local-ip {
      type inet:ip-address-no-zone;
      description
        "IP address of the local end of the tunnel.";
    }
    leaf remote-ip {
      type inet:ip-address-no-zone;
      description
        "IP address of the remote end of the tunnel.";
    }
    uses tunnel-oper-states;
    leaf bind-interface {
      type if:interface-state-ref;
      description
        "Bind to an interface.";
    }
    leaf user-configured {
      type boolean;
          description
        "Indicate the tunnel is user-configured or dynamic.
        False is for dynamic.";
    }
    leaf routing-instance {
      type routing-instance-ref;
      description
        "Name of the reference routing instance. ";
    }
    leaf tmtu {
      type uint16;
      description
        "The Maximum Transmission Unit (MTU) size for
      packets sent in a tunnel.";
    }
    leaf clear-df {
      type empty;
      description
        "Indicate that the DF bit is cleared.";
    }
    leaf down-reason {
      type string;
      description
        "The reason of the tunnel is down.";
    }
    leaf resolved-interface-name{
      type string;
      description
        "The egress interface name of the tunnel.";
    }
    leaf hop-limit {
      type uint32;
      description
        "The IPv4 TTL or IPv6 Hop Limit which is used in the outer IP
         header. A value of 0 indicates that the calue is copied from
         the payload's header.";
    }
    leaf tos {
      type int32;
      description
        "The high 6 bits (the differentiated
         services codepoint) of the IPv4 TOS or IPv6 Traffic Class in
         the outer IP header. A value of -1 indicates that the bits
         are copied from the payload\u2019s header. A value between 0 and
         63 inclusive indicates that the bit field is set to the
         indicated value.";
    }
  }

  container tunnel-state {
    config "false";
      description
        "Contain the information currently configured tunnels.";
      list tunnels {
        description
           "Operational state data of tunnels.";
         uses tunnel-state-components;
      }
  }

  //Augment operational state data of IP interfaces
  augment "/if:interfaces-state/if:interface" {
    when "if:type = 'ianaift:tunnel'" {
      description
        "Augment IP interface.";
    }
    description
      "Augment operational state data of IP interfaces.";
    leaf tunnel-protocol {
      type identityref;
      description
        "Indicate the state of the IP tunnel interface.";
    }
  }
}
