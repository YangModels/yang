module draft-ietf-ccamp-dwdm-if-param-yang-03 {
  namespace "urn:ietf:params:xml:ns:yang:ietf-ext-xponder-wdm-if";
  prefix ietf-ext-xponder-wdm-if;

  import ietf-interfaces {
    prefix if;
  }

  import ietf-layer0-types {
    prefix "layer0-types";
  }

  organization
    "IETF CCAMP
    Working Group";

  contact
    "WG Web:   <http://tools.ietf.org/wg/ccamp/>
     WG List:  <mailto:ccamp@ietf.org>

     Editor:   Dharini Hiremagalur
               <mailto:dharinih@juniper.net>";

  description
    "This module contains a collection of YANG definitions for
     configuring Optical interfaces.

     Copyright (c) 2016 IETF Trust and the persons identified
     as authors of the code.  All rights reserved.

     Redistribution and use in source and binary forms, with or
     without modification, is permitted pursuant to, and
     subject to the license terms contained in, the Simplified
     BSD License set forth in Section 4.c of the IETF Trust's
     Legal Provisions Relating to IETF Documents
     (http://trustee.ietf.org/license-info).";

  revision "2020-03-09" {
    description
      "Revision 1.5";
    reference
      "";
    }

  revision "2019-11-04" {
    description
      "Revision 1.4";
    reference
      "";
    }

  revision "2019-07-08" {
    description
      "Revision 1.3";
    reference
      "";
    }
    revision "2018-10-22" {
      description
        "Revision 1.2";
      reference
        "";
    }
    revision "2018-03-06" {
      description
        "Revision 1.1";
      reference
        "";
    }
    revision "2017-03-06" {
      description
        "Revision 1.0";
      reference
        "";
    }
    revision "2016-03-17" {
      description
        "Initial revision.";
      reference
        "";
    }

    typedef dbm-t {
        type int32;
        units ".01dbm";
      }
      description "
        Amplifiers and Transceivers Power in dBm";
    }
