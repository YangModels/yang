module ietf-lisp-mapserver {
  namespace "urn:ietf:params:xml:ns:yang:ietf-lisp-mapserver";
  prefix lisp-ms;
  import ietf-lisp {
    prefix lisp;
  }
  import ietf-lisp-address-types {
    prefix lcaf;
  }
  organization
    "IETF LISP (Locator/ID Separation Protocol) Working Group";
  contact
    "lisp@ietf.org";
  description
    "This YANG module defines the generic configuration
     data for a LISP Map-Server. The module can be extended by
     vendors to define vendor-specific configuration parameters
     and policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";

  revision 2016-06-30 {
    description
      "Initial revision.";
    reference
      "https://tools.ietf.org/html/rfc6833";
  }

  identity ms {
    base lisp:lisp-role;
      description
        "LISP Map-Server.";
  }

  augment "/lisp:lisp/lisp:lisp-router-instances"
  + "/lisp:lisp-router-instance/lisp:lisp-role" {
    when "lisp:lisp-role-type = 'lisp-ms:ms'" {
      description
        "Augment is valid when LISP device type is Map-Server.";
    }
    description
      "This augments LISP devices list with Map-Server specific
       parameters.";
    container map-server-cfg {
      description
        "Map-Server configuration parameters.";
      container sites {
        description
          "Sites for which the Map-Server accepts registrations.";
        list site {
          key "site-id";
          description
            "List of sites for which the Map-Server acceptes
             registrations.";
          leaf site-id {
            type uint64;
            description
              "Site identifier.";
          }
          container auth-key {
            description
              "Site authentication key.";
            leaf auth-key-value {
              type string;
              description
                "Clear text authentication key";
            }
            leaf auth-key-type {
              type lisp:auth-key-type;
              description
                "Authentication key type.";
            }
          }
          container eids {
            description
              "EIDs registered by device.";
            list eid {
              key "id";
              description
                "List of EIDs registered by device.";
              leaf id {
                type lisp:eid-id;
                description
                  "Id of the EID registered.";
              }
              container eid-address {
                uses lcaf:lisp-address;
                description
                  "EID in generic LISP address format registered
                   with the Map-Server.";
              }
              leaf more-specifics-accepted {
                  type boolean;
                  default "false";
                  description
                    "Flag indicating if more specific prefixes
                     can be registered.";
              }
              leaf mapping-expiration-timeout {
                  type int16;
                  units "seconds";
                  default "180"; //3 times the mapregister int
                  description
                    "Time before mapping is expired if no new
                     registrations are received.";
              }
    // This model can be augmented to have below for per-eid auth-key
    //          leaf auth-key {
    //            description "clear text authentication key";
    //            type string;
    //          }
            }
          }
        }
      }
      leaf mapping-system-type {
        type lisp:mapping-system-ref;
        description
          "A reference to the mapping system";
      }
    }
  }

  augment "/lisp:lisp-state/lisp:lisp-router-instances"
  + "/lisp:lisp-router-instance/lisp:lisp-role" {
    when "lisp:lisp-role-type = 'lisp-ms:ms'" {
      description
        "Augment is valid when LISP device type is Map-Server.";
    }
    description
      "This augments LISP devices list state with Map-Server
       specific parameters.";
    container ms-state {
      config false;
      description
        "Map-Server state.";
      container registered-mappings {
        uses lisp:mappings;
        description
          "Datastore of registred mappings.";
      }
    }
  }
}
