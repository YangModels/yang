module ietf-keyed-v6-tunnel {
  namespace "urn:ietf:params:xml:ns:yang:ietf-keyed-v6-tunnel";
  prefix k6tun;

  import ietf-interfaces {
    prefix if;
  }
  import ietf-inet-types {
    prefix inet;
  }
  import ietf-yang-types {
    prefix yang;
  }

  organization "IETF l2tpext Working Group";

  contact
    "qui.sun@external.telekom.de
     ian.farrer@telekom.de
     leo.liubing@huawei.com
     giheron@cisco.com
    ";

  description
    "Keyed IPv6 L2TPv3 Tunnel";

  revision 2016-03-21 {
    description
      "Added sequencing feature";
    reference
      "draft-ietf-l2tpext-keyed-v6-tunnel-yang-01";
  }

  revision 2015-07-06 {
    description
      "General clean-up"
      ;
    reference
      "draft-sun-l2tpext-keyed-v6-tunnel-yang-01";
  }

  revision 2015-03-09 {
    description
      "Initial version.
      ";
    reference
      "draft-sun-l2tpext-keyed-v6-tunnel-yang-00";
  }

  /*
   * features
   */
  feature FCS-Retention {
    description
      "Device supports the retention of frame check sequence (FCS)
      as per Section 4.7 of RFC4720";
  }
  feature VCCV {
    description
      "Device supports the Pseudowire Virtual Circuit Connectivity
      Verification (VCCV) as per RFC5085";
  }
  feature BFD {
    description
      "Device supports BFD over the tunnel as per RFC5883";
  }
  feature VCCV-BFD {
    description
      "Device supports BFD over VCCV as per RFC5885";
  }
  feature l2tpv3-fragmentation {
    description
      "Device supports L2TPv3 fragmentation as per RFC4623";
  }
  feature l2tpv3-sequencing {
    description
      "Device supports frame sequencing as per section 4.6.1 of
      RFC3931";
  }

  /*
   * typedefs
   */

  /*
   * groupings
   */
  /*
   * config parameters
   */
  container tunnelConfigurations {
    list tunnelConfiguration {
      key "tunnelName";
      unique "srcInterface remoteIPv6";
      unique "localIPv6 remoteIPv6";
      leaf tunnelName {
        type string;
        description "name for this keyed tunnel";
      }
      leaf srcInterface {
        type if:interface-ref;
        mandatory true;
        description
          "Source interface that identifies the L2 circuit
          endpoint.";
      }
      leaf localIPv6 {
        type inet:ipv6-address;
        mandatory true;
        description "IPv6 address for local end of keyed tunnel";
      }
      leaf remoteIPv6 {
        type inet:ipv6-address;
        mandatory true;
        description "IPv6 address for remote end of keyed tunnel";
      }
      leaf localSessionId {
        type uint32;
        default 0xFFFFFFFF;
        description
          "As the IPv6 address is used to determine the tunnel
          and there is a single session per tunnel, the Session ID
          can be ignored upon receipt. For compatibility with
          other tunnel termination platforms supporting two-stage
          resolution (IPv6 address + Session ID), the Session ID
          is configured with a random value other than all zeros.
          If both ends support one-stage (IPv6 address), then
          the Session ID is recommended to be set to all ones.";
      }
      leaf remoteSessionId {
        type uint32;
        default 0xFFFFFFFF;
        description
          "Since IPv6 address is used to determine the tunnel
          and there is one session per tunnel, the Session ID
          can be ignored upon receipt. For compatibility with
          other tunnel termination platforms supporting two-stage
          resolution (IPv6 address + Session ID) the Session ID
          is configured with a random value other than all zeros.
          If both ends support one-stage (IPv6 address), then
          the Session ID is recommended to be set to all ones.";
      }
      container localCookies {
        list localCookie {
          key "cookieName";
          leaf cookieName {
            type string;
            description "name identifying this cookie";
          }
          min-elements 2;
          max-elements 2;
          leaf cookieValue {
            type uint64;
            mandatory true;
            description "value of this cookie";
          }
          description
            "List of local cookies - must contain two entries at
            all times to enable lossless cookie rollover";
        }
        description
          "The length of cookie MUST be 64-bit. It MUST be
          possible to change the cookie value at any time
          in a manner that does not drop any legitimate
          tunneled packets - i.e. the receiver
          must accept a received cookie matching either
          value during a change of cookie value.";
      }
      leaf remoteCookie {
        type uint64;
        mandatory true;
        description
          "The length of cookie MUST be 64-bit. A single
          remote cookie is used for sending packets.";
      }
      leaf retainFCS {
        if-feature FCS-Retention;
        type empty;
        description
          "If this parameter is present, the router is configued
           to retain FCS. Any such router MUST retain the FCS
           for all frames sent over that tunnel.
          ";
      }
      container enable-vccv {
        if-feature VCCV;
        presence "Enable VCCV [RFC5085]";
        leaf enable-bfd {
          if-feature VCCV-BFD;
          type empty;
            description "Enable VCCV-BFD [RFC5885].";
        }
        description "Enable VCCV [RFC5085]";
      }
      leaf enable-bfd {
        if-feature BFD;
        type empty;
        description
          "Enable BFD over the tunnel [RFC5883].";
      }
      leaf disable-pmtu {
        type empty;
          description "Disable IPv6 PMTU discovery [RFC1981]";
      }
      container enable-fragmentation {
        if-feature l2tpv3-fragmentation;
        presence "Enable L2TPv3 fragmentation [RFC4623]";
        leaf fragment-mru {
          type uint16;
          description "Explicit override for fragmentation MRU";
        }
        description
          "Default is to fragment to PMTU (or 1500 if PMTU is
          disabled) minus 52 octets for the encapsulation
          overhead";
      }
      leaf enable-sequencing {
        if-feature l2tpv3-sequencing;
        type empty;
        description
          "Enable L2TPv3 sequencing [RFC3931 section 4.6.1]";
      }
      description
        "keyed-v6-tunnel typically supports one l2tpv3 session
        per tunnel. The srcInterface and localIPv6 both uniquely
        identify a tunnel endpoint. If a virtual interface
        is used, the localIPv6 and remoteIPv6 as a pair MUST
        also be unique.
        ";
    }
   description
     "container for list of keyed-v6-tunnel entries";
  }
  container tunnelStates {
    config false;
    list tunnelState {
      key "tunnelName";
      leaf tunnelName {
        type string;
        description "name of this keyed tunnel";
      }
      leaf sentPacket {
        type yang:zero-based-counter64;
        description
          "counter for the number of packets sent over tunnel";
      }
      leaf sentByte {
        type yang:zero-based-counter64;
        description
          "counter for total sent bytes (of inner packets)";
      }
      leaf rcvdPacket {
        type yang:zero-based-counter64;
        description
          "counter for number of valid packets received from
          tunnel";
      }
      leaf rcvdByte {
        type yang:zero-based-counter64;
        description
          "counter for total received bytes (of inner packets)";
      }
      leaf droppedPacket {
        type yang:zero-based-counter64;
        description
          "Counter for number of dropped packets matching this
          tunnel (e.g. due to invalid received cookie,
          insufficient resources to process).";
      }
      leaf droppedByte {
        type yang:zero-based-counter64;
        description
          "Counter for total dropped bytes (of inner packets)";
      }
      leaf fragmentCounter {
        type yang:zero-based-counter64;
        description
          "Counter for number of received fragments";
      }
      description "per-tunnel statistics";
    }
    description "container for list of tunnel statistics";
  }
}
