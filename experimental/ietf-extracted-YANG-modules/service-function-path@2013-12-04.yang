module service-function-path {

  namespace "urn:cisco:params:xml:ns:yang:sfc-path";

  prefix sfc-path;

  import ietf-inet-types { prefix inet; }
  import ietf-yang-types { prefix yang; }
  import service-node {prefix sfc-sn; }

  organization "Cisco Systems, Inc.";
  contact "Reinaldo Penno <repenno@cisco.com>";

  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2013-12-04 {
    description
    "Initial revision.";
  }

  // Service Function Path

  container service-function-path {
    description
      "A service chain defines the required functions and
      associated order (service-function1 --> service-function 2) that
      must be applied to packets and/or frames.  A service chain does
      not specify the network location or specific instance of service
      functions (e.g. firewall1 vs. firewall2).";
    leaf-list service-function {
      type string;
      ordered-by user;
      description
        "A list of service functions that compose the service chain";
    }
    leaf transport {
      type sfc-sn:transport-type;
    }
    uses network-service-base-header;
  }

/*
   Base Service Header:

      0                   1                   2                   3
      0 1 2 3 4 5 6 7 8 9 0 1 2 3 4 5 6 7 8 9 0 1 2 3 4 5 6 7 8 9 0 1
     +-+-+-+-+-+-+-+-+-+-+-+-+-+-+-+-+-+-+-+-+-+-+-+-+-+-+-+-+-+-+-+-+
     |O|C|R|R|R|R|R|R| Protocol Type                 |Service Index  |
     +-+-+-+-+-+-+-+-+-+-+-+-+-+-+-+-+-+-+-+-+-+-+-+-+-+-+-+-+-+-+-+-+
     |                 Service path                  | Reserved      |
     +-+-+-+-+-+-+-+-+-+-+-+-+-+-+-+-+-+-+-+-+-+-+-+-+-+-+-+-+-+-+-+-+

   Flags: 8
   Protocol Type (PT): 16
   Service Index: 8
   Service path: 24
   Reserved: 8
*/

  typedef service-header-flag-type {
    type bits {
      bit oam {
        position 0;
        description
          "Indicates that this packet is an operations and management
          (OAM) packet";
      }
      bit context-use {
        position 1;
        description
          "If a context header is not in use, the value of that context
          header MUST be zero";
      }
      bit r1 {
        position 2;
        description "Some description";
      }
      bit r2 {
        position 3;
        description "Some description";
      }
      bit r3 {
        position 4;
        description "Some description";
      }
      bit r4 {
        position 5;
        description "Some description";
      }
      bit r5 {
        position 6;
        description "Some description";
      }
      bit r6 {
        position 7;
        description "Some description";
      }
    }
    description "Service-Header Flags";
    reference "http://tools.ietf.org/html/draft-quinn-nsh-00";
  }

  grouping network-service-base-header {
    description "Network Service Base header";

    leaf service-header-flag-value {
        type service-header-flag-type;
    }

    leaf protocol-type {
        type uint8;
        // Reinaldo: Another option is to import Opendaylight L2 Types so have ethertype
    }

    leaf service-index {
      type uint8 {
        range "0 .. 255";
      }
      description "TTL functionality and location within the service
            path";
    }
    leaf-list service-path {
      type uint8;
      min-elements 3;
      max-elements 3;
    }

    leaf reserved {
      default 0;
      type uint8 {
        range "0 .. 255";
      }
      description "Reserved field";
    }
  }
}
