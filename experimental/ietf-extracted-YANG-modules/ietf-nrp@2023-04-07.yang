module ietf-nrp {
  yang-version 1.1;
  namespace "urn:ietf:params:xml:ns:yang:ietf-nrp";
  prefix nrp;

  import ietf-network {
    prefix nw;
    reference
      "RFC 8345: A YANG Data Model for Network Topologies";
  }
  import ietf-network-topology {
    prefix nt;
    reference
      "RFC 8345: A YANG Data Model for Network Topologies";
  }
  import ietf-routing-types {
    prefix rt-types;
    reference
      "RFC 8294: Common YANG Data Types for the Routing Area";
  }
  import ietf-te-types {
    prefix te-types;
    reference
      "RFC 8776: Traffic Engineering Common YANG Types";
  }
  import ietf-te-packet-types {
    prefix te-packet-types;
    reference
      "RFC 8776: Traffic Engineering Common YANG Types";
  }
  import ietf-srv6-types {
    prefix srv6-types;
  }
  import ietf-inet-types {
    prefix inet;
    reference
      "RFC 6991: Common YANG Data Types";
  }
  import ietf-access-control-list {
    prefix acl;
    reference
      "RFC 8519: YANG Data Model for Network Access Control Lists
       (ACLs)";
  }
  import ietf-topology-filter {
    prefix topo-filt;
    reference
      "draft-bestbar-teas-yang-topology-filter: YANG Data Model
       for Topology Filter";
  }

  organization
    "IETF TEAS Working Group";
  contact
    "
     WG Web: <http://tools.ietf.org/wg/teas/>
     WG List:<mailto:teas@ietf.org>

     Editor:   Bo Wu
            <mailto:lana.wubo@huawei.com>

     Editor:   Dhruv Dhody
            <mailto:dhruv.ietf@gmail.com>

     Editor:   Vishnu Pavan Beeram
               <mailto:vbeeram@juniper.net>
     Editor:   Tarek Saad
               <mailto:tsaad.net@gmail.com>

     Editor:   Shaofu Peng
               <mailto:peng.shaofu@zte.com.cn>";
  description
    "This YANG module defines a network data module for
     NRP(Network Resource Partition).

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
        (https://trustee.ietf.org/license-info).

     This version of this YANG module is part of RFC XXXX
     (https://www.rfc-editor.org/info/rfcXXXX); see the RFC itself
     for full legal notices.";

  revision 2023-04-07 {
    description
      "This is the initial version of NRP YANG model.";
    reference
      "RFC XXX: A YANG Data Model for Network Resource Partition";
  }

  /*
   * I D E N T I T I E S
   */

  identity nrp-partition-mode {
    description
      "Base identity for nrp partition type.";
  }

  identity nrp-control-plane-partition {
    base nrp-partition-mode;
    description
      "Identity for control plane partition.";
  }

  identity nrp-data-plane-partition {
    base nrp-partition-mode;
    description
      "Identity for data plane partition.";
  }

  identity nrp-hybrid-plane-partition {
    base nrp-partition-mode;
    description
      "Identity for both planes partition.";
  }

  identity nrp-link-partition-type {
    description
      "Base identity for interface partition type.";
  }

  identity virtual-sub-interface-partition {
    base nrp-link-partition-type;
    description
      "Identity for virtual interface or sub-interface, e.g. FlexE.";
  }

  identity queue-partition {
    base nrp-link-partition-type;
    description
      "Identity for queue partition type.";
  }

  /*
   * Identity:
   * MPLS Selector Label Position.
   */

  identity selector-mpls-label-position {
    description
      "Base identity for the position of the MPLS selector label.";
  }

  identity selector-mpls-label-position-top {
    base selector-mpls-label-position;
    description
      "MPLS selector label is at the top of the label stack.";
  }

  identity selector-mpls-label-position-bottom {
    base selector-mpls-label-position;
    description
      "MPLS selector label is either at the bottom or at a specific
       offset from the bottom of the label stack.";
  }
  identity selector-mpls-label-position-indicator {
    base selector-mpls-label-position;
    description
      "MPLS selector is preceded by a special purpose
       indicator label in the label stack.";
  }

  /*
   * T Y P E D E F S
   */

  typedef nrp-acl-ref {
    type leafref {
      path "/acl:acls/acl:acl/acl:name";
    }
    description
      "This type is used to reference an ACL.";
  }

  typedef nrp-topo-filter-ref {
    type leafref {
      path "/nw:networks/topo-filt:topology-filters/"
         + "topo-filt:topology-filter/topo-filt:name";
    }
    description
      "This type is used to reference a Topology Filter.";
  }

  /*
   * Grouping - NRP Resource Reservation
   */

  grouping nrp-resource-reservation {
    description
      "Grouping for NRP resource reservation.";
    container resource-reservation {
      description
        "Container for NRP resource reservation.";
      choice max-bw-type {
        description
          "Choice of maximum bandwidth specification.";
        case bw-value {
          leaf maximum-bandwidth {
            type uint64;
            description
              "The maximum bandwidth allocated to an NRP
               - specified as absolute value.";
          }
        }
        case bw-percentage {
          leaf maximum-bandwidth-percent {
            type rt-types:percentage;
            description
              "The maximum bandwidth allocated to an NRP
               - specified as percentage of link
               capacity.";
          }
        }
      }
    }
  }

  /*
   * G R O U P I N G S
   */
  /*
   * Grouping - MPLS selector label location specific fields
   */

  grouping nrp-selector-mpls-label-location {
    description
      "Grouping for MPLS FAS label location specific fields.";
    leaf label-position {
      type identityref {
        base selector-mpls-label-position;
      }
      description
        "MPLS selector label position.";
    }
    leaf label-position-offset {
      when "derived-from-or-self(../label-position,"
         + "'nrp:selector-mpls-label-position-bottom')" {
        description
          "MPLS label position offset is relevant only when the
           label-position is set to 'bottom'.";
      }
      type uint8;
      description
        "MPLS label position offset.";
    }
  }

  /*
   * Grouping - NRP Selector Configuration
   */

  grouping nrp-selector-config {
    description
      "Grouping for NRP selector configuration.";
    container selector {
      description
        "Container for NRP selector.";
      container ipv4 {
        description
          "Container for IPv4 NRP selector.";
        leaf-list destination-prefix {
          type inet:ipv4-prefix;
          description
            "Any prefix from the specified set of IPv4
             destination prefixes can be the selector.";
        }
      }
      container ipv6 {
        description
          "Container for IPv6 NRP selector.";
        choice selector-type {
          description
            "Choices for IPv6 selector type.";
          case dedicated {
            leaf ipv6-hbh-eh {
              type uint32;
              description
                "The selector value carried in Hop-by-Hop
                 Option of IPv6 extension header.";
            }
          }
          case srv6-sid-derived {
            leaf-list srv6-sid {
              type inet:ipv6-prefix;
              description
                "Any SID from the specified set of SRv6
                 SID can be the selector.";
            }
          }
          case ipv6-destination-derived {
            leaf-list destination-prefix {
              type inet:ipv6-prefix;
              description
                "Any prefix from the specified set of IPv6
                 destination prefixes can be the selector.";
            }
          }
        }
      }
      container mpls {
        description
          "Container for MPLS NRP selector.";
        choice selector-type {
          description
            "Choices for MPLS label specification.";
          case dedicated {
            leaf label {
              type rt-types:mpls-label;
              description
                "MPLS selector Label is explicitly
                 specified.";
            }
            uses nrp-selector-mpls-label-location;
          }
          case derived {
            leaf forwarding-label {
              type empty;
              description
                "MPLS selector Label is derived from
                 forwarding label.";
            }
          }
        }
      }
      leaf-list acl-ref {
        type nrp-acl-ref;
        description
          "Selection is done based on the specified list of ACLs.";
      }
    }
  }

  /*
   * Grouping - NRP QoS PHB profile
   */

  grouping nrp-qos-phb-profile {
    description
      "Grouping for NRP QoS PHB profile.";
    leaf phb-profile {
      type string;
      description
        "PHB profile identifier.";
    }
  }

  /*
   * Grouping - NRP IGP congruent
   */

  grouping nrp-igp-congruent {
    description
      "Grouping for NRP IGP congruent attributes.";
    container igp-congruent {
      presence "indicates NRP IGP congruent";
      description
        "The presence of the container node indicates NRP IGP
         congruent.";
      leaf multi-topology-id {
        type uint32;
        description
          "Indicates the MT-id of the NRP IGP instance.";
      }
      leaf algo-id {
        type uint32;
        description
          "Indicates the algo-id of the NRP IGP instance.";
      }
      leaf sharing {
        type boolean;
        default "true";
        description
          "'true' if the the NRP IGP instance can be shared with
           other NRPs;
           'false' if the the NRP IGP instance is dedicated
           to this NRP.";
      }
    }
  }

  /*
   * Grouping - NRP Topology Filter
   */

  grouping nrp-topology-filter {
    description
      "Grouping for NRP filter topology.";
    container filters {
      description
        "Container for filters.";
      list filter {
        key "filter-ref";
        description
          "List of filters.";
        leaf filter-ref {
          type nrp-topo-filter-ref;
          description
            "Reference to a specific topology filter from the
             list of global topology filters.";
        }
        uses nrp-resource-reservation;
        uses nrp-selector-config;
        uses nrp-qos-phb-profile;
      }
    }
  }

  /*
   * Grouping - NRP Select Topology
   */

  grouping nrp-select-topology {
    description
      "NRP topology specified by selection.";
    container select {
      description
        "The container of NRP select topology.";
      list topology-group {
        key "group-id";
        description
          "List of groups for NRP topology elements (node or links)
           that share common attributes.";
        leaf group-id {
          type string;
          description
            "The NRP topology group identifier.";
        }
        container base-topology-ref {
          description
            "Container for the base topology reference.";
          uses nw:network-ref;
        }
        list links {
          key "link-ref";
          description
            "A list of links with common attributes";
          leaf link-ref {
            type leafref {
              path
                "/nw:networks/nw:network[nw:network-id=current()"
              + "/../../base-topology-ref/network-ref]"
              + "/nt:link/nt:link-id";
            }
            description
              "A reference to a link in the base topology.";
          }
        }
        uses nrp-resource-reservation;
        leaf link-partition-type {
          type identityref {
            base nrp-link-partition-type;
          }
          description
            "Indicates the resource reservation type of an NRP link.";
        }
        uses nrp-qos-phb-profile;
      }
    }
  }

  /*
   * Grouping - NRP Topology
   */

  grouping nrp-topology {
    description
      "Grouping for NRP topology.";
    container topology {
      description
        "Container for NRP topology.";
      uses nrp-igp-congruent;
      choice topology-type {
        description
          "Choice of NRP topology type.";
        case selection {
          uses nrp-select-topology;
        }
        case filter {
          uses nrp-topology-filter;
        }
      }
    }
  }

  /*
   * Grouping - NRP Policy
   */

  grouping nrp-pol {
    description
      "Grouping for NRP policies.";
    container nrp-policies {
      description
        "Container for nrp policies.";
      list nrp-policy {
        key "name";
        unique "nrp-id";
        description
          "List of NRP policies.";
        leaf name {
          type string;
          description
            "A string that uniquely identifies the NRP policy.";
        }
        leaf nrp-id {
          type uint32;
          description
            "A 32-bit ID that uniquely identifies the NRP
             created by the enforcement of this NRP policy.";
        }
        leaf mode {
          type identityref {
            base nrp-partition-mode;
          }
          default "nrp-hybrid-plane-partition";
          description
            "Indicates the resource partition mode of the NRP, such as
             control plane partition, data plane partition,
             or hybrid partition.";
        }
        uses nrp-resource-reservation;
        uses nrp-selector-config;
        uses nrp-qos-phb-profile;
        uses nrp-topology;
      }
    }
  }

  /*
   * Grouping - NRP Selector State
   */

  grouping nrp-selector-state {
    description
      "The grouping of NRP selector.";
    container selector {
      config false;
      description
        "The container of NRP selector.";
      leaf srv6 {
        type srv6-types:srv6-sid;
        description
          "Indicates the SRv6 SID value as the NRP selector.";
      }
      leaf sr-mpls {
        type rt-types:mpls-label;
        description
          "Indicates the SR MPLS ID value as the NRP selector.";
      }
    }
  }

  /*
   * Grouping - NRP node attributes
   */

  grouping nrp-node-attributes {
    description
      "NRP node scope attributes.";
    container nrp {
      config false;
      description
        "Containing NRP attributes.";
      uses nrp-selector-state;
    }
  }

  /*
   * Grouping - NRP Link Attributes
   */

  grouping nrp-link-attributes {
    description
      "NRP link scope attributes.";
    leaf link-partition-type {
      type identityref {
        base nrp-link-partition-type;
      }
      config false;
      description
        "Indicates the resource partition type of an NRP link.";
    }
    leaf bandwidth-value {
      type uint64;
      units "bps";
      config false;
      description
        "Bandwidth allocation for the NRP as absolute value.";
    }
    uses nrp-selector-state;
  }

  /*
   * Grouping - NRP Bandwidth Metrics
   */

  grouping nrp-bandwidth-metrics {
    description
      "Grouping for NRP bandwidth metrics.";
    leaf one-way-available-bandwidth {
      type rt-types:bandwidth-ieee-float32;
      units "bytes per second";
      default "0x0p0";
      description
        "Available bandwidth that is defined to be NRP link
         bandwidth minus bandwidth utilization. For a
         bundled link, available bandwidth is defined to be the
         sum of the component link available bandwidths.";
    }
    leaf one-way-utilized-bandwidth {
      type rt-types:bandwidth-ieee-float32;
      units "bytes per second";
      default "0x0p0";
      description
        "Bandwidth utilization that represents the actual
         utilization of the link (i.e. as measured in the router).
         For a bundled link, bandwidth utilization is defined to
         be the sum of the component link bandwidth
         utilizations.";
    }
  }

  // nrp-link-statistics

  grouping nrp-statistics-per-link {
    description
      "Statistics attributes per NRP link.";
    container statistics {
      config false;
      description
        "Statistics for NRP link.";
      leaf admin-status {
        type te-types:te-admin-status;
        description
          "The administrative state of the link.";
      }
      leaf oper-status {
        type te-types:te-oper-status;
        description
          "The current operational state of the link.";
      }
      uses nrp-bandwidth-metrics;
      uses te-packet-types:one-way-performance-metrics-packet;
    }
  }

  grouping nrp-topology-type {
    description
      "Identifies the topology type to be NRP";
    container nrp {
      presence "indicates NRP topology";
      description
        "The presence of the container node indicates NRP
         topology";
    }
  }

  /*
   * Augment - Network Resource Partition Policies.
   */

  augment "/nw:networks" {
    description
      "Augment networks with network resource partition
       policies.";
    uses nrp-pol;
  }

  /*
   * Augment - NRP type.
   */

  augment "/nw:networks/nw:network/nw:network-types" {
    description
      "Introduces new network type for NRP topology";
    uses nrp-topology-type;
  }

  /*
   * Augment - NRP node operational status.
   */

  augment "/nw:networks/nw:network/nw:node" {
    when '../nw:network-types/nrp:nrp' {
      description
        "Augment only for NRP topology.";
    }
    description
      "Augment node configuration and state.";
    uses nrp-node-attributes;
  }

  /*
   * Augment - NRP link operational status.
   */

  augment "/nw:networks/nw:network/nt:link" {
    when '../nw:network-types/nrp:nrp' {
      description
        "Augment only for NRP topology.";
    }
    description
      "Augment link configuration and state.";
    container nrp {
      config false;
      description
        "Containing NRP attributes.";
      uses nrp-link-attributes;
      uses nrp-statistics-per-link;
    }
  }

  /*
   * Augment - Native topology with node operational status.
   */

  augment "/nw:networks/nw:network/nw:node" {
    description
      "Augment node with NRP aware attributes.";
    list nrps {
      key "nrp-id";
      config false;
      description
        "List of NRPs.";
      leaf nrp-id {
        type uint32;
        description
          "NRP identifier";
      }
      uses nrp-node-attributes;
    }
  }

  /*
   * Augment - Native topology with link operational status.
   */

  augment "/nw:networks/nw:network/nt:link" {
    description
      "Augment link with NRP attributes.";
    list nrps {
      key "nrp-id";
      config false;
      description
        "List of NRPs.";
      leaf nrp-id {
        type uint32;
        description
          "NRP identifier";
      }
      uses nrp-link-attributes;
    }
  }
}
