module ietf-ipipv4-tunnel-02{

  namespace "urn:ietf:params:xml:ns:yang:ietf-ipipv4-tunnel-02";

  prefix "v4tln";

  import ietf-interfaces {

    prefix "if";

  }

  import ietf-inet-types {

    prefix inet;

  }

  import ietf-routing {

    prefix "rt";
  }

  organization

    "IETF NETMOD (NETCONF Data Modeling Language) Working Group.";

  contact

    "Mandy.Liu@ericsson.com

   Adam.Foldes@ericsson.com

   zhengguangying@huawei.com";

  description

    "This YANG model defines the configuration data

   and operational state data for generic IPv4/6-in-IPv4 tunnel.

   It includes the IPv4 in IPv4, IPv6 to IPv4

   auto and IPv6 over IPv4 manual tunnels.";

  revision 2015-10-15 {

    description

      "Initial revision.";

    reference

      "RFC XXXX: A YANG Data Model for IPv4 Tunnel.";

  }

  /* Typedefs */
  typedef tunnel-type {

    type enumeration {

      enum ip-ip {

        description

          "IPv4-in-IPv4 tunnel interface.";

      }

      enum ipv6v4-manual {

        description

          "IPv6v4-manual tunnel interface.";

      }

      enum ipv6to4 {

        description

          "The 6to4 tunnel interface.";

      }

    }

    description

      "Indicate the type of the IP tunnel.";

  }

  /* Grouping for tunnel */

  grouping tunnel-components {

    description

      "Specify the IP addresses of the local and

      remote tunnel endpoint interfaces. Bind the
      tunnel circuit interface to the tunnel. Enable

      the tunnel.";

    leaf name {

      type string;

      description

        "Name of the tunnel.";

    }

    leaf description {

      type string {

        length "1..255";

      }

      description

        "Textual description for a tunnel. Can be any "+

        "alphanumeric string, including spaces, not to exceed "+

        "255 ASCII characters.";

    }

    leaf bind-interface {

      type if:interface-ref;

      description

         "Bind to an interface.";

    }

    leaf clear-df {

      type empty;

      description
        "If clear-df is absent, it means that fragmentation of

      tunnel packets are permitted. If clear-df is present,

      it means that fragmentation of tunnel packets are not

      permitted.";

    }

    leaf shutdown {

      type empty;

      description

        "Disable/enable the tunnel.";

    }

    leaf tmtu {

      type uint16 {

        range "256..16384";

      }

      description

        "Sets the Maximum Transmission Unit (MTU) size for

        packets sent in a tunnel. The default MTU is the MTU

        for the interface to which the tunnel is bound.";

    }

   leaf mirror-destination {

      type string;

      description

        "Designate the name of a tunnel as a circuit

      mirror destination. ";
    }

   leaf hop-limit {

     type uint8 {

       range "0|1..255";

     }

     description

       "The IPv4 TTL or IPv6 Hop Limit which is used in the outer IP

      header. A value of 0 indicates that the calue is copied from

      the payload's header.";

   }

   leaf tos {

     type int8 {

       range "-1..63";

     }

     description

       "The method used to set the high 6 bits (the differentiated

      services codepoint) of the IPv4 TOS or IPv6 Traffic Class in

      the outer IP header. A value of -1 indicates that the bits are

      copied from the payload's header. A value between 0 and 63

      inclusive indicates that the bit field is set to the indicated

      value.";

   }

  }

  /*Configuration Data*/

  container Tunnels{

    description

     "Configuration data for tunnels.";

    list Tunnel{

      key name;

     description

       "Configuration data for tunnels.";

     uses tunnel-components;

     choice tunnel-type{

       description

        "Peer end points configuration for tunnel.";

       case tunnel-ipinip{

        container ip-in-ip{

          description

           "The peer end points configuration of IP in IP tunnel.";

            leaf local {

              type inet:ipv4-address-no-zone;

              description

                "IP address of the local end of the tunnel.";

            }

            leaf remote {

              type inet:ipv4-address-no-zone;

              description
                "IP address of the remote end of the tunnel.";

            }

           leaf routing-instance {

              type rt:routing-instance-ref;

              description

                "Name of the reference routing instance. ";

            }

         }

        }

      case tunnel-ipv6to4{

        container ipv6to4{

          description

           "The peer end points configuration of 6to4 tunnel.";

            leaf local {

              type inet:ipv4-address-no-zone;

              description

                "IP address of the local end of the tunnel.";

            }

        }

      }

      case tunnel-ipv6v4-manual{

        container ipv6v4-manual{

          description

           "The peer end points configuration of IPv6-over-v4
           manual tunnel.";

            leaf local {

              type inet:ipv4-address-no-zone;

              description

                "IP address of the local end of the tunnel.";

            }

            leaf remote {

              type inet:ipv4-address-no-zone;

              description

                "IP address of the remote end of the tunnel.";

            }

           leaf routing-instance {

              type rt:routing-instance-ref;

              description

                "Name of the reference routing instance. ";

            }

         }

      }

      }

    }

  }

  /*Operational state data*/

  grouping tunnel-state-components {
    description

     "The basic tunnel information to be displayed.";

    leaf name {

      type string;

      description

        "Name of the tunnel.";

    }

    leaf local-ip {

      type inet:ipv4-address-no-zone;

      description

        "IP address of the local end of the tunnel.";

    }

    leaf remote-ip {

      type inet:ipv4-address-no-zone;

      description

        "IP address of the remote end of the tunnel.";

    }

    leaf state {

      type enumeration {

        enum Down {

        description

          "Tunnel down state.";
        }

        enum Up {

          description

            "Tunnel up state.";

        }

        enum Shutdown {

          description

            "Tunnel shutdown state.";

        }

      }

      description

        "Indicate the state of the tunnel.";

    }

    leaf bind-interface {

      type if:interface-state-ref;

      description

        "Bind to an interface.";

    }

    leaf user-configured {

      type boolean;

     description

        "Indicate the tunnel is user-configured or dynamic.

        False is for dynamic.";

    }
    leaf routing-instance {

      type rt:routing-instance-ref;

      description

        "Name of the reference routing instance. ";

    }

    leaf tmtu {

      type uint16;

      description

        "The Maximum Transmission Unit (MTU) size for

      packets sent in a tunnel.";

    }

    leaf clear-df {

      type empty;

      description

        "Indicate that the DF bit is cleared.";

    }

    leaf down-reason {

      type string;

      description

        "The reason of the tunnel is down.";

    }

    leaf resolved-interface-name{

      type string;

      description
        "The egress interface name of the tunnel.";

    }

   leaf hop-limit {

     type uint32;

     description

       "The IPv4 TTL or IPv6 Hop Limit which is used in the outer IP

      header. A value of 0 indicates that the calue is copied from

      the payload's header.";

   }

   leaf tos {

     type int32;

     description

       "The high 6 bits (the differentiated

      services codepoint) of the IPv4 TOS or IPv6 Traffic Class in

      the outer IP header. A value of -1 indicates that the bits are

      copied from the payload's header. A value between 0 and 63

      inclusive indicates that the bit field is set to the indicated

      value.";

   }

  }

  container tunnel-state {

    config "false";

      description
        "Contain the information currently configured tunnels.";

      list tunnels {

        description

           "Operational state data of tunnels.";

         uses tunnel-state-components;

      }

  }

  //Augment operational state data of IP interfaces

  augment "/if:interfaces-state/if:interface" {

    when "if:type = 'ianaift:tunnel'" {

      description

        "Augment IP interface.";

    }

    description

      "Augment operational state data of IP interfaces.";

    leaf tunnel-protocol {

      type tunnel-type;

      description

        "Indicate the type of the IP tunnel interface.";

    }

  }

}// end of module ietf-ipipv4-tunnel-02
