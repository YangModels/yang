module ietf-semver {
  yang-version 1.1;
  namespace "urn:ietf:params:xml:ns:yang:ietf-semver";
  prefix semver;

  organization
    "IETF NETMOD (Network Modeling) Working Group";
  contact
    "WG Web:   <https://datatracker.ietf.org/wg/netmod/>
     WG List:  <mailto:netmod@ietf.org>

     Author:   Benoit Claise
               <mailto:bclaise@cisco.com>

     Author:   Joe Clarke
               <mailto:jclarke@cisco.com>

     Author:   Reshad Rahman
               <mailto:rrahman@cisco.com>

     Author:   Robert Wilton
               <mailto:rwilton@cisco.com>

     Author:   Kevin D'Souza
               <mailto:kd6913@att.com>

     Author:   Balazs Lengyel
               <mailto:balazs.lengyel@ericsson.com>

     Author:   Jason Sterne
               <mailto:jason.sterne@nokia.com>";
  description
    "This module contains a definition for a YANG 1.1 extension to
     express the semantic version of YANG modules.";

  revision 2019-02-27 {
    description
      "* Move YANG library augmentations into a separate module.
       * Update references.";
    reference
      "draft-verdt-netmod-yang-semver:
       YANG Semantic Versioning for Modules";
    semver:module-version "0.3.0";
  }

  revision 2018-04-05 {
    description
      "* Properly import ietf-yang-library.
       * Fix the name of module-semver => module-version.
       * Fix regular expression syntax.
       * Augment yang-library with booleans as to whether or not
         deprecated and obsolete nodes are present.
       * Add an extension to enable import by semantic version.
       * Add an extension status-description to track deprecated
         and obsolete reasons.
       * Fix yang-library augments to use 7895bis.";
    reference
      "draft-clacla-netmod-yang-model-update:
       New YANG Module Update Procedure";
    semver:module-version "0.2.1";
  }
  revision 2017-12-15 {
    description
      "Initial revision.";
    reference
      "draft-clacla-netmod-yang-model-update:
       New YANG Module Update Procedure";
    semver:module-version "0.1.1";
  }
  typedef version {
    type string {
      pattern '[0-9]{1,5}\.[0-9]{1,5}\.[0-9]{1,5}(m|M)?';
    }
    description
      "The type used to represent a YANG semantic version number.

      The YANG semver version number is expressed as a string of the
      form: 'X.Y.Zv'; where X, Y, and Z each represent non-negative
      integers smaller than 32768, and v represents an optional
      single character suffix: 'm' or 'M'.

      o 'X' is the MAJOR version.  Changes in the major version
        number indicate changes that are non-backwards-compatible to
        versions with a lower major version number.

      o 'Y' is the MINOR version.  Changes in the minor version
         number indicate changes that are backwards-compatible to
         versions with the same major version number, but a lower
         minor version number.

     o 'Zv' is the PATCH version and modifier.  Changes in the patch
        version number can indicate editorial, backwards-compatible,
        or non-backwards-compatible changes relative to versions with
        the same major and minor version numbers, but lower patch
        version number, depending on what form modifier 'v' takes:

        *  'M' - the change represents a non-backwards-compatible
                 change

        *  'm' - the change represents a backwards-compatible change

        * If the modifier letter is absent, the change represents an
          editorial change";

    reference
      "draft-verdt-netmod-yang-semver: YANG Semantic Versioning";
  }

  extension module-version {
    argument semver;
    description
      "The version number for the module revision it is used in.

       This format of the argument matches the type version.

       The rules for updating the module-version number are described
       in section XXX of 'YANG Semantic Versioning for Modules';
       By comparing the module-version between two revisions of a
       given module, one can determine if different revisions are
       backwards compatible or not, as well as whether or not new
       features have been added to a newer revision.

       If a module contains this extension it indicates that for this
       module the updated status and update rules as this described
       in RFC XXXX are used.

       The statement MUST only be a substatement of the 'revision'
       statements.  Zero or one module-version statement is allowed
       per parent statement. No substatements are allowed.

       'revision' statements in submodules MAY contain a
       'module-version' statement for documentation purposes, but
       its meaning is undefined, and has no effect on the including
       module's semantic version.";
    reference
      "draft-verdt-netmod-yang-semver:
       YANG Semantic Versioning for Modules";
  }

  extension import-versions {
    argument version-clause;
    description
      "This extension specifies an acceptable set of semantic
       versions of a given module that may be imported.

       The statement MUST only be a substatement of the import
       statement.

       The statement MUST NOT be present if the import has a
       revision-date substatement.

       The statement MUST NOT be present if the imported module does
       not support semantic versioning.

       Zero or more versions statements are allowed per parent
       statement.  No substatements are allowed.

       The version-clause argument MUST follow one of the below
         patterns:
           (i)  "+' \d+\.\d+\.\d+ '+"
             Matches exact version, e.g. 3.6.1

           (ii) "+ '\d+\.\d+\.\d+\+ '+"
             Matches exact version or greater, e.g. 3.6.1+

           (iii) "+' \d+\.\d+.\d+-\d+\.(\d+|MAX).(\d|MAX)+ '+"
             Matches inclusive range,
             e.g. 3.6.1-7.8.4, or 3.2.1-3.MAX.MAX";

    reference
      "draft-verdt-netmod-yang-semver: Import by Semantic Version";
  }

  extension status-description {
    argument description;
    description
      "Freeform text that describes why a given node has been
       deprecated or made obsolete.  This may point to other schema
       elements that can be used in lieu of the given node.

       This statement MUST only be used as a substatement of the
       status statement

       Zero or more status-description statements are allowed per
       parent statement.  No substatements are allowed.";
    reference
      "draft-verdt-netmod-yang-semver: YANG status description
       extension";
  }
}
