module yang-catalog {
 namespace "urn:ietf:params:xml:ns:yang:yang-catalog";
 prefix yc;

 import ietf-yang-library {
   prefix yanglib;
 }

 organization
   "yangcatalog.org";
 contact
   "Benoit Claise <bclaise@cisco.com>

    Joe Clarke <jclarke@cisco.com>";
 description
   "This module contains metadata pertinent to each YANG module, as
    well as a list of vendor implementations for each module.  The
    structure is laid out in such a way as to make it possible to
    locate metadata and vendor implementation on a per-module basis
    as well as obtain a list of available modules for a given
    vendor's platform and specific software release.";

 revision 2017-07-03 {
   description
     "Initial revision.";
   reference "
     YANG Catalog <https://yangcatalog.org>";
 }

 container catalog {
   description
     "Root container of yang-catalog holding two main branches -
      modules and vendors. The modules sub-tree contains all the modules in
      the catalog and all of their metadata with their implementations.
      The vendor sub-tree holds modules for specific vendors, platforms,
      software-versions, and software-flavors. It contains reference to a
      name and revision of the module in order to reference the module's full
      set of metadata.";
   container modules {
     description
       "Container holding the list of modules";
     uses yanglib:module-list;
   } // end of modules

   container vendors {
     description
       "Container holding lists of organizations that publish YANG modules.";
     list vendor {
       key name;
       description
         "List of organizations publishing YANG modules.";
       leaf name {
         type string;
         description
           "Name of the maintaining organization -- the name should be
            supplied in the official format used by the organization.
            Standards Body examples:
              IETF, IEEE, MEF, ONF, etc.
            Commercial entity examples:
              AT&T, Facebook, <Vendor>
            Name of industry forum examples:
            OpenConfig, OpenDaylight, ON.Lab";
       }
       container platforms {
         description "Container holding list of platforms.";
         list platform {
           key name;
           description
             "List of platforms under specific vendor";
           leaf name {
             type string;
             description
               "Name of the platform";
           }
           container software-versions {
             description "Container holding list of versions of software versions.";
             list software-version {
               key name;
               description
                 "List of version of software versions under specific vendor, platform.";
               leaf name {
                 type string;
                 description
                   "Name of the version of software.  With respect to most network device appliances,
                    this will be the operating system version.  But for other YANG module
                    implementation, this would be a version of appliance software.  Ultimately,
                    this should correspond to a version string that will be recognizable by
                    the consumers of the platform.";
               }
               container software-flavors {
                 description "Container holding list of software flavors.";
                 list software-flavor {
                   key name;
                   description
                     "List of software flavors under specific vendor, platform, software-version.";
                   leaf name {
                     type string;
                     description
                       "A variation of a specific version where
                        YANG model support may be different.  Depending on the vendor, this could
                        be a license, additional software component, or a feature set.";
                   }
                   container protocols {
                     description
                       "List of the protocols";
                     list protocol {
                       key name;
                       description
                         "YANG-based protocol that is used on the device.  This enumeration will
                          is expected to be augmented to list other protocol names.";
                       leaf name {
                         type enumeration {
                           enum netconf {
                             description
                               "NETCONF protocol described in RFC 6241";
                           }
                           enum restconf {
                             description
                               "RESTCONF protocol described in RFC 8040";
                           }
                         }
                         description
                           "Name of the YANG-based protocol that is supported.";
                       } // end of name
                       leaf protocol-version {
                         type string;
                         description
                           "Version of the specific protocol.";
                       }
                       leaf-list capabilities {
                         type string;
                         description
                           "Listed name of capabilities that are
                            supported by the specific device.";
                       }
                     } // end of protocol
                   } // end of protocols
                   container modules {
                     description
                       "Container holding list of modules.";
                     list module {
                       key "name revision";
                       description
                        "List of references to YANG modules under specific vendor, platform, software-version,
                         software-flavor.  Using these references, the complete set of metadata can be
                         retrieved for each module.";
                       leaf name {
                         type leafref {
                           path "../../../../../../../../../../../modules/module/name";
                         }
                         description
                           "Reference to a name of the module that is contained in specific vendor, platform,
                            software-version, software-flavor.";
                       }
                       leaf revision {
                         type leafref {
                           path "../../../../../../../../../../../modules/module/revision";
                         }
                         description
                           "Reference to a revision of the module that is contained in specific vendor,
                            platform, software-version, software-flavor.";
                       }
                     } // end of list module
                   } // end of container modules
                 } // end of software-flavor
               } // end of software-flavors
             } // end of software-version
           } // end of software-versions
         } // end of platform
       } // end of platforms
     } // end of vendor
   } // end of vendors
 } //end of catalog

 augment "/catalog/modules/module" {
   uses module-data;
   container implementations {
     description
       "Container holding lists of per-module implementation details.";
     list implementation{
       key "vendor platform software-version software-flavor";
       description
         "List of module implementations.";
       leaf vendor {
         type string;
         description
           "Organization that created this module.";
       }
       leaf platform {
         type string;
         description
           "Platform on which this module is implemented.";
       }
       leaf software-version {
         type string;
         description
           "Name of the version of software.  With respect to most network device appliances,
            this will be the operating system version.  But for other YANG module
            implementation, this would be a version of appliance software.  Ultimately,
            this should correspond to a version string that will be recognizable by
            the consumers of the platform.";
       }
       leaf software-flavor {
         type string;
         description
           "A variation of a specific version where
            YANG model support may be different.  Depending on the vendor, this could
            be a license, additional software component, or a feature set.";
       }
       leaf os-version {
         type string;
         description
           "Version of the operating system using this module.  This is primarily useful if
            the software implementing the module is an application that requires a specific
            operating system.";
       }
       leaf feature-set {
         type string;
         description
           "An optional feature of the software that is required in order to implement this
            module.  Some form of this must be incorporated in software-version or
            software-flavor, but can be broken out here for additional clarity.";
       }
       leaf os-type {
         type string;
         description
           "Type of the operating system using this module.  This is primarily useful if
            the software implementing the module is an application that requires a
            specific operating system.";
       }
     }
   }
   description
     "This table augments the per-module metadata set and provides details about
      vendor implementations for each module.";
 }

 grouping module-data {
   leaf document-name {
     type string;
     description
       "The name of the document from which the module was extracted or taken;
        or that provides additional context about the module.";
   }
   leaf author-email {
     type string;
     description
      "Contact email of the author who created this module.";
   }
   leaf compilation-status {
     type enumeration {
       enum PASSED {
         value 0;
         description
           "In case that all compilers were able to compile this YANG module without
           any error/warning.";
       }
       enum PASSED-WITH-WARNINGS {
         value 1;
         description
           "In case that all compilers were able to compile this YANG module without
           any error, but at least one of them caught some warning.";
       }
       enum FAILED {
         value 2;
         description
           "In case that at least one of compilers found some error while
           compiling this YANG module.";
       }
       enum MISSING {
         value 3;
         description
           "In case that there is not sufficient information about compilation status.";
       }
     }
     description
       "Status of the module, whether it was possible to compile this YANG module or
        there are still some errors/warnings.";
   }
   leaf compilation-result {
     type string;
     description
       "Result of the compilation explaining specifically what error or warning occurred.
        This is not existing if compilation status is PASSED.";
   }
   leaf reference {
     type string;
     description
       "A string that is used to specify a textual cross-reference to an external document, either
        another module that defines related management information, or a document that provides
        additional information relevant to this definition.";
   }
   leaf prefix {
     type string;
     description
       "Statement of yang that is used to define the prefix associated with
        the module and its namespace. The prefix statement's argument is
        the prefix string that is used as a prefix to access a module. The
        prefix string MAY be used to refer to definitions contained in the
        module, e.g., if:ifName.";
   }
   leaf yang-version {
     type string;
     default "1.0";
     description
       "The optional yang-version statement specifies which version of the
        YANG language was used in developing the module. The statement's
        argument is a string. If present, it MUST contain the value 1,
        which is the current YANG version and the default value.";
   }
   leaf organization {
     type string;
     description
       "This statement defines the party responsible for this
        module.  The argument is a string that is used to specify a textual
        description of the organization(s) under whose auspices this module
        was developed.";
   }
   leaf description {
     type string;
     description
       "This statement takes as an argument a string that
        contains a human-readable textual description of this definition.
        The text is provided in a language (or languages) chosen by the
        module developer; for the sake of interoperability, it is RECOMMENDED
        to choose a language that is widely understood among the community of
        network administrators who will use the module.";
   }
   leaf contact {
     type string;
     description
       "This statement provides contact information for the module.
        The argument is a string that is used to specify contact information
        for the person or persons to whom technical queries concerning this
        module should be sent, such as their name, postal address, telephone
        number, and electronic mail address.";
   }
   leaf module-type {
     type enumeration {
       enum module {
         value 0;
         description "If YANG file contains module.";
       }
       enum submodule {
         value 1;
         description "If YANG file contains sub-module.";
       }
     }
     description "Whether a file contains a YANG module or sub-module.";
   }
   leaf maturity-level {
     type enumeration {
       enum ratified {
         value 0;
         description
           "Maturity of a module that is fully approved (e.g., a standard).";
       }
       enum working-group {
         value 1;
         description
           "Maturity of a module that is actively being developed by a organization towards ratification.";
       }
       enum individual {
         value 2;
         description
           "Maturity of a module that has been initially created, but has no official
            organization-level status.";
       }
     }
     description
       "The current maturity of the module with respect to the body that created it.
        This allows one to understand where the module is in its overall life cycle.";
   }
   description
     "Grouping of YANG module metadata that extends the common list defined in the YANG
      Module Library (RFC 7895).";
 }
}
