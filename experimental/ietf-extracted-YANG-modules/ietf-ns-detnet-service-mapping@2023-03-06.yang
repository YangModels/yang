module ietf-ns-detnet-service-mapping {
  yang-version 1.1;
  namespace
    "urn:ietf:params:xml:ns:yang:ietf-ns-detnet-service-mapping";
  prefix detnet-nssm;

  import ietf-ns-detnet-mapping-types {
    prefix nsdmt;
    reference
      "RFC XXXX:  YANG Data Model for DetNet Mapping with Network
              Slice";
  }
  import ietf-detnet {
    prefix dnet;
    reference
        "I-D.draft-ietf-detnet-yang: YANG Data Model for Detnet";
  }

  organization
    "IETF DetNet Working Group";

  contact
    "WG Web:   <https://datatracker.ietf.org/wg/detnet/>
     WG List:  <mailto:detnet@ietf.org>

     Editor:   Xueyan Song
               <song.xueyan@zte.com.cn>
     Editor:   Haisheng Wu
               <wu.haisheng@zte.com.cn>";

  description
    "This module contains a YANG module for the mapping of DetNet
        to the Network Slice.

     Copyright (c) 2022 IETF Trust and the persons identified as
     authors of the code.  All rights reserved.

     Redistribution and use in source and binary forms, with or
     without modification, is permitted pursuant to, and subject
             to the license terms contained in, the Revised BSD License
             set forth in Section 4.c of the IETF Trust's Legal
             Provisions Relating to IETF Documents
     (https://trustee.ietf.org/license-info).

     This version of this YANG module is part of RFC XXXX; see
             the RFC itself for full legal notices.";

  revision 2023-03-06 {
    description
      "Initial revision.";
    reference
      "RFC XXXX:  YANG Data Model for DetNet Mapping with Network
              Slice";
  }

  /*
   * Augmentation to Detnet
   */

   augment "/dnet:detnet/dnet:service/dnet:sub-layer"{
    description
      "Detnet augmented to include Network Slice parameters and
              mapping";
    container ns-detnet-mapping {
      presence "Indicates Detnet service to Network Slice mapping";
      description
        "Container to augment detnet to Network Slice parameters
                and mapping";
      uses nsdmt:ns-mapping;
    }
  }

  //augment

}
