module ietf-yp-notification {
  yang-version 1.1;
  namespace "urn:ietf:params:xml:ns:yang:ietf-yp-notification";
  prefix iypn;

  import ietf-yang-types {
    prefix yang;
    reference
      "RFC 9911: Common YANG Data Types";
  }
  import ietf-inet-types {
    prefix inet;
    reference
      "RFC 9911: Common YANG Data Types";
  }
  import ietf-subscribed-notifications {
    prefix sn;
    reference
      "RFC 8639: Subscription to YANG Notifications";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }
  import ietf-yang-structure-ext {
    prefix sx;
    reference
      "RFC 8791: YANG Data Structure Extensions";
  }

  organization
    "IETF NETCONF (Network Configuration) Working Group";
  contact
    "WG Web:   <https://datatracker.ietf.org/group/netconf/>
     WG List:  <mailto:netconf@ietf.org>

     Authors:  Alex Huang Feng
               <mailto:alex.huang-feng@t-systems.com>
               Pierre Francois
               <mailto:pierre.francois@insa-lyon.fr>
               Thomas Graf
               <mailto:thomas.graf@swisscom.com>
               Benoit Claise
               <mailto:benoit@everything-ops.net>";
  description
    "Defines a notification header for Subscribed Notifications
     [RFC8639] and YANG-Push [RFC8641]. When this notification header
     is enabled through configuration, the root container of the
     notification is encoded as defined in RFC XXXX.

     This module can be used to validate XML-encoded notifications
     [RFC7950], JSON-encoded messages [RFC7951], and CBOR-encoded
     messages [RFC9254]. Refer to Section 3.1.2 of RFC XXXX for more
     details.

     Copyright (c) 2026 IETF Trust and the persons identified as
     authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-07-30 {
    description
      "Initial version.";
    reference
      "RFC XXXX: Extensible YANG Model for YANG-Push Notifications";
  }

  feature hostname-sequence-number {
    description
      "This feature indicates that hostname and sequence numbers are
       supported.";
  }

  grouping notif-env-capabilities {
    description
      "This grouping defines the capabilities for the
       notification-envelope, and the different supported metadata.";
    reference
      "RFC XXXX: Extensible YANG Model for YANG-Push Notifications";
    leaf envelope {
      type boolean;
      default "true";
      description
        "Supports YANG-Push to use the notification-envelope. If set
         to true, the publisher supports the notification envelope. If
         set to false, the notification envelope is not supported by
         the publisher.";
    }
    container metadata {
      description
        "Container with the supported optional metadata by the
         YANG-Push publisher.";
      leaf hostname-sequence-number {
        if-feature "hostname-sequence-number";
        type boolean;
        default "false";
        description
          "Supports hostname and sequence-number in the YANG-Push
           notifications. If set to true, the publisher supports
           sending the hostname and sequence numbers within the
           notification envelope. If set to false, the hostname
           and sequence numbers are not supported.";
      }
    }
  }

  sx:structure envelope {
    leaf event-time {
      type yang:date-and-time;
      mandatory true;
      description
        "The date and time the event was generated by the network
         node.";
    }
    leaf hostname {
      if-feature "hostname-sequence-number";
      type inet:host-name;
      description
        "The hostname of the network node. This value is usually
         configured on the node by the administrator to identify
         the node in the network uniquely.";
    }
    leaf sequence-number {
      if-feature "hostname-sequence-number";
      type yang:counter32;
      description
        "Unique sequence number for each published message
         by the publisher process. The initial number is 1 and
         counts up by 1 at every published notification message
         until it reaches 4294967295. Then, it wraps around and
         restarts at 0. The value 0 is used to detect wrap
         arounds.";
    }
    anydata contents {
      mandatory true;
      description
        "This contains the values defined by the 'notification'
         statement unchanged.";
    }
  }

  // Subscription container
  augment "/sn:subscriptions" {
    description
      "This augmentation adds the configuration switches for
       enabling the notification envelope and metadata.";
    leaf enable-notification-envelope {
      type boolean;
      default "false";
      description
        "Enables YANG-Push to use the notification-envelope. Enabling
         or disabling this leaf terminates all existing active dynamic
         and configured YANG-Push subscriptions. Before terminating
         each subscription, the publisher MUST send a
         'subscription-terminated' notification using the header
         configuration that was in effect before the change.";
      reference
        "Section 4 of RFC XXXX.";
    }
    container metadata {
      description
        "This container is intended to be augmented by modules
         defining optional notification metadata extensions.";
      reference
        "Section 4 of RFC XXXX.";
    }
  }

  // YANG-Push Capabilities extension
  augment "/sysc:system-capabilities"
        + "/notc:subscription-capabilities" {
    description
      "Extension to the subscription-capabilities model to enable
       clients to learn whether the publisher supports the
       notification-envelope";
    container notification-metadata {
      description
        "Adds the notification metadata capabilities to subscription
         capabilities.";
      uses notif-env-capabilities;
    }
  }
}
