module ietf-mpls-te-tunnel-ifs {

 namespace 
   "urn:ietf:params:xml:ns:yang:ietf-mpls-te:ietf-mpls-te-tunnel-
ifs";

 organization
   "IETF NETMOD (NETCONF Data Modeling Language) Working Group";

 contact
   "WG Web:   <http://tools.ietf.org/wg/netmod/>
   WG List:  mailto:netmod@ietf.org";

 description
   "This module contains a collection of YANG definitions for
   managing MPLS-TE tunnel interfaces.  Copyright (c) 2014 IETF Trust
   and the persons identified as authors of the code.  All rights
   reserved.

   Redistribution and use in source and binary forms, with or without
   modification, is permitted pursuant to, and subject to the license
   terms contained in, the Simplified BSD License set forth in
   Section 4.c of the IETF Trust's Legal Provisions Relating to IETF
   Documents (http://trustee.ietf.org/license-info).

   This version of this YANG module is part of RFC XXXX; see the RFC
   itself for full legal notices.";

   /*
    *   YANG Module to be defined in the next revision.
    */
}
