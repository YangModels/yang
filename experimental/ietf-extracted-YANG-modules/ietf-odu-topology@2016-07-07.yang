module ietf-odu-topology { 
 yang-version 1; 

 namespace "urn:ietf:params:xml:ns:yang:ietf-odu-topology"; 
 prefix "l1topo"; 

 import ietf-network { 
   prefix "nd"; 
 } 

 import ietf-network-topology { 
   prefix "lnk"; 
 } 

 import ietf-te-topology { 
   prefix "tet"; 
 } 

 import ietf-transport-types { 
   prefix "tran-types";  
 } 

 organization  
   "Internet Engineering Task Force (IETF) CCAMP WG"; 
 contact 
   " 
   WG List: <mailto:ccamp@ietf.org> 

   ID-draft editor:  
   Xian ZHANG (zhang.xian@huawei.com); 
   Anurag Sharma (AnSharma@infinera.com); 
   "; 
 description 
   "This module defines a protocol independent Layer 1/ODU  
   topology data model."; 

 revision 2016-07-07 { 
   description 
     "Initial version."; 
   reference 
     "draft-zhang-ccamp-l1-topo-yang-01.txt"; 
 } 

 /* 
 typedef 
 */ 

 typedef adaptation-type { 
   type enumeration { 
     enum CBR { 
       description "Constant Bit Rate."; 
     } 
     enum ATMvp { 
       description "ATM VP."; 
     } 
     enum GFP { 
       description "Generic Framing Procedure."; 
     } 
     enum NULL { 
       description "NULL"; 
     }      
     enum PRBS { 
       description "Pseudo Random Binary Sequence"; 
     } 
     enum RSn { 
       description "TBD"; 
     } 
   } 

   description 
     "Defines a type representing the adaptation type  
     on the termination point."; 
 } 

 /* 
 Groupings 
 */ 
 grouping l1-network-type { 
   container l1-network { 
     presence "indicates a L1 network, i.e., Optical  
     Transport Network (OTN)."; 
     description "l1 network type"; 
   } 
   description "l1-network-type"; 
 } 

 grouping l1-network-attributes { 
   leaf name { 
     type string; 
     description "the network name"; 
   } 
   description "name attribute for l1 network";      
 } 

 grouping l1-node-attributes { 
   description "l1-node-attributes"; 
   leaf name { 
     type string; 
     description "a name for this node."; 
   }  
 } 

 grouping l1-link-attributes { 
   description "l1 link attributes"; 

   leaf odu-type { 
     type identityref{ 
       base tran-types:tributary-protocol-type; 
     } 
     description "the ODU type supported by this link"; 
   } 

   leaf distance { 
     type uint32;  
     description "distance in the unit of kilometers"; 
   } 
 } 

 grouping ttp-odu-attributes { 
   description "ttp ODU attributes"; 

   leaf odu-Type { 
     type identityref{ 
       base tran-types:tributary-protocol-type; 
     } 
     description "the ODU type supported by this ttp"; 
   } 
 } 

 grouping sch-odu-attributes { 
   description "additional odu attributes for scheduled link"; 

   leaf odu-type { 
     type identityref{ 
       base tran-types:tributary-protocol-type; 
     } 
     description "the ODU type scedhuled"; 
   } 

   leaf oduflex-bw { 
     type uint32; 
     description "banwidth for ODUflex type"; 
   } 
 } 

 grouping l1-tp-attributes { 
   description "l1-tp-attributes"; 

   leaf client-facing { 
     type empty; 
     description  
       "if present, it means this tp is a client-facing tp"; 
   } 

   leaf tpn { 
     type uint16 { 
       range "0..4095"; 
     } 
     description  
     "Tributary Port Number. Applicable in case of mux services."; 
     reference 
     "RFC7139: GMPLS Signaling Extensions for Control of Evolving 
      G.709 Optical Transport Networks."; 
   } 

   leaf tsg { 
     type identityref { 
       base tran-types:tributary-slot-granularity; 
     } 
     description "Tributary slot granularity."; 
     reference 
     "G.709/Y.1331, February 2012: Interfaces for the Optical 
      Transport Network (OTN)"; 
   } 

   leaf protocol-type { 
     type identityref { 
       base tran-types:tributary-protocol-type; 
     } 
     description "Protocol type for the Termination Point."; 
   } 

   leaf fec-enabled { 
     type boolean; 
     description 
      "This attribute is optional and indicates whether Forward 
      Error Correction (FEC) is enabled or not for the  
      Termination Point."; 
   } 

   leaf adaptation-type { 
     type adaptation-type; 
     description 
      "This attribute indicates the type of the supported  
      adaptation function at the termination point."; 
     reference 
     "G.874.1, January 2002: Optical transport network (OTN):  
     Protocol-neutral management information model for the  
     network element view."; 
   } 

   leaf sink-adapt-active { 
     type boolean; 
     description 
     "This attribute allows for activation or deactivation of  
    the sink adaptation function. The value of TRUE means active."; 
     reference 
     "G.874.1, January 2002: Optical transport network (OTN):  
     Protocol-neutral management information model for the  
     network element view "; 
   } 

   leaf source-adapt-active { 
     type boolean; 
     description 
     "This attribute allows for activation or deactivation of  
     the sink adaptation function. The value of TRUE  
     means active."; 
     reference 
     "G.874.1, January 2002: Optical transport network (OTN):  
     Protocol-neutral management information model for  
     the network element view "; 
   } 

   container timeslots { 
     description  
      "A list of tributary timeslots used by the ODU  
      Termination Point."; 
     leaf-list values { 
       type uint8; 
       description  
         "Tributary timeslot value."; 
       reference 
        "G.709/Y.1331, February 2012: Interfaces for the  
        Optical Transport Network (OTN)"; 
     }  
   } 
 } 

  /* 
  * Data nodes 
  */ 
 augment "/nd:networks/nd:network/nd:network-types/tet:te-topology" { 
   uses l1-network-type; 
   description "augment network types to include L1 newtork"; 
 } 

 augment "/nd:networks/nd:network" { 
   when "nd:network-types/tet:te-topology/l1-network" { 
     description "Augment only for L1 network"; 
   } 
   uses l1-network-attributes;     
   description "Augment network configuration";    
 } 

 augment "/nd:networks/nd:network/nd:node" { 
   when "nd:network-types/tet:te-topology/l1-network" { 
     description "Augment only for L1 network"; 
   } 
   description "Augment node configuration"; 
   uses l1-node-attributes; 
 } 

 augment "/nd:networks/nd:network/nd:node/" 
    +"lnk:termination-point/tet:te/tet:config" { 
   when "nd:network-types/tet:te-topology/l1-network" { 
     description "Augment only for L1 network"; 
   } 
   description "OTN TP attributes config in a ODU topology."; 
   uses l1-tp-attributes; 
 } 

 augment "/nd:networks/nd:network/nd:node" + 
         "/lnk:termination-point/tet:te/tet:state" { 
   when "nd:network-types/tet:te-topology/l1-network" { 
     description "Augment only for L1 network"; 
   } 
   description "OTN TP attributes state in a ODU topology."; 
   uses l1-tp-attributes; 
 }  

 augment "/nd:networks/nd:network/lnk:link/tet:te/tet:config" { 
   when "nd:network-types/tet:te-topology/l1-network" { 
     description "Augment only for L1 network."; 
   } 
   description "Augment link configuration"; 

   uses l1-link-attributes; 
 } 

 augment "/nd:networks/nd:network/lnk:link/tet:te/tet:state" { 
   when "nd:network-types/tet:te-topology/l1-network" { 
     description "Augment only for L1 network."; 
   } 
   description "Augment link state"; 

   uses l1-link-attributes; 
 } 

 augment "/nd:networks/nd:network/nd:node/tet:te" + 
     "/tet:tunnel-termination-point/tet:state"{ 
   when "nd:network-types/tet:te-topology/l1-network" { 
     description "Augment only for L1 network"; 
   } 
   description "Augment ttp state"; 
   uses ttp-odu-attributes; 
 } 

 augment "/nd:networks/nd:network/lnk:link/tet:te/tet:config" 
     +"/tet:te-link-attributes/tet:schedules/tet:schedule"{ 
   when "nd:network-types/tet:te-topology/l1-network" { 
     description "Augment only for L1 network."; 
   } 
   description "Augment link schedule config"; 

   uses sch-odu-attributes; 
 } 

 augment "/nd:networks/nd:network/lnk:link/tet:te/tet:state" 
     +"/tet:te-link-attributes/tet:schedules/tet:schedule"{ 
   when "nd:network-types/tet:te-topology/l1-network" { 
     description "Augment link schedule state."; 
   } 
   description "Augment link schedule config"; 

   uses sch-odu-attributes; 
 } 
}
