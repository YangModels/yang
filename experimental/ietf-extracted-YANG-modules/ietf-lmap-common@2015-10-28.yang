module ietf-lmap-common {

  namespace "urn:ietf:params:xml:ns:yang:ietf-lmap-common";
  prefix "lmap-common";

  import ietf-yang-types {
    prefix yang;
  }
  import ietf-inet-types {
    prefix inet;
  }

  organization
    "IETF Large-Scale Measurement Platforms Working Group";

  contact
    "WG Web:   <http://tools.ietf.org/wg/lmap/>
     WG List:  <mailto:lmap@ietf.org>

     Editor:   Juergen Schoenwaelder
               <j.schoenwaelder@jacobs-university.de>

     Editor:   Vaibhav Bajpai
               <v.bajpai@jacobs-university.de>";

  description
    "This module provides common definitions used by the data
     models written for Large-Scale Measurement Platforms (LMAP).
     This module defines typedefs and groupings but no schema
     tree elements.";

  revision "2015-10-28" {
    description
     "Initial version";
    reference
     "RFC XXX: A YANG Data Model for LMAP Measurement Agents";
  }

  /*
   * Typedefs
   */

  typedef tag-type {
    type string {
      length "1..max";
      pattern '[^\*].*';
    }
    description
      "A tag consists of at least one character and a tag is
       not allowed to start with an asterisk '*'.";
    // XXX: Does it make sense to have stricter rules,
    // XXX: e.g., disallow white space?
  }

  typedef tag-matchall-type {
    type string {
      pattern '\*';
    }
    description
      "The string containing a single asterisk '*' is used
       to match all tags.";
    // XXX: Allow glob-style matching, turning this into a
    // XXX: tag-match-type?
  }

  typedef wildcard {
    type string {
      pattern '\*';
    }
    description
      "A wildcard for calendar scheduling entries.";
  }

  typedef weekday {
    type enumeration {
      enum sunday {
        value 0;
        description "Sunday of the week";
      }
      enum monday {
        value 1;
        description "Monday of the week";
      }
      enum tuesday {
        value 2;
        description "Tuesday of the week";
      }
      enum wednesday {
        value 3;
        description "Wednesday of the week";
      }
      enum thursday {
        value 4;
        description "Thursday of the week";
      }
      enum friday {
        value 5;
        description "Friday of the week";
      }
      enum saturday {
        value 6;
        description "Saturday of the week";
      }
    }
    description
     "A type modeling the weekdays in the Greco-Roman
      tradition.";
  }
  typedef month {
    type enumeration {
      enum january {
        value 1;
        description "January of the Julian and Gregorian calendar";
      }
      enum february {
        value 2;
        description "February of the Julian and Gregorian calendar";
      }
      enum march {
        value 3;
        description "March of the Julian and Gregorian calendar";
      }
      enum april {
        value 4;
        description "April of the Julian and Gregorian calendar";
      }
      enum may {
        value 5;
        description "May of the Julian and Gregorian calendar";
      }
      enum june {
        value 6;
        description "June of the Julian and Gregorian calendar";
      }
      enum july {
        value 7;
        description "July of the Julian and Gregorian calendar";
      }
      enum august {
        value 8;
        description "August of the Julian and Gregorian calendar";
      }
      enum september {
        value 9;
        description "September of the Julian and Gregorian calendar";
      }
      enum october {
        value 10;
        description "October of the Julian and Gregorian calendar";
      }
      enum november {
        value 11;
        description "November of the Julian and Gregorian calendar";
      }
      enum december {
        value 12;
        description "December of the Julian and Gregorian calendar";
      }
    }
    description
      "A type modeling the month in the Julian and Gregorian
       tradition.";
  }

  typedef status-code {
    type int32;
    description
      "A status code returned by the execution of a task. Note that
       the actual range is implementation dependent but it should
       be portable to use values in the range 0..127 for regular
       exit codes. By convention, 0 indicates successful termination.
       Negative values may be used to indicate abnormal termination
       due to a signal; the absolute value may identify the signal
       number in this case.";
  }

  typedef timezone-offset {
    type string {
      pattern 'Z|[\+\-]\d{2}:\d{2}';
    }
    description
      "A timezone-offset as it is use in the yang:date-and-time
       type. The value Z is equivalent to +00:00. The value -00:00
       indicates and unknown time-offset.";
  }

  /*
   * Groupings
   */

  grouping metrics-grouping {
    description
      "This grouping models a list of entry in a metrics registry.";

    list metric {
      key uri;
      description
        "A list of entries in a metrics registry.";

      leaf uri {
        type inet:uri;
        description
          "A URI identifying an entry in a metrics registry.";
      }
      leaf-list role {
        type string;
        description
          "A set of roles for this metrics.";
      }
    }
  }

  grouping task-options-grouping {
    description
      "A list of options of a task. Each option is a name/value
       pair (where the value may be absent).";

    list option {
      key "name";
      ordered-by user;

      description
        "A list of options passed to the task. It is a list of
         key / value pairs and may be used to model options.
         Options may be used to identify the role of a task
         or to pass a channel name to a task.";

      // XXX This is kind of broken since making the option name
      // XXX a key means that a certain option may only appear once.
      // XXX This is not workable since some tests require a list of
      // XXX targets. Turning this into a leaf-list of args also
      // XXX does not work since YANG requires leaf-list values to
      // XXX be unique. Oops.

      leaf name {
        type string;
        description
          "The name of the option.";
      }

      leaf value {
        type string;
        description
          "The value of the option.";
      }
    }
  }
}
