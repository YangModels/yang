module ietf-supa-service-flow-policy { 
  namespace "urn:ietf:params:xml:ns:yang:ietf-supa-service-flow-" 
  +"policy"; 
  // replace with IANA namespace when assigned 
  prefix flow; 

  /*import ietf-yang-types { 
    prefix yang; 
  }*/ 
  import ietf-inet-types { 
    prefix inet; 
  } 
  import ietf-eca-policy { 
    prefix supa; 
  } 
  organization "IETF"; 
  contact 
    "Editor: Maoke Chen"; 

  description 
    "This YANG module defines a component that describing 
     the specific ECA policy data model for service flow 
     refining from SGPIM and EPRIM. 

     Terms and Acronyms 
     "; 

  revision 2015-08-25 { 
    reference ""; 
  } 

  //flow filter parameters for a flow  
  augment "/supa:supa-policy/supa:supa-policy-
target/supa:instance" { 
    description 
         "Use the base ECA policy model to define service flow 
         policy."; 
    container flowFilter{ 
      description 
        "Self defined flow filter to specify the policy 
        target."; 
      leaf dscp { 
        type uint32; 
        description 
          "dscp value of the indicated flow"; 
      } 
      leaf src-ip-addr{ 
        type inet:ipv4-address; 
        description 
          "source ip addresses of the flow"; 
      } 
      leaf dst-ip-addr{ 
        type inet:ipv4-address; 
        description 
          "destination ip addresses of the flow"; 
      } 
      leaf src-port{ 
        type uint32; 
        description 
          "source port number of the flow"; 
      } 
      leaf dst-port{ 
        type uint32; 
        description 
          "destination port number of the flow"; 
      } 
    } 
  } 
  //Add condition clauses into the condition list  
  augment "/supa:supa-policy/supa:supa-policy-statement/supa:" 
  +"condition-list" { 
    description 
      "Define the condition clause with parameters."; 
    container condition-bandwidth{ 
      description 
        "Define the bandwidth with threshold value."; 
      leaf bandwidth{ 
        type uint32; 
        description 
          "The flow bandwidth, unit is Mbps"; 
      } 
      leaf threshold{ 
        type uint32; 
        description 
          "The threshold to trigger the action."; 
      } 
    }  
  } 
  //action node is depending on the condition 
  augment "/supa:supa-policy/supa:supa-policy-
statement/supa:action-" 
  +"list" { 
    container action-redirect{ 
      when "/ietf-supa-policy/supa-policy/supa-policy-
statement/" 
      +"condition-list/condition-bandwidth/bandwidth>/ietf-
supa-" 
      +"policy/supa-policy/supa-policy-statement/condition-
list/" 
      +"condition-bandwidth/threshold"{ 
        description 
               "If the condition has been evaluated as TRUE, then 
               the action is added to the policy."; 
      } 
      leaf cir { 
        type uint32; 
        description 
          "Committed information rate"; 
      } 
      leaf pir { 
        type uint32; 
        description 
          "Peak information rate"; 
      } 
      leaf Cbs { 
        type uint32; 
        description 
          "Committed burst size"; 
      } 
      leaf Pbs { 
        type uint32; 
        description 
          "Peak burst size"; 
      } 
      description 
        "Define the action clause in the policy statement."; 
    } 
    description 
      "The augment of the action node is only valid when the  
      condition is evaluated as TRUE"; 
  } 
}
