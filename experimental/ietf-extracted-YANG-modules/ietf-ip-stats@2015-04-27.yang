module ietf-ip-stats {

  namespace "urn:ietf:params:xml:ns:yang:ietf-ip-stats";
  prefix ip-stats;

  import ietf-ip {
  prefix ip;  
  }
  import ietf-interfaces {
  prefix if;
  }
  import ietf-yang-types {
  prefix yang;
  }

  organization
    "IETF NETMOD (NETCONF Data Modeling Language) Working Group";

  contact
    "WG Web:   <http://tools.ietf.org/wg/netmod/>
     WG List:  <mailto:netmod@ietf.org>

     WG Chair: Thomas Nadeau
               <mailto:tnadeau@lucidvision.com>

     WG Chair: Juergen Schoenwaelder
               <mailto:j.schoenwaelder@jacobs-university.de>

     Editor:   Steve Baillargeon
               <mailto:steve.baillargeon@ericsson.com>";

  description
    "This YANG module contains a collection of IP and ICMP statistics
     for monitoring IPv4 and IPv6 implementations.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of TBD; see
     the RFC itself for full legal notices.";

  revision 2015-04-27 {
    description
      "Initial revision.";
    reference
      "TBD";
  }

  /*
   * Groupings
   */

  grouping ip-if-stats {
    description
      "A group of IP layer statistics for IP traffic 
       received and transmitted by an interface.";

    container stats {
      config false;
	  description
        "A collection of IP layer statistics for IP traffic 
         received and transmitted by an interface.";

      leaf in-receives {
        type yang:counter64;
        units packets;
        description
          "The number of input IP packets received on the
           interface, including those received in error.

           Discontinuities in the value of this counter can occur
           at re-initialization of the management system, and at
           other times as indicated by the value of
           'discontinuity-time'.";
        reference
          "RFC 4293: The IP MIB - ipIfStatsHCInReceives";
      }

      leaf in-octets {
        type yang:counter64;
        units octets;
        description
          "The number of octets received in IP packets,
           including those received in error. Octets from packets
           counted in in-receives MUST be counted.

           Discontinuities in the value of this counter can occur
           at re-initialization of the management system, and at
           other times as indicated by the value of
           'discontinuity-time'.";
        reference
          "RFC 4293: The IP MIB - ipIfStatsHCInOctets";
      }

      leaf in-hdr-errors {
        type yang:counter32;
        units packets;
        description
          "The number of input IP packets discarded due to errors 
           in their IP headers, including version number mismatch, 
           other format errors, hop count exceeded, errors 
           discovered in processing their IP options, etc.

           Discontinuities in the value of this counter can occur
           at re-initialization of the management system, and at
           other times as indicated by the value of
           'discontinuity-time'.";
        reference
          "RFC 4293: The IP MIB - ipIfStatsInHdrErrors";
      }

      leaf in-mcast-pkts {
        type yang:counter64;
        units packets;
        description
          "The number of input IP multicast packets received on 
           the interface.

           Discontinuities in the value of this counter can occur
           at re-initialization of the management system, and at
           other times as indicated by the value of
           'discontinuity-time'.";
        reference
          "RFC 4293: The IP MIB - ipIfStatsHCInMcastPkts";
      }

      leaf in-mcast-octets {
        type yang:counter64;
        units octets;
        description
          "The number of octets received in IP multicast 
           packets. Octets from packets counted in 
           /ipv4/in-mcast-pkts MUST be counted.

           Discontinuities in the value of this counter can occur
           at re-initialization of the management system, and at
           other times as indicated by the value of
           'discontinuity-time'.";
        reference
          "RFC 4293: The IP MIB - ipIfStatsHCInMcastOctets";
      }

      leaf in-bcast-pkts {
        type yang:counter64;
        units packets;
        description
          "The number of input IP broadcast packets received on 
           the interface.

           Discontinuities in the value of this counter can occur
           at re-initialization of the management system, and at
           other times as indicated by the value of
           'discontinuity-time'.";
        reference
          "RFC 4293: The IP MIB - ipIfStatsHCInBcastPkts";
      }

      leaf in-truncates {
        type yang:counter32;
        units packets;
        description
          "The number of input IP packets discarded because the
           packet didn't carry enough data.

           Discontinuities in the value of this counter can occur
           at re-initialization of the management system, and at
           other times as indicated by the value of
           'discontinuity-time'.";
        reference
          "RFC 4293: The IP MIB - ipIfStatsInTruncatedPkts";
      }

      leaf in-dest-addr-errors {
        type yang:counter32;
        units packets;
        description
          "The number of input IP packets discarded because the IP
           address in their IP header's destination field was not a
           valid address to be received at this system.  For systems
		   that are not IP routers and therefore do not forward packets, 
		   this counter includes packets that are discarded because 
           the destination address was not a local address.

           Discontinuities in the value of this counter can occur
           at re-initialization of the management system, and at
           other times as indicated by the value of
           'discontinuity-time'.";
        reference
          "RFC 4293: The IP MIB - ipIfStatsInAddrErrors";
      }

      leaf in-scr-addr-errors {
        type yang:counter32;
        units packets;
        description
          "The number of input IP packets discarded because the IP
           address in their IP header's source field was not a
           valid address to be received at this system.  This count
           includes source filtering on multicast packets.  

           Discontinuities in the value of this counter can occur
           at re-initialization of the management system, and at
           other times as indicated by the value of
           'discontinuity-time'.";
        reference
          "RFC 4293: The IP MIB - ipIfStatsInAddrErrors";
      }
	  
      leaf in-forwards {
        type yang:counter64;
        units packets;
        description
          "The number of input IP packets for which this system
           was not their final IP destination and for which this 
           system attempted to find a route to forward them to that
           final destination.

           Discontinuities in the value of this counter can occur
           at re-initialization of the management system, and at
           other times as indicated by the value of
           'discontinuity-time'.";
        reference
          "RFC 4293: The IP MIB - ipIfStatsHCInForwDatagrams";
      }
      leaf in-no-routes {
        type yang:counter32;
        units packets;
        description
          "The number of input IP packets for which this system was
           not their final IP destination and for which this system
           attempted to find a route to forward them to that final
           destination.

           Discontinuities in the value of this counter can occur
           at re-initialization of the management system, and at
           other times as indicated by the value of
           'discontinuity-time'.";
        reference
          "RFC 4293: The IP MIB - ipIfStatsInNoRoutes";
      }

      leaf in-reasm-requires {
        type yang:counter64;
        units fragments;
        description
          "The number of input IP fragments received that needed 
           to be reassembled at this interface.

           When tracking interface statistics, the counter of the
           interface to which these fragments were addressed is
           incremented.  This interface might not be the same as the
           input interface for some of the fragments.

           Discontinuities in the value of this counter can occur
           at re-initialization of the management system, and at
           other times as indicated by the value of
           'discontinuity-time'.";
        reference
          "RFC 4293: The IP MIB - ipIfStatsReasmReqds";
      }

      leaf in-reasm-fails {
        type yang:counter32;
        units failures;
        description
          "The number of failures detected by the IP re-assembly
           algorithm (for whatever reason: timed out, errors, etc.).
           Note that this is not necessarily a count of discarded IP
           fragments since some algorithms can lose track of the 
           number of fragments by combining them as they are 
           received.

           When tracking interface statistics, the counter of the
           interface to which these fragments were addressed is
           incremented.  This interface might not be the same as the
           input interface for some of the fragments.

           Discontinuities in the value of this counter can occur
           at re-initialization of the management system, and at
           other times as indicated by the value of
           'discontinuity-time'.";
        reference
          "RFC 4293: The IP MIB - ipIfStatsReasmFails";
      }

      leaf in-reasm-OKs {
        type yang:counter64;
        units datagrams;
        description
          "The number of input IP datagrams successfully 
           reassembled.

           When tracking interface statistics, the counter of the
           interface to which these datagrams were addressed is
           incremented.  This interface might not be the same as the
           input interface for some of the datagrams.

           Discontinuities in the value of this counter can occur
           at re-initialization of the management system, and at
           other times as indicated by the value of
           'discontinuity-time'.";
        reference
          "RFC 4293: The IP MIB - ipIfStatsReasmOKs";
      }

      leaf in-unknown-protos {
        type yang:counter32;
        units datagrams;
        description
          "The number of locally-addressed input IP datagrams 
           received successfully but discarded because of an unknown 
           or unsupported protocol.

           When tracking interface statistics, the counter of the
           interface to which these datagrams were addressed is
           incremented.  This interface might not be the same as the
           input interface for some of the datagrams.

           Discontinuities in the value of this counter can occur
           at re-initialization of the management system, and at
           other times as indicated by the value of
           'discontinuity-time'.";
        reference
          "RFC 4293: The IP MIB - ipIfStatsInUnknownProtos";
      }

      leaf in-discards {
        type yang:counter32;
        units datagrams;
        description
          "The number of input IP datagrams for which no problems 
           were encountered to prevent their continued processing,
           but were discarded (e.g., for lack of buffer space).  
           Note that this counter does not include any datagrams 
           discarded while awaiting re-assembly.

           Discontinuities in the value of this counter can occur
           at re-initialization of the management system, and at
           other times as indicated by the value of
           'discontinuity-time'.";
        reference
          "RFC 4293: The IP MIB - ipIfStatsInDiscards";
      }

      leaf in-delivers {
        type yang:counter64;
        units datagrams;
        description
          "The number of input IP datagrams successfully 
           delivered to IP user protocols (including ICMP).

           When tracking interface statistics, the counter of the
           interface to which these datagrams were addressed is
           incremented.  This interface might not be the same as the
           input interface for some of the datagrams.

           Discontinuities in the value of this counter can occur
           at re-initialization of the management system, and at
           other times as indicated by the value of
           'discontinuity-time'.";
        reference
          "RFC 4293: The IP MIB - ipIfStatsHCInDelivers";
      }

      leaf out-requests {
        type yang:counter64;
        units datagrams;
        description
          "The number of output IP datagrams that local IP user
           protocols (including ICMP) supplied to IP in requests for
           transmission.  Note that this counter does not include any
           datagrams counted out-forwards.

           Discontinuities in the value of this counter can occur
           at re-initialization of the management system, and at
           other times as indicated by the value of
           'discontinuity-time'.";
        reference
          "RFC 4293: The IP MIB - ipIfStatsHCOutRequests";
      }

      leaf out-no-routes {
        type yang:counter32;
        units datagrams;
        description
          "The number of locally generated output IP datagrams 
           discarded because no route could be found to transmit 
           them to their destination.

           Discontinuities in the value of this counter can occur
           at re-initialization of the management system, and at
           other times as indicated by the value of
           'discontinuity-time'.";
        reference
          "RFC 4293: The IP MIB";
      }

      leaf out-forwards {
        type yang:counter64;
        units packets;
        description
          "The number of output IP packets for which this system 
           was not their final IP destination and for which it was 
           successful in finding a path to their final destination.

           When tracking interface statistics, the counter of the
           outgoing interface is incremented for a successfully
           forwarded packet.

           Discontinuities in the value of this counter can occur
           at re-initialization of the management system, and at
           other times as indicated by the value of
           'discontinuity-time'.";
        reference
          "RFC 4293: The IP MIB - ipIfStatsHCOutForwDatagrams";
      }
      leaf out-frag-requires {
        type yang:counter64;
        units datagrams;
        description
          "The number of output IP datagrams that would require 
           fragmentation in order to be transmitted.

           When tracking interface statistics, the counter of the
           outgoing interface is incremented for a successfully
           fragmented datagram.

           Discontinuities in the value of this counter can occur
           at re-initialization of the management system, and at
           other times as indicated by the value of
           'discontinuity-time'.";
        reference
          "RFC 4293: The IP MIB - ipIfStatsOutFragReqds";
      }

      leaf out-frag-fails {
        type yang:counter32;
        units datagrams;
        description
          "The number of output IP datagrams that have been 
           discarded because they needed to be fragmented but 
           could not be.  This includes IPv4 packets that have 
           the DF bit set or IPv6 packets that are being 
           forwarded and exceed the outgoing link MTU.

           When tracking interface statistics, the counter of the
           outgoing interface is incremented for a successfully
           fragmented datagram.

           Discontinuities in the value of this counter can occur
           at re-initialization of the management system, and at
           other times as indicated by the value of
           'discontinuity-time'.";
        reference
          "RFC 4293: The IP MIB - ipIfStatsOutFragFails";
      }

      leaf out-frag-OKs {
        type yang:counter64;
        units datagrams;
        description
          "The number of output IP datagrams that have been 
           successfully fragmented.

           When tracking interface statistics, the counter of the
           outgoing interface is incremented for a successfully
           fragmented datagram.

           Discontinuities in the value of this counter can occur
           at re-initialization of the management system, and at
           other times as indicated by the value of
           'discontinuity-time'.";
        reference
          "RFC 4293: The IP MIB - ipIfStatsOutFragOKs";
      }

      leaf out-frag-creates {
        type yang:counter64;
        units fragments;
        description
          "The number of output IP fragments that have been
           generated as a result of IP fragmentation.

           When tracking interface statistics, the counter of the
           outgoing interface is incremented for a successfully
           fragmented datagram.

           Discontinuities in the value of this counter can occur
           at re-initialization of the management system, and at
           other times as indicated by the value of
           'discontinuity-time'.";
        reference
          "RFC 4293: The IP MIB - ipIfStatsOutFragCreates";
      }

      leaf out-mcast-pkts {
        type yang:counter64;
        units packets;
        description
          "The number of output IP multicast packets transmitted 
           on the interface.

           Discontinuities in the value of this counter can occur
           at re-initialization of the management system, and at
           other times as indicated by the value of
           'discontinuity-time'.";
        reference
          "RFC 4293: The IP MIB - ipIfStatsHCOutMcastPkts";
      }

      leaf out-mcast-octets {
        type yang:counter64;
        units octets;
        description
          "The number of octets transmitted in IP 
           multicast packets. Octets from packets
           counted in /ipv4/out-mcast-pkts MUST be counted.

           Discontinuities in the value of this counter can occur
           at re-initialization of the management system, and at
           other times as indicated by the value of
           'discontinuity-time'.";
        reference
          "RFC 4293: The IP MIB - ipIfStatsHCOutMcastOctets";
      }

      leaf out-bcast-pkts {
        type yang:counter64;
        units packets;
        description
          "The number of output IP broadcast packets transmitted 
           on the interface.

           Discontinuities in the value of this counter can occur
           at re-initialization of the management system, and at
           other times as indicated by the value of
           'discontinuity-time'.";
        reference
          "RFC 4293: The IP MIB - ipIfStatsHCOutBcastPkts";
      }

      leaf out-discards {
        type yang:counter32;
        units packets;
        description
          "The number of output IP packets for which no problem was
           encountered to prevent their transmission to their
           destination, but were discarded (e.g., for lack of
           buffer space).  Note that this counter would include
           datagrams counted in out-forwards if any such
           packets met this (discretionary) discard criterion.

           Discontinuities in the value of this counter can occur
           at re-initialization of the management system, and at
           other times as indicated by the value of
           'discontinuity-time'.";
        reference
          "RFC 4293: The IP MIB - ipIfStatsOutDiscards";
      }

      leaf out-transmits {
        type yang:counter64;
        units packets;
        description
          "The number of output IP packets that this system 
           supplied to the lower layers for transmission.  

           Discontinuities in the value of this counter can occur
           at re-initialization of the management system, and at
           other times as indicated by the value of
           'discontinuity-time'.";
        reference
          "RFC 4293: The IP MIB - ipIfStatsHCOutTransmits";
      }

      leaf out-octets {
        type yang:counter64;
        units octets;
        description
          "The number of octets in output IP packets delivered 
           to the lower layers for transmission. Octets from packets
           counted in out-transmits MUST be counted.

           Discontinuities in the value of this counter can occur
           at re-initialization of the management system, and at
           other times as indicated by the value of
           'discontinuity-time'.";
        reference
          "RFC 4293: The IP MIB - ipIfStatsHCOutOctets";
      }
    }
  }

  /*
   * Data nodes for ICMP statistics for IP-capable system
   */

  container system-stats {
    config false;
    description
      "A collection of system wide statistics";

    container icmpv4 {
	  presence
        "Present if IPv4 is enabled on this system";
      description
        "A collection of ICMPv4 layer statistics processed by 
	     this system.";    
      leaf in-msgs {
        type yang:counter32;
        units messages;
        description
          "The number of ICMPv4 messages received by this system.
           Note that this counter includes all those counted by
           /icmpv4/in-errors.";
        reference
          "RFC 4293: The IP MIB - icmpStatsInMsgs";
      }

      leaf in-errors {
        type yang:counter32;
        units messages;
        description
          "The number of ICMPv4 messages that this system received 
		   but determined as having ICMP-specific errors (bad ICMP
           checksums, bad length, etc).";
        reference
          "RFC 4293: The IP MIB - icmpStatsInErrors";
      }

      leaf in-echo-requests {
        type yang:counter32;
        units messages;
        description
          "The number of ICMPv4 Echo Request messages
           (type 8) received by this system.";
        reference
          "RFC 4293: The IP MIB";
      }   

      leaf in-echo-replies {
        type yang:counter32;
        units messages;
        description
          "The number of ICMPv4 Echo Reply messages
           (type 0) received by this system.";
        reference
          "RFC 4293: The IP MIB";
      }  

      leaf in-dest-unreachs {
        type yang:counter32;
        units messages;
        description
          "The number of ICMPv4 Destination Unreachable messages
           (type 3) received by this system.";
        reference
          "RFC 4293: The IP MIB";
      }  

      leaf in-param-problems {
        type yang:counter32;
        units messages;
        description
          "The number of ICMPv4 Parameter Problem messages
           (type 12) received by this system.";
        reference
          "RFC 4293: The IP MIB";
      } 

      leaf in-time-exceeds {
        type yang:counter32;
        units messages;
        description
          "The number of ICMPv4 Time Exceeded messages
           (type 11) received by this system.";
        reference
          "RFC 4293: The IP MIB";
      }

      leaf in-others {
        type yang:counter32;
        units messages;
        description
          "The number of any other ICMPv4 message types 
           received by this system.";
        reference
          "RFC 4293: The IP MIB";
      } 

      leaf out-msgs {
        type yang:counter32;
        units messages;
        description
          "The number of ICMPv4 messages this system attempted to 
		   send. Note that this counter includes all those counted 
		   by /icmpv4/out-errors.";
        reference
          "RFC 4293: The IP MIB - icmpStatsOutMsgs";
      }

      leaf out-errors {
        type yang:counter32;
        units messages;
        description
          "The number of ICMPv4 messages this system did not send
           due to problems discovered within ICMP, such as a lack of
           buffers. This value should not include errors discovered
           outside the ICMP layer, such as the inability of IP to 
		   route the resultant datagram.";
        reference
          "RFC 4293: The IP MIB - icmpStatsOutErrors";
      }

      leaf out-echo-requests {
        type yang:counter32;
        units messages;
        description
           "The number of ICMPv4 Echo Request messages
           (type 8) this system attempted to send.";
        reference
          "RFC 4293: The IP MIB";
      }   

      leaf out-echo-replies {
        type yang:counter32;
        units messages;
        description
          "The number of ICMPv4 Echo Reply messages
           (type 0) this system attempted to send.";
        reference
          "RFC 4293: The IP MIB";
      }  

      leaf out-dest-unreachs {
        type yang:counter32;
        units messages;
        description
          "The number of ICMPv4 Destination Unreachable messages
           (type 3) this system attempted to send.";
        reference
          "RFC 4293: The IP MIB";
      }  

      leaf out-param-problems {
        type yang:counter32;
        units messages;
        description
          "The number of ICMPv4 Parameter Problem messages
           (type 12) this system attempted to send.";
        reference
          "RFC 4293: The IP MIB";
      } 

      leaf out-time-exceeds {
        type yang:counter32;
        units messages;
        description
          "The number of ICMPv4 Time Exceeded messages
           (type 11) this system attempted to send.";
        reference
          "RFC 4293: The IP MIB";
      }

      leaf out-others {
        type yang:counter32;
        units messages;
        description
          "The number of any other ICMPv4 message types this 
           system attempted to send.";
        reference
          "RFC 4293: The IP MIB";
      }
    }

    container icmpv6 {
	  presence
        "Present if IPv6 is enabled on this system";
      description
        "A collection of ICMPv6 layer statistics for ICMPv6 traffic 
         processed by this system.";

      leaf in-msgs {
        type yang:counter32;
        units messages;
        description
          "The number of ICMPv6 messages received by this system.
           Note that this counter includes all those counted by
           icmpv6/in-errors.";
      reference
        "RFC 4293: The IP MIB - icmpStatsInMsgs";
      }

      leaf in-errors {
        type yang:counter32;
        units messages;
        description
          "The number of ICMPv6 messages that this system received 
		   but determined as having ICMP-specific errors (bad ICMP
           checksums, bad length, etc).";
        reference
          "RFC 4293: The IP MIB - icmpStatsInErrors";
      }

      leaf in-echo-requests {
        type yang:counter32;
        units messages;
        description
          "The number of ICMPv6 Echo Request messages
           (type 128) received by this system.";
        reference
          "RFC 4293: The IP MIB";
      }   

      leaf in-echo-replies {
        type yang:counter32;
        units messages;
        description
          "The number of ICMPv6 Echo Reply messages
           (type 129) received by this system.";
        reference
          "RFC 4293: The IP MIB";
      }  

      leaf in-dest-unreachs {
        type yang:counter32;
        units messages;
        description
          "The number of ICMPv6 Destination Unreachable messages
           (type 1) received by this system.";
        reference
          "RFC 4293: The IP MIB";
      }  

      leaf in-param-problems {
        type yang:counter32;
        units messages;
        description
          "The number of ICMPv6 Parameter Problem messages
           (type 4) received by this system.";
        reference
          "RFC 4293: The IP MIB";
      } 

      leaf in-time-exceeds {
        type yang:counter32;
        units messages;
        description
          "The number of ICMPv6 Time Exceeded messages
           (type 3) received by this system.";
        reference
          "RFC 4293: The IP MIB";
      }

      leaf in-redirects {
        type yang:counter32;
        units messages;
        description
          "The number of ICMPv6 Redirect messages
           (type 137) received by this system.";
        reference
          "RFC 4293: The IP MIB";
      } 

      leaf in-pkt-too-bigs {
        type yang:counter32;
        units messages;
        description
          "The number of ICMPv6 Packet Too Big messages
           (type 2) received by this system.";
        reference
          "RFC 4293: The IP MIB";
      }  

      leaf in-router-solicits {
        type yang:counter32;
        units messages;
        description
          "The number of ICMPv4 Router Solicit messages
           (type 133) received by this system.";
        reference
          "RFC 4293: The IP MIB";
      } 

      leaf in-router-adverts {
        type yang:counter32;
        units messages;
        description
          "The number of ICMPv4 Router Advertisement messages
           (type 134) received by this system.";
        reference
          "RFC 4293: The IP MIB";
      } 

      leaf in-neighbor-solicits {
        type yang:counter32;
        units messages;
        description
          "The number of ICMPv6 Neighbor Solicit messages
           (type 135) received by this system.";
        reference
          "RFC 4293: The IP MIB";
      } 

      leaf in-neighbor-adverts {
        type yang:counter32;
        units messages;
        description
          "The number of ICMPv6 Neighbor Advertisement messages
           (type 136) received by this system.";
        reference
          "RFC 4293: The IP MIB";
      } 

      leaf in-MLDv2-queries {
        type yang:counter32;
        units messages;
        description
          "The number of Multicast Listener Discovery version 2 
           Query messages(type 130 with length equal or greater 
           than 28 bytes) received by this system.";
        reference
          "RFC 3810: MLDv2 for IPv6";
      } 

      leaf in-MLDv2-reports {
        type yang:counter32;
        units messages;
        description
          "The number of Multicast Listener Discovery version 2
           Report messages(type 143) received by this system.";
        reference
          "RFC 3810: MLDv2 for IPv6";
      } 

      leaf in-others {
         type yang:counter32;
        units messages;
        description
          "The number of any other ICMPv6 message types received 
           by this system.";
        reference
         "RFC 4293: The IP MIB";
      } 
      leaf out-msgs {
        type yang:counter32;
        units messages;
        description
          "The number of ICMPv6 messages this system attempted to 
		   send. Note that this counter includes all those counted 
		   by /icmpv6/out-errors.";
        reference
          "RFC 4293: The IP MIB - icmpStatsInMsgs";
      }

      leaf out-errors {
        type yang:counter32;
        units messages;
        description
           "The number of ICMPv6 messages that this system received 
		   but determined as having ICMP-specific errors (bad ICMP
           checksums, bad length, etc).";
        reference
          "RFC 4293: The IP MIB - icmpStatsInErrors";
      }

      leaf out-echo-requests {
        type yang:counter32;
        units messages;
        description
          "The number of ICMPv6 Echo Request messages
           (type 128) this system attempted to send.";
        reference
          "RFC 4293: The IP MIB";
      }   

      leaf out-echo-replies {
        type yang:counter32;
        units messages;
        description
          "The number of ICMPv6 Echo Reply messages
           (type 129) this system attempted to send.";
        reference
          "RFC 4293: The IP MIB";
      }  

      leaf out-dest-unreachs {
        type yang:counter32;
        units messages;
        description
          "The number of ICMPv6 Destination Unreachable messages
           (type 1) this system attempted to send.";
        reference
          "RFC 4293: The IP MIB";
      }  

      leaf out-param-problems {
        type yang:counter32;
        units messages;
        description
          "The number of ICMPv6 Parameter Problem messages
           (type 4) this system attempted to send.";
        reference
          "RFC 4293: The IP MIB";
      } 

      leaf out-time-exceeds {
        type yang:counter32;
        units messages;
        description
          "The number of ICMPv6 Time Exceeded messages
           (type 3) this system attempted to send.";
        reference
          "RFC 4293: The IP MIB";
      }

      leaf out-redirects {
        type yang:counter32;
        units messages;
        description
          "The number of ICMPv6 Redirect messages
           (type 137) this system attempted to send.";
        reference
          "RFC 4293: The IP MIB";
      } 

      leaf out-pkt-too-bigs {
        type yang:counter32;
        units messages;
        description
          "The number of ICMPv6 Packet Too Big messages
           (type 2) this system attempted to send.";
        reference
          "RFC 4293: The IP MIB";
      }  

      leaf out-router-solicits {
        type yang:counter32;
        units messages;
        description
          "The number of ICMPv6 Router Solicit messages
           (type 133) this system attempted to send.";
        reference
          "RFC 4293: The IP MIB";
      } 

      leaf out-router-adverts {
        type yang:counter32;
        units messages;
        description
          "The number of ICMPv6 Router Advertisement messages
           (type 134) this system attempted to send.";
        reference
          "RFC 4293: The IP MIB";
      } 

      leaf out-neighbor-solicits {
        type yang:counter32;
        units messages;
        description
          "The number of ICMPv6 Neighbor Solicit messages
           (type 135) this system attempted to send.";
        reference
          "RFC 4293: The IP MIB";
      } 

      leaf out-neighbor-adverts {
        type yang:counter32;
        units messages;
        description
          "The number of ICMPv6 Neighbor Advertisement messages
           (type 136) this system attempted to send.";
        reference
          "RFC 4293: The IP MIB";
      } 

      leaf out-MLDv2-queries {
        type yang:counter32;
        units messages;
        description
          "The number of Multicast Listener Discovery version 2 
           Query messages(type 130 with length equal or greater 
           than 28 bytes) this system attempted to send.";
        reference
          "RFC 3810: MLDv2 for IPv6";
      } 

      leaf out-MLDv2-reports {
        type yang:counter32;
        units messages;
        description
          "The number of Multicast Listener Discovery version 2
           Report messages(type 143) this system attempted to send.";
        reference
          "RFC 3810: MLDv2 for IPv6";
      } 

      leaf out-others {
        type yang:counter32;
        units messages;
        description
          "The number of any other ICMPv6 message types 
           this system attempted to send.";
        reference
          "RFC 4293: The IP MIB";
      } 
    }
  }
  /*
   * Data nodes for IP statistics for IPv4-capable interface
   */

  augment "/if:interfaces-state/if:interface/ip:ipv4" {
    description
      "Data nodes for statistics about IPv4 traffic on an 
       interface when IPv4 is enabled on that interface.

       The interface can be any IPv4-capable interface including 
       an Ethernet interface, a link aggregate (LAG) interface,
       a L3 IP VLAN interface and a loopback interface.";

    uses ip-if-stats;
  }

  /*
   * Data nodes for IP statistics for IPv6-capable interface
   */

  augment "/if:interfaces-state/if:interface/ip:ipv6" {
    description
      "Data nodes for statistics about IPv6 traffic on an 
       interface when IPv6 is enabled on that interface.

       The interface can be any IPv6-capable interface including 
       an Ethernet interface, a link aggregate (LAG) interface,
       a L3 IP VLAN interface and a loopback interface.";
    uses ip-if-stats;
  }
}
