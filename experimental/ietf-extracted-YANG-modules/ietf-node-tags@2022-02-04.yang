module ietf-node-tags {
  yang-version 1.1;
  namespace "urn:ietf:params:xml:ns:yang:ietf-node-tags";
  prefix ntags;

  import ietf-netconf-acm {
    prefix nacm;
    reference
    "RFC 8341: Network Configuration Access Control
               Model";
  }
  import ietf-module-tags {
    prefix tags;
    reference
    "RFC 8819: YANG Module Tags";
  }

  organization
    "IETF NetMod Working Group (NetMod)";
  contact
   "WG Web:  <https://datatracker.ietf.org/wg/netmod/>
    WG List: <mailto:netmod@ietf.org>

    Editor: Qin Wu
            <mailto:bill.wu@huawei.com>

    Editor: Benoit Claise
            <mailto:benoit.claise@huawei.com>

    Editor: Mohamed Boucadair
            <mailto:mohamed.boucadair@orange.com>
    Editor: Peng Liu
            <mailto:liupengyjy@chinamobile.com>

    Editor: Zongpeng Du
            <mailto:duzongpeng@chinamobile.com>";
   // RFC Ed.: replace XXXX with actual RFC number and
   // remove this note.
  description
    "This module describes a mechanism associating
     tags with YANG node within YANG modules. Tags may be IANA
     assigned or privately defined.

     Copyright (c) 2022 IETF Trust and the persons identified as
     authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://datatracker.ietf.org/html/rfcXXXX); see the RFC
     itself for full legal notices.";

   // RFC Ed.: Update the date below with the date of RFC
   // publication and RFC number and remove this note.
  revision 2022-02-04 {
    description
      "Initial revision.";
    reference
      "RFC XXXX: Node Tags in YANG Modules";
  }
  extension node-tag {
    argument tag;
    description
      "The argument 'tag' is of type 'tag'. This extension statement
       is used by module authors to indicate node tags that should
       be added automatically by the system. As such,  the origin of
       the value for the pre-defined tags should be set to 'system'.";
  }

  augment "/tags:module-tags/tags:module" {
    description
      "Augment the Module Tags module with node tag
       attributes.";
    container node-tags {
      description
        "Contains the list of nodes or node instances and their
         associated node tags.";
      list node {
        key "id";
        description
          "Includes a list of nodes and their associated
           node tags.";
        leaf id   {
          type uint64;
          description
            "Identification of each data node within YANG module. It is
             unique 64-bit unsigned integers.";
        }
        leaf node-selector {
          type nacm:node-instance-identifier;
          description
            "Selects the data nodes for which tags are specified.";
        }
       leaf-list tags {
          type tags:tag;
          description
            "Lists the tags associated with the node within
             the YANG  module.

             See the IANA 'YANG Node Tag Prefixes' registry
             for reserved prefixes and the IANA 'IETF YANG Data
             Node Tags' registry for IETF tags.

             The 'operational' state view of this list is
             constructed using the following steps:

             1) System tags (i.e., tags of 'system' origin) are
                added.
             2) User configured tags (i.e., tags of 'intended'
                origin) are added.
             3) Any tag that is equal to a masked-tag is removed.";
          reference
            "RFC XXXX: node Tags in YANG Data
                       Modules, Section 9";
       }
        leaf-list masked-tag {
          type tags:tag;
          description
            "The list of tags that should not be associated with the
             node within the YANG module. The user can remove (mask)
             tags from the operational state datastore by adding them
             to this list. It is not an error to add tags to this list
             that are not associated with the data node within YANG
             module, but they have no operational effect.";
        }
       }
      }
   }
  }
