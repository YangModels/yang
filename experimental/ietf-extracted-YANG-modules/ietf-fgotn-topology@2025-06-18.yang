module ietf-fgotn-topology {
  /* TODO: FIXME */
 yang-version 1.1;

 namespace "urn:ietf:params:xml:ns:yang:ietf-fgotn-topology";
 prefix "fgotnt";

 import ietf-network {
   prefix "nw";
   reference
     "RFC8345: A YANG Data Model for Network Topologies";
 }

 import ietf-network-topology {
   prefix "nt";
   reference
     "RFC8345: A YANG Data Model for Network Topologies";
 }

 import ietf-te-topology {
   prefix "tet";
   reference
     "RFC 8795: YANG Data Model for Traffic Engineering (TE)
                Topologies";
 }

 import ietf-layer1-types {
   prefix "l1-types";
   reference
     "RFC YYYY: A YANG Data Model for Layer 1 Types";
 }

 /* Note: The RFC Editor will replace YYYY with the number assigned
    to the RFC once draft-ietf-ccamp-layer1-types becomes an RFC.*/

 import ietf-otn-topology {
   prefix "otnt";
   reference
     "RFC ZZZZ: A YANG Data Model for Optical Transport Network
                Topology";
 }

 /* Note: The RFC Editor will replace ZZZZ with the number assigned
    to the RFC once draft-ietf-ccamp-otn-topo-yang becomes an RFC.*/

 organization
   "Internet Engineering Task Force (IETF) CCAMP WG";
 contact
   "
     ID-draft editor:
       Yanxia Tan (tanyx11@chinaunicom.cn);
       Yanlei Zheng (zhengyanlei@chinaunicom.cn);
       Italo Busi (italo.busi@huawei.com);
       Chaode Yu (yuchaode@huawei.com);
       Xing Zhao (zhaoxing@caict.ac.cn);
   ";

 description
   "This module defines a YANG data model for fgOTN-specific 
    extension based on existing network topology models. The model 
    fully conforms to the Network Management Datastore Architecture
    (NMDA).

    Copyright (c) 2024 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.";

 // RFC Ed.: replace XXXX with actual RFC number and remove this
 // note.
 // RFC Ed.: update the date below with the date of RFC publication
 // and remove this note.

 revision 2025-06-18 {
   description
     "initial version";
   reference
     "RFC XXXX: YANG Data Models for fine grain Optical Transport
                Network";
 }

 augment "/nw:networks/nw:network/nt:link/tet:te" + 
         "/tet:te-link-attributes/tet:max-link-bandwidth" + 
         "/tet:te-bandwidth/otnt:otn-bandwidth/otnt:odulist" {
   description
     "specific augmentation of fgOTN link on maximum link 
     bandwidth";
   leaf fgotn-bandwidth {
     type uint16;
     description
       "It is used to indicate how much of the bandwidth has been
        allocated for the usage of fgOTN.";
   }
 }  

 augment "/nw:networks/nw:network/nt:link/tet:te" + 
         "/tet:te-link-attributes/tet:unreserved-bandwidth" +
         "/tet:te-bandwidth/otnt:otn-bandwidth" {
   description
     "specific augmentation of fgOTN link on unreserved link 
     bandwidth";
   list fgotnlist {
     key "odu-type odu-ts-number";
     description
       "This structure is used to describe the unsreserved
        bandwidth of fgOTN in the server ODUk";
     leaf odu-type {
       type identityref {
         base l1-types:odu-type;
       }
       description 
         "The granularity of server ODUk";
     }

     leaf odu-ts-number {
       type uint16;
       description 
         "The index of server ODUk channel";
     }

     leaf fgotn-bandwidth {
       type uint16;
       description 
         "The unsreserved bandwidth of fgOTN in this server ODUk";
     }
   }
 }

 augment "/nw:networks/tet:te/tet:templates/tet:link-template"+ 
         "/tet:te-link-attributes/tet:label-restrictions" +
         "/tet:label-restriction/otnt:otn-label-range" {
   description
     "specific augmentation of fgOTN label";
   list fgts-range {
     key "odu-type odu-ts-number";
     description 
       "This structure is used to describe the availability of
        fgOTN timeslot in the server ODUk";
     leaf odu-type {
       type identityref {
         base l1-types:odu-type;
       }
       description
         "The granularity of server ODUk";
     }

     leaf odu-ts-number {
       type uint16;
       description 
         "The index of server ODUk channel"; 
     }

     leaf fgts-reserved {
       type string;
       description 
         "The reserved fgOTN timeslot in this server ODUk";
     }

     leaf fgts-unreserved {
       type string;
       description 
         "The unreserved fgOTN timeslot in this server ODUk";
     }
   }
 }
}
