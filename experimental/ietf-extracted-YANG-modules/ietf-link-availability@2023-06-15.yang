module ietf-link-availability {
  yang-version 1.1;
  namespace "urn:ietf:params:xml:ns:yang:ietf-link-availability";
  prefix ln-avail;

  import ietf-yang-types {
    prefix yang;
  }

  import ietf-te-types {
    prefix te-types;
  }

  organization
    "IETF Time-Variant Routing Working Group";

  contact
    "WG Web:   <https://datatracker.ietf.org/wg/tvr/>
     WG List:  <mailto:tvr@ietf.org>

     Editors:  Eric Kinzie
               <mailto:ekinzie@labn.net>
               Don Fedyk
               <mailto:dfedyk@labn.net>";

  description
    "This YANG module contains YANG definitions for describing
    network links with an time-variant availability schedule.

    Copyright (c) 2023 IETF Trust and the persons identified as
    authors of the code.  All rights reserved.

    Redistribution and use in source and binary forms, with or
    without modification, is permitted pursuant to, and subject to
    the license terms contained in, the Revised BSD License set forth
    in Section 4.c of the IETF Trust's Legal Provisions Relating
    to IETF Documents (https://trustee.ietf.org/license-info).

    This version of this YANG module is part of RFC XXXX
    (https://www.rfc-editor.org/info/rfcXXXX); see the RFC itself
    for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  revision 2023-06-15 {
    description
      "Initial revision";
    reference
      "RFC XXXX A YANG Data Model for Time Variant Link
      Availability";
  }

  container link-availability {
    config false;

    leaf next-update {
      type yang:date-and-time;
      description
        "This data is current until the specified time.";
    }

    list link {
      key "avail-from source-node source-link-id";
      leaf avail-from {
        type yang:date-and-time;
        description
          "The time at which this link becomes available.";
      }
      leaf source-node {
        type string;
        description
          "A name that refers to the source (transmitting)
           node of the link.";
      }
      leaf source-link-id {
        type string;
        description
          "A name, as known to the source node, that refers to
          this link.";
      }
      leaf destination-node {
        type string;
        description
          "A name that refers to the destination (receiving) node
          of the link.";
      }
      leaf avail-until {
        type yang:date-and-time;
        description
          "The time at which this link is no longer available.";
      }
      leaf bandwidth {
        type te-types:te-bandwidth;
        description
          "The predicted link capacity specified in a generic
          format. If the value measured by the system is less than
          this value, the system value is used.  If the value
          measured by the system is greater than this value the
          predicted value SHOULD be used.";
        reference
          "RFC 8776: Common YANG Data Types for Traffic Engineering";
      }
      leaf delay {
        type uint32 {
          range "0..16777215";
        }
        description
          "The one-way delay or latency in microseconds. If the
          value measured by the system is less than this value
          the predicted value SHOULD be used.";
        reference
          "RFC 8776: Common YANG Data Types for Traffic Engineering";
      }
      leaf igp-link-metric {
        type uint32;
        description
          "OSPF or IS-IS link metric.  If this metric is supplied
           it is the predicted metric that is used by the system.
           The system may adjust operational metric as needed.";
        reference
          "RFC 9129: YANG Data Model for the OSPF Protocol
           RFC 9130: YANG Data Model for the IS-IS Protocol";
      }
      leaf te-default-metric {
        type uint32;
        description
          "The Traffic Engineering metric. The system may adjust this
           value on the operational link.";
        reference
          "RFC 3630: Traffic Engineering (TE) Extensions to OSPF
          Version 2
           RFC 5305: IS-IS Extensions for Traffic Engineering";
      }
      container link-affinity-names {
        description
          "Link affinities represented as names.";
        list link-affinity-name {
          key "usage";
          description
            "An optional list of named affinity constraints.";
          leaf usage {
            type identityref {
              base te-types:resource-affinities-type;
            }
            description
              "Identifies an entry in the list of named affinity
               constraints.";
          }
          list affinity-name {
            key "name";
            leaf name {
              type string;
              description
                "Identifies a named affinity entry.";
            }
            description
              "List of named affinities.";
            reference
              "RFC 8776: Common YANG Data Types for Traffic
               Engineering";
          }
        }
      }
      container link-srlgs-names {
        description
          "Container for the list of named SRLGs.";
        list link-srlgs-name {
          key "usage";
          description
            "List of named SRLGs to be included or excluded.";
          leaf usage {
            type identityref {
              base te-types:route-usage-type;
            }
            description
              "Identifies an entry in a list of named SRLGs to either
               include or exclude.";
          }
          leaf-list names {
            type string;
            description
              "List of named SRLGs.";
            reference
              "RFC 8776: Common YANG Data Types for Traffic
               Engineering";
          }
        }
      }
      description
        "This list represents a set of links each which has
         time variant link attributes.";
    }
    description
      "A container with a list links with time variant link
       availabilities.";
  }
}
