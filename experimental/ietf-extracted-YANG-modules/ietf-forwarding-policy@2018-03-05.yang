module ietf-forwarding-policy {
  yang-version "1.1";
  namespace "urn:ietf:params:xml:ns:yang:ietf-forwarding-policy";
  prefix "fwd";

  import ietf-inet-types {
    prefix "inet";
  }

  import ietf-network-instance {
    prefix "ni";
  }

  import ietf-qos-policy {
    prefix "pol";
  }

  organization "";
  contact "";
  description "";

  revision 2018-03-05 {
    description "Initial version";
    reference "";
  }

  identity forwarding-policy {
    base pol:policy-type;
    description "Forwarding policy type";
  }

  identity redirect-action {
    base pol:action-type;
    description "Redirect action type";
  }

  augment "/pol:policies" +
          "/pol:policy-entry" +
          "/pol:classifier-entry" +
          "/pol:classifier-action-entry-cfg" +
          "/pol:action-cfg-params" {
    when "../../pol:policy-type = 'fwd:forwarding-policy'" {
      description "Forwarding policy's action augmentation";
    }
    description "Forwarding policy's action parameters";
    case drop {
      description "Drop action choice";
      container drop-actions {
        description "Redirect action that are drop actions";
        leaf drop {
          type empty;
          description "Redirect packet such that it is dropped";
        }
      }
    }
    case redirect-to-ipv4-nexthops {
      container redirect-to-ipv4-nexthops-actions {
        description "Actions to redirect to a list of nexthops";
        list ipv4-nexthop {
          key "address";
          leaf address {
            type inet:ipv4-address;
            description "The IPv4 address";
          }
          description "A list of IPv4 nexthops";
        }
        leaf network-instance {
          type leafref {
            path "/ni:network-instances/ni:network-instance/ni:name";
          }
          description "The routing instance in which the addresses " +
                      "reside";
        }
      }
    }
    case redirect-to-ipv6-nexthops {
      container redirect-to-ipv6-nexthops {
        description "Redirect actions to IPv6 nexthops";
        list ipv6-nexthop {
          key "address";
          leaf address {
            type inet:ipv6-address;
            description "The IPv6 address";
          }
          description "A list of IPv6 nexthop addresses";
        }
        leaf network-instance {
          type leafref {
            path "/ni:network-instances/ni:network-instance/ni:name";
          }
          description "The routing instance in which the addresses " +
                      "reside";
        }
      }
    }
  }
}
