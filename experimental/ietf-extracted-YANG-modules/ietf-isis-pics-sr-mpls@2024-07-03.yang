module ietf-isis-pics-sr-mpls {
  yang-version 1.1;
  namespace "urn:ietf:params:xml:ns:yang:ietf-isis-pics-sr-mpls";
  prefix isis-pics-sr-mpls;

  import iana-isis-pics {
    prefix "iana-isis-pics";
  }

  import ietf-isis-pics {
    prefix "isis-pics";
  }

  organization
    "IETF LSR - Link State Routing Working Group";
  contact
    "WG Web:   <http://datatracker.ietf.org/wg/lsr>
     WG List:  <mailto:lsr@ietf.org>

     Author:   Yingzhen Qu
               <mailto:yingzhen.ietf@gmail.com>
     Author:   Les Ginsberg
               <mailto:ginsberg@cisco.com>
     Author:   Tony Przygienda
               <mailto:prz@juniper.net>
     Author:   Yongqing Zhu
               <mailto:zhuyq8@chinatelecom.cn>";

  description
    "The YANG module is used to query an IS-IS Protocol
     Implementation Conformance Statement (PICS) of Segment
     Routing for MPLS data plane (RFC8667).

     This YANG model conforms to the Network Management
     Datastore Architecture (NMDA) as described in RFC 8342.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  reference
    "RFC XXXX: YANG Data Model for IS-IS Segment Routing MPLS PICS";

  revision 2024-07-03 {
    description
      "Initial Version";
    reference
      "RFC XXXX: YANG Data Model for IS-IS Segment Routing MPLS PICS.";
  }

  container isis-pics-sr-mpls {
    when "/isis-pics:isis-pics/isis-pics:supported-isis-pics "
       + "= 'iana-isis-pics:isis-pics-sr-mpls'" {
      description
        "This container only exists when isis-pics-sr-mpls is present
         in the ietf-isis-pics module.";
    }
    config false;
    description
      "IS-IS Protocol Implementation Conformance Statement (PICS) of
       Segment Routing on MPLS data plane.";
    reference
       "RFC 8667: IS-IS Extensions for Segment Routing";

    container sr-capability-sub-tlv-support {
      presence "Support of sr-capability sub-tlv.";
      //config false;
      description
        "Support of sr-capability sub-tlv (Type 2).";

      leaf i-bit-support {
        type isis-pics:support;
        description
          "support mpls-ipv4 capability.";
      }
      leaf v-bit-support {
        type isis-pics:support;
        description
          "support mpls-ipv6 capability.";
      }
    }

    container prefix-sid-sub-tlv-support {
      presence "Support of prefix-sid sub-tlv.";
      description
        "Support of prefix-sid sub-tlv (Type 3).";

      leaf tlv-135 {
        type isis-pics:support;
        description
          "May present in TLV-135, extended IPv4 reachability.";
      }
      leaf tlv-235 {
        type isis-pics:support;
        description
          "May present in TLV-235, multi-topology IPv4 reachability.";
      }
      leaf tlv-236 {
        type isis-pics:support;
        description
          "May present in TLV-236, IPv6 IP reachability.";
      }
      leaf tlv-237 {
        type isis-pics:support;
        description
          "May present in TLV-237, multi-topology IPv6 IP
           reachability.";
      }
    }

    container adj-sid-sub-tlv-support {
      presence "Support of adj-sid sub-tlv.";
      description
        "Support of adjacency segment identifier sub-tlv (Type 31).";

      leaf tlv-22 {
        type isis-pics:support;
        description
          "May present in TLV-22, extended IS reachability.";
      }
      leaf tlv-222 {
        type isis-pics:support;
        description
          "May present in TLV-222, MT-ISN.";
      }
      leaf tlv-23 {
        type isis-pics:support;
        description
          "May present in TLV-23, IS neighbor attribute.";
      }
      leaf tlv-223 {
        type isis-pics:support;
        description
          "May present in TLV-223, MT IS neighbor attribute.";
      }
      leaf tlv-141 {
        type isis-pics:support;
        description
          "May present in TLV-141, inter-AS reachability information.";
      }
    }

    container lan-adj-sid-sub-tlv-support {
      presence "Support of lan-adj-sid sub-tlv.";
      description
        "Support of LAN adj-sid sub-tlv (Type 32).";

      leaf tlv-22 {
        type isis-pics:support;
        description
          "May present in TLV-22, extended IS reachability.";
      }
      leaf tlv-222 {
        type isis-pics:support;
        description
          "May present in TLV-222, MT-ISN.";
      }
      leaf tlv-23 {
        type isis-pics:support;
        description
          "May present in TLV-23, IS neighbor attribute.";
      }
      leaf tlv-223 {
        type isis-pics:support;
        description
          "May present in TLV-223, MT IS neighbor attribute.";
      }
    }

    leaf sid-label-tlv-support {
      type isis-pics:support;
      description
        "Support of sid/label sub-tlv (Type 1).";
    }

    container sid-label-binding-tlv-support {
      presence "Support of sid-label-binding sub-tlv.";
      description
        "Support of sid/label binding tlv (Type 149).";

      container srms {
        description
          "Support to advertise or receive prefix to sid/label
           mapping.";

        leaf sending {
          type isis-pics:support;
          description
            "Support to advertise SR mappings.";
        }
        leaf receiving {
          type isis-pics:support;
          description
            "Support to receive and use the MS mapping advertisement.";
        }
      }

      leaf mirror-sid {
        type isis-pics:support;
        description
          "Support to advertise a mirror sid indicating the ability
           of a node to process traffic originally destined to
           another IGP node.";
      }
    }

    container mt-sid-label-binding-tlv-support {
      presence "Support of multi-topology sid-label-binding sub-tlv.";
      description
        "Support of multi-topology sid/label binding tlv (Type 150).";

      container srms {
        description
          "Support to advertise or receive prefix to sid/label
           mapping.";

        leaf sending {
          type isis-pics:support;
          description
            "Support to advertise SR mappings.";
        }
        leaf receiving {
          type isis-pics:support;
          description
            "Support to receive and use the MS mapping advertisement.";
        }
      }

      leaf mirror-sid {
        type isis-pics:support;
        description
          "Support to advertise a mirror sid indicating the ability
           of a node to process traffic originally destined to
           another IGP node.";
      }
    }

    container sr-algorithm-tlv-support {
      presence "Support of SR-Algorithm sub-tlv.";
      description
        "Support of SR-Algorithm sub-tlv (Type 19).";

      leaf-list algo-support {
        type uint8;
        description
          "Supported algorithms.";
      }
    }

    leaf sr-lb-tlv-support {
      type isis-pics:support;
      description
       "Support of the SR Local Block sub-tlv (Type 22).";
    }

    leaf srms-preference-tlv-support {
      type isis-pics:support;
      description
       "Support of the SRMS Preference sub-tlv (Type 24).";
    }
  }

  augment "/isis-pics:isis-pics/isis-pics:isis-pics-mptlv"
  {
    description
      "Augment isis-pics-mptlv container with the tlvs defined
       in RFC 8667.";

    leaf sid-label-binding-support {
      type isis-pics:support;
      description
        "MP-TLV support of sid/label binding tlv (Type 149).";
    }

    leaf mt-sid-label-binding-support {
      type isis-pics:support;
      description
        "MP-TLV support of multi-topology sid/label
        binding tlv (Type 150).";
    }
  }
}
