module ietf-ose-reachability-svc {
  namespace "urn:ietf:params:xml:ns:yang:ietf-ose-reachability-svc";
  prefix reach-svc;

  import ietf-inet-types {
    prefix inet;
  }
  import ietf-yang-types {
    prefix yang;
  }

  feature ose-option-A {
    description
      "This feature means that ose reachability service option-A is supported by the Serving SDWAN manager";
    reference
      "ONUG-OSE-2 SDWAN Reachability and Segmentation Specification";
  }

  feature ose-option-B {
    description
      "This feature means that ose reachability service option-B is supported by the Serving SDWAN manager";
    reference
      "ONUG-OSE-2 SDWAN Reachability and Segmentation Specification";
  }

  container ose-gateways {
    list ose-gateway {
      key "gw-name";
      leaf gw-name {
        type string;
        description
          "OSE gateway name.";
      }
      leaf gw-id {
        type uint32;
        description
          "Identifier for Gateway.";
      }
      leaf ose-interworking-option {
        type enumeration {
          enum ose-option-A;
          enum ose-option-B;
        }
        description
          "OSE interworking options.";
      }
      leaf encap-type {
        type enumeration {
          enum IPSEC_TUNNEL;
          enum IPSEC_TRANSPORT;
          enum GRE;
        }
        description
          "encapsulation type of tunnel.";
      }
      leaf auth-type {
        type enumeration {
          enum PSK;
          enum PKI;
        }
        description
          "authentication type.";
      }
      leaf crypto {
        type enumeration {
          enum AES-128;
          enum AES-256;
          enum AES-256-GCM;
        }
        description
          "crypto algorithm type.";
      }
      list peer-list {
        key "name";
        leaf name {
          type string;
          description
            "peer index.";
        }
        leaf Local-gw-id {
          type uint32;
          description
            "Identifier for the local gateway.";
        }
        leaf peer-gw-id {
          type uint32;
          description
            "Identifier for the remote peer gateway.";
        }
        leaf peer-gw-name {
          type string;
          description
            "Name of remote peer gateway. ";
        }
        leaf authType {
          type enumeration {
            enum PSK;
            enum PKI;
          }
          description
            "authentication type.";
        }
        leaf crypto-option {
          type enumeration {
            enum AES-256;
            enum AES-128;
            enum AES-256-GCM;
          }
          description
            "Crypto algorithm selection. Others to be added";
        }
        leaf ose-interworking-option {
          type enumeration {
            enum ose-option-A;
            enum ose-option-B;
          }
          description
            "ose interworking options.";
        }
      }
      list segment-list {
        key "segment-name";
        leaf segment-name {
          type string;
          description
            "segment name.";
        }
        leaf vlan-id {
          type uint16;
          description
            "vlan ID.";
        }
        leaf vrf-id {
          type uint16;
          description
            "vrf ID.";
        }
        leaf segment-type {
          type enumeration {
            enum overlay;
            enum nsw;
          }
          description
            "segment type.";
        }
        container CrossConnects {
          leaf CCname {
            type string;
            description
              "cross connection name.";
          }
          leaf local-seg-name {
            type string;
            description
              "local segment name.";
          }
          leaf local-Seg-id-vlan {
            if-feature "ose-option-A";
            type uint16;
            description
              "local segment VLAN ID.";
          }
          leaf local-seg-id-vrf {
            if-feature "ose-option-B";
            type uint16;
            description
              "lcoal segment vrf ID.";
          }
          leaf peer-seg-name {
            type string;
            description
              "Peer segment name.";
          }
          leaf peer-seg-id-vlan {
            if-feature "ose-option-A";
            type uint16;
            description
              "Peer segment vlan ID.";
          }
          leaf peer-seg-id-vrf {
            if-feature "ose-option-B";
            type uint16;
            description
              "Peer Segment vrf ID.";
          }
        }
      }
      description
        "Segment List";
    }
    description
      "OSE gateway.";
  }
}
