module ietf-bgp-rib-ext {
  yang-version "1.1";
  namespace "urn:ietf:params:xml:ns:yang:ietf-bgp-rib-ext";

  prefix "bre";

  import ietf-routing {
    prefix "rt";
    reference
      "RFC 8349: YANG Routing Management.";
  }
  import ietf-bgp-rib {
    prefix bgprib;
  }
  import ietf-bgp-rib-types {
    prefix bgpribt;
  }

  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "Defines additional data nodes for the OpenConfig BGP RIB model.
     These items reflect extensions that are desirable features but
     are not currently supported in a majority of BGP
     implementations.";

  revision "2019-02-25" {
    description
      "Initial Revision.";
    reference
      "RFC XXXX: BGP YANG Model for Service Providers.";
  }

  grouping rib-ext-route-annotations {
    description
      "Extended annotations for routes in the routing tables";

    leaf reject-reason {
      type union {
        type identityref {
          base bgpribt:bgp-not-selected-bestpath;
        }
        type identityref {
          base bgpribt:bgp-not-selected-policy;
        }
      }
      description
        "Indicates the reason the route is not used, either due to
        policy filtering or bestpath selection";
    }
  }

  augment "/rt:routing/rt:ribs/bgprib:rib/bgprib:afi-safis/" +
    "bgprib:afi-safi/bgprib:ipv4-unicast/bgprib:loc-rib/" +
    "bgprib:routes/bgprib:route" {
      description
        "Add extended annotations to the Loc-RIB for IPv4";

      uses rib-ext-route-annotations;
  }

  augment "/rt:routing/rt:ribs/bgprib:rib/bgprib:afi-safis/" +
    "bgprib:afi-safi/bgprib:ipv6-unicast/bgprib:loc-rib/" +
    "bgprib:routes/bgprib:route" {
      description
        "Add extended annotations to the Loc-RIB for IPv6";

      uses rib-ext-route-annotations;
  }

  augment "/rt:routing/rt:ribs/bgprib:rib/bgprib:afi-safis/" +
    "bgprib:afi-safi/bgprib:ipv4-unicast/" +
    "bgprib:neighbors/bgprib:neighbor/" +
    "bgprib:adj-rib-in-pre/bgprib:routes/bgprib:route" {
      description
        "Add extended annotations to Adj-RIB for IPv4";

      uses rib-ext-route-annotations;
  }

  augment "/rt:routing/rt:ribs/bgprib:rib/bgprib:afi-safis/" +
    "bgprib:afi-safi/bgprib:ipv4-unicast/" +
    "bgprib:neighbors/bgprib:neighbor/" +
    "bgprib:adj-rib-in-post/bgprib:routes/bgprib:route" {
      description
        "Add extended annotations to Adj-RIB for IPv4";

      uses rib-ext-route-annotations;
  }

  augment "/rt:routing/rt:ribs/bgprib:rib/bgprib:afi-safis/" +
    "bgprib:afi-safi/bgprib:ipv4-unicast/" +
    "bgprib:neighbors/bgprib:neighbor/" +
    "bgprib:adj-rib-out-pre/bgprib:routes/bgprib:route" {
      description
        "Add extended annotations to Adj-RIB for IPv4";

      uses rib-ext-route-annotations;
  }

  augment "/rt:routing/rt:ribs/bgprib:rib/bgprib:afi-safis/" +
    "bgprib:afi-safi/bgprib:ipv4-unicast/" +
    "bgprib:neighbors/bgprib:neighbor/" +
    "bgprib:adj-rib-out-post/bgprib:routes/bgprib:route" {
      description
        "Add extended annotations to Adj-RIB for IPv4";

      uses rib-ext-route-annotations;
  }

  augment "/rt:routing/rt:ribs/bgprib:rib/bgprib:afi-safis/" +
    "bgprib:afi-safi/bgprib:ipv6-unicast/" +
    "bgprib:neighbors/bgprib:neighbor/" +
    "bgprib:adj-rib-in-pre/bgprib:routes/bgprib:route" {
      description
        "Add extended annotations to Adj-RIB for IPv6";

      uses rib-ext-route-annotations;
  }
  augment "/rt:routing/rt:ribs/bgprib:rib/bgprib:afi-safis/" +
    "bgprib:afi-safi/bgprib:ipv6-unicast/" +
    "bgprib:neighbors/bgprib:neighbor/" +
    "bgprib:adj-rib-in-post/bgprib:routes/bgprib:route" {
      description
        "Add extended annotations to Adj-RIB for IPv6";

      uses rib-ext-route-annotations;
  }

  augment "/rt:routing/rt:ribs/bgprib:rib/bgprib:afi-safis/" +
    "bgprib:afi-safi/bgprib:ipv6-unicast/" +
    "bgprib:neighbors/bgprib:neighbor/" +
    "bgprib:adj-rib-out-pre/bgprib:routes/bgprib:route" {
      description
        "Add extended annotations to Adj-RIB for IPv6";

      uses rib-ext-route-annotations;
  }

  augment "/rt:routing/rt:ribs/bgprib:rib/bgprib:afi-safis/" +
    "bgprib:afi-safi/bgprib:ipv6-unicast/" +
    "bgprib:neighbors/bgprib:neighbor/" +
    "bgprib:adj-rib-out-post/bgprib:routes/bgprib:route" {
      description
        "Add extended annotations to Adj-RIB for IPv6";

      uses rib-ext-route-annotations;
  }
}
