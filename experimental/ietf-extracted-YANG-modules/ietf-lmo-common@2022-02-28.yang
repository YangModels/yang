module ietf-lmo-common {
  namespace "urn:ietf:params:xml:ns:yang:ietf-lmo-common";
  prefix ietf-lmo-common;
  organization
    "IETF OPSA (Operations and Management Area) Working Group";
  contact
    "WG Web:   <https://datatracker.ietf.org/wg/opsawg/>
     WG List:  <mailto:opsawg@ietf.org>
     Editor:  Marisol Palmero
              <mailto:mpalmero@cisco.com>
     Editor:  Josh Suhr
              <mailto:josuhr@cisco.com>
     Editor:  Sudhendu Kumar
              <mailto:skumar23@ncsu.edu>";
  description
    "This YANG module defines a collection of useful data types
     and identity for Lifecycle Management and Operations (LMO).

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.";

  revision 2022-02-28 {
    description
      "Introduced flexible root structure";
    reference
      "RFC XXXX: LMO YANG Model";
  }
  revision 2021-08-23 {
    description
      "Initial revision for Common Module as part of the LMO
       YANG Model";
    reference
      "RFC XXXX: LMO YANG Model";
  }

  typedef license-id-t {
    type string;
    description
      "License ID Type";
  }
  typedef license-model-t {
    type enumeration {
      enum perpetual {
        description
          "Perpetual license";
      }
      enum subscription {
        description
          "Subscription license";
      }
      enum usage-based {
        description
          "Usage-based license";
      }
      enum other {
        description
          "Undefined license type";
      }
    }
    description
      "License Model Type";
  }
  identity license-buying-program-t {
    description
      "License Buying Program that contains the plan to generate
       revenue for specific asset";
  }
  identity enterprise-agreement {
        base license-buying-program-t;
        description
          "Enterprise Agreement";
  }
  identity managed-service-license-agreement {
        base license-buying-program-t;
        description
          "Managed Service License Agreement";
  }
  identity service-provider-network-agreement {
        base license-buying-program-t;
        description
          "Service Provider Network Agreement";
  }
  identity collab-active-user {
        base license-buying-program-t;
        description
          "Collaboration Active User";
  }
  identity service-full-coverage {
        base license-buying-program-t;
        description
          "Service Full-Coverage";
  }
  identity offer-type-t {
    description
      "License Offer Type, part of the plan to generate revenue
       for specific asset";
  }
  identity perpetual-software {
      base offer-type-t;
      description
          "Perpetual softwar gives the user the right to use the
           program indefinitely";
  }
  identity standalone-hardware {
      base offer-type-t;
      description
          "Standalone hardware is able to function independently
           of other hardware";
  }
  identity on-premise-software-subscription {
      base offer-type-t;
      description
          "On-Premise software subscription, relates to a temporary
           on-prem licencing model, allowing users to pay a per user
           fee";
  }
  identity cloud-software-saas-subscription {
      base offer-type-t;
      description
          "Cloud Software (SaaS) subscription is a service busines
           model where the user is entitled to use the cloud software
           for a specific time period";
  }
  identity third-party-software {
      base offer-type-t;
      description
          "It includes licenses, agreements, obligations or other
          commitment under which the user can use the asset not
          directly sold by the manufacturer";
  }
  identity flex-cloud-prem-subscription {
      base offer-type-t;
      description
          "Flex Cloud-Prem subscription allows software vendros to
          limit the number of licenses for the use of the specific
          asset";
  }
  typedef license-key-t {
    type string;
    description
      "License Key Type";
  }
  typedef purchase-order-t {
    type string;
    description
      "License purchase order number";
  }
  typedef license-state-t {
    type enumeration {
      enum inactive {
        description
          "Inactive State";
      }
      enum active {
        description
          "Active State";
      }
      enum unknown {
        description
          "Unknown State";
      }
    }
    description
      "License State Type";
  }

  typedef asset-id {
    type string;
    description
      "Asset ID Type";
  }

  typedef vendor-id {
    type enumeration {
      enum cisco {
        description
          "Vendor-id is Cisco";
      }
      enum other {
        description
          "Vendor-id is not determined";
      }
    }
    description
      "Vendor identifier";
  }

  identity asset-type {
    description
      "type of the asset: hardware, software, software cloud, ...";
  }
  identity hw {
    base asset-type;
    description
      "Hardware refers to any physical device";
  }
  identity sw {
    base asset-type;
    description
      "Software refers to a collection of code installed on a
      hardware asset";
  }
  identity sw-cloud {
    base asset-type;
    description
      "Cloud-based software, that allows users access to software
      application that run on a shared computing resources via
      Internet";
  }
  identity phone {
    base asset-type;
    description
      "Mobile telephone or a handheld two-way communication device
      over a cellular network.";
  }
  identity other {
    base asset-type;
    description
      "Different or additional type not specified as part of another
      defined asset-type.";
  }
  identity asset-subtype {
    description
      "subtype of the asset: router, switch, wireless,
      controller, ...";
  }
  identity router {
    base asset-subtype;
    description
      "Network connecting device. It operates at layer-3 of the OSI
      model.";
  }
  identity switch {
    base asset-subtype;
    description
      "Network connecting device. It operates at layer-2(Data Link
      Layer) of the OSI model.";
  }
  identity wireless {
    base asset-subtype;
    description
      "Network connecting device. It creates a wireless local area
      network. It connects to a wired router, switch, or hub via an
      Ethernet cable, and projects a Wi-Fi signal to a designated
      area";
  }
  identity controller {
    base asset-subtype;
    description
      "Centralized device in the network which is used in combination
      with network connection devices, when there is a need to manage
      them in large quantities.";
  }
  identity board {
    base asset-subtype;
    description
      "Electronic circuit board in an asset which interconnects
      another hardware assets attached to it.";
  }
  identity p-supply {
    base asset-subtype;
    description
      "Power supply, as it might have independent identity.";
  }
  identity transceiver {
    base asset-subtype;
    description
      "Device that is both a transmitter and a receiver. Usually
      it's in a single device.
      This is commonly used as a modular network interface";
  }
  identity others {
    base asset-subtype;
    description
      "Different or additional type not specified as part of another
      defined asset-subtype.";
  }
  identity version {
    description
      "Base identity for all version types";
  }
  identity version-sw {
  base version;
    description
      "Version release of the operating system that runs on the
      asset";
  }
  identity platform-dependency-os {
    description
      "Operating system that creates an environment for the asset
       to get deployed. Enum of options covering OS platform
       dependency.";
  }
  identity linux {
    base platform-dependency-os;
    description
      "UNIX like operating system";
  }
  identity windows {
    base platform-dependency-os;
    description
      "Windows operating system";
  }
  identity macOS {
    base platform-dependency-os;
    description
      "Mac operating system develop by Apple, Inc.";
  }
  identity darwin {
    base platform-dependency-os;
    description
      "Open-source Unix-like operating system first released by Apple
      Inc.";
  }
  identity ubuntu {
    base platform-dependency-os;
    description
      "Linux distribution, used in desktop distribution";
  }
  identity red-hat {
    base platform-dependency-os;
    description
      "Red Hat Enterprise Linux, released in multiple server and
      desktop versions";
  }
// NEED to extend and include iOS, Android, etc.;

  identity role {
    description
      "What the role of a given device/component is in the network.
      This attribute normally will be configured on the specific
      component during setup. This attribute normally will be
      configured on the specific component during setup";
  }
  identity border-router {
    base role;
    description
      "Router that provides connectivity between interior and
      exterior network routers or to the cloud";
  }
  identity access {
    base role;
    description
      "Router that provides access to a larger communication network
      of some sort.";
  }
  identity control-plane {
    base role;
    description
      "Network component that controls how data packets are
      forwarded";
  }
  identity edge {
    base role;
    description
      "Router that provides an entry point into enterprise or service
      provider core networks";
  }
  identity core {
    base role;
    description
      "Component part of the high-speed backbone of the network. It
      provides fast and efficient data transport";
  }
  identity datacenter {
    base role;
    description
      "Component placed in the data center, mantaining and housing
      back-end IT system and data stores";
  }
  identity branch {
    base role;
    description
      "Router in a remote branch of an enterprise's network";

  }
  identity deployment-mode {
    description
      "This attribute will denote the configured deployment mode
       for the asset and features, if applicable; e.g.,
       High Availability(HA) or Faiover cluster, virtual appliance,
       etc.";
  }
  identity primary {
    base deployment-mode;
    description
      "Asset or featurs that support critical applications to
      minimize system downtime, to achieve high availabiilty or
      failover";
  }
  identity secondary {
    base deployment-mode;
    description
      "Redundant asset or feature, that is triggered when the
      primary encounters performance issues, to achieve high
      availability or failover";
  }
  identity cloud {
    base deployment-mode;
    description
      "Especially it refers to remote, distributed and shared asset
      resources (i.e. data storage, computing power, etc.), which
      are hooked together and meant to operate as a single
      ecosystem.";
  }
  identity virtual-appliance {
    base deployment-mode;
    description
      "pre-configured virtual machine image, ready to run on a
      hypervisor";
  }
  identity container {
    base deployment-mode;
    description
      "Standard unit of software that packages up code and all its
      dependencies so the application runs quickly and reliably from
      one computing environment to another";

  }
  identity undeployed {
    base deployment-mode;
    description
      "it refers to an asset that is undeployed";

  }
  identity counter-type {
    description
      "Specify the different type of counters, i.e accumulated-count,
       average-count, last-count, high-water mark count, low-water
       mark count" ;
  }
  identity accumulated {
    base counter-type;
    description
      "monotonically increasing counters. They're useful for
       aggregating metric information such as the number of hits
       on a web page, how many users log into a portal, etc.";
  }
  identity average {
    base counter-type;
    description
      "typical value in a set of metrics, in particular the mean,
      which is calculated by dividing the sum of the values in the
      set by their number.";
  }
  identity last {
    base counter-type;
    description
      "Last value measured and collected for specific metric.";
  }
  identity high-water-mark {
    base counter-type;
    description
      "Highest level of value in a set of metrics.";
  }
  identity low-water-mark {
    base counter-type;
    description
      "Lowest level of value in a set of metrics.";
  }
  identity feature-scope {
    description
      "Optional tag that could apply to any usage feature, so that
       if there are multiple dimensions of reporting that need to
       be accommodated (i.e., report feature usage by 'site')";
  }
  identity site {
    base feature-scope;
    description
      "Single location, part of the network";
  }
  identity network {
    base feature-scope;
    description
      "scope limited to the networking assets";
  }
  typedef feature-usage-type {
    type enumeration {
      enum none {
        description
          "No Usage";
      }
      enum low {
        description
          "Usage meeting the Low Threshold";
      }
      enum medium {
        description
          "Usage meeting the Medium Threshold";
      }
      enum high {
        description
          "Usage meeting the High Threshold";
      }
      // NEED to elaborate more on this list, based on use case
      // validation
    }
    description
      "feature usage % 0-25-50-75-100";
  }

  identity lmo-class {
    description "Base identity for classes of LMOs";
  }
}
