module l2-topology {
    yang-version 1;
    namespace "urn:TBD:params:xml:ns:yang:nt:l2-topology";
    // replace with IANA namespace when assigned
    prefix "l2t";
    import network-topology {
        prefix "nt";
    }

    import ietf-inet-types {
        prefix "inet";
    }

    import ietf-yang-types {
        prefix "yang";
    }

    organization "TBD";
    contact "TBD";

    revision "2014-10-21" {
        description "Initial revision";
        reference "TBD";
    }

    typedef vlan {
        description "VLAN ID";
        type uint32 {
            range "1..4095";
        }
    }

    identity flag-identity {
        description "Base type for flags";
    }

    typedef flag-type {
        type identityref {
            base "flag-identity";
        }
    }

    grouping l2-topology-type {
        container l2-topology {
            presence "indicates L2 Topology";
        }
    }

    grouping l2-topology-attributes {
        container l2-topology-attributes {
            leaf name {
                description "Name of the topology";
                type string;
            }
            leaf-list flag {
                description "Topology flags";
                type flag-type;
            }
        }
    }

    grouping l2-node-attributes {
        container l2-node-attributes {
            leaf name {
                description "Node name";
                type string;
            }
            leaf description {
                description "Node description";
                type string;
            }
            leaf chassis-id {
                description "System MAC address";
                type yang:mac-address;
            }
            leaf-list management-address {
                description "System management address";
                type inet:ip-prefix;
            }
            leaf management-vid {
                description "System management VID";
                type vlan;
            }
            leaf capabilities-support {
                description "System capabilities";
                type bits {
                    bit other {
                        position 1;
                    }
                    bit mac-bridge {
                        position 2;
                    }
                    bit router {
                        position 3;
                    }
                }
            }
            leaf capabilities-enable {
                description "System enabled capabilities";
                type bits {
                    bit other {
                        position 1;
                    }
                    bit mac-bridge {
                        position 2;
                    }
                    bit router {
                        position 3;
                    }
                }
            }
            leaf-list flag {
                description "Node operational flags";
                type flag-type;
            }
        }
    }

    grouping l2-link-attributes {
        container l2-link-attributes {
            leaf name {
                description "Link Name";
                type string;
            }
            leaf rate {
                description "Link rate";
                type decimal64 {
                 fraction-digits 2;
                }
            }
            leaf-list flag {
                description "Link flags";
                type flag-type;
            }
        }
    } // grouping l2-link-attributes

    grouping l2-termination-point-attributes {
        container l2-termination-point-attributes {
             leaf description {
                description "Port description";
                type string;
             }
             leaf mac-address {
                 description "Interface MAC address";
                 type yang:mac-address;
             }
             leaf port-vlan-id {
                  description "Port VLAN ID";
                 type vlan;
             }
             container ppvid {
                  description "Port and protocol VLAN ID";
                  leaf ppvid {
                      type vlan;
                  }
                  leaf ppvid-flags {
                      type bits {
                          bit port-protocol-vlan-supported {
                               position 1;
                          }
                          bit port-protocol-vlan-enabled {
                              position 2;
                          }
                      }
                  }
             }
             list vlan-name {
                 key "vlan-id";
                 description "Interface configured VLANs";
                 leaf vlan-id {
                     type vlan;
                 }
                 leaf vlan-name {
                     type string;
                 }
             }
             leaf auto-negotiation {
                 type bits {
                     bit auto-negotiation-support {
                         position 0;
                     }
                     bit auto-negotiation-enable {
                         position 1;
                     }
                 }
             }
             container link-aggregation {
                 leaf aggregation-status {
                     description "Link aggregation capabilities and status";
                     type bits {
                         bit aggregation-capability {
                             position 0;
                         }
                         bit aggregation-status {
                             position 1;
                         }
                     }
                 }
                 leaf aggregated-port-id {
                     type string;
                 }
             }
             leaf oper-mau {
                 type bits {
                     bit bother {
                         position 0;
                     }
                     bit b10base-t {
                         position 1;
                     }
                     bit b10base-tfd {
                         position 2;
                     }
                     bit b100base-t4 {
                         position 3;
                     }
                     bit b100base-tx {
                         position 4;
                     }
                     bit b100base-txfd {
                         position 5;
                     }
                     bit b100base-t2 {
                         position 6;
                     }
                     bit b100base-t2fd {
                         position 7;
                     }
                     bit bfdx-pause {
                         position 8;
                     }
                     bit bfdx-apause {
                         position 9;
                     }
                     bit bfdx-spause {
                         position 10;
                     }
                     bit bfdx-bpause {
                         position 11;
                     }
                     bit b1000base-X {
                         position 12;
                     }
                     bit b1000base-xfd {
                         position 13;
                     }
                     bit b1000base-t {
                         position 14;
                     }
                     bit b1000base-tfd {
                         position 15;
                     }
                 }
             }
             leaf maximum-frame-size {
                description "interface maximum frame size";
                type uint32;
             }
        }
    } // grouping l2-termination-point-attributes

    augment "/nt:network-topology/nt:topology/nt:topology-types" {
        uses l2-topology-type;
    }

    augment "/nt:network-topology/nt:topology" {
        when "nt:topology-types/l2-topology";
        uses l2-topology-attributes;
    }

    augment "/nt:network-topology/nt:topology/nt:node" {
        when "../nt:topology-types/l2-topology";
        uses l2-node-attributes;
    }
    augment "/nt:network-topology/nt:topology/nt:link" {
        when "../nt:topology-types/l2-topology";
        uses l2-link-attributes;
    }
    augment "/nt:network-topology/nt:topology/nt:node/nt:termination-point" {
        when "../../nt:topology-types/l2-topology";
        uses l2-termination-point-attributes;
    }
}
