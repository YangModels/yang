module ietf-l2-topology {
    yang-version 1;
    namespace "urn:ietf:params:xml:ns:yang:ietf-l2-topology";
    prefix "l2t";

    import network {
        prefix "nt";
    }

    import network-topology {
        prefix "ntopo";
    }

    import ietf-inet-types {
        prefix "inet";
    }

    import ietf-yang-types {
        prefix "yang";
    }

    organization "TBD";
    contact "I-D Editor: jie.dong@huawei.com";

    description
      "This module defines a model for the layer-2 topology of a network";

    revision "2015-04-22" {
        description "Initial revision";
        reference "draft-ietf-i2rs-yang-l2-network-topology-00";
    }

   /*
    * Typedefs
    */

    typedef vlan {
        description "VLAN ID";
        type uint16 {
            range "0..4095";
        }
    }

    typedef nickname {
        description "TRILL Nickname";
        type uint16;
    }

    typedef flag-type {
        type identityref {
            base "flag-identity";
        }
    }

    /*
    * Features
    */

    feature QinQ {
        description
          "Indicates that the system supports the qinq functions";
    }

    feature PBB {
        description
         "Indicates that the device supports the
          provider-backbone-bridging functions";
    }

    feature VPLS {
        description
          "Indicates that the device supports the VPLS functions";
        reference "RFC 4761, RFC 4762";
    }

    feature TRILL {
        description
          "Indicates that the device supports the TRILL functions";
        reference "RFC 6325";
    }

    feature VXLAN {
        description
          "Indicates that the device supports the VXLAN functions";
        reference "RFC 7348";
    }

   /*
    * Identities
    */

    identity flag-identity {
        description "Base type for flags";
    }

    identity encapsulation-type {
        description
          "Base identity from which specific encapsulation types are
           derived.";
    }

    identity ethernet {
        base encapsulation-type;
        description
          "native ethernet encapsulation";
    }

    identity vlan {
        base encapsulation-type;
        description
          "vlan encapsulation";
    }

    identity qinq {
        base encapsulation-type;
        description
          "qinq encapsulation";
    }

    identity pbb {
        base encapsulation-type;
        description
          "pbb encapsulation";
    }

    identity trill {
        base encapsulation-type;
        description
          "trill encapsulation";
    }

    identity vpls {
        base encapsulation-type;
        description
          "vpls encapsulation";
    }

    identity vxlan {
        base encapsulation-type;
        description
          "vxlan encapsulation";
    }

   /*
    * Groupings
    */

    grouping l2-network-type {
        container l2-network {
            presence "indicates L2 Network";
        }
    }

    grouping l2-network-attributes {
        container l2-network-attributes {
            leaf name {
                description "Name of the network";
                type string;
            }

            leaf-list flag {
                description "L2 network flags";
                type flag-type;
            }
        }
    }

    grouping l2-node-attributes {
        container l2-node-attributes {
            leaf name {
                description "Node name";
                type string;
            }
            leaf description {
                description "Node description";
                type string;
            }
            leaf chassis-id {
                description "System MAC address";
                type yang:mac-address;
            }
            leaf-list management-address {
                description "System management address";
                type inet:ip-prefix;
            }

            leaf management-vid {
                description "System management VID";
                type vlan;
            }

            leaf nick-name {
                if-feature TRILL;
                description "Nickname of RBridge";
                type nickname;
            }

            leaf-list flag {
                description "Node operational flags";
                type flag-type;
            }
        }
    }  // grouping l2-node-attributes

    grouping l2-link-attributes {
        container l2-link-attributes {
            leaf name {
                description "Link name";
                type string;
            }
            leaf rate {
                description "Link rate";
                type decimal64 {
                    fraction-digits 2;
                }
            }
            leaf-list flag {
                description "Link flags";
                type flag-type;
            }

        }
    } // grouping l2-link-attributes

    grouping l2-termination-point-attributes {
        container l2-termination-point-attributes {
             leaf description {
                 description "Port description";
                 type string;
             }
             leaf mac-address {
                 description "Interface MAC address";
                 type yang:mac-address;
             }
             leaf port-vlan-id {
                 description "Port VLAN ID";
                 type vlan;
             }

             container ppvid {
                 description "Port and protocol VLAN ID";
                 leaf ppvid {
                     type vlan;
                 }
                 leaf ppvid-flags {
                     type bits {
                         bit port-protocol-vlan-supported {
                             position 1;
                         }
                         bit port-protocol-vlan-enabled {
                             position 2;
                         }
                     }
                 }
             }

             list vlan-name {
                 key "vlan-id";
                 description "Interface configured VLANs";
                 leaf vlan-id {
                     type vlan;
                 }
                 leaf vlan-name {
                     type string;
                 }
             }

             leaf encapsulation {
                 description "encapsulation type of this termination point.";
                 type identityref {
                     base encapsulation-type;
                 }
             }

             leaf maximum-frame-size {
                 description "interface maximum frame size";
                 type uint32;
             }

             container link-aggregation {
                 leaf aggregation-status {
                     description "Link aggregation capabilities and status";
                     type bits {
                         bit aggregation-capability {
                             position 0;
                         }
                         bit aggregation-status {
                             position 1;
                         }
                     }
                 }
                 leaf aggregated-port-id {
                     type string;
                 }
             }

             leaf tp-state {
                 config false;
                 type enumeration {
                     enum "forwarding" {
                         value 0;
                         description
                           "the termination point is in forwarding state";
                     }
                     enum "blocking" {
                         value 1;
                           description
                             "the termination point is in blocking state";
                     }
                     enum "others" {
                         value 2;
                           description
                             "the termination point is in other state";
                     }
                 }
             }
        }
    } // grouping l2-termination-point-attributes

   /*
    * Data nodes
    */

    augment "/nt:network/nt:network-types" {
        uses l2-network-type;
    }

    augment "/nt:network" {
        when "nt:network-types/l2-network";
        uses l2-network-attributes;
    }

    augment "/nt:network/nt:node" {
        when "../nt:network-types/l2-network";
        uses l2-node-attributes;
    }

    augment "/nt:network/ntopo:link" {
        when "/nt:network/nt:network-types/l2-network";
        uses l2-link-attributes;
    }

    augment "/nt:network/nt:node/ntopo:termination-point" {
        when "/nt:network/nt:network-types/l2-network";
        uses l2-termination-point-attributes;
    }

   /*
    * Notifications: to be added
    */

}  // module l2-topology
