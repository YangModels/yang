module sensor {
  yang-version 1.1;
  namespace "http://sensorexample.in/sensor-example";
  prefix sen1;

  organization
    "Internet Engineering Task Force (IETF), CORE Working Group.";

  contact
    "CORE Working Group.";

  description
    "An illustrative YANG module used to demonstrate the
     serialization of a physical object with battery status,
     an LED indicator, and attached sensors.";

  revision 2026-11-02 {
    description
      "Initial revision.";
    reference
      "draft-toutain-core-sid-extension-00";
  }

  identity battery-indicator-base-type {
    description
      "Base identity for battery level indicators.";
  }

  identity high-level {
    base battery-indicator-base-type;
    description
      "Indicates a high battery level.";
  }

  identity med-level {
    base battery-indicator-base-type;
    description
      "Indicates a medium battery level.";
  }

  identity low-level {
    base battery-indicator-base-type;
    description
      "Indicates a low battery level.";
  }

  typedef battery-level {
    type identityref {
      base battery-indicator-base-type;
    }
    description
      "Represents the battery level using an identity.";
  }

  container sensorObject {
    description
      "Represents a physical object containing sensors.";

    leaf statusLED {
      type enumeration {
        enum green {
          value 0;
          description "Green LED indicator.";
        }
        enum yellow {
          value 1;
          description "Yellow LED indicator.";
        }
        enum red {
          value 2;
          description "Red LED indicator.";
        }
      }
      description
        "Indicates the status LED color.";
    }

    leaf battery {
      type battery-level;
      description
        "Indicates the battery level.";
    }

    list sensorReadings {
      key "index";
      description
        "Contains measurements from attached sensors.";

      leaf index {
        type uint8;
        description
          "Identifies the sensor reading.";
      }

      leaf sensorValue {
        type uint32;
        description
          "Contains the integer sensor measurement.";
      }
    }
  }
}
