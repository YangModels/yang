module ietf-yl-packages {
  yang-version 1.1;
  namespace "urn:ietf:params:xml:ns:yang:ietf-yl-packages";
  prefix yl-pkgs;

  import ietf-yang-revisions {
    prefix rev;
    reference "RFC XXXX: Updated YANG Module Revision Handling";
  }

  import ietf-yang-semver  {
    prefix ys;
    reference "RFC XXXX: YANG Semantic Versioning";
  }

  import ietf-yang-package-types {
    prefix pkg-types;
    ys:recommended-min-version 0.10.0;
    reference "RFC XXXX: YANG Packages";
  }

  import ietf-yang-packages {
    prefix pkgs;
    ys:recommended-min-version 0.10.0;
    reference "RFC XXXX: YANG Packages";
  }

  import ietf-yang-library {
    prefix yanglib;
    rev:recommended-min-date 2019-01-04;
    reference "RFC 8525: YANG Library";
  }

  organization
    "IETF NETMOD (Network Modeling) Working Group";

  contact
    "WG Web:   <https://datatracker.ietf.org/wg/netmod/>
     WG List:  <mailto:netmod@ietf.org>
     Editor:   Robert Wilton
               <mailto:rwilton@cisco.com>";

  description
    "This module provides defined augmentations to YANG library to
     allow a server to report YANG package information.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,

     they appear in all capitals, as shown here.";

  revision 2026-07-06 {
    ys:version 0.10.0;
    description
      "Initial revision";
    reference
      "RFC XXXX: YANG Packages";
  }

  /*
   * Augmentations
   */

  augment "/yanglib:yang-library/yanglib:schema" {
    description
      "Allow datastore schema to be related to a set of YANG
       packages.

       Features enabled by the server in addition to the mandatory
       features from the package definitions are listed in the
       'feature' list.
       ";

    list package {
      key "name version";
      ordered-by user;

      description
        "Identifies the YANG packages that collectively define the
         schema for the associated datastore.

         The referenced packages are resolved as if they were all
         directly included in a single package definition, as
         described in RFC XXXX, Section 5.4.3.

         The resolved datastore schema MUST be referentially
         complete.";
      reference
        "RFC XXXX: YANG Packages, Section 5.4.3";

      uses pkgs:yang-pkg-ref;
      uses pkg-types:yang-pkg-location;
    }

    leaf-list feature {
      type pkg-types:scoped-feature;
      description
        "The name of YANG features enabled by the server in addition
         to the enabled features from the resolved package
         definitions associated with this datastore schema.

         Although this list identifies additional features rather
         than the complete set of supported features, features
         already enabled by the resolved packages MAY be listed.

         The features listed here MUST be defined by implemented
         modules in the datastore schema.

         Features are identified using <module-name>:<feature-name>.

         This list, combined with the enabled features from the
         resolved package schemas, MUST be equivalent to the
         list of supported features advertised in YANG library.";
    }
  }
}
