module ietf-data-export-capabilities {
  yang-version 1.1;
  namespace "urn:ietf:params:xml:ns:yang:ietf-data-export-capabilities";
  prefix dec;

  import ietf-system-capabilities {
    prefix sysc;
  }
  import ietf-notification-capabilities {
    prefix inc;
  }
  organization
    "IETF NETCONF (Network Configuration) Working Group";
  contact
    "WG Web:   <https://tools.ietf.org/wg/netconf/>
     WG List:  <mailto:netconf@ietf.org>
     Editor:   Qin Wu <mailto:bill.wu@huawei.com>
     Editor:   Qiufang Ma <mailto: maqiufang1@huawei.com>
     Editor:   Peng Liu <mailto: liupengyjy@chinamobile.com>
     Editor:   Wei Wang <mailto: wangw36@chinatelecom.cn>";
  description
    "This module defines an extension to System Capability and YANG Push
     Notification Capabilities model and provides additional data export
     attributes for transport specific notification.

     Copyright (c) 2019 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";

  revision 2020-07-03 {
    description
      "Initial revision.";
    reference
      "RFC XXXX: Telemetry Data Export capability";
  }

  identity transport-protocol {
    description
      "Base identity for transport protocol type.";
  }

  identity tcp {
    base transport-protocol;
    description
      "Identity for tcp as transport protocol.";
  }

  identity udp-notif {
    base transport-protocol;
    description
      "Identity for udp notif as transport protocol.";
    reference
      "draft-ietf-netconf-udp-notif:UDP-based Transport
       for Configured Subscriptions";
  }

  identity http-notif {
    base transport-protocol;
    description
      "Identity for http notif as transport protocol.";
    reference
      "draft-ietf-netconf-https-notif: An HTTPS-based
       Transport for Configured Subscriptions";
  }

  identity grpc {
    base transport-protocol;
    description
      "Identity for grpc as transport protocol.";
  }

  identity security-protocol {
    description
      "Base identity for security protocol type.";
  }

  identity tls {
    base security-protocol;
    description
      "Identity for tls security protocol.";
  }

  identity dtls {
    base security-protocol;
    description
      "Identity for dtls security protocol.";
  }

  identity ssh {
    base security-protocol;
    description
      "Identity for ssh transport protocol.";
  }

  identity encoding-format {
    description
      "Base identity for encoding format type.";
  }

  identity xml {
    base encoding-format;
    description
      "Identity for xml encoding format.";
  }

  identity json {
    base encoding-format;
    description
      "Identity for json encoding format.";
  }

  identity binary {
    base encoding-format;
    description
      "Identity for binary encoding format.";
  }

  identity cbor {
    base binary;
    description
      "Identity for cbor encoding format.";
  }

  augment "/sysc:system-capabilities" {
    description
      "Add system level capability.";
    container data-export-capabilities {
      description
        "Capabilities related to data export notification capabilities negotiation.";
      list data-export-capability {
        description
          "Capability list related to data export notification capabilities negotiation.";
        leaf transport-protocol {
          type identityref {
            base transport-protocol;
          }
          description
            "Type of transport protocol.";
        }
        leaf-list encoding-format {
          type identityref {
            base encoding-format;
          }
          description
            "Type of encoding format.";
        }
        leaf security-protocol {
          type identityref {
            base security-protocol;
          }
          description
            "Type of secure transport.";
        }
        leaf message-bundling-support {
          type empty;
          description
            "Enables message bundling support.";
        }
      }
    }
  }
}
