module ietf-vpn-common {
  yang-version 1.1;
  namespace "urn:ietf:params:xml:ns:yang:ietf-vpn-common";
  prefix vpn-common;

  import ietf-netconf-acm {
    prefix nacm;
    reference
      "RFC 8341: Network Configuration Access Control Model";
  }
  import ietf-routing-types {
    prefix rt-types;
    reference
      "RFC 8294: Common YANG Data Types for the Routing Area";
  }
  import ietf-yang-types {
    prefix yang;
    reference
      "RFC 6991: Common YANG Data Types, Section 3";
  }
  import ietf-packet-fields {
    prefix packet-fields;
    reference
      "RFC 8519: YANG Data Model for Network Access
                 Control Lists (ACLs)";
  }

  organization
    "IETF OPSA (Operations and Management Area) Working Group";
  contact
    "WG Web:   <https://datatracker.ietf.org/wg/opsawg/>
     WG List:  <mailto:opsawg@ietf.org>

     Author:  Samier Barguil
              <mailto:samier.barguilgiraldo.ext@telefonica.com>
     Author:  Oscar Gonzalez de Dios
              <mailto:oscar.gonzalezdedios@telefonica.com>
     Editor:  Mohamed Boucadair
              <mailto:mohamed.boucadair@orange.com>
     Author:  Qin Wu
              <mailto:bill.wu@huawei.com>";
  description
    "This YANG module defines a common module that is meant
     to be reused by various VPN-related modules (e.g.,
     Layer 3 VPN Service Model (L3SM), Layer 2 VPN Service
     Model (L2SM), Layer 3 VPN Network Model (L3NM), Layer 2
     VPN Network Model (L2NM)).

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2021-04-08 {
    description
      "Initial revision.";
    reference
      "RFC XXXX: A Layer 2/3 VPN Common YANG Model";
  }

  /******** Collection of VPN-related Features ********/
  /*
   * Features related to encapsulation schemes
   */

  feature dot1q {
    description
      "Indicates the support of the Dot1q encapsulation.";
    reference
      "IEEE Std 802.1Q: Bridges and Bridged Networks";
  }

  feature qinq {
    description
      "Indicates the support of the QinQ encapsulation.";
    reference
      "IEEE Std 802.1ad: Provider Bridges";
  }

  feature vxlan {
    description
      "Indicates the support of the Virtual eXtensible
       Local Area Network (VXLAN) encapsulation.";
    reference
      "RFC 7348: Virtual eXtensible Local Area  Network (VXLAN):
                 A Framework for Overlaying Virtualized Layer 2
                 Networks over Layer 3 Networks";
  }

  feature qinany {
    description
      "Indicates the support of the QinAny encapsulation.";
  }

  feature lag-interface {
    description
      "Indicates the support of Link Aggregation Group (LAG)
       between VPN network accesses.";
  }

  /*
   * Features related to multicast
   */

  feature multicast {
    description
      "Indicates multicast capabilities support in a VPN.";
    reference
      "RFC 6513: Multicast in MPLS/BGP IP VPNs";
  }

  feature igmp {
    description
      "Indicates support of Internet Group Management Protocol
       (IGMP).";
    reference
      "RFC 1112: Host Extensions for IP Multicasting
       RFC 2236: Internet Group Management Protocol, Version 2
       RFC 3376: Internet Group Management Protocol, Version 3";
  }

  feature mld {
    description
      "Indicates support of Multicast Listener Discovery (MLD).";
    reference
      "RFC 2710: Multicast Listener Discovery (MLD) for IPv6
       RFC 3810: Multicast Listener Discovery Version 2 (MLDv2)
                 for IPv6";
  }

  feature pim {
    description
      "Indicates support of Protocol Independent Multicast (PIM).";
    reference
      "RFC 7761: Protocol Independent Multicast - Sparse Mode
                (PIM-SM): Protocol Specification (Revised)";
  }

  /*
   * Features related to address family types
   */

  feature ipv4 {
    description
      "Indicates IPv4 support in a VPN.";
  }

  feature ipv6 {
    description
      "Indicates IPv6 support in a VPN.";
  }

  /*
   * Features related to routing protocols
   */

  feature rtg-ospf {
    description
      "Indicates support of the OSPF as the Provider Edge (PE)/
       Customer Edge (CE) routing protocol.";
    reference
      "RFC 4577: OSPF as the Provider/Customer Edge Protocol
                 for BGP/MPLS IP Virtual Private Networks (VPNs)";
  }

  feature rtg-ospf-sham-link {
    description
      "Indicates support of OSPF sham links.";
    reference
      "RFC 4577: OSPF as the Provider/Customer Edge Protocol
                 for BGP/MPLS IP Virtual Private Networks (VPNs),
                 Section 4.2.7";
  }

  feature rtg-bgp {
    description
      "Indicates support of BGP as the PE/CE routing protocol.";
  }

  feature rtg-rip {
    description
      "Indicates support of RIP as the PE/CE routing protocol.";
  }

  feature rtg-isis {
    description
      "Indicates support of IS-IS as the PE/CE routing protocol.";
  }

  feature rtg-vrrp {
    description
      "Indicates support of the Virtual Router Redundancy
       Protocol (VRRP) between a cutsomer LAN and the PE.";
    reference
      "RFC 5798: Virtual Router Redundancy Protocol (VRRP) Version 3
                 for IPv4 and IPv6";
  }

  feature bfd {
    description
      "Indicates support of Bidirectional Forwarding Detection (BFD)
       between the CE and the PE.";
    reference
      "RFC 5880: Bidirectional Forwarding Detection (BFD)";
  }

  /*
   * Features related to VPN service constraints
   */

  feature bearer-reference {
    description
      "Indicates support of the bearer reference access constraint.
       That is, the reuse of a network connection that was already
       ordered to the service provider apart from the IP VPN site.";
  }

  feature placement-diversity {
    description
      "Indicates support of placement diversity constraints in the
       customer premises. An example of these constraints may be to
       avoid connecting a site network access to the same Provider
       Edge as a target site network access.";
  }

  /*
   * Features related to bandwidth and Quality of Service (QoS)
   */

  feature qos {
    description
      "Indicates support of Classes of Services (CoSes).";
  }

  feature input-bw {
    description
      "Indicates support of the input bandwidth in a VPN.";
  }

  feature output-bw {
    description
      "Indicates support of the output bandwidth in a VPN.";
  }

  /*
   * Features related to security and resilience
   */

  feature encryption {
    description
      "Indicates support of encryption.";
  }

  feature fast-reroute {
    description
      "Indicates support of Fast Reroute (FRR).";
  }

  /*
   * Features related to advanced VPN options
   */

  feature external-connectivity {
    description
      "Indicates support of the VPN to provide external
       connectivity (e.g., Internet, private or public cloud).";
  }

  feature extranet-vpn {
    description
      "Indicates support of extranet VPNs. That is, the capability of
       a VPN to access a list of other VPNs.";
  }

  feature carrierscarrier {
    description
      "Indicates support of Carrier-of-Carrier VPNs.";
    reference
      "RFC 4364: BGP/MPLS IP Virtual Private Networks
                (VPNs), Section 9";
  }

  /*
   * Address family related identities
   */

  identity address-family {
    description
      "Defines a type for the address family.";
  }

  identity ipv4 {
    base address-family;
    description
      "Identity for IPv4 address family.";
  }

  identity ipv6 {
    base address-family;
    description
      "Identity for IPv6 address family.";
  }

  identity dual-stack {
    base address-family;
    description
      "Identity for IPv4 and IPv6 address family.";
  }

  /*
   * Identities related to VPN topology
   */

  identity vpn-topology {
    description
      "Base identity of the VPN topology.";
  }

  identity any-to-any {
    base vpn-topology;
    description
      "Identity for any-to-any VPN topology.";
  }

  identity hub-spoke {
    base vpn-topology;
    description
      "Identity for Hub-and-Spoke VPN topology.";
  }

  identity hub-spoke-disjoint {
    base vpn-topology;
    description
      "Identity for Hub-and-Spoke VPN topology where Hubs cannot
       communicate with each other.";
  }

  identity custom {
    base vpn-topology;
    description
      "Identity for custom VPN topologies where the role of the nodes
       is not strictly hub or spoke. The VPN topology is controlled by
       the import/export policies. The custom topology reflects more
       complex VPN nodes such as VPN node that acts as Hub for certain
       nodes and Spoke to others.";
  }

  /*
   * Identities related to network access types
   */

  identity site-network-access-type {
    description
      "Base identity for site network access type.";
  }

  identity point-to-point {
    base site-network-access-type;
    description
      "Identity for point-to-point connections.";
  }
  identity multipoint {
    base site-network-access-type;
    description
      "Identity for multipoint connections, e.g., Ethernet broadcast
       segment.";
  }

  identity irb {
    base site-network-access-type;
    description
      "Integrated Routing Bridge (IRB).
       Identity for pseudowire connections.";
  }

  identity loopback {
    base site-network-access-type;
    description
      "Identity for loopback connections.";
  }

  /*
   * Identities related to operational and administrative status
   */

  identity operational-status {
    description
      "Base identity for the operational status.";
  }

  identity operational-state-up {
    base operational-status;
    description
      "Operational status is UP/Enabled.";
  }

  identity operational-state-down {
    base operational-status;
    description
      "Operational status is DOWN/Disabled.";
  }

  identity operational-state-unknown {
    base operational-status;
    description
      "Operational status is UNKNOWN.";
  }

  identity administrative-status {
    description
      "Base identity for administrative status.";
  }

  identity administrative-state-up {
    base administrative-status;
    description
      "Administrative status is UP/Enabled.";
  }

  identity administrative-state-down {
    base administrative-status;
    description
      "Administrative status is DOWN/Disabled.";
  }

  identity administrative-state-testing {
    base administrative-status;
    description
      "Administrative status is up for testing purposes.";
  }

  identity administrative-state-pre-deployment {
    base administrative-status;
    description
      "Administrative status is pre-deployment phase. That is prior to
       the actual deployment of a service.";
  }

  /*
   * Identities related to site or node role
   */

  identity role {
    description
      "Base identity of a site or a node role.";
  }

  identity any-to-any-role {
    base role;
    description
      "Identity of any-to-any IP VPN.";
  }

  identity spoke-role {
    base role;
    description
      "A node or a site is acting as a Spoke IP VPN.";
  }

  identity hub-role {
    base role;
    description
      "A node or a site isacting as a Hub IP VPN.";
  }

  identity custom-role {
    base role;
    description
      "VPN-Node with custom or complex role in the VPN. For some
       sources/destinations, it can behave as a hub but for others it
       can act as a spoke depending on the configured policy.";
  }

  /*
   * Identities related to VPN service constraints
   */

  identity placement-diversity {
    description
      "Base identity for access placement constraints.";
  }

  identity bearer-diverse {
    base placement-diversity;
    description
      "Identity for bearer diversity.

       The bearers should not use common elements.";
  }

  identity pe-diverse {
    base placement-diversity;
    description
      "Identity for PE diversity.";
  }

  identity pop-diverse {
    base placement-diversity;
    description
      "Identity for Point Of Presence (POP) diversity.";
  }

  identity linecard-diverse {
    base placement-diversity;
    description
      "Identity for linecard diversity.";
  }

  identity same-pe {
    base placement-diversity;
    description
      "Identity for having sites connected on the same PE.";
  }

  identity same-bearer {
    base placement-diversity;
    description
      "Identity for having sites connected using the same bearer.";
  }

  /*
   * Identities related to service types
   */

  identity service-type {
    description
      "Identity of service type.";
  }

  identity l3vpn {
    base service-type;
    description
      "Identity for L3VPN service.";
    reference
      "RFC 4364: BGP/MPLS IP Virtual Private Networks (VPNs)";
  }

  identity vpls {
    base service-type;
    description
      "Identity for the VPLS service type.";
    reference
      "RFC 4761: Virtual Private LAN Service (VPLS) Using BGP for
                 Auto-Discovery and Signaling
       RFC 4762: Virtual Private LAN Service (VPLS) Using Label
                 Distribution Protocol (LDP) Signaling";
  }

  identity vpws-evpn {
    base service-type;
    description
      "Identity for the Point-to-point Virtual Private Wire Service
       (VPWS) service type.";
    reference
      "RFC 8214: Virtual Private Wire Service Support in Ethernet VPN";
  }

  identity pbb-evpn {
    base service-type;
    description
      "Identity for Provider Backbone Bridging (PBB) EVPNs.";
    reference
      "RFC 7623: Provider Backbone Bridging Combined with Ethernet VPN
                (PBB-EVPN)";
  }

  identity mpls-evpn {
    base service-type;
    description
      "Identity for MPLS based EVPNs.";
    reference
      "RFC 7432: BGP MPLS-Based Ethernet VPN";
  }

  identity vxlan-evpn {
    base service-type;
    description
      "Identity for VXLAN based EVPNs.";
    reference
      "RFC 8365: A Network Virtualization Overlay Solution Using
                 Ethernet VPN (EVPN)";
  }

  /*
   * Identities related to VPN signaling type
   */

  identity vpn-signaling-type {
    description
      "Identity for VPN signaling types";
  }

  identity bgp-signaling {
    base vpn-signaling-type;
    description
      "Identity for Layer 2 VPNs using BGP";
    reference
      "RFC 6624: Layer 2 Virtual Private Networks Using BGP for
                 Auto-Discovery and Signaling
       RFC 7432: BGP MPLS-Based Ethernet VPN";
  }
  identity ldp-signaling {
    base vpn-signaling-type;
    description
      "Identity for Targeted Label Distribution Protocol.";
    reference
      "RFC 5036: LDP Specification";
  }

  identity l2tp-signaling {
    base vpn-signaling-type;
    description
      "Identity for Layer Two Tunneling Protocol (L2TP).";
    reference
      "RFC 3931: Layer Two Tunneling Protocol - Version 3 (L2TPv3)";
  }

  /*
   * Identities related to routing protocols
   */

  identity routing-protocol-type {
    description
      "Base identity for routing protocol type.";
  }

  identity static {
    base routing-protocol-type;
    description
      "Identity for static routing protocol type.";
  }

  identity bgp {
    if-feature "rtg-bgp";
    base routing-protocol-type;
    description
      "Identity for BGP routing protocol type.";
  }

  identity ospf {
    if-feature "rtg-ospf";
    base routing-protocol-type;
    description
      "Identity for OSPF routing protocol type.";
    reference
      "RFC 4577: OSPF as the Provider/Customer Edge Protocol
                 for BGP/MPLS IP Virtual Private Networks(VPNs)";
  }

  identity rip {
    if-feature "rtg-rip";
    base routing-protocol-type;
    description
      "Identity for RIP routing protocol type.";
  }

  identity isis {
    if-feature "rtg-isis";
    base routing-protocol-type;
    description
      "Identity for IS-IS routing protocol type.";
  }

  identity vrrp {
    if-feature "rtg-vrrp";
    base routing-protocol-type;
    description
      "Identity for VRRP protocol type.

       This is to be used when LANs are directly connected to PEs.";
  }

  identity direct {
    base routing-protocol-type;
    description
      "Identity for direct routing protocol type.

       This is to be used when LANs are directly connected to PEs
       and must be advertised in the VPN.";
  }

  identity any {
    base routing-protocol-type;
    description
      "Identity for any routing protocol type.

       This can be, e.g., used to set policies that apply to any
       routing protocol in place.";
  }

  identity isis-level {
    if-feature "rtg-isis";
    description
      "Identity for the IS-IS level.";
  }

  identity level1 {
    base isis-level;
    description
      "Identity for IS-IS level 1.";
  }

  identity level2 {
    base isis-level;
    description
      "Identity for IS-IS level 2.";
  }

  identity level1-2 {
    base isis-level;
    description
      "Identity for IS-IS levels 1 and 2.";
  }

  /*
   * Identities related to Routes Import and Export
   */

  identity ie-type {
    description
      "Identity for 'import/export' routing profiles. These profiles
       can be reused between VPN nodes.";
  }

  identity import {
    base ie-type;
    description
      "Identity for 'import' routing profile.";
    reference
      "RFC 4364: BGP/MPLS IP Virtual Private Networks
                (VPNs), Section 4.3.1";
  }

  identity export {
    base ie-type;
    description
      "Identity for 'export' routing profile.";
    reference
      "RFC 4364: BGP/MPLS IP Virtual Private Networks
                (VPNs), Section 4.3.1";
  }

  identity import-export {
    base ie-type;
    description
      "Identity for 'import/export' routing profile.";
  }

  /*
   * Identities related to bandwidth and QoS
   */

  identity bw-direction {
    description
      "Identity for the bandwidth direction.";
  }

  identity input-bw {
    if-feature "input-bw";
    base bw-direction;
    description
      "Identity for the input bandwidth.";
  }

  identity output-bw {
    if-feature "output-bw";
    base bw-direction;
    description
      "Identity for the output bandwidth.";
  }

  identity bw-type {
    description
      "Identity of the bandwidth type.";
  }

  identity bw-per-cos {
    if-feature "qos";
    base bw-type;
    description
      "The bandwidth is per CoS.";
  }

  identity bw-per-port {
    base bw-type;
    description
      "The bandwidth is per site network access.";
  }

  identity bw-per-site {
    base bw-type;
    description
      "The bandwidth is per site. It is applicable to all the site
       network accesses within a site.";
  }

  identity bw-per-service {
    base bw-type;
    description
      "The bandwidth is per VPN service.";
  }

  identity qos-profile-direction {
    if-feature "qos";
    description
      "Base identity for the QoS profile direction.";
  }

  identity site-to-wan {
    base qos-profile-direction;
    description
      "Identity for Site-to-WAN direction.";
  }

  identity wan-to-site {
    base qos-profile-direction;
    description
      "Identity for WAN-to-Site direction.";
  }

  identity both {
    base qos-profile-direction;
    description
      "Identity for both WAN-to-Site and Site-to-WAN directions.";
  }

  /*
   *  Identities related to underlay transport instances
   */

  identity transport-instance-type {
    description
      "Base identity for underlay transport instance type.";
  }

  identity virtual-network {
    base transport-instance-type;
    description
      "Identity for the virtual network.";
    reference
      "RFC 8453: Framework for Abstraction and Control of TE
                 Networks (ACTN)";
  }

  identity enhanced-vpn {
    base transport-instance-type;
    description
      "Identity for the Enhanced VPN (VPN+). VPN+ is an
       approach that is based on existing VPN and Traffic
       Engineering (TE) technologies but adds characteristics
       that specific services require over and above traditional
       VPNs.";
  }

  identity ietf-network-slice {
    base transport-instance-type;
    description
      "Identity for the IETF network slice. An IETF network slice
       is a logical network topology connecting a number of
       endpoints using a set of shared or dedicated network
       resources that are used to satisfy specific service
       objectives.";
  }

  /*
   *  Identities related to protocol types. These types are typically
   *  used to identify the underlay transport.
   */

  identity protocol-type {
    description
      "Base identity for Protocol Type.";
  }

  identity ip-in-ip {
    base protocol-type;
    description
      "Transport is based on IP-in-IP.";
    reference
      "RFC 2003: IP Encapsulation within IP
       RFC 2473: Generic Packet Tunneling in IPv6 Specification";
  }

  identity ip-in-ipv4 {
    base ip-in-ip;
    description
      "Transport is based on IP over IPv4.";
    reference
      "RFC 2003: IP Encapsulation within IP";
  }

  identity ip-in-ipv6 {
    base ip-in-ip;
    description
      "Transport is based on IP over IPv6.";
    reference
      "RFC 2473: Generic Packet Tunneling in IPv6 Specification";
  }

  identity gre {
    base protocol-type;
    description
      "Transport is based on Generic Routing Encapsulation (GRE).";
    reference
      "RFC 1701: Generic Routing Encapsulation (GRE)
       RFC 1702: Generic Routing Encapsulation over IPv4 networks
       RFC 7676: IPv6 Support for Generic Routing Encapsulation (GRE)";
  }

  identity gre-v4 {
    base gre;
    description
      "Transport is based on GRE over IPv4.";
    reference
      "RFC 1702: Generic Routing Encapsulation over IPv4 networks";
  }

  identity gre-v6 {
    base gre;
    description
      "Transport is based on GRE over IPv6.";
    reference
      "RFC 7676: IPv6 Support for Generic Routing Encapsulation (GRE)";
  }

  identity vxlan-trans {
    base protocol-type;
    description
      "Transport is based on VXLAN.";
    reference
      "RFC 7348: Virtual eXtensible Local Area  Network (VXLAN):
                 A Framework for Overlaying Virtualized Layer 2
                 Networks over Layer 3 Networks";
  }

  identity geneve {
    base protocol-type;
    description
      "Transport is based on Generic Network Virtualization
       Encapsulation (GENEVE).";
    reference
      "RFC 8926: Geneve: Generic Network Virtualization Encapsulation";
  }

  identity ldp {
    base protocol-type;
    description
      "Transport is based on LDP.";
    reference
      "RFC 5036: LDP Specification";
  }

  identity mpls-in-udp {
    base protocol-type;
    description
      "Transport is MPLS in UDP.";
    reference
      "RFC 7510: Encapsulating MPLS in UDP";
  }

  identity sr {
    base protocol-type;
    description
      "Transport is based on Segment Routing (SR).";
    reference
      "RFC 8660: Segment Routing with the MPLS Data Plane
       RFC 8663: MPLS Segment Routing over IP
       RFC 8754: IPv6 Segment Routing Header (SRH)";
  }

  identity sr-mpls {
    base sr;
    description
      "Transport is based on SR with MPLS.";
    reference
      "RFC 8660: Segment Routing with the MPLS Data Plane";
  }

  identity srv6 {
    base sr;
    description
      "Transport is based on SR over IPv6.";
    reference
      "RFC 8663: MPLS Segment Routing over IP
       RFC 8754: IPv6 Segment Routing Header (SRH)";
  }

  identity rsvp-te {
    base protocol-type;
    description
      "Transport is based on RSVP-TE.";
    reference
      "RFC 3209: RSVP-TE: Extensions to RSVP for LSP Tunnels";
  }

  identity bgp-lu {
    base protocol-type;
    description
      "Transport is based on BGP-LU.";
    reference
      "RFC 8277: Using BGP to Bind MPLS Labels to Address Prefixes";
  }

  identity unknown {
    base protocol-type;
    description
      "Not known protocol type.";
  }

  /*
   * Identities related to encapsulations
   */

  identity encapsulation-type {
    description
      "Base identity for the encapsulation type.";
  }

  identity priority-tagged {
    base encapsulation-type;
    description
      "Identity for the priority-tagged interface.";
  }

  identity dot1q {
    if-feature "dot1q";
    base encapsulation-type;
    description
      "Identity for the support of the Dot1q encapsulation.";
  }

  identity qinq {
    if-feature "qinq";
    base encapsulation-type;
    description
      "Identity for the support of the QinQ encapsulation.";
  }

  identity qinany {
    if-feature "qinany";
    base encapsulation-type;
    description
      "Identity for the support of the QinAny encapsulation.";
  }

  identity vxlan {
    if-feature "vxlan";
    base encapsulation-type;
    description
      "Identity for the support of the VxLAN encapsulation.";
  }

  identity ethernet-type {
    base encapsulation-type;
    description
      "Identity of the Ethernet encapsulation type.";
  }

  identity vlan-type {
    base encapsulation-type;
    description
      "Identity of the VLAN encapsulation.";
  }

  identity untagged-int {
    base encapsulation-type;
    description
      "Identity of the untagged interface type.";
  }

  identity tagged-int {
    base encapsulation-type;
    description
      "Identity of the tagged interface type.";
  }

  identity lag-int {
    if-feature "lag-interface";
    base encapsulation-type;
    description
      "Identity of the LAG interface type.";
    reference
      "IEEE Std. 802.1AX: Link Aggregation";
  }

  /*
   * Identities related to VLAN Tag
   */

  identity tag-type {
    description
      "Base identity of the tag types.";
  }

  identity c-vlan {
    base tag-type;
    description
      "Indicates Customer VLAN (C-VLAN) tag, normally using
       the 0x8100 Ethertype.";
  }

  identity s-vlan {
    base tag-type;
    description
      "Indicates Service VLAN (S-VLAN) tag.";
  }

  identity c-s-vlan {
    base tag-type;
    description
      "Uses both a C-VLAN tag and a S-VLAN tag.";
  }

  /*
   * Identities related to VXLAN
   */

  identity vxlan-peer-mode {
    if-feature "vxlan";
    description
      "Base identity for the VXLAN peer mode.";
  }

  identity static-mode {
    base vxlan-peer-mode;
    description
      "Identity for VXLAN access in the static mode.";
  }

  identity bgp-mode {
    base vxlan-peer-mode;
    description
      "Identity for VXLAN access by BGP EVPN learning.";
  }

  /*
   * Identities related to multicast
   */

  identity multicast-gp-address-mapping {
    if-feature "multicast";
    description
      "Identity for multicast group mapping type.";
  }

  identity static-mapping {
    base multicast-gp-address-mapping;
    description
      "Identity for static mapping, i.e., attach the interface to the
       multicast group as a static member.";
  }

  identity dynamic-mapping {
    base multicast-gp-address-mapping;
    description
      "Identity for dynamic mapping, i.e., an interface is added to the
       multicast group as a result of snooping.";
  }

  identity multicast-tree-type {
    if-feature "multicast";
    description
      "Base identity for multicast tree type.";
  }

  identity ssm-tree-type {
    base multicast-tree-type;
    description
      "Identity for Source-Specific Multicast (SSM) tree type.";
  }

  identity asm-tree-type {
    base multicast-tree-type;
    description
      "Identity for Any-Source Multicast (ASM) tree type.";
  }

  identity bidir-tree-type {
    base multicast-tree-type;
    description
      "Identity for bidirectional tree type.";
  }

  identity multicast-rp-discovery-type {
    if-feature "multicast";
    description
      "Base identity for Rendezvous Point (RP) discovery type.";
  }

  identity auto-rp {
    base multicast-rp-discovery-type;
    description
      "Base identity for Auto-RP discovery type.";
  }

  identity static-rp {
    base multicast-rp-discovery-type;
    description
      "Base identity for static type.";
  }

  identity bsr-rp {
    base multicast-rp-discovery-type;
    description
      "Base identity for Bootstrap Router (BSR) discovery type.";
  }

  identity group-management-protocol {
    if-feature "multicast";
    description
      "Identity for multicast group management protocol.";
  }

  identity igmp-proto {
    base group-management-protocol;
    description
      "Identity for IGMP.";
    reference
      "RFC 1112: Host Extensions for IP Multicasting
       RFC 2236: Internet Group Management Protocol, Version 2
       RFC 3376: Internet Group Management Protocol, Version 3";
  }

  identity mld-proto {
    base group-management-protocol;
    description
      "Identity for MLD.";
    reference
      "RFC 2710: Multicast Listener Discovery (MLD) for IPv6
       RFC 3810: Multicast Listener Discovery Version 2 (MLDv2)
                 for IPv6";
  }

  identity pim-proto {
    if-feature "pim";
    base routing-protocol-type;
    description
      "Identity for PIM.";
    reference
      "RFC 7761: Protocol Independent Multicast - Sparse Mode
                (PIM-SM): Protocol Specification (Revised)";
  }

  identity igmp-version {
    if-feature "igmp";
    description
      "Base identity for IGMP version.";
  }

  identity igmpv1 {
    base igmp-version;
    description
      "Identity for IGMPv1.";
    reference
      "RFC 1112: Host Extensions for IP Multicasting";
  }

  identity igmpv2 {
    base igmp-version;
    description
      "Identity for IGMPv2.";
    reference
      "RFC 2236: Internet Group Management Protocol, Version 2";
  }

  identity igmpv3 {
    base igmp-version;
    description
      "Identity for IGMPv2.";
    reference
      "RFC 3376: Internet Group Management Protocol, Version 3";
  }

  identity mld-version {
    if-feature "mld";
    description
      "Base identity for MLD version.";
  }

  identity mldv1 {
    base mld-version;
    description
      "Identity for MLDv1.";
    reference
      "RFC 2710: Multicast Listener Discovery (MLD) for IPv6";
  }

  identity mldv2 {
    base mld-version;
    description
      "Identity for MLDv2.";
    reference
      "RFC 3810: Multicast Listener Discovery Version 2 (MLDv2)
                 for IPv6";
  }

  /*
   * Identities related to traffic types
   */

  identity tf-type {
    description
      "Identity for the traffic type.";
  }

  identity multicast-traffic {
    base tf-type;
    description
      "Identity for multicast traffic.";
  }

  identity broadcast-traffic {
    base tf-type;
    description
      "Identity for broadcast traffic.";
  }

  identity unknown-unicast-traffic {
    base tf-type;
    description
      "Identity for unknown unicast traffic.";
  }

  /*
   * Identities related to customer applications
   */

  identity customer-application {
    description
      "Base identity for customer applications.";
  }

  identity web {
    base customer-application;
    description
      "Identity for a Web application (e.g., HTTP, HTTPS).";
  }

  identity mail {
    base customer-application;
    description
      "Identity for a mail application.";
  }

  identity file-transfer {
    base customer-application;
    description
      "Identity for a file transfer application (e.g., FTP, SFTP).";
  }

  identity database {
    base customer-application;
    description
      "Identity for a database application.";
  }

  identity social {
    base customer-application;
    description
      "Identity for a social-network application.";
  }

  identity games {
    base customer-application;
    description
      "Identity for a gaming application.";
  }

  identity p2p {
    base customer-application;
    description
      "Identity for a peer-to-peer application.";
  }

  identity network-management {
    base customer-application;
    description
      "Identity for a management application (e.g., Telnet, syslog,
       SNMP).";
  }

  identity voice {
    base customer-application;
    description
      "Identity for a voice application.";
  }

  identity video {
    base customer-application;
    description
      "Identity for a video conference application.";
  }

  identity embb {
    base customer-application;
    description
      "Identity for an enhanced Mobile Broadband (eMBB) application.
       Note that an eMBB application demands network performance with a
       wide variety of characteristics, such as data rate, latency,
       loss rate, reliability, and many other parameters.";
  }

  identity urllc {
    base customer-application;
    description
      "Identity for an Ultra-Reliable and Low Latency Communications
       (URLLC) application.  Note that an URLLC application demands
       network performance with a wide variety of characteristics, such
       as latency, reliability, and many other parameters.";
  }

  identity mmtc {
    base customer-application;
    description
      "Identity for a massive Machine Type Communications (mMTC)
       application.  Note that an mMTC application demands network
       performance with a wide variety of characteristics, such as data
       rate, latency, loss rate, reliability, and many other
       parameters.";
  }

  /*
   * Identities related to service bundling
   */

  identity bundling-type {
    description
      "The base identity for the bundling type. It supports a subset or
       all CE-VLANs associated with an L2VPN service.";
  }

  identity multi-svc-bundling {
    base bundling-type;
    description
      "Identity for multi-service bundling, i.e., multiple C-VLAN IDs
       can be associated with an L2VPN service at a site.";
  }

  identity one2one-bundling {
    base bundling-type;
    description
      "Identity for one-to-one service bundling, i.e., each L2VPN can
       be associated with only one C-VLAN ID at a site.";
  }

  identity all2one-bundling {
    base bundling-type;
    description
      "Identity for all-to-one bundling, i.e., all C-VLAN IDs are mapped
       to one L2VPN service.";
  }

  /*
   * Identities related to Ethernet Services
   */

  identity control-mode {
    description
      "Defines the type of control mode on Layer 2 Control Protocol
       (L2CP).";
  }

  identity peer {
    base control-mode;
    description
      "'peer' mode, i.e., participate in the protocol towards the CE.
       Peering is common for Link Aggregation Control Protocol (LACP)
       and the Ethernet Local Management Interface (E-LMI) and,
       occasionally, for Link Layer Discovery Protocol (LLDP).
       For VPLSs and VPWSs, the subscriber can also request that the
       peer service provider enables spanning tree.";
  }

  identity tunnel {
    base control-mode;
    description
      "'tunnel' mode, i.e., pass to the egress or destination site. For
       Ethernet Private Lines (EPLs), the expectation is that L2CP
       frames are tunnelled.";
  }

  identity discard {
    base control-mode;
    description
      "Identity for 'discard' mode, i.e., discard the frame.";
  }

  identity neg-mode {
    description
      "Identity for the negotiation mode.";
  }

  identity full-duplex {
    base neg-mode;
    description
      "Identity for the full-duplex mode.";
  }

  identity auto-neg {
    base neg-mode;
    description
      "Identity for auto-negotiation mode.";
  }

  /******** Collection of VPN-related Types & Identities ********/

  typedef vpn-id {
    type string;
    description
      "Defines an identifier that is used as a service identifier,
       for example.";
  }

  /*
   * Types related to Ethernet Services
   */

  typedef ccm-priority-type {
    type uint8 {
      range "0..7";
    }
    description
      "A 3-bit priority value to be used in the VLAN tag,
       if present in the transmitted frame.";
  }

  /******* VPN-related reusable groupings *******/

  grouping vpn-description {
    description
      "Provides common VPN information.";
    leaf vpn-id {
      type vpn-id;
      description
        "VPN identifier.
         This identifier has a local meaning.";
    }
    leaf vpn-name {
      type string;
      description
        "A name used to refer to the VPN.";
    }
    leaf vpn-description {
      type string;
      description
        "Textual description of a VPN.";
    }
    leaf customer-name {
      type string;
      description
        "Name of the customer that actually uses the VPN.";
    }
  }

  grouping vpn-profile-cfg {
    description
      "Grouping for VPN Profile configuration.";
    container valid-provider-identifiers {
      description
        "Container for valid provider profile identifiers.";
      list external-connectivity-identifier {
        if-feature "external-connectivity";
        key "id";
        description
          "List for profile identifiers that uniquely identify profiles
           governing how external connectivity is provided to a VPN.
           A profile indicates the type of external connectivity
           (Internet, cloud, etc.), the sites/nodes that are associated
           with a connectivity profile, etc. A profile can also indicate
           filtering rules and/or address translation rules. Such
           features may involve PE, P, or dedicated nodes as a function
           of the deployment.";
        leaf id {
          type string;
          description
            "Identification of an external connectivity profile. It has
             a local administration meaning.";
        }
      }
      list encryption-profile-identifier {
        key "id";
        description
          "List for encryption profile identifiers.";
        leaf id {
          type string;
          description
            "Identification of the encryption profile to be used. It
             has a local administration meaning.";
        }
      }
      list qos-profile-identifier {
        key "id";
        description
          "List for QoS Profile Identifiers.";
        leaf id {
          type string;
          description
            "Identification of the QoS profile to be used. It has
             a local administration meaning.";
        }
      }
      list bfd-profile-identifier {
        key "id";
        description
          "List for BFD profile identifiers.";
        leaf id {
          type string;
          description
            "Identification of the BFD profile to be used.
             This identifier has a local administration meaning.";
        }
      }
      list forwarding-profile-identifier {
        key "id";
        description
          "List for forwarding profile identifiers.";
        leaf id {
          type string;
          description
            "Identification of the Forwrding Profile Filter to be used.
             Local administration meaning.";
        }
      }
      list routing-profile-identifier {
        key "id";
        description
          "List for Routing Profile Identifiers.";
        leaf id {
          type string;
          description
            "Identification of the routing profile to be used by the
             routing protocols within sites, vpn-network-accesses, or
             vpn-nodes for refering VRF's import/export policies.

             This identifier has a local meaning.";
        }
      }
      nacm:default-deny-write;
    }
  }

  grouping status-timestamp {
    description
      "This grouping defines some operational parameters for the
       service.";
    leaf status {
      type identityref {
        base operational-status;
      }
      config false;
      description
        "Operations status.";
    }
    leaf last-updated {
      type yang:date-and-time;
      config false;
      description
        "Indicates the actual date and time of the service status
         change.";
    }
  }

  grouping service-status {
    description
      "Service status grouping.";
    container status {
      description
        "Service status.";
      container admin-status {
        description
          "Administrative service status.";
        leaf status {
          type identityref {
            base administrative-status;
          }
          description
            "Administrative service status.";
        }
        leaf last-updated {
          type yang:date-and-time;
          description
            "Indicates the actual date and time of the service status
             change.";
        }
      }
      container oper-status {
        description
          "Operational service status.";
        uses status-timestamp;
      }
    }
  }

  grouping underlay-transport {
    description
      "This grouping defines the type of underlay transport for the
       VPN service. It can include an identifier to an abstract
       transport instance to which the VPN is grafted or indicate a
       technical implementation that is expressed as an ordered list
       of protocols.";
    choice type {
      description
        "A choice based on the type of underlay transport
         constraints.";
      case abstract {
        description
          "Indicates that the transport constraint is an abstract
           concept.";
        leaf transport-instance-id {
          type string;
          description
            "Includes an identifier of an abstract transport instance.";
        }
        leaf instance-type {
          type identityref {
            base transport-instance-type;
          }
          description
            "Indicates a transport instance type. For example, it can
             be a VPN+, an IETF network slice, a virtual network, etc.";
        }
      }
      case protocol {
        description
          "Indicates a list of protocols.";
        leaf-list protocol {
          type identityref {
            base protocol-type;
          }
          ordered-by user;
          description
            "Indicates an ordered-by user list of transport protocols.";
        }
      }
    }
  }

  grouping vpn-route-targets {
    description
      "A grouping that specifies Route Target (RT) import-export rules
       used in a BGP-enabled VPN.";
    reference
      "RFC 4364: BGP/MPLS IP Virtual Private Networks (VPNs)
       RFC 4664: Framework for Layer 2 Virtual Private Networks
                 (L2VPNs)";
    list vpn-target {
      key "id";
      description
        "Route targets. AND/OR operations are available
         based on the RTs assigment.";
      leaf id {
        type int8;
        description
          "Identifies each VPN Target.";
      }
      list route-targets {
        key "route-target";
        description
          "List of RTs.";
        leaf route-target {
          type rt-types:route-target;
          description
            "Conveys an RT value.";
        }
      }
      leaf route-target-type {
        type rt-types:route-target-type;
        mandatory true;
        description
          "Import/export type of the RT.";
      }
    }
    container vpn-policies {
      description
        "VPN policies.";
      leaf import-policy {
        type string;
        description
          "Defines the 'import' policy.";
      }
      leaf export-policy {
        type string;
        description
          "Defines the 'export' policy.";
      }
    }
  }

  grouping route-distinguisher {
    description
      "Grouping for route distinguisher (RD).";
    choice rd-choice {
      description
        "Route distinguisher choice between several options
         on providing the route distinguisher value.";
      case directly-assigned {
        description
          "Explicitly assign an RD value.";
        leaf rd {
          type rt-types:route-distinguisher;
          description
            "Indicates an RD value that is explicitly
             assigned.";
        }
      }
      case directly-assigned-suffix {
        description
          "Explicitly the value of the Assigned Number subfield
           of the RD. The Administrator subfield of the RD will
           be based on other configuration information such as
           router-id or ASN.";
        leaf rd-suffix {
          type uint16;
          description
            "Indicates the value of the Assigned Number
             subfield that is explicitly assigned.";
        }
      }
      case auto-assigned {
        description
          "The RD is auto-assigned.";
        container rd-auto {
          description
            "The RD is auto-assigned.";
          choice auto-mode {
            description
              "Indicates the auto-assignment mode. RD can be
               automatically assigned either with or without
               indicating a pool from which the RD should be
               taken.

               For both cases, the server will auto-assign an RD
               value 'auto-assigned-rd' and use that value
               operationally.";
            case from-pool {
              leaf rd-pool-name {
                type string;
                description
                  "The auto-assignment will be made from the pool
                   identified by the rd-pool-name.";
              }
            }
            case full-auto {
              leaf auto {
                type empty;
                description
                  "Indicates an RD is fully auto-assigned.";
              }
            }
          }
          leaf auto-assigned-rd {
            type rt-types:route-distinguisher;
            config false;
            description
              "The value of the auto-assigned RD.";
          }
        }
      }
      case auto-assigned-suffix {
        description
          "The value of the Assigned Number subfield will
           be auto-assigned. The Administrator subfield
           will be based on other configuration information such as
           router-id or ASN.";
        container rd-auto-suffix {
          description
            "The Assigned Number subfield is auto-assigned.";
          choice auto-mode {
            description
              "Indicates the auto-assignment mode of the Assigned Number
               subfield. This number can be automatically assigned
               either with or without indicating a pool from which
               the value should be taken.

               For both cases, the server will auto-assign
               'auto-assigned-rd-suffix' and use that value to build
               the RD that will be used operationally.";
            case from-pool {
              leaf rd-pool-name {
                type string;
                description
                  "The assignment will be made from the pool identified
                   by the rd-pool-name.";
              }
            }
            case full-auto {
              leaf auto {
                type empty;
                description
                  "Indicates that the Assigned Number is fully auto
                   assigned.";
              }
            }
          }
          leaf auto-assigned-rd-suffix {
            type uint16;
            config false;
            description
              "Includes the value of the Assigned Number subfield that
               is auto-assigned .";
          }
        }
      }
      case no-rd {
        description
          "Use the empty type to indicate RD has no value and is not to
           be auto-assigned.";
        leaf no-rd {
          type empty;
          description
            "No RD is assigned.";
        }
      }
    }
  }

  grouping vpn-components-group {
    description
      "Grouping definition to assign group-ids to associate VPN nodes,
       sites, or network accesses.";
    container groups {
      description
        "Lists the groups to which a VPN node,a site, or a network
         access belongs to.";
      list group {
        key "group-id";
        description
          "List of group-ids.";
        leaf group-id {
          type string;
          description
            "Is the group-id to which a VPN node, a site, or a network
             access belongs to.";
        }
      }
    }
  }

  grouping placement-constraints {
    description
      "Constraints for placing a network access.";
    list constraint {
      key "constraint-type";
      description
        "List of constraints.";
      leaf constraint-type {
        type identityref {
          base placement-diversity;
        }
        description
          "Diversity constraint type.";
      }
      container target {
        description
          "The constraint will apply against this list of groups.";
        choice target-flavor {
          description
            "Choice for the group definition.";
          case id {
            list group {
              key "group-id";
              description
                "List of groups.";
              leaf group-id {
                type string;
                description
                  "The constraint will apply against this particular
                   group-id.";
              }
            }
          }
          case all-accesses {
            leaf all-other-accesses {
              type empty;
              description
                "The constraint will apply against all other network
                 accesses of a site.";
            }
          }
          case all-groups {
            leaf all-other-groups {
              type empty;
              description
                "The constraint will apply against all other groups that
                 the customer is managing.";
            }
          }
        }
      }
    }
  }

  grouping ports {
    description
      "Choice of specifying a source or destination port numbers.";
    choice source-port {
      description
        "Choice of specifying the source port or referring to a group
         of source port numbers.";
      container source-port-range-or-operator {
        description
          "Source port definition.";
        uses packet-fields:port-range-or-operator;
      }
    }
    choice destination-port {
      description
        "Choice of specifying a destination port or referring to a group
         of destination port numbers.";
      container destination-port-range-or-operator {
        description
          "Destination port definition.";
        uses packet-fields:port-range-or-operator;
      }
    }
  }

  grouping qos-classification-policy {
    description
      "Configuration of the traffic classification policy.";
    list rule {
      key "id";
      ordered-by user;
      description
        "List of marking rules.";
      leaf id {
        type string;
        description
          "An identifier of the QoS classification policy rule.";
      }
      choice match-type {
        default "match-flow";
        description
          "Choice for classification.";
        case match-flow {
          choice l3 {
            description
              "Either IPv4 or IPv6.";
            container ipv4 {
              description
                "Rule set that matches IPv4 header.";
              uses packet-fields:acl-ip-header-fields;
              uses packet-fields:acl-ipv4-header-fields;
            }
            container ipv6 {
              description
                "Rule set that matches IPv6 header.";
              uses packet-fields:acl-ip-header-fields;
              uses packet-fields:acl-ipv6-header-fields;
            }
          }
          choice l4 {
            description
              "Includes Layer 4 specific information.
               This version focuses on TCP and UDP.";
            container tcp {
              description
                "Rule set that matches TCP header.";
              uses packet-fields:acl-tcp-header-fields;
              uses ports;
            }
            container udp {
              description
                "Rule set that matches UDP header.";
              uses packet-fields:acl-udp-header-fields;
              uses ports;
            }
          }
        }
        case match-application {
          leaf match-application {
            type identityref {
              base customer-application;
            }
            description
              "Defines the application to match.";
          }
        }
      }
      leaf target-class-id {
        if-feature "qos";
        type string;
        description
          "Identification of the class of service. This identifier is
           internal to the administration.";
      }
    }
  }
}
