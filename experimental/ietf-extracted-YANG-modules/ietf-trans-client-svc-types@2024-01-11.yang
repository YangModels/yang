module ietf-trans-client-svc-types {
  yang-version 1.1;
  namespace
    "urn:ietf:params:xml:ns:yang:ietf-trans-client-svc-types";
  prefix clnt-types;

  organization
     "Internet Engineering Task Force (IETF) CCAMP WG";
  contact
    "WG Web: <https://datatracker.ietf.org/wg/ccamp/>
     WG List: <mailto:ccamp@ietf.org>

     Editor: Haomian Zheng
             <mailto:zhenghaomian@huawei.com>

     Editor: Aihua Guo
             <mailto:aihuaguo.ietf@gmail.com>

     Editor: Italo Busi
             <mailto:italo.busi@huawei.com>

     Editor: Anton Snitser
             <mailto:asnizar@cisco.com>

     Editor: Chaode Yu
             <mailto:yuchaode@huawei.com>";

  description
    "This module defines a collection of common YANG identity
    definitions for describing Costant Bit Rate (CBR) transport
    network clients.

    Copyright (c) 2024 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.";

  revision 2024-01-11 {
    description
      "Initial Version";
    reference
      "RFC XXXX: A YANG Data Model for Transport Network Client
      Signals";
  }
  // RFC Editor: replace XXXX with the actual RFC number assigned
  // to the RFC once this draft
  // becomes an RFC, update date information and remove this note.

  /*
   * Identities
   */

  identity direction {
    description
      "Direction information of Client Signal.";
  }

    identity bidirectional {
      base direction;
      description
        "Client Signal is bi-directional.";
    }

    identity unidirectional {
      base direction;
      description
        "Client Signal is uni-directional.";
    }
}
