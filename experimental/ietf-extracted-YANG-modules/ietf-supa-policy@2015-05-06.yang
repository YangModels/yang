module ietf-supa-policy { 
  namespace "urn:ietf:params:xml:ns:yang:ietf-supa-policy"; 
  // replace with IANA namespace when assigned 
  prefix policy; 

  import ietf-inet-types { 
    prefix inet; 
  } 

  organization "IETF"; 
  contact 
    "Editor: Jun Bi 
     junbi@tsinghua.edu.cn"; 

  description 
    "This YANG module defines a component that describing 
     the ddc policy model for monitoring and optimizing 
     tenant's DC (data center) services that are deployed 
     between multiple data centers. 

     Terms and Acronyms 
       DDC: Distributed Data Center 
       L2VPN: Layer 2 Virtual Private Network 
       L3VPN: Layer 3 Virtual Private Network"; 

  revision 2015-05-06 { 
    description 
      "Revised revision."; 
      reference 
        " Network Policy YANG Data Model "; 
  } 

container supa-ddc-policy{ 
  description 
    "Distributed Data Center Service Operation Data"; 

  container adjust-flow-path-policy { 
    description 
      "To improve the bandwidth utilization (or reduce the cost, 
       or other reason) and mitigate traffic congestion,management 
       system/ application requires controller to adjust certain 
       flows to pass/bypass certain nodes(or links), when, e.g., 
       bandwidth utilization exceed certain threshold. Vpn name, 
       vpn type, adjusted flow and specified nodes (that the flow 
       should pass) should be told to controller. So that the 
       controller can configure the network elements to change the 
       VRF table and routing table. If the link bandwidth usage is 
       above certain threshold, the monitored flow will be forced 
       to routed to the third place to bypass the overloaded node 
       or site."; 

    list adjust-flow-path { 
      key "vpn-name"; 
      description 
        "The list of VPN and flow that need to be adjusted in  
         specific paths. So as to optimize traffic in the links  
         that are between data centers."; 
      leaf vpn-name { 
        type string; 
        mandatory true; 
        description 
          "Indicates the name of VPN that the adjusted flow 
           belongs to. A VPN instance is identified by vpn-name. 
           It should be one of the created VPN instance names"; 
      } 
      leaf vpn-type { 
        type enumeration { 
          enum L2VPN { 
            description "L2VPN";        
          } 
          enum L3VPN { 
            description "L3VPN";        
          } 
        } 
        description "Indicates the type of VPN instance that the 
        adjusted flow belongs to. L2VPN or L3VPN"; 
      } 
      leaf flow-name { 
         type string; 
         description "The name of the adjusted flow. So as to tell 
         the Controller which flow should be adjusted"; 
      } 

    container traffic-steering-policy-rule{ 

      leaf policy-rule-deploy-status { 
        description "It defines the current deployment status 
        of this policy rule. Both operational and test mode values
        are included in its definition."; 
           type enumeration { 
             enum 0{ 
              description "undefined";        
             } 
             enum 1{ 
              description "deployed and enabled";        
             } 
          enum 2{ 
              description "deployed and in test";        
             } 
          enum 3{ 
              description "deployed but not enabled";        
             } 
          enum 4{ 
              description "ready to be deployed";        
             } 
          enum 5{ 
              description "not deployed";        
             } 
           } 
         } 
      leaf policy-rule-exec-status { 
        description "It defines the current execution status 
        of this policy rule. Both operational and test mode values 
        are included in its definition"; 
           type enumeration { 
             enum 0{ 
              description "undefined";        
             } 
             enum 1{ 
              description "executed and SUCEEDED (operational 
              mode)";        
             } 
             enum 2{ 
              description "executed and FAILED (operational 
              mode)";        
             } 
             enum 3{ 
              description "currently executing (operational 
              mode)";        
             } 
             enum 4{ 
              description "executed and SUCEEDED (test mode)";        
             } 
             enum 5{ 
              description "executed and FAILED (test mode)";        
             } 
             enum 6{ 
              description "currently executing (test mode)";        
             } 
           } 
         } 

      container policy-event{ 
        description "The Policy defines an ECA type policy 
        model for the service management of traffic optimization 
        between DCs. If the predefined event is monitored, then 
        the controller will evaluate if the condition is matched. 
        If the condition is matched, the corresponding action will 
        be performed. Here in this case, bandwidth is the 'event' 
        to monitor in the traffic steering policy case"; 

        leaf bandwidth { 
          type string;  
        } 
      } 

      container policy-condition {  
        description "There are several types of 'condition' 
        match, here it is above/below"; 
        leaf bandwidth-utilization { 
          type enumeration { 
               enum utilization { 
               description "In this case, the bandwidth 
               utilization is the 'event'. The controller will 
               monitor the bandwidth utilization if it is above 
	          the threshold which is the link utilization ratio, 
                  0-100%"; 
                  } 
                  enum BW { 
                  description " In this case, the bandwidth usage 
                  is the 'event'. The controller will monitor the 
                  bandwidth usage if it is above the threshold which 
                  is bandwidth value, 2G,10G e.g."; 
               } 
             } 
           } 

           leaf operator{    
             type enumeration { 
                  enum above { 
                  description "If the value of the monitored event 
                  is above the threshold, do the action. E.g., in 
	          this case, if the bandwidth utilization is above 
                  70%, 'above' is the 'match-type' here."; 
                  } 
                  enum below { 
                  description "If the value of the monitored event 
                  is below the threshold, do the action. E.g., in this 
                  case, if the bandwidth usage is below 2Gb, 'below' 
                  is the 'match-type' here."; 
               } 
             } 
           } 

           leaf value { 
             description "The target value of the monitored 
             'event' or the threshold to trigger the action. E.g., 
             in this case, if the bandwidth utilization is above 70%, 
             '70%' is the 'value' here. If the bandwidth usage is 
             above 2Gb, here '2Gb' is the 'value' here"; 
             type uint32; 
           } 
         } 

         container policy-action-adjust-path { 

           description "This is the corresponding 'action' when 
           the condition has been triggered. E.g., if the link 
           occupied ratio is above 70%, adjust the path of the flow. 
           Here the 'adjust-path' is the action of the ECA policy. If 
           the 'event' is monitored, and the 'condition' is triggered, 
           the corresponding 'action', rerouted the flow path, will 
           be performed."; 

           container constraint-nodes { 
               description "The generated 'action' of the ECA 
               policy. It is a description of the constraints on the 
               nodes those need to be adjusted. Here the 'action' only 
               describe the constraint not the real operation. And 
               then, the controller will compute a new route based on 
               the constraint. More specifically, the constraint-nodes 
               are a set of nodes that specify the constraints by the 
               up-level. Each node in the list will be passed/bypassed 
               when computing the new route."; 
             list constraint-node { 

               max-elements unbounded; 
               min-elements 0; 
               description "There can be a set of nodes to be 
               constrained. Each node in the list will be passed/
               bypassed when computing the new route."; 
               key nodeId; 
               description " List of nodes that the adjusted 
               flow needs to pass or bypass so as to adjust the flow 
               path between data centers. E.g. if the event and 
               condition has been triggered that the vpn flow will be 
               adjusted. The constraint-nodes specify how to adjust 
               the flow and which nodes will be adjusted. Each node 
               in the list will be told to controller to pass/bypass 
               when computing the new route."; 
               leaf nodeId { 
                 description "The node needs to be constrained 
                 that describe which nodes will be adjusted in the 
                 path. The node ID is the identifier of the node that 
                 the controller will take into account when computing 
                 the new route."; 
                 config true;       
                 type string { 
                 length "0..64"; 
                 pattern "([^?]*)"; 
                 } 
               } 
               leaf constraint-type { 
                 description "The node can be bypassed or 
                 passed."; 
                 config false; 
                 type enumeration { 
                   enum bypass { 
                     value 0; 
                     description "The node will be bypassed. 
                     E.g., if the corresponding action of the ECA 
                     policy is to bypass the busy node 1, 2 and 3, 
                     then the node-list will be nodeId: 1, 2 and 3, 
                     while the'constraint-type' of each node is 
                     'bypass' which denote all these nodes should be 
                     bypassed when computing the new route. Then the 
                     controller will compute the new route based on 
                     the constraint to compute a new path without 
                     node 1, 2 
                     and 3."; 
                   } 
                   enum pass { 
                     value 1; 
                     description "The node will be passed. E.g., if 
                     the corresponding action of the ECA policy is to 
                     pass the light loaded nodes 1, 2 and 3, then the 
                     node-list will be nodeId: 1, 2 and 3, while the 
                     'constraint-type' of each node is 'pass' which 
                     denote all these nodes should be passed when 
                     computing the new route. Then the controller 
                     will compute the new route based on the 
                     constraint to compute a new path without node 
                     1, 2 and 3."; 
                   } 
                 } 
               } 
               leaf sequence { 
                 description "Constraint node sequence. The 
                 corresponding action can also specify the sequence 
                 of the node list that should be passed/bypassed. 
                 E.g., if the 'action' is to adjust the flow to a 
                 new path with node 1, 2 and 3, while the pass the 
                 node 1 first, then 3, finally 2. Here the sequence 
                 of the node-list will be 1-3-2. Then the controller 
                 will compute the new path based on the sequence."; 
                 config true; 
                 default 1; 
                 type uint32 { 
                   range "0..128"; 
                 } 
               } 
             } 
           } 
           container constraint-sites { 
             list constraint-site { 

               max-elements unbounded; 
               min-elements 0; 
               description "."; 
               key siteId; 
               description " List of sites that the adjusted 
               flow needs to pass or bypass So as to adjust the flow 
               path between data centers. The site can be a group of 
               nodes at different granularities for example data 
               centers."; 

               description " List of sites that the adjusted 
               flow needs to pass or bypass So as to adjust the flow 
               path between data centers."; 

               leaf siteId { 
                 description "The site needs to be adjusted in 
                 the flow path. The site"; 
                 config true; 
                 type string { 
                 length "0..64"; 
                 pattern "([^?]*)"; 
                 } 
               } 
               leaf constraint-type { 

                 description "The constraint type of the site 
                 to specify whether the node site will be passed or 
                 bypassed"; 
                 config false; 

                 type enumeration { 
                   enum bypass { 
                     value 0; 
                    description "The site will be bypassed"; 
                   } 
                   enum pass { 
                     value 1; 
                     description "The site will be passed"; 
                   } 
                 } 
               } 

               leaf sequence { 
                 description "constraint site sequence"; 
                 config true; 
                 default 1; 
                 type uint32 { 
                 range "0..128"; 
                 } 
               } 
             } 
           } 
          }  
         } 
        } 
       } 
     } 
   }
