module ietf-traffic-policy {
  yang-version 1.1;
  namespace "urn:ietf:params:xml:ns:yang:ietf-traffic-policy";
  prefix traffic-policy;

  import ietf-interfaces {
    prefix if;
  }
  import ietf-qos-types {
    prefix qos-types;
    reference
      "RFC XXXX: YANG Data Models for Quality of Service (QoS).";
  }

  organization
    "IETF Routing Area Working Group.";

  contact
    "WG Web:   <https://datatracker.ietf.org/wg/rtgwg/>
     WG List:  <mailto:rtgwg@ietf.org>

     Editor:   Aseem Choudhary
               <mailto:asechoud@cisco.com>
     Editor:   Mahesh Jethanandani
               <mailto:mjethanandani@gmail.com>";

  description
    "This module contains a collection of YANG definitions for
     configuring QoS Traffic Policies.

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2025-07-06 {
    description
      "Initial version.";
    reference
      "RFC XXXX: YANG Models for Quality of Service (QoS).";
  }

  grouping filters {
    description
      "Filters types in a Classifier entry.";

    leaf type {
      type identityref {
        base qos-types:filter-type;
      }
      description
        "This leaf defines the type of filter.";
    }

    leaf logical-not {
      type boolean;
      description
        "This is logical-not operator for filter values and/or value
         ranges. When true, it indicates filter looks for absence
         of values and/or value ranges defined by the filter.";
    }
  }

  grouping generic-classifier-attr {
    description
      "Generic Classifier attributes like name,
       description, operation type.";

    leaf name {
      type string;
      description
        "A unique name for Classifier entry.";
    }

    leaf description {
      type string;
      description
        "Description statement for classifier entry.";
    }

    leaf filter-operation {
      type qos-types:match-operation-type;
      description
        "match-any or match-all filters.";
    }
  }

  grouping inline-attr {
    description
      "Attributes of inline classifier in a policy.";

    leaf filter-operation {
      type qos-types:match-operation-type;
      description
        "match-any or match-all filters.";
    }

    list filter {
      key "type logical-not";
      uses filters;
      description
        "Filters configured inline in a policy.";
    }
  }

  container classifiers {
    description
      "List of classifier entries.";

    list classifier {
      key "name";
      description
        "Each classifier entry contains a list of filters.";

      uses generic-classifier-attr;

      list filter {
        key "type logical-not";
        uses filters;
        description
          "Filter entries for a classifier.";
      }
    }
  }

  container policies {
    description
      "List of policy templates.";

    list policy {
      key "name type";
      description
        "Policy template.";

      leaf name {
        type string;
        description
          "A unique name for the policy.";
      }

      leaf type {
        type identityref {
          base qos-types:policy-type;
        }
        description
          "The type of policy.";
      }

      leaf description {
        type string;
        description
          "A description for policy.";
      }

      list classifier {
        key "name";
        ordered-by user;
        description
          "Classifier configuration in a policy.";

        leaf name {
          type union {
            type string;
            type leafref {
              path "/traffic-policy:classifiers/" +
              "traffic-policy:classifier/traffic-policy:name";
            }
          }
          description
            "A unique name for classifier entry.";
        }

        container inline {
          presence "This container is present for when the device
                    is configured for inline classification.";
          uses inline-attr;
          description
            "Container for when an inline classification
             is desired.";
        }

        list action {
          key "type";
          ordered-by user;
          description
            "List of action for a Classifier.";

          leaf type {
            type identityref {
              base qos-types:action-type;
            }
            description
              "Type of action.";
          }

        }
      }
    }
  }

  augment "/if:interfaces/if:interface" {
    description
      "Augments Interface module to add Target Entry.";

    list qos-target-policy {
      key "direction type";
      description
        "Policy target for inbound or outbound direction.";

      leaf direction {
        type identityref {
          base qos-types:direction;
        }
        description
          "Direction of the traffic flow either inbound or
           outbound.";
      }

      leaf type {
        type identityref {
          base qos-types:policy-type;
        }
        description
          "Policy type.";
      }

      leaf name {
        type leafref  {
          path "/traffic-policy:policies/" +
              "traffic-policy:policy/traffic-policy:name";
        }
        mandatory true;
        description
          "A unique name for the Policy.";
      }
    }
  }
}
