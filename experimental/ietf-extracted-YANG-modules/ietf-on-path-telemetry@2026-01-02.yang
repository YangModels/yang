module ietf-on-path-telemetry {
  yang-version 1.1;
  namespace "urn:ietf:params:xml:ns:yang:ietf-on-path-telemetry";
  prefix "on-path-telemetry";

     import ietf-access-control-list {
       prefix acl;
       reference
         "RFC 8519: YANG Data Model for Network Access Control
          Lists (ACLs)";
     }

     import ietf-interfaces {
       prefix if;
      reference
        "RFC 8343: A YANG Data Model for Interface Management";
     }

     import ietf-yang-types {
       prefix yang;
       reference
         "Section 3 of RFC 6991";
     }

  organization
    "IETF IPPM (IP Performance Metrics) Working Group";

  contact
    "WG Web: <https://datatracker.ietf.org/wg/ippm>
     WG List: <ippm@ietf.org>
     Author: giuseppe.fioccola@huawei.com
     Author: zhoutianran@huawei.com
     Author: zhuyq8@chinatelecom.cn
     Author: zhangwq@chinatelecom.cn
     Author: zhukeyi@huawei.com";

  description
    "This YANG module specifies a vendor-independent data
     model for Alternate Marking Telemetry.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-01-02 {
    description "First revision.";
    reference "RFC XXXX: A YANG Data Model for On-path Telemetry";
  }

 /*
  * FEATURES
  */

  feature altmark
  {
    description
      "This feature indicated that the Alternate-Marking Method is
      supported.";
    reference
      "RFC 9341: Alternate-Marking Method;
       RFC 9342: Clustered Alternate-Marking Method";
  }

  feature pathdelay
  {
    description
      "This feature indicated that the Path Delay is
      supported.";
    reference
      "[I-D.ietf-opsawg-ipfix-on-path-telemetry]";
  }

  feature incremental-trace
  {
    description
      "This feature indicated that the incremental tracing option is
      supported.";
    reference "RFC 9197: Data Fields for In-situ OAM";
  }

  feature preallocated-trace
  {
    description
      "This feature indicated that the preallocated tracing option is
      supported.";
    reference "RFC 9197: Data Fields for In-situ OAM";
  }

  feature direct-export
  {
    description
      "This feature indicated that the direct export option is
      supported.";
    reference "RFC 9326: In-situ OAM Direct Exporting";
  }

  feature proof-of-transit
  {
    description
      "This feature indicated that the proof of transit option is
      supported";
    reference "RFC 9197: Data Fields for In-situ OAM";
  }

  feature edge-to-edge
  {
    description
      "This feature indicated that the edge-to-edge option is
      supported.";
    reference "RFC 9197: Data Fields for In-situ OAM";
  }

 /*
  * IDENTITIES
  */

  identity filter {
    description
      "Base identity to represent a filter. A filter is used to
      specify the flow to which the On-Path Telemetry method is applied.";
  }

  identity acl-filter {
    base filter;
    description
      "Apply ACL rules to specify the flow.";
  }

  identity protocol {
    description
      "Base identity to represent the protocol. It's used to
      indicate the protocol for the application of the On-Path Telemetry
      method.";
  }

  identity ipv6 {
    base protocol;
    description
      "The On-Path Telemetry method is applied to IPv6 protocol.";
    reference
      "RFC 9343: IPv6 Application of the Alternate-Marking Method,
       RFC 9486: In-situ OAM IPv6 Options";
  }

  identity srh  {
    base protocol;
    description
      "The On-Path Telemetry method is applied to SRH.";
    reference
      "[I-D.fz-spring-srv6-alt-mark]: Application of the
      Alternate Marking Method to the Segment Routing Header";
  }

  identity mpls  {
    base protocol;
    description
      "The On-Path Telemetry method is applied to MPLS.";
    reference
      "RFC 9714: Application of the Alternate Marking Method
      to the MPLS Label Stack";
  }

  identity nsh  {
    base protocol;
    description
      "The described IOAM data is embedded in NSH.";
    reference
      "RFC 9452: Network Service Header (NSH)
      Encapsulation for In-situ OAM (IOAM) Data";
   }

  identity node-action {
    description
      "Base identity to represent the node actions. It's used to
       indicate what action the node will take.";
  }

  identity action-marking {
    base node-action;
    description
      "It indicates that the node must mark the AltMark data field,
      according to the operations described in RFC 9341 and
      RFC 9342";
  }

  identity action-unmarking {
    base node-action;
    description
      "It indicates that the node must unmark the AltMark data field,
      according to the operations described in RFC 9341 and
      RFC 9342";
  }

  identity action-read {
    base node-action;
    description
      "It indicates the node only reads the AltMark data,
      according to the operations described in RFC 9341 and
      RFC 9342";
  }

  identity action-encapsulate {
    base node-action;
    description
      "It indicates the node is to encapsulate the IOAM packet";
  }

  identity action-decapsulate {
    base node-action;
    description
      "It indicates the node is to decapsulate the IOAM packet";
  }

  identity action-transit {
    base node-action;
    description
      "It indicates the node is to transit the IOAM packet";
  }

  identity measurement-period {
    description
      "It indicates the On-Path Telemetry Period.";
  }

  identity measurement-period-number {
    description
      "It indicates the Period Number.";
  }

  identity flow-mon-id {
    description
      "It indicates the FlowMonID.";
  }

  identity method {
    description
      "Base identity to represent the AltMark method type.";
  }

  identity trace-data {
    description
      "Base identity to represent trace data.";
  }

  identity pot-data {
    description
      "Base identity to represent POT data.";
   }

  identity e2e-data {
    description
      "Base identity to represent E2E data.";
   }

  identity telemetry-param-type {
    description
       "Base identity for telemetry param types";
   }

  identity loss-measurement {
    base telemetry-param-type;
    description
      "To specify loss counters according to RFC 9341";
   }

  identity delay-measurement {
    base telemetry-param-type;
    description
      "To specify timestamps for delay according to RFC 9341";
   }
 /*
  * TYPE DEFINITIONS
  */

  typedef telemetry-filter-type {
    type identityref {
      base filter;
    }
    description
      "It specifies a known type of filter.";
  }

  typedef telemetry-node-action {
    type identityref {
      base node-action;
    }
    description
      "It specifies a node action.";
  }

  typedef telemetry-protocol-type {
    type identityref {
      base protocol;
    }
    description
      "It specifies a known type of carrier protocol for the On-path
      Telemetry data.";
  }

  typedef altmark-method-type {
    type identityref {
      base method;
    }
    description
      "It specifies the AltMark method used.";
  }

  typedef ioam-trace-data {
    type identityref {
      base trace-data;
    }
    description
      "It specifies the trace data.";
  }

  typedef ioam-pot-data {
    type identityref {
      base pot-data;
    }
    description
      "It specifies the pot data.";
  }

  typedef ioam-e2e-data {
    type identityref {
      base e2e-data;
    }
    description
      "It specifies the edge-to-edge data.";
  }

 /*
  * GROUP DEFINITIONS
  */

  grouping telemetry-filter {
    description "A grouping for On-path Telemetry filter definition";

    leaf filter-type {
      type telemetry-filter-type;
      description "filter type";
    }

    leaf ace-name {
      when "derived-from-or-self(../filter-type,
      'on-path-telemetry:acl-filter')";
      type leafref {
        path "/acl:acls/acl:acl/acl:aces/acl:ace/acl:name";
      }
      description "The Access Control Entry name is used to
      refer to an ACL specification.";
    }
  }

  grouping telemetry-setup {
    description
      "A grouping for On-path Telemetry profile.";

    leaf node-action {
      type telemetry-node-action;
      description
        "This object indicates the action that the node needs to
         take, i.e. marking/read/unmarking/encapsulate/transit/decapsulate.";
    }

    leaf measurement-period {
      type uint64;
      description
      "It specifies the On-path Telemetry period.
      It is the marking period for AltMark.";
    }

    leaf measurement-period-number {
      type uint64;
      description
      "It specifies the On-path Telemetry period number.";
    }

    leaf flow-mon-id {
      type uint32;
      description
      "It specifies the 20-bit FlowMonID.";
    }

    leaf method-type {
      type altmark-method-type;
      description
      "It specifies the AltMark method type.";
    }

   }

  grouping loss-counters {
    description
      "The set of counters for RFC 9341 loss calculation.";

    leaf in-traffic-pkts {
      type yang:counter64;
      description
        "Total inbound packets of the period according to RFC 9341";
    }
    leaf out-traffic-pkts {
      type yang:counter64;
      description
        "Total outbound packets of the period according to RFC 9341";
    }

    leaf in-traffic-bytes {
      type uint64;
      description
        "Total inbound bytes of the period according to RFC 9341";
    }

    leaf out-traffic-bytes {
      type uint64;
      description
        "Total outbound bytes of the period according to RFC 9341";
    }

   }

  grouping delay-timestamps {
    description
      "It indicates the set of timestamps for RFC 9341 delay calculation.";

    container pkts-timestamps {
      description
        "The list of timestamps of the period according to RFC 9341";

      leaf pkt-timestamp {
        type yang:date-and-time;
        description
          "To specify the timestamp of the delay packet for delay measurements";
      }
      leaf pkt-seq-num {
        type yang:counter32;
        description
          "To specify the sequence number of the delay packet for delay measurements";
      }
     }
    }

  grouping path-delay-metrics {
    description
      "It indicates the path delay measurements.";

    leaf path-delay-mean {
      type uint32;
      description
        "mean path delay as per [I-D.ietf-opsawg-ipfix-on-path-telemetry]";
    }
    leaf path-delay-min {
      type uint32;
      description
        "min path delay as per [I-D.ietf-opsawg-ipfix-on-path-telemetry]";
    }

    leaf path-delay-max {
      type uint32;
      description
        "max path delay as per [I-D.ietf-opsawg-ipfix-on-path-telemetry]";
    }
    leaf path-delay-sum {
      type uint64;
      description
        "sum of the path delay as per [I-D.ietf-opsawg-ipfix-on-path-telemetry]";
    }
   }

  grouping ioam-incremental-tracing-data-list {
    description
      "A grouping for incremental tracing data.";

    container ioam-incremental-tracing {
      description
        "The list of incremental tracing data";
      leaf-list incremental-tracing {
        type ioam-trace-data;
        description
          "This object indicates the incremental tracing data.";
     }
    }
   }

  grouping ioam-preallocated-tracing-data-list {
    description
      "A grouping for the list of pre-allocated tracing data.";

      leaf-list preallocated-tracing {
        type ioam-trace-data;
        description
          "This object indicates the preallocated tracing data.";
     }
   }

  grouping ioam-direct-export-tracing-data-list {
    description
      "A grouping for the list of direct export data.";

      leaf-list direct-export {
        type ioam-trace-data;
        description
          "This object indicates the direct export data.";
     }
   }

   grouping ioam-proof-of-transit-data-list {
    description
       "A grouping for the list of proof of transit data.";

      leaf-list proof-of-transit {
        type ioam-pot-data;
        description
          "This object indicates the proof of transit data.";
     }
   }

   grouping ioam-edge-to-edge-data-list {
    description
       "A grouping for the list of edge-to-edge data.";

      leaf-list edge-to-edge {
        type ioam-e2e-data;
        description
          "This object indicates the edge to edge data.";
     }
   }

 /*
  * DATA NODES
  */

   container on-path-telemetry-data {
     config false;
     description "On-path Telemetry top level container";

      list interface {
      key "if-name";
      description
          "It contains the list of the interfaces activated for AltMark and IOAM";
        leaf if-name {
          type if:interface-ref;
          description "This is a reference to the Interface name.";
        }

        leaf profile-name {
          type string{
            length "1..300";
          }
        description
            "Unique identifier for the On-path Telemetry profile.";
        }

        container filter {
          uses telemetry-filter;
          description
            "The filter which is used to indicate the flow where
            the On-path Telemetry is applied.";
        }

        leaf protocol-type {
          type telemetry-protocol-type;
          description
            "This item is used to indicate the carrier protocol where
            the On-path Telemetry is applied.";
        }

        uses telemetry-setup;

        container altmark-loss-measurement {
           if-feature altmark;
           description
             "It reports the loss measurement data.";

           uses loss-counters;
        }

        container altmark-delay-measurement {
           if-feature altmark;
           description
             "It reports the delay measurement data.";

           uses delay-timestamps;
        }

        container path-delay {
           if-feature pathdelay;
           description
             "It reports the path delay measurements.";

           uses path-delay-metrics;
        }

        container ioam-incremental-tracing {
           if-feature incremental-trace;
           presence "Enables incremental tracing option.";
           description
             "It reports the incremental tracing option data.";

           uses ioam-incremental-tracing-data-list;
        }

        container ioam-preallocated-tracing {
           if-feature preallocated-trace;
           presence "Enables preallocated tracing option.";
           description
             "It reports the preallocated tracing option data.";

           uses ioam-preallocated-tracing-data-list;
        }

        container ioam-direct-export {
           if-feature direct-export;
           presence "Enables direct-export option.";
           description
             "It reports the direct-export option data";

           uses ioam-direct-export-tracing-data-list;
        }

        container ioam-proof-of-transit {
           if-feature proof-of-transit;
           presence "Enables Proof of Transit option.";
           description
             "It reports the PoT option data.";

           uses ioam-proof-of-transit-data-list;
        }

        container ioam-edge-to-edge {
           if-feature edge-to-edge;
           presence "Enables edge-to-edge option.";
           description
             "It reports the edge-to-edge option data.";

           uses ioam-edge-to-edge-data-list;
        }
      }
  }
}
