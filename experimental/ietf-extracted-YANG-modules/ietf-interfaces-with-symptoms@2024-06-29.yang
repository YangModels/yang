module ietf-interfaces-with-symptoms {
    yang-version 1.1;
    namespace "http://example.org/example-ietf-interfaces-with-symptoms";
    prefix "ifws";

    import ietf-symptom-semantic-metadata {
        prefix "sm";
    }
    import ietf-interfaces {
        prefix "if";
    }

    revision 2024-06-29 {
        description
          "Initial version";
        reference
          "Example: Symptoms Annotated IETF Interface";
    }

    augment "/if:interfaces/if:interface" {
        description
        "Augment interfaces with symptoms";
        uses sm:symptom-group;
    }
    augment "/if:interfaces-state/if:interface" {
        description
         "Augment interfaces with symptoms";
        uses sm:symptom-group;
  }
}
