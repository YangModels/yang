module ietf-restconf-restore {
  namespace
    "urn:ietf:params:xml:ns:yang:ietf-restconf-restore";
  prefix rct;

 import ietf-inet-types {
   prefix inet;
 }
  organization
    "IETF NETCONF (Network Configuration) Working Group";

  contact
    "WG Web:   <https://tools.ietf.org/wg/netconf/>
     WG List:  <mailto:netconf@ietf.org>
     WG Chair: Kent Watsen
               <mailto:kwatsen@juniper.net>

     WG Chair: Mahesh Jethanandani
               <mailto:mjethanandani@gmail.com>

     Editor:   Qin Wu
               <mailto:bill.wu@huawei.com>";

  description
    "This module defines operations that implement factory-default and
     system restore capability in the RESTCONF protocol.

     Copyright (c) 2018 IETF Trust and the persons identified as
     authors of the code. All rights reserved.

     Redistribution and use in source and binary forms, with or
     without modification, is permitted pursuant to, and subject to
     the license terms contained in, the Simplified BSD License set
    forth in Section 4.c of the IETF Trust's Legal Provisions
     Relating to IETF Documents
     (https://trustee.ietf.org/license-info).

     The key words 'MUST', 'MUST NOT', 'REQUIRED', 'SHALL', 'SHALL
     NOT', 'SHOULD', 'SHOULD NOT', 'RECOMMENDED', 'MAY', and
     'OPTIONAL' in the module text are to be interpreted as described
     in RFC 2119 (https://tools.ietf.org/html/rfc2119).

     This version of this YANG module is part of RFC XXXX
     (https://tools.ietf.org/html/rfcXXXX); see the RFC itself for
     full legal notices.";

  revision 2018-06-21 {
    description
      "Initial revision.";
    reference
      "RFC XXXX: Factory default Setting Capability for RESTCONF";
  }

// NETCONF capabilities defined as features
    feature startup {
      description
        "NETCONF :startup capability;
         If the server advertises the :startup
         capability for a session, then this feature must
         also be enabled for that session.  Otherwise,
         this feature must not be enabled.";
      reference "RFC 6241, Section 8.7";
    }

    feature url {
      description
        "NETCONF :url capability;
         If the server advertises the :url
         capability for a session, then this feature must
         also be enabled for that session.  Otherwise,
         this feature must not be enabled.";
      reference "RFC 6241, Section 8.8";
    }
      feature writable-running {
      description
        "NETCONF :writable-running capability;
         If the server advertises the :writable-running
         capability for a session, then this feature must
         also be enabled for that session.  Otherwise,
         this feature must not be enabled.";
      reference "RFC 6241, Section 8.2";
    }

    feature candidate {
      description
        "NETCONF :candidate capability;
         If the server advertises the :candidate
         capability for a session, then this feature must
         also be enabled for that session.  Otherwise,
         this feature must not be enabled.";
      reference "RFC 6241, Section 8.3";
    }

     /* Operations */

     rpc factory-recovery {
       description
         "The <factor-restore> operation atomically returns any target datastore
         to factory default setting.  The <factor-restore>operation replaces the
          entire contents of a writable Datastore with the contents of complete
         factory default setting, similar to the <delete-config> operation defined in
         [RFC6241], but with additional flexibility in specifying the target Datastore.
          ";

      input {
        container target {
          description
            "Particular configuration to return factory default setting to.";
          choice config-target {
            mandatory true;
            description
              "The configuration target of the copy operation.";
            leaf candidate {
              if-feature candidate;
              type empty;
              description
                "The candidate configuration is the config target.";
            }
            leaf running {
              if-feature writable-running;
              type empty;
              description
                "The running configuration is the config target.
                 This is optional-to-implement on the server.";
            }

            leaf startup {
              if-feature startup;
              type empty;
              description
                "The startup configuration is the config target.";
            }
            leaf url {
              if-feature url;
              type inet:uri;
              description
                "The URL-based configuration is the config target.";
            }
          }
        }

        container source {
          description
            "Particular configuration to copy from.";
          choice config-source {
            mandatory true;
           description
              "The configuration source for the copy operation.";

            leaf factory {
              if-feature candidate;
              type empty;
              description
                "The factory-default-setting configuration is the config source.";
            }

            leaf url {
              if-feature url;
              type inet:uri;
              description
                "The URL-based configuration is the config source.";
            }
          }
        }
      leaf restart {
       type boolean;
            description
              "indicate whether restart or zero touch bootstrapping
               service is enabled.";
        }
      }
     }
}
