module ietf-dots-data-channel {
  yang-version 1.1;
  namespace "urn:ietf:params:xml:ns:yang:ietf-dots-data-channel";
  prefix data-channel;

  import ietf-access-control-list {
    prefix ietf-acl;
  }
  import ietf-packet-fields {
    prefix packet-fields;
  }
  import ietf-dots-signal-channel {
    prefix dots-signal;
  }

  organization
    "IETF DDoS Open Threat Signaling (DOTS) Working Group";
  contact
    "WG Web:   <https://datatracker.ietf.org/wg/dots/>
     WG List:  <mailto:dots@ietf.org>

     Editor:  Konda, Tirumaleswar Reddy
              <mailto:TirumaleswarReddy_Konda@McAfee.com>

     Editor:  Mohamed Boucadair
              <mailto:mohamed.boucadair@orange.com>

     Author:  Kaname Nishizuka
              <mailto:kaname@nttv6.jp>

     Author:  Liang Xia
              <mailto:frank.xialiang@huawei.com>

     Author:  Prashanth Patil
              <mailto:praspati@cisco.com>

     Author:  Andrew Mortensen
              <mailto:amortensen@arbor.net>

     Author:  Nik Teague
              <mailto:nteague@verisign.com>

     Author:  Jon Shallow
              <mailto:jon.shallow@nccgroup.trust>";
  description
    "This module contains YANG definition for configuring
     aliases for resources and filtering rules using DOTS
     data channel.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2018-01-22 {
    description
      "Initial revision.";
    reference
      "RFC XXXX: Distributed Denial-of-Service Open Threat
                 Signaling (DOTS) Data Channel Specification";
  }

  grouping aliases {
    description
      "Top level container for aliases";
    list alias {
      key "name";
      description
        "List of aliases";
      leaf name {
        type string;
        description
          "The name of the alias";
      }
      uses dots-signal:target;
      leaf lifetime {
        type int32;
        units "minutes";
        mandatory true;
        description
          "Indicates the lifetime of the alias entry.

           A lifetime of negative one (-1) indicates indefinite
           lifetime for the alias.";
      }
    }
  }

  grouping access-lists {
    description
      "Specifies the ordered set of Access Control Lists.";
    list acl {
      key "name";
      ordered-by user;
      description
        "An Access Control List (ACL) is an ordered list of
         Access List Entries (ACE). Each Access Control Entry has a
         list of match criteria and a list of actions.";
      leaf name {
        type string {
          length "1..64";
        }
        description
          "The name of access-list.";
        reference
           "RFC ZZZZ: Network Access Control List (ACL)
                      YANG Data Model";
      }
      leaf type {
        type ietf-acl:acl-type;
        description
          "Type of access control list. Indicates the primary intended
           type of match criteria (e.g., IPv4, IPv6) used in the list
           instance.";
        reference
           "RFC ZZZZ: Network Access Control List (ACL)
                      YANG Data Model";
      }
      leaf lifetime {
        type int32;
        units "minutes";
        mandatory true;
        description
          "Indicates the lifetime of the filtering rule

           A lifetime of negative one (-1) indicates indefinite
           lifetime for the filtering request.";
      }
      container aces {
        description
          "The access-list-entries container contains
           a list of ACEs.";
        list ace {
          key "name";
          ordered-by user;
          description
            "List of access list entries.";
          leaf name {
            type string {
              length "1..64";
            }
            description
              "A unique name identifying this Access List
               Entry (ACE).";
            reference
              "RFC ZZZZ: Network Access Control List (ACL)
                         YANG Data Model";
          }
          container matches {
            description
              "The rules in this set determine what fields will be
               matched upon before any action is taken on them.

               If no matches are defined in a particular container,
               then any packet will match that container.

               If no matches are specified at all in an ACE, then any
               packet will match the ACE.";
            reference
               "RFC ZZZZ: Network Access Control List (ACL)
                          YANG Data Model";

            choice l3 {
              container ipv4 {
                when "derived-from(../../../../type," +
                     "'ietf-acl:ipv4-acl-type')";
                uses packet-fields:acl-ip-header-fields;
                uses packet-fields:acl-ipv4-header-fields;
                leaf v4-fragments {
                  type empty;
                  description
                    "Handle IPv4 fragments.";
                }
                description
                  "Rule set that matches IPv4 header.";
              }
              container ipv6 {
                when "derived-from(../../../../type," +
                     "'ietf-acl:ipv6-acl-type')";
                uses packet-fields:acl-ip-header-fields;
                uses packet-fields:acl-ipv6-header-fields;
                leaf v6-fragments {
                  type empty;
                  description
                    "Handle IPv6 fragments.";
                }
                description
                  "Rule set that matches IPv6 header.";
              }
              description
                "Either IPv4 or IPv6.";
            }
            choice l4 {
              container tcp {
                uses packet-fields:acl-tcp-header-fields;
                description
                  "Rule set that matches TCP header.";
              }
              container udp {
                uses packet-fields:acl-udp-header-fields;
                description
                  "Rule set that matches UDP header.";
              }
              container icmp {
                uses packet-fields:acl-icmp-header-fields;
                description
                  "Rule set that matches ICMP header.";
              }
              description
                "Can be TCP, UDP, or ICMP";
            }
          }
          container actions {
            description
              "Definitions of action for this ACE.";
            leaf forwarding {
              type identityref {
                base ietf-acl:forwarding-action;
              }
              mandatory true;
              description
                "Specifies the forwarding action per ACE.";
              reference
                 "RFC ZZZZ: Network Access Control List (ACL)
                            YANG Data Model";
            }
            leaf rate-limit {
              when "../forwarding = 'ietf-acl:accept'" {
                description
                  "rate-limit valid only when accept action is used";
              }
              type decimal64 {
                fraction-digits 2;
              }
              description
                "rate-limit traffic";
            }
          }
          container statistics {
            config false;
            description
              "Aggregate statistics.";
            uses ietf-acl:acl-counters;
          }
        }
      }
    }
  }

  container dots-data {
    description
      "Main container for DOTS data channel.";
    list dots-client {
      key "cuid";
      description
        "List of DOTS clients.";
      leaf cuid {
        type string;
        description
          "A unique identifier that is randomly generated by
           a DOTS client to prevent request collisions.";
        reference
          "RFC YYYY: Distributed Denial-of-Service Open Threat
                  Signaling (DOTS) Signal Channel Specification";
      }
      leaf cdid {
        type string;
        description
          "A client domain identifier conveyed by a
           server-domain DOTS gateway to a remote DOTS server.";
        reference
          "RFC YYYY: Distributed Denial-of-Service Open Threat
                  Signaling (DOTS) Signal Channel Specification";
      }
      container aliases {
        description
          "Set of aliases that are bound to a DOTS client.";
        uses aliases;
      }
      container access-lists {
        description
          "Access lists that are bound to a DOTS client.";
         uses access-lists;
      }
    }
  }
}
