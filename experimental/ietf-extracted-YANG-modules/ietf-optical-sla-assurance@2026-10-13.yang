module ietf-optical-sla-assurance {
  yang-version 1.1;
  namespace "urn:ietf:params:xml:ns:yang:ietf-optical-sla-assurance";
  prefix ietf-optical-sla-assurance;

  import ietf-yang-types {
    prefix yang;
    reference
      "RFC 9911: Common YANG Data Types";
  }

  organization
    "IETF CCAMP Working Group";
  contact
    "WG Web:   <https://datatracker.ietf.org/wg/ccamp/>
     WG List:  <mailto:ccamp@ietf.org>

     Author:   Henry Yu
               <mailto:hyu2010b@gmail.com>
     Author:   Xiao Li
               <mailto:lixiao33@huawei.com>";
  description
    "This module defines a data model for reporting Service Level
     Agreement (SLA) assurance issues and service interruption
     statistics in optical transport networks.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2026-10-13 {
    description
      "Issue inventory made operational state; availability
       precision, duration units and timestamp types corrected;
       module metadata completed.";
    reference
      "RFC XXXX: A YANG Data Model for Service Level Agreement
       (SLA) Assurance Management in Optical Transport Networks";
  }
  revision 2026-07-02 {
    description
      "Initial revision.";
    reference
      "draft-yu-ccamp-sla-assurance-optical-yang-01";
  }

  grouping issue-base {
    description
      "Attributes common to all SLA assurance issues.";
    leaf issue-id {
      type int64 {
        range "0..1000000000";
      }
      description
        "Optional issue identifier for legacy compatibility or
         cross-system referencing.";
    }
    leaf issue-name {
      type string {
        length "0..1000";
      }
      description
        "Human-readable issue name.";
    }
    leaf issue-sla-type {
      type enumeration {
        enum bandwidth {
          value 1;
          description
            "The issue affects service bandwidth.";
        }
        enum availability {
          value 2;
          description
            "The issue affects network or service availability.";
        }
        enum delay {
          value 3;
          description
            "The issue affects traffic delay.";
        }
      }
      description
        "SLA dimension affected by the issue.";
    }
    leaf layer {
      type enumeration {
        enum service-layer {
          value 1;
          description
            "Service layer.";
        }
        enum electrical-layer {
          value 2;
          description
            "Electrical layer (OTUk/ODUk).";
        }
        enum optical-layer {
          value 3;
          description
            "Optical layer (OTS/OMS/OCh).";
        }
        enum fiber-layer {
          value 4;
          description
            "Fiber layer.";
        }
      }
      description
        "Transport layer at which the issue originates.";
    }
  }

  grouping issue {
    description
      "An SLA assurance issue record.";
    leaf csn {
      type uint64 {
        range "0..9223372036854775807";
      }
      mandatory true;
      description
        "Serial number of the issue, unique within the reporting
         server.";
    }
    uses issue-base;
    leaf issue-category {
      type enumeration {
        enum fault {
          value 1;
          description
            "An existing failure or impairment.";
        }
        enum risk {
          value 2;
          description
            "A condition that may lead to an SLA violation.";
        }
      }
      description
        "Whether the issue is an observed fault or a risk.";
    }
    leaf occur-time {
      type yang:date-and-time;
      description
        "Time at which the issue was first detected.";
    }
    leaf clear-time {
      type yang:date-and-time;
      description
        "Time at which the issue was cleared.  Absent while the
         issue is current.";
    }
    leaf description {
      type string {
        length "0..1000";
      }
      description
        "Description of the issue.";
    }
    leaf suggestion {
      type string {
        length "0..1000";
      }
      description
        "Recommended handling of the issue.";
    }
    leaf severity {
      type enumeration {
        enum critical {
          value 1;
          description
            "Critical.";
        }
        enum major {
          value 2;
          description
            "Major.";
        }
        enum minor {
          value 3;
          description
            "Minor.";
        }
        enum info {
          value 4;
          description
            "Informational.";
        }
      }
      description
        "Severity of the issue.";
    }
    list related-issues {
      key "csn";
      description
        "Issues related to this issue.";
      leaf csn {
        type uint64 {
          range "0..9223372036854775807";
        }
        description
          "Serial number of the related issue.";
      }
    }
    list source-objects {
      key "object-id";
      description
        "Resources on which the issue was detected.";
      leaf object-name {
        type string {
          length "0..255";
        }
        description
          "Name of the resource.";
      }
      leaf object-id {
        type yang:uuid;
        description
          "UUID of the resource.";
      }
      leaf object-type {
        type string {
          length "0..64";
        }
        description
          "Type of the resource.";
      }
    }
  }

  grouping service-info {
    description
      "Identifiers of a service and the tunnel carrying it.";
    leaf service-name {
      type yang:uuid;
      description
        "UUID of the service.";
    }
    leaf tunnel-name {
      type yang:uuid;
      description
        "UUID of the tunnel.";
    }
  }

  container sla {
    config false;
    description
      "SLA assurance issues reported by the server.";
    list issues {
      key "csn";
      description
        "List of SLA assurance issues.";
      uses issue;
      leaf issue-type {
        type enumeration {
          enum current {
            value 1;
            description
              "The issue is current.";
          }
          enum history {
            value 2;
            description
              "The issue has been cleared.";
          }
        }
        description
          "Whether the issue is current or historical.";
      }
      list impacted-objects {
        key "service-name tunnel-name";
        description
          "Services and tunnels impacted by the issue.";
        uses service-info;
      }
    }
  }

  rpc query-history-issue-statistics-by-service {
    description
      "Retrieve historical SLA issue statistics for a service or
       tunnel over a time range.";
    input {
      uses service-info;
      leaf begin-time {
        type yang:date-and-time;
        description
          "Start of the observation window.";
      }
      leaf end-time {
        type yang:date-and-time;
        description
          "End of the observation window.";
      }
      leaf sftp-url {
        type string {
          length "0..255";
        }
        description
          "Optional SFTP destination to which the results are
           exported.";
      }
    }
    output {
      list sla-issue-statistic {
        key "service-name tunnel-name";
        description
          "Statistics for one service and tunnel.";
        uses service-info;
        container service-pm {
          description
            "Service performance statistics for the observation
             window.";
          leaf interruptions {
            type uint64 {
              range "0..9223372036854775807";
            }
            description
              "Number of service interruptions.";
          }
          leaf interrupt-duration {
            type uint64 {
              range "0..9223372036854775807";
            }
            units "seconds";
            description
              "Total duration of service interruptions.";
          }
          leaf availability {
            type decimal64 {
              fraction-digits 6;
              range "0..100";
            }
            units "percent";
            description
              "Service availability over the observation window,
               as a percentage.";
          }
          list interrupt-history {
            key "interrupt-begin-time interrupt-end-time";
            description
              "Individual service interruptions.";
            leaf interrupt-begin-time {
              type yang:date-and-time;
              description
                "Start of the interruption.";
            }
            leaf interrupt-end-time {
              type yang:date-and-time;
              description
                "End of the interruption.";
            }
            leaf interrupt-duration {
              type uint64 {
                range "0..9223372036854775807";
              }
              units "seconds";
              description
                "Duration of the interruption.";
            }
          }
        }
      }
    }
  }
}
