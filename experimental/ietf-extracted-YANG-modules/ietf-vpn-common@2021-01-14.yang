module ietf-vpn-common {
  yang-version 1.1;
  namespace "urn:ietf:params:xml:ns:yang:ietf-vpn-common";
  prefix vpn-common;

  import ietf-netconf-acm {
    prefix nacm;
    reference
      "RFC 8341: Network Configuration Access Control Model";
  }
  import ietf-routing-types {
    prefix rt-types;
    reference
      "RFC 8294: Common YANG Data Types for the Routing Area";
  }
  import ietf-yang-types {
    prefix yang;
    reference
      "Section 3 of RFC 6991";
  }
  import ietf-packet-fields {
    prefix packet-fields;
    reference
      "RFC 8519: YANG Data Model for Network Access
                 Control Lists (ACLs)";
  }

  organization
    "IETF OPSA (Operations and Management Area) Working Group";
  contact
    "WG Web:   <https://datatracker.ietf.org/wg/opsawg/>
     WG List:  <mailto:opsawg@ietf.org>

     Editor:  Samier Barguil
              <mailto:samier.barguilgiraldo.ext@telefonica.com>
     Editor:  Oscar Gonzalez de Dios
              <mailto:oscar.gonzalezdedios@telefonica.com>
     Editor:  Mohamed Boucadair
              <mailto:mohamed.boucadair@orange.com>
     Editor:  Qin Wu
              <mailto:bill.wu@huawei.com>";
  description
    "This YANG module defines a common module that is meant
     to be reused by various VPN-related modules (e.g.,
     Layer 3 VPN Service Model (L3SM), Layer 2 VPN Service
     Model (L2SM), Layer 3 VPN Network Model (L3NM), Layer 2
     VPN Network Model (L2NM)).

     Copyright (c) 2021 IETF Trust and the persons identified as
     authors of the code.  All rights reserved.

     Redistribution and use in source and binary forms, with or
     without modification, is permitted pursuant to, and subject to
     the license terms contained in, the Simplified BSD License set
     forth in Section 4 of the IETF Trust's Legal Provisions
     Relating to IETF Documents
     (https://trustee.ietf.org/license-info).

     This version of this YANG module is part of RFC XXXX
     (https://www.rfc-editor.org/info/rfcXXXX); see the RFC itself
     for full legal notices.";

  revision 2021-01-14 {
    description
      "Initial revision.";
    reference
      "RFC XXXX: A Layer 2/3 VPN Common YANG Model";
  }

  /******** Collection of VPN-related Features ********/

  /*
   * Features related to encapsulation schemes
   */

  feature dot1q {
    description
      "Indicates the support of the 'dot1q'
       encapsulation.";
    reference
      "IEEE Std 802.1Q: Bridges and Bridged Networks";
  }

  feature qinq {
    description
      "Indicates the support of the 'qinq'
       encapsulation.";
    reference
      "IEEE Std 802.1ad: Provider Bridges";
  }

  feature vxlan {
    description
      "Indicates the support of the 'vxlan'
       encapsulation.";
    reference
      "RFC 7348: Virtual eXtensible Local Area  Network (VXLAN):
                 A Framework for Overlaying Virtualized Layer 2
                 Networks over Layer 3 Networks";
  }

  feature qinany {
    description
      "Indicates the support of the 'qinany'
       encapsulation.";
  }

  feature lag-interface {
    description
      "Indicates the support of Link Aggregation Group (LAG)
       between VPN network accesses.";
  }

  /*
   * Features related to multicast and address family types
   */

  feature multicast {
    description
      "Indicates multicast capabilities support in a VPN.";
    reference
      "RFC 6513: Multicast in MPLS/BGP IP VPNs";
  }

  feature ipv4 {
    description
      "Indicates IPv4 support in a VPN.";
  }

  feature ipv6 {
    description
      "Indicates IPv6 support in a VPN.";
  }

  /*
   * Features related to routing protocols
   */

  feature rtg-ospf {
    description
      "Indicates support of the OSPF as the PE/CE protocol.";
    reference
      "RFC 4577: OSPF as the Provider/Customer Edge Protocol
                 for BGP/MPLS IP Virtual Private Networks(VPNs)";
  }

  feature rtg-ospf-sham-link {
    description
      "This feature indicates the support of OSPF sham links.";
    reference
      "Section 4.2.7 of RFC 4577";
  }

  feature rtg-bgp {
    description
      "Indicates support of BGP as the PE/CE protocol.";
  }

  feature rtg-rip {
    description
      "Indicates support of RIP as the PE/CE protocol.";
  }

  feature rtg-vrrp {
    description
      "Indicates support of the Virtual Router Redundancy
       Protocol (VRRP) between a cutsomer LAN and the PE.";
  }

  feature rtg-isis {
    description
      "Indicates the support of IS-IS as the PE-CE protocol.";
  }

  feature bfd {
    description
      "Indicates support of Bidirectional Forwarding Detection
       (BFD) between the CE and the PE.";
    reference
      "RFC 5880: Bidirectional Forwarding Detection (BFD)";
  }

  /*
   * Features related to VPN service constraints
   */

  feature bearer-reference {
    description
      "Indicates support of the bearer reference access
       constraint. That is, the reuse of a network connection
       that was already ordered to the SP apart from the IP VPN
       site.";
  }

  feature placement-diversity {
    description
      "Indicates the support of placement diversity
       constraints in the customer premises. An example
       of these constraints may be to avoid connecting
       a site network access to the same Provider
       Edge as a target site network access.";
  }

  /*
   * Features related to Quality of Service (QoS)
   */

  feature qos {
    description
      "Indicates support of Classes of Services (CoSes).";
  }

  feature input-bw {
    description
      "Indicates the support of the input bandwidth in a VPN.";
  }

  /*
   * Features related to security and resilience
   */
  feature encryption {
    description
      "Indicates support of encryption.";
  }

  feature fast-reroute {
    description
      "Indicates support of Fast Reroute (FRR).";
  }

  /*
   * Features related to advanced VPN options
   */

  feature cloud-access {
    description
      "Indicates support of the VPN to connect to a Cloud
       Service Provider (CSP).";
  }

  feature extranet-vpn {
    description
      "Indicates support of extranet VPNs. That is,
       the capability of a VPN to access a list of
       other VPNs.";
  }

  feature carrierscarrier {
    description
      "Indicates support of Carrier-of-Carrier VPNs.";
    reference
      "Section 9 of RFC 4364";
  }

  /*
   * Address family related identities
   */

  identity address-family {
    description
      "Defines a type for the address family.";
  }

  identity ipv4 {
    if-feature "ipv4";
    base address-family;
    description
      "IPv4 address family.";
  }

  identity ipv6 {
    if-feature "ipv6";
    base address-family;
    description
      "IPv6 address family.";
  }

  /*
   * Identities related to VPN topology
   */

  identity vpn-topology {
    description
      "Base identity of the VPN topology.";
  }

  identity any-to-any {
    base vpn-topology;
    description
      "Identity for any-to-any VPN topology.";
  }

  identity hub-spoke {
    base vpn-topology;
    description
      "Identity for Hub-and-Spoke VPN topology.";
  }

  identity hub-spoke-disjoint {
    base vpn-topology;
    description
      "Identity for Hub-and-Spoke VPN topology
       where Hubs cannot communicate with each other.";
  }

  identity custom {
    base vpn-topology;
    description
      "Identity for custom VPN topologies where the
       role of the nodes is not strictly hub or spoke.
       VPN topology controlled by the import/export
       policies. The custom topology reflects more complex
       VPN nodes such as VPN node that acts as Hub for
       certain nodes and Spoke to others.";
  }

  /*
   * Identities related to network access types
   */

  identity site-network-access-type {
    description
      "Base identity for site-network-access type.";
  }

  identity point-to-point {
    base site-network-access-type;
    description
      "Identity for point-to-point connections.";
  }

  identity multipoint {
    base site-network-access-type;
    description
      "Identity for multipoint connections.
       Example: Ethernet broadcast segment.";
  }

  identity irb {
    base site-network-access-type;
    description
      "Integrated Routing Bridge (IRB).
       Identity for pseudowire connections.";
  }

  identity loopback {
    base site-network-access-type;
    description
      "Identity for loopback connections.";
  }

  /*
   * Identities related to operational and administrative status
   */

  identity operational-status {
    description
      "Base identity for the operational status.";
  }

  identity operational-state-up {
    base operational-status;
    description
      "Operational status is UP/Enabled.";
  }

  identity operational-state-down {
    base operational-status;
    description
      "Operational status is DOWN/Disabled.";
  }

  identity operational-state-unknown {
    base operational-status;
    description
      "Operational status is UNKNOWN.";
  }

  identity administrative-status {
    description
      "Base identity for administrative status.";
  }

  identity administrative-state-up {
    base administrative-status;
    description
      "Administrative status is UP/Enabled.";
  }

  identity administrative-state-down {
    base administrative-status;
    description
      "Administrative status is DOWN/Disabled.";
  }

  identity administrative-state-testing {
    base administrative-status;
    description
      "Administrative status is up for testing purposes.";
  }

  identity administrative-state-pre-deployment {
    base administrative-status;
    description
      "Administrative status is pre-deployment phase.
       That is prior to the actual deployment of a service.";
  }

  /*
   * Identities related to site or node role
   */

  identity role {
    description
      "Base identity of a site or a node role.";
  }

  identity any-to-any-role {
    base role;
    description
      "Identity of any-to-any IP VPN.";
  }

  identity spoke-role {
    base role;
    description
      "A node or a site is acting as a Spoke IP VPN.";
  }

  identity hub-role {
    base role;
    description
      "A node or a site isacting as a Hub IP VPN.";
  }

  identity custom-role {
    base role;
    description
      "VPN-Node with custom or complex role in the VPN.
       For certain sources/destinations,  it can behave
       as a hub but for others it can act as a spoke
       depending on the configured policy.";
  }

  /*
   * Identities related to VPN service constraints
   */

  identity placement-diversity {
    description
      "Base identity for access placement constraints.";
  }

  identity bearer-diverse {
    base placement-diversity;
    description
      "Identity for bearer diversity.

       The bearers should not use common elements.";
  }
  identity pe-diverse {
    base placement-diversity;
    description
      "Identity for PE diversity.";
  }

  identity pop-diverse {
    base placement-diversity;
    description
      "Identity for POP diversity.";
  }

  identity linecard-diverse {
    base placement-diversity;
    description
      "Identity for linecard diversity.";
  }

  identity same-pe {
    base placement-diversity;
    description
      "Identity for having sites connected on the same PE.";
  }

  identity same-bearer {
    base placement-diversity;
    description
      "Identity for having sites connected using the same bearer.";
  }

  /*
   * Identities related to service types
   */

  identity service-type {
    description
      "Identity of service type.";
  }

  identity l3vpn {
    base service-type;
    description
      "Identity of L3VPN service.";
  }

  identity vpls {
    base service-type;
    description
      "Identity of the VPLS service type.";
    reference
      "RFC 4761: Virtual Private LAN Service (VPLS) Using
                 BGP for Auto-Discovery and Signaling
       RFC 4762: Virtual Private LAN Service (VPLS) Using
                 Label Distribution Protocol (LDP) Signaling";
  }

  identity vpws-evpn {
    base service-type;
    description
      "Identity of the Point-to-point Virtual Private
       Wire Service (VPWS) service type.";
    reference
      "RFC8214: Virtual Private Wire Service Support in
                Ethernet VPN";
  }

  identity pbb-evpn {
    base service-type;
    description
      "Identity of Provider Backbone Bridging (PBB) EVPNs.";
    reference
      "RFC 7623: Provider Backbone Bridging Combined
                 with Ethernet VPN (PBB-EVPN)";
  }

  identity mpls-evpn {
    base service-type;
    description
      "Identity of MPLS based EVPNs.";
    reference
      "RFC 7432: BGP MPLS-Based Ethernet VPN";
  }

  identity vxlan-evpn {
    base service-type;
    description
      "Identity of VXLAN based EVPNs.";
    reference
      "RFC 8365: A Network Virtualization Overlay Solution
                 Using Ethernet VPN (EVPN)";
  }

  /*
   * Identities related to VPN signaling type
   */

  identity vpn-signaling-type {
    description
      "Identity of VPN signaling types";
  }

  identity bgp-signaling {
    base vpn-signaling-type;
    description
      "Identity of Layer 2 VPNs using BGP";
    reference
      "RFC 6624: Layer 2 Virtual Private Networks Using BGP for
                 Auto-Discovery and Signaling
       RFC 7432: BGP MPLS-Based Ethernet VPN";
  }

  identity ldp-signaling {
    base vpn-signaling-type;
    description
      "Identity of Targeted Label Distribution Protocol.";
    reference
      "RFC 5036: LDP Specification";
  }

  identity l2tp-signaling {
    base vpn-signaling-type;
    description
      "Identity of l2tp.";
    reference
      "RFC3931: Layer Two Tunneling Protocol - Version 3 (L2TPv3)";
  }

  /*
   * Identities related to routing protocols
   */

  identity routing-protocol-type {
    description
      "Base identity for routing protocol type.";
  }

  identity ospf {
    if-feature "rtg-ospf";
    base routing-protocol-type;
    description
      "Identity for OSPF protocol type.";
  }

  identity bgp {
    if-feature "rtg-bgp";
    base routing-protocol-type;
    description
      "Identity for BGP protocol type.";
  }

  identity static {
    base routing-protocol-type;
    description
      "Identity for static routing protocol type.";
  }

  identity rip {
    if-feature "rtg-rip";
    base routing-protocol-type;
    description
      "Identity for RIP protocol type.";
  }

  identity isis {
    if-feature "rtg-isis";
    base routing-protocol-type;
    description
      "Identity for IS-IS protocol type.";
  }

  identity vrrp {
    if-feature "rtg-vrrp";
    base routing-protocol-type;
    description
      "Identity for VRRP protocol type.

       This is to be used when LANs are directly connected
       to PE routers.";
  }

  identity direct {
    base routing-protocol-type;
    description
      "Identity for direct protocol type.

       This is to be used when LANs are directly connected
       to PE routers and and must be advertised in the VPN.";
  }

  /*
   * Identities related to Routes Import and Export
   */
  identity ie-type {
    description
      "Defines Import-Export routing profiles.
       Those profiles can be reused between VPN nodes.";
  }

  identity import {
    base ie-type;
    description
      "Import a routing profile.";
  }

  identity export {
    base ie-type;
    description
      "Export a routing profile.";
  }

  identity import-export {
    base ie-type;
    description
      "Import/Export a routing profile.";
  }

  /*
   * Identities related to bandwidth and QoS
   */

  identity bw-direction {
    description
      "Identity for the bandwidth direction.";
  }

  identity input-bw {
    base bw-direction;
    description
      "Identity for the input bandwidth.";
  }

  identity output-bw {
    base bw-direction;
    description
      "Identity for the output bandwidth.";
  }

  identity bw-type {
    description
      "Identity of the bandwidth type.";
  }

  identity bw-per-cos {
    base bw-type;
    description
      "Bandwidth is per CoS.";
  }

  identity bw-per-port {
    base bw-type;
    description
      "Bandwidth is per site network access.";
  }

  identity bw-per-site {
    base bw-type;
    description
      "Bandwidth is per site.  It is applicable to
       all the site network accesses within a site.";
  }

  identity bw-per-svc {
    base bw-type;
    description
      "Bandwidth is per VPN service.";
  }

  identity qos-profile-direction {
    description
      "Base identity for the QoS profile direction.";
  }

  identity site-to-wan {
    base qos-profile-direction;
    description
      "Identity for Site-to-WAN direction.";
  }

  identity wan-to-site {
    base qos-profile-direction;
    description
      "Identity for WAN-to-Site direction.";
  }

  identity both {
    base qos-profile-direction;
    description
      "Identity for both WAN-to-Site and Site-to-WAN
       directions.";
  }

  /*
   *  Identities related to protocol types
   */

  identity protocol-type {
    description
      "Base identity for Protocol Type.";
  }

  identity gre {
    base protocol-type;
    description
      "GRE encapsulation.";
    reference
      "RFC 1701: Generic Routing Encapsulation (GRE)
       RFC 1702: Generic Routing Encapsulation over IPv4 networks
       RFC 7676: IPv6 Support for Generic Routing Encapsulation
                 (GRE)";
  }

  identity ldp {
    base protocol-type;
    description
      "Transport based on LDP.";
    reference
      "RFC 5086: LDP Specification";
  }

  identity sr {
    base protocol-type;
    description
      "Transport based on Segmnet Routing (SR).";
    reference
      "RFC 8660: Segment Routing with the MPLS Data Plane
       RFC 8663: MPLS Segment Routing over IP
       RFC 8754: IPv6 Segment Routing Header (SRH)";
  }

  identity sr-te {
    base protocol-type;
    description
      "Transport based on SR-TE.";
    reference
      "RFC 8426: Recommendations for RSVP-TE and Segment Routing (SR)
                 Label Switched Path (LSP) Coexistence";
  }

  identity rsvp-te {
    base protocol-type;
    description
      "Transport based on RSVP-TE.";
    reference
      "RFC 2205: Resource ReSerVation Protocol (RSVP) --
                 Version 1 Functional Specification";
  }

  identity bgp-lu {
    base protocol-type;
    description
      "Transport based on BGP-LU.";
    reference
      "RFC 8277: Using BGP to Bind MPLS Labels to Address
                 Prefixes";
  }

  identity unknown {
    base protocol-type;
    description
      "Not known protocol type.";
  }

  /*
   * Identities related to encapsulations
   */

  identity encapsulation-type {
    description
      "Base identity for the encapsulation type.";
  }

  identity priority-tagged {
    base encapsulation-type;
    description
      "Identity for the priority-tagged interface.";
  }

  identity dot1q {
    if-feature "dot1q";
    base encapsulation-type;
    description
      "Identity for the support of the 'dot1q'
       encapsulation.";
  }
  identity qinq {
    if-feature "qinq";
    base encapsulation-type;
    description
      "Identity for the support of the 'qinq'
       encapsulation.";
  }

  identity qinany {
    if-feature "qinany";
    base encapsulation-type;
    description
      "Identity for the support of the 'qinany'
       encapsulation.";
  }

  identity vxlan {
    if-feature "vxlan";
    base encapsulation-type;
    description
      "Identity for the support of the 'vxlan'
       encapsulation.";
  }

  identity ethernet-type {
    base encapsulation-type;
    description
      "Identity of the Ethernet encapsulation type.";
  }

  identity vlan-type {
    base encapsulation-type;
    description
      "Identity of the VLAN encapsulation.";
  }

  identity untagged-int {
    base encapsulation-type;
    description
      "Identity of the untagged interface type.";
  }

  identity tagged-int {
    base encapsulation-type;
    description
      "Identity of the tagged interface type.";
  }

  identity lag-int {
    if-feature "lag-interface";
    base encapsulation-type;
    description
      "Identity of the LAG interface type.";
    reference
      "IEEE Std. 802.1AX: Link Aggregation";
  }

  /*
   * Identities related to VLAN Tag
   */

  identity tag-type {
    description
      "Base identity of the tag types.";
  }

  identity c-vlan {
    base tag-type;
    description
      "A CVLAN tag, normally using the 0x8100 Ethertype.";
  }

  identity s-vlan {
    base tag-type;
    description
      "An SVLAN tag.";
  }

  identity c-s-vlan {
    base tag-type;
    description
      "Uses both a CVLAN tag and an SVLAN tag.";
  }

  /*
   * Identities related to VXLAN
   */

  identity vxlan-peer-mode {
    if-feature "vxlan";
    description
      "Base identity for the VXLAN peer mode.";
  }

  identity static-mode {
    base vxlan-peer-mode;
    description
      "Identity for VXLAN access in the static mode.";
  }

  identity bgp-mode {
    base vxlan-peer-mode;
    description
      "Identity for VXLAN access by BGP EVPN learning.";
  }

  /*
   * Identities related to multicast
   */

  identity multicast-gp-address-mapping {
    if-feature "multicast";
    description
      "Identity for multicast group mapping type.";
  }

  identity static-mapping {
    base multicast-gp-address-mapping;
    description
      "Identity for static mapping, i.e., attach the interface
       to the multicast group as a static member.";
  }

  identity dynamic-mapping {
    base multicast-gp-address-mapping;
    description
      "Identity for dynamic mapping, i.e., an interface was added
       to the multicast group as a result of snooping.";
  }

  identity multicast-tree-type {
    if-feature "multicast";
    description
      "Base identity for multicast tree type.";
  }

  identity ssm-tree-type {
    base multicast-tree-type;
    description
      "Identity for SSM tree type.";
  }

  identity asm-tree-type {
    base multicast-tree-type;
    description
      "Identity for ASM tree type.";
  }

  identity bidir-tree-type {
    base multicast-tree-type;
    description
      "Identity for bidirectional tree type.";
  }

  identity multicast-rp-discovery-type {
    if-feature "multicast";
    description
      "Base identity for RP discovery type.";
  }

  identity auto-rp {
    base multicast-rp-discovery-type;
    description
      "Base identity for Auto-RP discovery type.";
  }

  identity static-rp {
    base multicast-rp-discovery-type;
    description
      "Base identity for static type.";
  }

  identity bsr-rp {
    base multicast-rp-discovery-type;
    description
      "Base identity for BSR discovery type.";
  }

  /*
   * Identities related to traffic types
   */

  identity tf-type {
    description
      "Identity for the traffic type.";
  }

  identity multicast-traffic {
    if-feature "multicast";
    base tf-type;
    description
      "Identity for multicast traffic.";
  }

  identity broadcast-traffic {
    base tf-type;
    description
      "Identity for broadcast traffic.";
  }

  identity unknown-unicast-traffic {
    base tf-type;
    description
      "Identity for unknown unicast traffic.";
  }

  identity bundling-type {
    description
      "The base identity for the bundling type.  It supports
       multiple CE-VLANs associated with an L2VPN service or
       all CE-VLANs associated with an L2VPN service.";
  }

  /*
   * Identities related to service bundling
   */

  identity multi-svc-bundling {
    base bundling-type;
    description
      "Identity for multi-service bundling, i.e.,
       multiple CE-VLAN IDs can be associated with an
       L2VPN service at a site.";
  }

  identity one2one-bundling {
    base bundling-type;
    description
      "Identity for one-to-one service bundling, i.e.,
       each L2VPN can be associated with only one CE-VLAN ID
       at a site.";
  }

  identity all2one-bundling {
    base bundling-type;
    description
      "Identity for all-to-one bundling, i.e., all CE-VLAN IDs
       are mapped to one L2VPN service.";
  }

  /*
   * Identities related to customer applications
   */

  identity customer-application {
    description
      "Base identity for customer applications.";
  }

  identity web {
    base customer-application;
    description
      "Identity for a aWeb application (e.g., HTTP, HTTPS).";
  }

  identity mail {
    base customer-application;
    description
      "Identity for a mail application.";
  }

  identity file-transfer {
    base customer-application;
    description
      "Identity for a file transfer application
       (e.g., FTP, SFTP).";
  }

  identity database {
    base customer-application;
    description
      "Identity for a database application.";
  }

  identity social {
    base customer-application;
    description
      "Identity for a social-network application.";
  }

  identity games {
    base customer-application;
    description
      "Identity for a gaming application.";
  }

  identity p2p {
    base customer-application;
    description
      "Identity for a peer-to-peer application.";
  }

  identity network-management {
    base customer-application;
    description
      "Identity for a management application
       (e.g., Telnet, syslog, SNMP).";
  }

  identity voice {
    base customer-application;
    description
      "Identity for a voice application.";
  }

  identity video {
    base customer-application;
    description
      "Identity for a video conference application.";
  }

  identity embb {
    base customer-application;
    description
      "Identity for an enhanced Mobile Broadband (eMBB)
       application.  Note that an eMBB application demands
       network performance with a wide variety of
       characteristics, such as data rate, latency,
       loss rate, reliability, and many other parameters.";
  }

  identity urllc {
    base customer-application;
    description
      "Identity for an Ultra-Reliable and Low Latency
       Communications (URLLC) application.  Note that a
       URLLC application demands network performance
       with a wide variety of characteristics, such as latency,
       reliability, and many other parameters.";
  }

  identity mmtc {
    base customer-application;
    description
      "Identity for a massive Machine Type
       Communications (mMTC) application.  Note that an
       mMTC application demands network performance
       with a wide variety of characteristics, such as data
       rate, latency, loss rate, reliability, and many
       other parameters.";
  }

  /*
   * Identities related to Ethernet Services
   */

  identity control-mode {
    description
      "Defines the type of control mode on L2CP protocols.";
  }

  identity peer {
    base control-mode;
    description
      "'peer' mode, i.e., participate in the protocol towards
       the CE.  Peering is common for LACP and the Ethernet
       Local Management Interface (E-LMI) and, occasionally,
       for LLDP.  For VPLSs and VPWSs, the subscriber can also
       request that the SP peer enable spanning tree.";
  }

  identity tunnel {
    base control-mode;
    description
      "'tunnel' mode, i.e., pass to the egress or destination
       site.  For  Ethernet Private Lines (EPLs), the
       expectation is that L2CP frames are tunnelled.";
  }

  identity discard {
    base control-mode;
    description
      "'discard' mode, i.e., discard the frame.";
  }

  identity neg-mode {
    description
      "Defines the type of negotiation mode.";
  }

  identity full-duplex {
    base neg-mode;
    description
      "Refers to the auto-negotiation mode.";
  }

  identity auto-neg {
    base neg-mode;
    description
      "Indicates the auto-negotiation mode.";
  }

  /******** Collection of VPN-related Types & Identities ********/

  typedef vpn-id {
    type string;
    description
      "Defines an identifier that is used as
       a service identifier, for example.";
  }

  /*
   * Types related to Ethernet Services
   */

  typedef ccm-priority-type {
    type uint8 {
      range "0..7";
    }
    description
      "A 3-bit priority value to be used in the VLAN tag,
       if present in the transmitted frame.";
  }

  /******* VPN-related reusable groupings *******/

  grouping vpn-description {
    description
      "Provides common VPN information.";
    leaf vpn-id {
      type vpn-id;
      description
        "VPN identifier.
         This identifier has a local meaning.";
    }
    leaf vpn-name {
      type string;
      description
        "A name used to refer to the VPN.";
    }
    leaf vpn-description {
      type string;
      description
        "Textual description of a VPN service.";
    }
    leaf customer-name {
      type string;
      description
        "Name of the customer that actually uses the VPN service.";
    }
  }

  grouping vpn-profile-cfg {
    description
      "Grouping for VPN Profile configuration.";
    container valid-provider-identifiers {
      description
        "Container for Valid Provider Identifies.";
      list cloud-identifier {
        if-feature "cloud-access";
        key "id";
        description
          "List for Cloud Identifiers.";
        leaf id {
          type string;
          description
            "Identification of cloud service.
             Local administration meaning.";
        }
      }
      list encryption-profile-identifier {
        key "id";
        description
          "List for encryption profile identifiers.";
        leaf id {
          type string;
          description
            "Identification of the SP encryption profile
             to be used.  Local administration meaning.";
        }
      }
      list qos-profile-identifier {
        key "id";
        description
          "List for QoS Profile Identifiers.";
        leaf id {
          type string;
          description
            "Identification of the QoS Profile to be used.
             Local administration meaning.";
        }
      }
      list bfd-profile-identifier {
        key "id";
        description
          "List for BFD Profile identifiers.";
        leaf id {
          type string;
          description
            "Identification of the SP BFD Profile to be used.
             Local administration meaning.";
        }
      }
      list forwarding-profile-identifier {
        key "id";
        description
          "List for Forwrding Profile identifiers.";
        leaf id {
          type string;
          description
            "Identification of the Forwrding Profile Filter to be used.
             Local administration meaning.";
        }
      }
      list routing-profile-identifier {
        key "id";
        description
          "List for Routing Profile Identifiers.";
        leaf id {
          type string;
          description
            "Identification of the routing Profile to be used
             by the routing-protocols within sites, vpn-
             network-accesses or vpn-nodes for refering
             vrf-import/export policies.

             This identifier has a local meaning.";
        }
      }
      nacm:default-deny-write;
    }
  }

  grouping status-timestamp {
    description
      "This grouping defines some operational
       parameters for the service.";
    leaf status {
      type identityref {
        base operational-status;
      }
      config false;
      description
        "Operations status.";
    }
    leaf last-updated {
      type yang:date-and-time;
      config false;
      description
        "Indicates the actual date and time of the service
         status change.";
    }
  }

  grouping service-status {
    description
      "Service status grouping.";
    container status {
      description
        "Service status.";
      container admin-status {
        description
          "Administrative service status.";
        leaf status {
          type identityref {
            base administrative-status;
          }
          description
            "Administrative service status.";
        }
        leaf last-updated {
          type yang:date-and-time;
          description
            "Indicates the actual date and time of the service
             status change.";
        }
      }
      container oper-status {
        description
          "Operational service status.";
        uses status-timestamp;
      }
    }
  }
  grouping svc-transport-encapsulation {
    description
      "This grouping defines the type of underlay transport
       for VPN service.";
    container underlay-transport {
      description
        "Container for the Transport underlay.";
      leaf-list type {
        type identityref {
          base protocol-type;
        }
        ordered-by user;
        description
          "Protocols used to deliver a VPN service.";
      }
    }
  }

  grouping rt-rd {
    description
      "Grouping for RT and RD.";
    choice rd-choice {
      description
        "Route distinguisher choice between several options
         on providing the route distiniguisher value.";
      case directly-assigned {
        description
          "Explicitly assign a RD value";
        leaf rd {
          type rt-types:route-distinguisher;
          description
            "Explicitly assign a route distinguisher (RD) value.";
        }
      }
      case pool-assigned {
        leaf rd-pool-name {
          type string;
          description
            "The server will auto-assign a route
             distinguisher value and use that value operationally.
             The assignment will be selected from the pool
             identified by the rd-pool-name.";
        }
        leaf rd-from-pool {
          type rt-types:route-distinguisher;
          config false;
          description
            "The RD assigned from the pool name.";
        }
      }
      case full-autoasigned {
        leaf auto {
          type empty;
          description
            "Indicates an RD is fully auto assigned.";
        }
        leaf rd-auto {
          type rt-types:route-distinguisher;
          config false;
          description
            "Auto assigned RD.";
        }
      }
      case no-rd {
        description
          "Use the empty type to indicate RD has no value and
           is not to be auto-assigned.";
        leaf no-rd {
          type empty;
          description
            "No RD is assigned.";
        }
      }
    }
    container vpn-targets {
      description
        "Set of route-targets to match for import and export routes
         to/from VRF";
      uses vpn-route-targets;
    }
  }

  grouping vpn-route-targets {
    description
      "A grouping that specifies Route Target import-export rules
       used in a BGP-enabled VPN.";
    reference
      "RFC 4364: BGP/MPLS IP Virtual Private Networks (VPNs)
       RFC 4664: Framework for Layer 2 Virtual Private Networks
                 (L2VPNs)";
    list vpn-target {
      key "id";
      description
        "L3VPN route targets. AND/OR Operations are available
         based on the RTs assigment.";
      leaf id {
        type int8;
        description
          "Identifies each VPN Target";
      }
      list route-targets {
        key "route-target";
        description
          "List of Route Targets.";
        leaf route-target {
          type rt-types:route-target;
          description
            "Route Target value";
        }
      }
      leaf route-target-type {
        type rt-types:route-target-type;
        mandatory true;
        description
          "Import/export type of the Route Target.";
      }
    }
    container vpn-policies {
      description
        "VPN policies";
      leaf import-policy {
        type string;
        description
          "Defines the import policy.";
      }
      leaf export-policy {
        type string;
        description
          "Defines the export policy.";
      }
    }
  }

  grouping vpn-components-group {
    description
      "Grouping definition to assign
       group-ids to associate VPN nodes, sites,
       or network accesses.";
    container groups {
      description
        "Lists the groups to which a VPN node,
         a site, or a network access belongs to.";
      list group {
        key "group-id";
        description
          "List of group-ids.";
        leaf group-id {
          type string;
          description
            "Is the group-id to which a VPN node,
             a site, or a network access belongs to.";
        }
      }
    }
  }

  grouping placement-constraints {
    description
      "Constraints for placing a network
       access.";
    list constraint {
      key "constraint-type";
      description
        "List of constraints.";
      leaf constraint-type {
        type identityref {
          base placement-diversity;
        }
        description
          "Diversity constraint type.";
      }
      container target {
        description
          "The constraint will apply against
           this list of groups.";
        choice target-flavor {
          description
            "Choice for the group definition";
          case id {
            list group {
              key "group-id";
              description
                "List of groups";
              leaf group-id {
                type string;
                description
                  "The constraint will apply
                   against this particular
                   group-id.";
              }
            }
          }
          case all-accesses {
            leaf all-other-accesses {
              type empty;
              description
                "The constraint will apply
                 against all other network
                 accesses of a site.";
            }
          }
          case all-groups {
            leaf all-other-groups {
              type empty;
              description
                "The constraint will apply
                 against all other groups the
                 customer is managing.";
            }
          }
        }
      }
    }
  }

  grouping ports {
    description
      "Choice of specifying a source or destination port numbers.";
    choice source-port {
      description
        "Choice of specifying the source port or referring to
         a group of source port numbers.";
      container source-port-range-or-operator {
        description
          "Source port definition.";
        uses packet-fields:port-range-or-operator;
      }
    }
    choice destination-port {
      description
        "Choice of specifying a destination port or referring
         to a group of destination port numbers.";
      container destination-port-range-or-operator {
        description
          "Destination port definition.";
        uses packet-fields:port-range-or-operator;
      }
    }
  }

  grouping qos-classification-policy {
    description
      "Configuration of the traffic classification
       policy.";
    list rule {
      key "id";
      ordered-by user;
      description
        "List of marking rules.";
      leaf id {
        type string;
        description
          "A description identifying the
           qos-classification-policy rule.";
      }
      choice match-type {
        default "match-flow";
        description
          "Choice for classification.";
        case match-flow {
          choice l3 {
            description
              "Either IPv4 or IPv6.";
            container ipv4 {
              description
                "Rule set that matches IPv4 header.";
              uses packet-fields:acl-ip-header-fields;
              uses packet-fields:acl-ipv4-header-fields;
            }
            container ipv6 {
              description
                "Rule set that matches IPv6 header.";
              uses packet-fields:acl-ip-header-fields;
              uses packet-fields:acl-ipv6-header-fields;
            }
          }
          choice l4 {
            description
              "Can be TCP or UDP";
            container tcp {
              description
                "Rule set that matches TCP header.";
              uses packet-fields:acl-tcp-header-fields;
              uses ports;
            }
            container udp {
              description
                "Rule set that matches UDP header.";
              uses packet-fields:acl-udp-header-fields;
              uses ports;
            }
          }
        }
        case match-application {
          leaf match-application {
            type identityref {
              base customer-application;
            }
            description
              "Defines the application to match.";
          }
        }
      }
      leaf target-class-id {
        type string;
        description
          "Identification of the class of service.
           This identifier is internal to the
           administration.";
      }
    }
  }
}
