module ietf-yang-api {
  namespace "urn:ietf:params:xml:ns:yang:ietf-yang-api";
  prefix "api";

  organization
    "IETF NETCONF (Network Configuration) Working Group";

  contact
    "Editor:   Andy Bierman
               <mailto:andy@yumaworks.com>

     Editor:   Martin Bjorklund
               <mailto:mbj@tail-f.com>";

  description
    "This module contains a collection of YANG language extensions
     to describe REST API Resources using YANG data definition
     statements.

     Copyright (c) 2012 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: remove this note
  // Note: extracted from draft-bierman-netconf-yang-api-00.txt

  // RFC Ed.: update the date below with the date of RFC publication
  // and remove this note.
  revision 2012-05-27 {
    description
      "Initial revision.";
    reference
      "RFC XXXX: YANG-API Protocol.";
  }

  /*
   * Extensions
   */

  extension optional-key {
    description
      "This extension is used to allow the client to create
       a new instance of a resource without providing a
       value for the key leaf containing this statement.
       This extension is ignored for NETCONF, and only
       applies to YANG-API resources and fields.
       This extension is ignored unless it appears
       directly within a 'leaf' data definition statement.";
  }

  /*
   * Operations
   */

  rpc lock-datastore {
    description
      "Lock the running configuration datastore for writing.";
  }

  rpc save-datastore {
    description
      "Save the running configuration datastore to non-volatile
       storage.";
  }

  rpc unlock-datastore {
    description
      "Unlock the running configuration datastore.";
  }

  rpc commit {
    description
      "Commit the transaction datastore contents to
       the running configuration datastore.";
  }

  rpc discard-changes {
    description
      "Replace the transaction datastore contents with
       the running configuration datastore contents.";
  }

  rpc update {
    description
      "Attempt to merge the running configuration datastore
       contents into the transaction datastore contents.";
  }

  rpc validate {
    description
      "Validate the transaction datastore contents.";
  }

}
