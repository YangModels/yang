module ietf-ipfix-data-export {
  yang-version 1.1;

  namespace
    "urn:ietf:params:xml:ns:yang:ietf-ipfix-data-export";

  prefix ipfixde;

  import ietf-inet-types {
    prefix inet;
    reference
      "RFC 6991: Common YANG Data Types";
  }

  import ietf-yang-types {
    prefix yang;
    reference
      "RFC 6991: Common YANG Data Types";
  }

  import ietf-interfaces {
    prefix if;
    reference
      "RFC 8343: A YANG Model for Interface Management";
  }

  import ietf-tls-client {
    prefix tlsc;
    reference
      "I-D.ietf-netconf-tls-client-server:
       YANG Groupings for TLS Clients and TLS Servers";
  }

  organization
    "IETF";

  contact
    "Web:      TBD
     List:     TBD

     Editor:   Marta Seda
               <mailto:marta.seda@calix.com>

     Editor:   Anand Arokiaraj
               <mailto:anand.arokiaraj@nokia.com>";

  // RFC Ed.: replace XXXX with actual RFC numbers and
  // remove this note.
  description
    "This module contains a collection of YANG definitions for the
     management exporting data over IPFIX.

     This data model is designed for the Network Management Datastore
     Architecture defined in RFC 8342.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2022-08-12 {
    description
      "Initial revision.";
    reference
      "RFC XXXX: YANG Data Model for the IP Flow Information Export
                 (IPFIX) Data Export";
  }

  feature exporter {
    description
      "If supported, the Exporting Device can be used as
       an Exporter. Exporting Processes can be configured.";
  }

  feature if-mib {
    description
      "This feature indicates that the device implements
       the IF-MIB.";
    reference
      "RFC 2863: The Interfaces Group MIB";
  }
  identity export-mode {
    description
      "Base identity for different usages of export
       destinations configured for an Exporting Process.";
    reference
      "RFC 6728, Section 4.4 (exportMode)";
  }

  identity parallel {
    base export-mode;
    description
      "Parallel export of Data Records to all destinations configured
       for the Exporting Process.";
    reference
      "RFC 6728, Section 4.4 (exportMode)";
  }

  identity load-balancing {
    base export-mode;
    description
      "Load-balancing between the different destinations
       configured for the Exporting Process.";
    reference
      "RFC 6728, Section 4.4 (exportMode)";
  }

  identity fallback {
    base export-mode;
    description
      "Export to the primary destination (i.e., the first
       destination configured for the Exporting Process). If the
       export to the primary destination fails, the Exporting Process
       tries to export to the secondary destination.  If the
       secondary destination fails as well, it continues with the
       tertiary, etc.";
    reference
      "RFC 6728, Section 4.4 (exportMode)";
  }

  identity options-type {
    description
      "Base identity for report types exported with
       options templates.";
  }

  identity exporting-reliability {
    base options-type;
    description
      "Exporting Process Reliability Statistics.";
    reference
      "RFC 7011, Section 4.3";
  }

  identity reducing-redundancy {
    base options-type;
    description
      "Enables the utilization of Options Templates to reduce
       redundancy in the exported Data Records.";
    reference
      "RFC 5473";
  }

  identity extended-type-information {
    base options-type;
    description
      "Export of extended type information for enterprise-specific
       Information Elements used in the exported Templates.";
    reference
      "RFC 5610";
  }

  typedef ie-id-type {
    type uint16 {
      range "1..32767";
    }
    description
      "Type for Information Element identifiers.";
  }

  typedef transport-session-status {
    type enumeration {
      enum "inactive" {
        value 0;
        description
          "This value MUST be used for Transport Sessions that are
           specified in the system but currently not active.

           The value can be used for Transport Sessions that are
           backup (secondary) sessions.";
      }
      enum "active" {
        value 1;
        description
          "This value MUST be used for Transport Sessions that are
           currently active and transmitting or receiving data.";
      }
      enum "unknown" {
        value 2;
        description
          "This value MUST be used if the status of the Transport
           Sessions cannot be detected by the device.

           This value should be avoided as far as possible.";
      }
    }
    description
      "Status of a Transport Session.";
    reference
      "RFC 6728, Section 4.7 (status)";
  }

  typedef resource {
    type instance-identifier {
      require-instance false;
    }
    description
      "A resource from which data will be exported.";
  }

  grouping transport-session-state-parameters {
    description
      "State parameters of a Transport Session originating from an
       Exporting Process.";
    reference
      "RFC 7011; RFC 6615, Section 8 (ipfixTransportSessionEntry,
       ipfixTransportSessionStatsEntry)";

    leaf name {
      type string;
      description
        "The name of the interface.

         An implementation MAY map this leaf to the ifName
         MIB object.  Such an implementation needs to use some
         mechanism to handle the differences in size and characters
         allowed between this leaf and ifName.  The definition of
         such a mechanism is outside the scope of this document.";
      reference
        "RFC 2863: The Interfaces Group MIB - ifName";
    }

    leaf source-address {
      type inet:host;
      description
        "The source address of the Exporter of the IPFIX Transport
         Session.";
      reference
        "RFC 6728, Section 4.7 (sourceAddress);
         RFC 4960, Section 6.4";
    }

    leaf destination-address {
      type inet:host;
      description
        "The destination address of the path that is selected by the
         Exporter to send IPFIX messages to the Collector.

         It is possible that if an FQDN address
         is configured it resolves into many addresses.";
      reference
        "RFC 6728, Section 4.7 (destinationAddress);
         RFC 4960, Section 6.4";
    }

    leaf source-port {
      type inet:port-number;
      description
        "The transport-protocol port number of the Exporter of the
         IPFIX Transport Session.";
      reference
        "RFC 6728, Section 4.7 (sourcePort).";
    }

    leaf destination-port {
      type inet:port-number;
      description
        "The TCP port number of the Collector of the IPFIX Transport
         Session.";
      reference
        "RFC 6728, Section 4.7 (destinationPort)";
    }

    leaf status {
      type transport-session-status;
      description
        "Status of the Transport Session.";
        reference
         "RFC 6728, Section 4.7 (status)";
    }

    leaf rate {
      type yang:gauge32;
      units "bytes per second";
      description
        "The number of bytes per second transmitted by the
         Exporting Process.";
      reference
        "RFC 6728, Section 4.7 (rate)";
    }

    leaf bytes {
      type yang:counter64;
      units "bytes";
      description
        "The number of bytes transmitted by the Exporting Process.

         Discontinuities in the value of this counter can occur at
         re-initialization of the management system, and at other
         times as indicated by the value of discontinuity-time.";
      reference
        "RFC 6728, Section 4.7 (bytes)";
    }

    leaf messages {
       type yang:counter64;
       units "IPFIX Messages";
       description
         "The number of messages transmitted by the Exporting
          Process.

          Discontinuities in the value of this counter can occur at
          re-initialization of the management system, and at other
          times as indicated by the value of discontinuity-time.";
       reference
         "RFC 6728, Section 4.7 (messages)";
    }

    leaf discarded-messages {
      type yang:counter64;
      units "IPFIX Messages";
      description
        "This parameter indicates the number of messages that could
         not be sent due to internal buffer overflows, network
         congestion, routing issues, etc.

         Discontinuities in the value of this counter can occur at
         re-initialization of the management system, and at other
         times as indicated by the value of discontinuity-time.";
      reference
        "RFC 6728, Section 4.7 (discardedMessages)";
    }

    leaf data-records {
      type yang:counter64;
      units "Data Records";
      description
        "The number of Data Records transmitted by the Exporting
         Process.

         Discontinuities in the value of this counter can occur at
         re-initialization of the management system, and at other
         times as indicated by the value of discontinuity-time.";
      reference
        "RFC 6728, Section 4.7 (records)";
    }

    leaf templates {
      type yang:counter32;
      units "Templates";
      description
        "The number of Templates transmitted by the Exporting
         Process.

         Discontinuities in the value of this counter can occur at
         re-initialization of the management system, and at other
         times as indicated by the value of discontinuity-time.";
      reference
        "RFC 6728, Section 4.7 (templates)";
    }

    leaf options-templates {
      type yang:counter32;
      units "Options Templates";
      description
        "The number of Option Templates transmitted by the Exporting
         Process.

         Discontinuities in the value of this counter can occur at
         re-initialization of the management system, and at other
         times as indicated by the value of discontinuity-time.";
      reference
        "RFC 6728, Section 4.7 (optionsTemplates)";
    }

    leaf start-time {
      type yang:date-and-time;
      description
        "Timestamp of the start of the given Transport Session.";
    }

    leaf discontinuity-time {
      type yang:date-and-time;
      description
        "Timestamp of the most recent occasion at which one or more
         of the Transport Session counters suffered a
         discontinuity.";
      reference
        "RFC 6728, Section 4.7 (transportSessionDiscontinuityTime)";
    }
  }

  grouping export-template-state-parameters {
    description
      "State parameters of a (Options) Template used by an Exporting
       Process in a specific Transport Session.";
    reference
      "RFC 7011; RFC 6728, Section 4.8 (Template Class)";

    list template {
      key "name";
      description
        "This list contains the Templates and Options Templates that
         are transmitted by the Exporting Process.

         Withdrawn or invalidated (Options) Templates MUST be removed
         from this list.";

      leaf name {
        type string;
        description
          "An arbitrary string which uniquely identifies the
           template.";
      }

      leaf observation-domain-id {
        type uint32;
        description
          "The ID of the Observation Domain for which this Template
           is defined.";
        reference
          "RFC 6728, Section 4.8 (observationDomainId).";
      }

      leaf id {
        type uint16 {
          range "256..65535";
        }
        description
          "This number indicates the Template ID in the IPFIX
           message.";
        reference
          "RFC 6728, Section 4.8 (templateId).";
      }

      leaf set-id {
        type uint16 {
          range "2..3 | 256..65535";
        }
        description
          "This number indicates the Set ID of the Template.
           A value of 2 is reserved for Template Sets.  A value of 3
           is reserved for Options Template Sets.  Values from 4 to
           255 are reserved for future use.  Values 256 and above
           are used for Data Sets.  The Set ID values of 0 and 1 are
           not used for historical reasons.";
        reference
          "RFC 7011, Section 3.3.2;
           RFC 6728, Section 4.8 (setId)";
      }

      leaf access-time {
        type yang:date-and-time;
        description
          "This parameter contains the time when this (Options)
           Template was last sent to the Collector(s).";
        reference
          "RFC 6728, Section 4.8 (accessTime).";
      }

      leaf data-records {
        type yang:counter64;
        description
          "The number of transmitted Data Records defined by this
           (Options) Template.

           Discontinuities in the value of this counter can occur at
           re-initialization of the management system, and at other
           times as indicated by the value of discontinuity-time.";
        reference
          "RFC 6728, Section 4.8 (templateDataRecords).";
      }

      leaf discontinuity-time {
        type yang:date-and-time;
        description
          "Timestamp of the most recent occasion at which the counter
           data-records suffered a discontinuity.";
        reference
          "RRFC 6728, Section 4.8 (templateDiscontinuityTime).";
      }

      list field {
        key "name";
        description
          "This list contains the (Options) Template fields of which
           the (Options) Template is defined.

           The order of the list corresponds to the order
           of the fields in the (Option) Template Record.";

        leaf name {
          type string;
          description
            "An arbitrary string which uniquely identifies the
             template field.";
        }

        leaf ie-id {
          type ie-id-type;
          description
            "This parameter indicates the Information Element
             identifier of the field.";
          reference
            "RFC 7011; RFC 6728, Section 4.8 (ieId).";
        }

        leaf ie-length {
          type uint16;
          units "octets";
          description
            "This parameter indicates the length of the Information
             Element of the field.";
          reference
            "RFC 7011; RFC 6728, Section 4.8 (ieLength).";
        }

        leaf ie-enterprise-number {
          type uint32;
          description
            "This parameter indicates the IANA enterprise number of
             the authority defining the Information Element
             identifier.
             If the Information Element is not enterprise-specific,
             this state parameter is zero.";
          reference
            "RFC 6728, Section 4.8 (ieEnterpriseNumber);
             IANA registry for Private Enterprise Numbers,
             http://www.iana.org/assignments/enterprise-numbers.";
        }

        leaf is-scope {
          when "../../set-id = 3" {
          description
            "This parameter is available for Options Templates
             (Set ID is 3).";
          }
          type empty;
          description
            "If present, this is a scope field.";
          reference
            "RFC 6728, Section 4.8 (isScope).";
        }
      }
    }
  }

  grouping exporter-parameters {
    description
      "Parameters of an exporter.";

    leaf ipfix-version {
      type uint16;
      default '10';
      description
        "IPFIX version number.";
      reference
        "RFC 7011.";
    }

    container source {
      description
        "Configuration corresponding to how exporter's source IP
         address is specified.";

      choice source-method {
        description
          "Method to configure the source address of the exporter
           or the interface to be used by the exporter.

           Note that it is expected that other methods be available.
           Those methods can augment this choice.";

        case interface {
          leaf interface {
            type if:interface-ref;
            description
              "The interface to be used by the Exporting Process.";
          }
        }

        case source-address {
          leaf source-address {
            type inet:host;
            description
              "The source IP address or hostname used by the
               Exporting Process.";
          }
        }
      }
    }

    container destination {
      description
        "Configuration corresponding to how exporter's destination IP
         address is specified.";

      choice destination-method {
        mandatory true;
        description
          "Method to configuring the destination address of the
           Collection Process to which IPFIX Messages are sent.

           Note it is expected that if other methods are available
           that they would augment from this statement.";

        case destination-address {
          leaf destination-address {
            type inet:host;
            description
              "The destination IP address or hostname of the
               Collecting Process to which IPFIX Messages are sent.
               A hostname may resolve to one or more IP
               addresses.";
          }
        }
      }
    }

    leaf destination-port {
      type inet:port-number;
      description
        "If not configured by the user, the Exporting Device uses
         the default port number for IPFIX, which is 4739 without TLS
         and 4740 if TLS is activated.";
    }

    leaf send-buffer-size {
      type uint32;
      units "bytes";
      description
        "Size of the socket send buffer.

         If not configured by the user, this parameter is set by
         the Exporting Device.";
      reference
        "RFC 6728, Section 4.4.3 (sendBufferSize).";
    }

    leaf rate-limit {
      type uint32;
      units "bytes per second";
      description
        "Maximum number of bytes per second the Exporting Process may
         export to the given destination.  The number of bytes is
         calculated from the lengths of the IPFIX Messages exported.
         If not configured, no rate limiting is performed.";
      reference
        "RFC 6728, Section 4.4.3 (rateLimit).";
    }

    leaf connection-timeout {
      type uint32;
      units seconds;
      description
        "Time after which the exporting process deems the TCP
         connection to have failed.";
      reference
        "RFC 7011, Sections 10.4.4 and 10.4.5.";
    }

    leaf retry-schedule {
      type uint32 {
      range "60..max";
      }
      units seconds;
      description
        "Time after which the exporting process retries the TCP
         connection to a collector.";
      reference
        "RFC 7011, Section 10.4.4.";
    }

    container security {
      description
        "Security related parameters.";

      uses tlsc:tls-client-grouping;
    }
  }

  grouping exporting-process-parameters {
    description
      "Parameters of an Exporting Process.";

    leaf export-mode {
      type identityref {
        base export-mode;
      }
      default 'fallback';
      description
        "This parameter determines to which configured destination(s)
         the incoming Data Records are exported.";
    }

    list destination {
      key "name";
      min-elements 1;
      ordered-by user;
      description
        "List of export destinations.";

      leaf name {
        type string;
        description
          "An arbitrary string which uniquely identifies the export
           destination.";
      }

      container exporter {
        description
          "Exporter parameters.";

        uses exporter-parameters;

        container transport-session {
          config false;
          description
            "Transport session state data.";

          uses transport-session-state-parameters;
          uses export-template-state-parameters;
        }
      }
    }

    list options {
      key "name";
      description
        "List of options reported by the Exporting Process.";

      leaf name {
        type string;
        description
          "An arbitrary string which uniquely identifies the
           option.";
      }
      uses options-parameters;
    }
  }

  grouping options-parameters {
    description
      "Parameters specifying the data export using an Options
       Template.";

    leaf options-type {
      type identityref {
        base options-type;
      }
      mandatory true;
      description
        "Type of the exported options data.";
    }

    leaf options-timeout {
      type uint32;
      units "milliseconds";
      description
        "Time interval for periodic export of the options data. If
         set to zero, the export is triggered when the options data
         has changed.

         If not configured by the user, this parameter is set by the
         Exporting Device.";
    }
  }

  grouping data-template-parameters {
    description
      "Field Layout parameters.";

    leaf observation-domain-id {
      type uint32;
      default 0;
      description
        "An identifier of an Observation Domain that is locally
         unique to an Exporting Process (see RFC 7011 Section 3.1).

         Typically, this Information Element is for limiting the
         scope of other Information Elements.

         A value of 0 indicates that no specific Observation Domain
         is identified by this Information Element.";
    }

    container field-layout {
      description
        "Field Layout parameters.";

      list field {
        key name;
        min-elements 1;
        description
          "Superset of statistics field names or special field-names
           (e.g., timestamps, etc) for interpreting statistics that
           are included in the Data Records generated by the
           device.";

        leaf name {
          type string;
          description
            "An arbitrary string which uniquely identifies the
             field.";
        }

        choice identifier {
          mandatory true;
          description
            "The Information Element to be added to the template.";

          case ie-name {
            leaf ie-name {
              type string;
              description
                "Name of the Information Element.";
            }
          }

          case ie-id {
            leaf ie-id {
              type ie-id-type;
              description
                "ID of the Information Element.";
            }
          }
        }

        leaf ie-length {
          type uint16;
          units octets;
          description
            "Length of the field in which the Information Element is
             encoded.  A value of 65535 specifies a variable-length
             Information Element.  For Information Elements of
             integer and float type, the field length MAY be set to a
             smaller value than the standard length of the abstract
             data type if the rules of reduced size encoding are
             fulfilled.

             If not configured by the user, this parameter is set by
             the Exporting Device.";
          reference
            "RFC 7011, Section 6.2";
        }

        leaf ie-enterprise-number {
          type uint32;
          default 0;
          description
            "If this parameter is zero, the Information Element is
             registered in the IANA registry of IPFIX Information
             Elements or unspecified (if the Informational Element is
             not IANA registered).

             If this parameter is configured with a non-zero private
             enterprise number, the Information Element is
             enterprise-specific.";
          reference
            "RFC 7011; RFC 5103;
             IANA registry for Private Enterprise Numbers,
             http://www.iana.org/assignments/enterprise-numbers;
             IANA registry for IPFIX Entities,
             http://www.iana.org/assignments/ipfix";
        }
      }
    }
  }

  container ipfix-data-export {
    description
      "IPFIX data export node.";

    list exporting-process {
      if-feature exporter;
      key "name";
      description
        "List of Exporting Processes of the IPFIX Exporting Device
         for which configuration will be applied.";

      leaf name {
        type string;
        description
          "An arbitrary string which uniquely identifies the
           Exporting Process.";
      }

      leaf enabled {
        type boolean;
        default "true";
        description
          "If true, this Exporting Process is enabled for
           exporting.";
      }

      uses exporting-process-parameters;

      leaf exporting-process-id {
        type uint32;
        config false;
        description
          "The identifier of the Exporting Process.  This parameter
           corresponds to the Information Element exportingProcessId.
           Its occurrence helps to associate Exporting Process
           parameters with Exporing Process statistics exported by
           the Exporting Device using the Exporting Process
           Reliability Statistics Template as defined by the IPFIX
           protocol specification.";
        reference
          "RFC 7011, Section 4.3; IANA registry for IPFIX
           Entities, http://www.iana.org/assignments/ipfix.";
      }
    }

    list template {
      key name;
      description
        "List of data templates of the Exporting Device.";

      leaf name {
        type string;
        description
          "An arbitrary string which uniquely identifies the data
           template.";
      }

      leaf enabled {
        type boolean;
        default "true";
        description
          "If true, this template is enabled and the specified data
           is able to be exported.";
      }

      leaf export-interval {
        type uint32;
        units "seconds";
        description
          "This parameter configures the interval (in seconds) for
           periodical export of Data Records.

           If not configured by the user, the Exporting Device
           sets this parameter.";
      }

      uses data-template-parameters;

      leaf-list exporting-process {
        if-feature exporter;
        type leafref {
          path "/ipfix-data-export"
             + "/exporting-process/name";
        }
        description
          "Data Records are exported by all Exporting Processes in
           the list.";
      }

      choice resource-identifier {
        description
          "Method to select the resources from which the Data
           Records are to be exported.

           Note that it is expected that other methods be available.
           Those methods can augment this choice.";

        case resource-instance {
          leaf-list resource-instance {
            type resource;
            description
              "Data Records are sourced from all the resources in
               this list.";
          }
        }
      }

      leaf data-records {
        type yang:counter64;
        units "Data Records";
        config false;
        description
          "The number of Data Records generated for this template.

           Discontinuities in the value of this counter can occur
           at re-initialization of the management system, and at
           other times as indicated by the value of Discontinuity
           Time.";
      }

      leaf discontinuity-time {
        type yang:date-and-time;
        config false;
        description
          "Timestamp of the most recent occasion at which the
           counter data records suffered a discontinuity.";
      }
    }
  }
}
