module ietf-bmp-tcp-dependencies {
  yang-version 1.1;
  namespace "urn:ietf:params:xml:ns:yang:ietf-bmp-tcp-dependencies";
  prefix bmp-tcp;

  import ietf-bmp {
    prefix bmp;
    reference
      "RFC XXXX: BMP YANG Module.";
  }
  import ietf-tcp {
    prefix tcp;
    reference
      "RFC 9648: YANG Data
       Model for TCP.";
  }
  import ietf-tcp-common {
    prefix tcpcmn;
    reference
      "RFC 9643: YANG Groupings for TCP
       Clients and TCP Servers.";
  }
  import ietf-key-chain {
    prefix key-chain;
    reference
      "RFC 8177: YANG Key Chain.";
  }

  organization
    "IETF GROW Working Group";
  contact
    "WG Web:   <https://datatracker.ietf.org/wg/grow/>
     WG List:  <mailto:grow@ietf.org>

     Author:  Camilo Cardona
        <mailto:camilo@ntt.net>

     Author:  Paolo Lucente
        <mailto:paolo@ntt.net>

     Author:  Thomas Graf
        <mailto:thomas.graf@swisscom.com>

     Author:  Benoit Claise
        <mailto:benoit@everything-ops.net>

     Author:  Dhananjay Patki
        <mailto:dhpatki@cisco.com>

     Author:  Prasad S. Narasimha
        <mailto:snprasad@cisco.com>";
  description
    "This module specifies a structure for BMP
     (BGP Monitoring Protocol) configuration and monitoring.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.
    ";

  revision 2025-01-02 {
    description
      "initial version";
    reference
      "RFC XXXX: BMP YANG Data Model";
  }

  augment "/bmp:bmp/bmp:monitoring-stations/"
        + "bmp:monitoring-station/"
        + "bmp:connection/bmp:tcp-options" {
    description
      "Augment the TCP options of the ietf-bmp module";
    leaf mss {
      type tcp:mss;
      description
        "Maximum segment size (MSS) for the TCP connections.
         In the absence of this leaf, the system
         will select the maximum segment size for this
         connection.";
      reference
        "RFC 9293: Transmission Control
         Protocol (TCP) Specification.
         RFC 9648: YANG Data Model for TCP.";
    }
    uses tcpcmn:tcp-common-grouping;
    container secure-session {
      if-feature "tcp:authentication";
      presence "The presence of this container means the
                session should be secured. ";
      description
        "Container for describing how a particular BMP session
         is to be secured, based on RFC 9293 implementation,
         in the context of BMP [draft-ietf-grow-bmp-tcp-ao/]";
      reference
        "RFC 9293: Transmission Control
         Protocol (TCP) Specification";
      choice authentication {
        mandatory true;
        description
          "Choice of TCP authentication.";
        case ao {
          description
            "Uses TCP-AO to secure the session.";
          reference
            "RFC 5925: The TCP Authentication Option.
             RFC 9648: YANG Data Model for TCP (grouping ao)
             draft-ietf-grow-bmp-tcp-ao: BMP TCP Authentication
             Option";
          uses tcp:ao;
          leaf ao-keychain {
            type key-chain:key-chain-ref;
            description
              "Reference to the key chain that will be used by
               this model. Applicable for TCP-AO and TCP-MD5
               only";
            reference
              "RFC 8177: YANG Key Chain.";
          }
        }
        case md5 {
          description
            "Uses TCP-MD5 to secure the session.";
          reference
            "RFC 2385: Protection of BGP Sessions
             via the TCP MD5 Signature Option.";
          leaf md5-keychain {
            type key-chain:key-chain-ref;
            description
              "Reference to the key chain that will be used by
               this model. Applicable for TCP-AO and TCP-MD5
               only";
            reference
              "RFC 8177: YANG Key Chain.";
          }
        }
      }
    }
  }
}
