module ietf-schedule {
  yang-version 1;
  namespace "urn:ietf:params:xml:ns:yang:ietf-schedule";
  // replace with IANA namespace when assigned

  prefix "sch";

  import ietf-yang-types {
    prefix "yang";
  }

  organization "TBD";
  contact "TBD";
  description
    "The model allows time scheduling parameters to be specified.";

  revision "2016-10-11" {
    description "Initial revision";
    reference "TBD";
  }

  /*
   * Groupings
   */

  grouping schedule-config-attributes {
    description
      "A group of attributes for a schedule.";

    leaf inclusive-exclusive {
      type enumeration {
        enum inclusive {
          description "The schedule element is inclusive.";
        }
        enum exclusive {
          description "The schedule element is exclusive.";
        }
      }
      default "inclusive";
      description
        "Whether the list item is inclusive or exclusive.";
    }
    leaf start {
      type yang:date-and-time;
      description "Start time.";
    }
    leaf schedule-duration {
      type string {
        pattern
          'P(\d+Y)?(\d+M)?(\d+W)?(\d+D)?T(\d+H)?(\d+M)?(\d+S)?';
      }
      description "Schedule duration in ISO 8601 format.";
    }
    leaf repeat-interval {
      type string {
        pattern
          'R\d*/P(\d+Y)?(\d+M)?(\d+W)?(\d+D)?T(\d+H)?(\d+M)?'
          + '(\d+S)?';
      }
      description "Repeat interval in ISO 8601 format.";
    }
  } // schedule-config-attributes

  grouping schedule-state-attributes {
    description
      "State attributes for a schedule.";
    container next-event {
      description
        "The state information of the nexte scheduled event.";
      leaf start {
        type yang:date-and-time;
        description "Start time.";
      }
      leaf duration {
        type string {
          pattern
            'P(\d+Y)?(\d+M)?(\d+W)?(\d+D)?T(\d+H)?(\d+M)?(\d+S)?';
        }
        description "Schedule duration in ISO 8601 format.";
      }
      leaf operation {
        type enumeration {
          enum configure {
            description
              "Create the configuration data.";
          }
          enum deconfigure {
            description
              "Remove the configuration data.";
          }
          enum set {
            description
              "Set the specified configuration data.";
          }
          enum reset {
            description
              "Revert the specified configuration data back to the
               original value.";
          }
        }
        description "Operation type.";
      }
    } // next-event
  } // schedule-state-attributes

  grouping schedules {
    description
      "A list of schedules defining when a particular
       configuration takes effect.";
    container schedules {
      description
        "Container of a schedule list defining when a particular
         configuration takes effect.";
      list schedule {
        key "schedule-id";
        description "A list of schedule elements.";
        leaf schedule-id {
          type uint32;
          description "Identifies the schedule element.";
        }
        uses schedule-config-attributes;
      }
    }
  } // schedules

  /*
   * Configuration data nodes
   */
  container configuration-schedules {
    description
      "Serves as top-level container for a list of configuration
       schedules.";
    list target {
      key "object";
      description
        "A list of targets that configuration schedules are
         applied.";
      leaf object {
        type yang:xpath1.0;
        description
          "Xpath defining the data items of interest.";
      }
      leaf data-value {
        type string;
        description
          "The ephemeral value applied to the leaf data node
           specified by data-objects.
           This is applicable when object is a leaf.";
      }
      uses schedules;
      container state {
        config false;
        description
          "Operational state data.";
        uses schedule-state-attributes;
      } // state
    } // target
  } // configuration-schedules
}
