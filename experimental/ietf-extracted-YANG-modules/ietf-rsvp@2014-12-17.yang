module ietf-rsvp {

    namespace "urn:ietf:params:xml:ns:yang:rsvp";

    /* Replace with IANA when assigned */
    prefix "rsvp";

    /* import ietf-inet-types { prefix inet; } */
    import ietf-interfaces {
        prefix "if";
    }

    import ietf-inet-types {
        prefix inet;
    }

    organization
        "IETF TEAS Working Group";

    contact "TBA";

    description
        "This module contains the RSVP YANG data model.";

    revision 2014-12-17 {
        description "Initial revision.";
    }

    /* RSVP features */
    feature authentication {
        description
            "Indicates support for RSVP authentication";
    }

    feature graceful-restart {
        description
            "Indicates support for RSVP graceful restart";
    }

    feature refresh-reduction {
        description
            "Indicates support for RSVP refresh reduction";
    }

    feature hellos {
        description
            "Indicates support for RSVP hellos";
    }

    grouping graceful-restart {
        description "Configure RSVP Graceful-Restart parameters.";
        container graceful-restart {
            if-feature graceful-restart;
            presence "Enable RSVP graceful restart on the node.";

            leaf restart-time {
                description
                    "Graceful restart time (seconds).";
                reference
                    "RFC 5495: Description of the Resource
                    Reservation Protocol - Traffic-Engineered (RSVP-TE)
                    Graceful Restart Procedures";
                type uint32;
            }
            leaf recovery-time {
                description
                    "";
                type uint32;
            }
        }
    }

    grouping authentication {
        container authentication {
            if-feature authentication;
            description
                "Configure RSVP authentication.";
            leaf key-chain {
                description
                    "Key chain name to authenticate RSVP signaling
                    messages.";
                reference
                    "RFC 2747: RSVP Cryptographic Authentication";
                type string {
                     length "1..32";
                }
            }
            leaf lifetime {
                description
                    "Life time for each security association";
                reference
                    "RFC 2747: RSVP Cryptographic Authentication";
                type uint32 {
                     range "30..86400";
                }
            }
            leaf window-size {
                description
                    "Window-size to limit number of out-of-order
                    messages.";
                reference
                    "RFC 2747: RSVP Cryptographic Authentication";
                type uint32 {
                    range "1..64";
                }
            }
            leaf challenge {
                description
                    "Enable challenge messages.";
                reference
                    "RFC 2747: RSVP Cryptographic Authentication";
                type empty;
            }
            leaf retransmits {
                description
                    "Number of retransmits when messages are dropped.";
                reference
                    "RFC 2747: RSVP Cryptographic Authentication";
                 type uint32 {
                    range "1..10000";
                 }
            }
        }
    }

    grouping signaling {
        container signaling {
            uses graceful-restart;
            container hello {
                if-feature hellos;
                description "Configure Hello parameters.";
                leaf interface-based {
                     description "Enable interface-based
                                  Hello adjacency if present.";
                     type empty;
                }
                leaf hello-interval {
                    description
                        "Configure interval between successive Hello
                         messages in milliseconds.";
                    reference
                        "RFC 3209: RSVP-TE: Extensions to RSVP for LSP
                        Tunnels RFC 5495: Description of the Resource
                        Reservation Protocol - Traffic-Engineered
                        (RSVP-TE) Graceful Restart Procedures";
                    type uint32 {
                        range "3000..30000";
                    }
                }
                leaf hello-misses {
                    description
                        "Configure max number of consecutive missed
                        Hello messages.";
                    reference
                        "RFC 3209: RSVP-TE: Extensions to RSVP for LSP
                        Tunnels.
                        RFC 5495: Description of the Resource
                        Reservation Protocol - Traffic-Engineered
                        (RSVP-TE)
                        Graceful Restart Procedures";
                    type uint32 {
                         range "1..10";
                    }
                }
            }

            container path-err {
                leaf state-removal {
                    description
                        "State-Removal flag in Path Error message
                        if present.";
                    type empty;
                }
            }

            container refresh {
                leaf interval {
                    description
                        "Set interval between successive refreshes";
                    type uint32;
                }
                leaf missed {
                    description
                        "Set max number of consecutive missed messages
                        for state expiry";
                    type uint32;
                }

                container reduction {
                    if-feature refresh-reduction;
                    description
                        "Configure RSVP Refresh Reduction parameters.";
                    leaf bundle-message-max-size {
                        description
                            "Configure maximum size (bytes) of a single
                            RSVP Bundle message.";
                        type uint32 {
                            range "512..65000";
                        }
                    }
                    leaf disable {
                        description
                            "Disable refresh reduction if present.";
                        type empty;
                    }
                    leaf reliable-ack-hold-time {
                        description
                            "Configure hold time in milliseconds for
                            sending RSVP ACK message(s).";
                        type uint32 {
                            range "100..5000";
                        }
                    }
                    leaf reliable-ack-max-size {
                        description
                            "Configure max size of a single RSVP ACK
                            message.";
                        type uint32 {
                            range "20..65000";
                        }
                    }
                    leaf reliable-retransmit-time {
                        description
                            "Configure min delay in milliseconds to wait
                            for an ACK before a retransmit.";
                        type uint32 {
                            range "100..10000";
                        }
                    }
                    leaf reliable-srefresh {
                        description
                            "Configure use of reliable messaging fori
                            summary refresh if present.";
                        type empty;
                    }
                    leaf summary-max-size {
                        description
                            "Configure max size (bytes) of a single RSVP
                            summary refresh message.";
                        type uint32 {
                            range "20..65000";
                        }
                    }
                }
            }
        }
    }

    container rsvp {
        presence "Enable RSVP feature";

        container globals {
            description "RSVP global properties.";
            uses signaling;
        }

        container interfaces {
            uses authentication;
            uses signaling;
            list interface {
                key "interface";
                description
                    "RSVP interfaces.";
                leaf interface {
                     description
                        "RSVP interface.";
                     type if:interface-ref;
                }
                uses authentication;
                uses signaling;
            }
        }

        container sessions {
            list session {
                key "src_port dst_port source destination";
                leaf src_port {
                    type uint16;
                    description "RSVP source port";
                    reference "RFC2205";
                }
                leaf dst_port {
                    type uint16;
                    description "RSVP destination port";
                    reference "RFC2205";
                }
                leaf source {
                    type inet:ip-address;
                    description "RSVP source address";
                    reference "RFC2205";
                }
                leaf destination {
                    type inet:ip-address;
                    description "RSVP destination address";
                    reference "RFC2205";
                }
            }
        }

        container neighbors {
            list neighbor {
                key "address";
                leaf address {
                    type inet:ip-address;
                }
            }
        }

        container interface-state {
            config "false";
            list session {
                key "interface";
                description
                    "RSVP interfaces.";
                leaf interface {
                     description
                        "RSVP interface.";
                     type if:interface-ref;
                }
            }
        }

        container sessions-state {
            config "false";
            list session {
                key "src_port dst_port source destination";
                leaf src_port {
                    type uint16;
                    description "RSVP source port";
                    reference "RFC2205";
                }
                leaf dst_port {
                    type uint16;
                    description "RSVP destination port";
                    reference "RFC2205";
                }
                leaf source {
                    type inet:ip-address;
                    description "RSVP source address";
                    reference "RFC2205";
                }
                leaf destination {
                    type inet:ip-address;
                    description "RSVP destination address";
                    reference "RFC2205";
                }
            }
        }

        container neighbors-state {
            config "false";
            list neighbor {
                key "address";
                leaf address {
                    type inet:ip-address;
                }
            }
        }
    }
}
