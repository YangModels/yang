module ietf-network-slice-connectivity {
  yang-version 1.1;
  namespace "urn:ietf:params:xml:ns:yang:"
    + "ietf-network-slice-connectivity";
  prefix "ns-con-types";

  import ietf-network {
    prefix "nw";
    reference "RFC 8345: A YANG Data Model for Network Topologies";
  }
  import ietf-te-topology {
    prefix "tet";
    reference
      "RFC 8795: YANG Data Model for Traffic Engineering (TE)
       Topologies";
  }
  import ietf-te-types {
    prefix "te-types";
    reference
      "RFC 8776: Traffic Engineering Common YANG Types";
  }

  organization
    "IETF Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Luis Miguel Contreras Murillo
               <mailto:luismiguel.contrerasmurillo@telefonica.com>

     Editor:   Sergio Belotti
               <mailto:sergio.belotti@nokia.com>
    ";

  description
    "YANG augmentations to support various connectivity types for
     IETF network slices.

     Copyright (c) 2022 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2022-03-04 {
    description "Initial revision";
    reference
      "RFC XXXX: YANG Data Model for Network Slices";
  }

  /*
   * Groupiings
   */
  grouping network-slice-connectivity-types {
    description "Network Slice topology scope attributes.";
    list replication-group {
      key "id";
      description
        "A list of replication groups. Each replication group
         contains a list of connectivity constructs
         (that are called connectivity matrix entries in RFC 8795).
         When traffic is sent to one entry in this replication group,
         the traffic is replicated to all other entries in the same
         replication group.";
      leaf id {
        type uint32;
        description
          "Identifies the replication group.";
      }
      leaf-list entry {
        type leafref {
          path "../../tet:id";
        }
        description
          "References a connectivity matrix entry that belongs to
           this replication group.";
      }
    }
    list receiver-constraint-group {
      key "id";
      description
        "A list of receiver constraint groups. Each receiver
         constraint group contains a list of connectivity constructs
         (that are called connectivity matrix entries in RFC 8795).
         When traffic is sent to one or more entries in this
         receiver constraint group, the constraints specified in this
         receiver constraint group are applied to the receiver-side
         termination points referenced by all entries in this
         receiver constraint group.";
      leaf id {
        type uint32;
        description
          "Identifies the receiver constraint group.";
      }
      leaf-list entry {
        type leafref {
          path "../../tet:id";
        }
        description
          "References a connectivity matrix entry that belongs to
           this receiver constraint group..";
      }
      uses te-types:te-bandwidth;
    }
  }

  /*
   * Data nodes
   */
  augment "/nw:networks/nw:network/nw:node/tet:te/"
    + "tet:te-node-attributes/tet:connectivity-matrices/"
    + "tet:connectivity-matrix" {
    description "Augment node configuration and state.";
    uses network-slice-connectivity-types;
  }

  augment "/nw:networks/nw:network/nw:node/tet:te/"
    + "tet:information-source-entry/tet:connectivity-matrices/"
    + "tet:connectivity-matrix" {
    description "Augment node configuration and state.";
    uses network-slice-connectivity-types;
  }
}
