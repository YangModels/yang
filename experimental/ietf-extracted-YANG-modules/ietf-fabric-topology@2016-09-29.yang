module ietf-fabric-topology {

    yang-version 1.1;
    namespace "urn:ietf:params:xml:ns:yang:ietf-fabric-topology";
    prefix fabric;

        import ietf-network { prefix nw;  }
        import ietf-network-topology { prefix nt;  }
    import ietf-fabric-types { prefix fabrictype; revision-date "2016-09-29"; }

        organization
    "IETF I2RS (Interface to the Routing System) Working Group";

        contact
   "WG Web:    <http://tools.ietf.org/wg/i2rs/ >
     WG List:   <mailto:i2rs@ietf.org>

     WG Chair:  Susan Hares
                <mailto:shares@ndzh.com>

     WG Chair:  Russ White
                <mailto:russ@riw.us>

     Editor:    Yan Zhuang
                <mailto:zhuangyan.zhuang@huawei.com>

     Editor:    Danian Shi
                <mailto:shidanian@huawei.com>";

    description
        "This module contains a collection of YANG definitions for Fabric.

                Copyright (c) 2016 IETF Trust and the persons identified as
                authors of the code.  All rights reserved.

                Redistribution and use in source and binary forms, with or
                without modification, is permitted pursuant to, and subject
                to the license terms contained in, the Simplified BSD License
                set forth in Section 4.c of the IETF Trust's Legal Provisions
                Relating to IETF Documents
                (http://trustee.ietf.org/license-info).

                This version of this YANG module is part of
                draft-zhuang-i2rs-yang-dc-fabric-network-topology;
                see the RFC itself for full legal notices.";

    revision "2016-09-29" {
        description
            "Initial revision of fabric topology.";
                reference
                        "draft-zhuang-i2rs-yang-dc-fabric-network-topology-02";
    }

    identity fabric-context {
                description
                        "identity of fabric context";
    }

    typedef fabric-id {
        type nw:node-id;
        description
            "An identifier for a fabric in a topology.
            The identifier is generated by compose-fabric RPC.";
    }
        //grouping statements
        grouping fabric-network-type {
      description "Identify the topology type to be fabric.";
      container fabric-network {
        presence "indicates fabric Network";
        description
        "The presence of the container node indicates
         fabric Topology";
      }
    }

    grouping fabric-options {
                description "options for a fabric";

        leaf gateway-mode {
            type enumeration {
                enum centralized {
                    description "centerilized gateway";
                }
                enum distributed {
                    description "distributed gateway";
                }
            }
            default "distributed";
                        description "gateway mode";
        }

        leaf traffic-behavior {
            type enumeration {
                enum normal {
                    description "normal";
                }
                enum policy-driven {
                    description "policy driven";
                }
            }
            default "normal";
                        description "traffic behavior of the fabric";
        }

        leaf-list capability-supported {
            type fabrictype:service-capabilities;
                        description
                                "supported services of the fabric";
        }
    }

    grouping device-attributes {
                description "device attributes";
        leaf device-ref {
            type fabrictype:node-ref;
                        description
                                "the device it includes to";
        }
        leaf role {
            type fabrictype:device-role;
            default "LEAF";
                        description
                                "role of the node";
        }
    }

    grouping link-attributes {
                description "link attributes";
        leaf link-ref {
            type fabrictype:link-ref;
                        description
                                "the link it includes";
        }
    }

    grouping fabric-attributes {
                description "attributes of a fabric";
        leaf name {
            type string;
                        description
                                "name of the fabric";
        }

        leaf type {
            type fabrictype:underlayer-network-type;
            description
                                "The type of physical network that implements this fabric.Examples are vlan, and trill.";
        }

        leaf description {
            type string;
                        description
                                "description of the fabric";
        }

        container options {
                        description "options of the fabric";
            uses fabric-options;
        }

        list device-nodes {
                        key device-ref;
                        description "include device nodes in the fabric";
            uses device-attributes;
        }

        list device-links {
                        key link-ref;
                        description "include device links within the fabric";
            uses link-attributes;
        }

    }

        // augment statements

        augment "/nw:networks/nw:network/nw:network-types" {
    description
      "Introduce new network type for Fabric-based logical topology";

                uses fabric-network-type;
        }

    augment "/nw:networks/nw:network/nw:node" {
        when "/nw:networks/nw:network/nw:network-types/fabric-network" {
        description
          "Augmentation parameters apply only for networks
           with fabric topology";
      }
        description "Augmentation for fabric nodes created by faas.";

        container fabric-attribute {
                        description
                        "attributes for a fabric network";

            uses fabric-attributes;
        }
    }

    augment "/nw:networks/nw:network/nw:node/nt:termination-point" {
        when "/nw:networks/nw:network/nw:network-types/fabric-network" {
        description
          "Augmentation parameters apply only for networks
           with fabric topology";
      }
        description "Augmentation for port on fabric.";

        container fport-attribute {
            config false;
                        description
                        "attributes for fabric ports";
            uses fabrictype:fabric-port;
        }
    }

    /*******************************RPC*********************************************/
    rpc get-all-fabrics {
                description "get all fabrics";
        output {
            leaf-list fabric-id {
               type fabric-id;
                           description
                                "fabric id list";
            }
        }
    }

    rpc compose-fabric {
                description "compose a fabric";
        input {
            uses fabric-attributes;
        }
        output {
            leaf fabric-id {
                type fabric-id;
                                description
                                        "fabric id";
            }
        }
    }

    rpc decompose-fabric {
                description "decompose a fabric";
        input {
            leaf fabric-id {
                type fabric-id;
                                description
                                        "fabric id";
            }
        }
    }

    rpc add-node-to-fabric {
                description "add nodes to a fabric";
        input {
            leaf fabric-id {
                type fabric-id;
                                description
                                        "fabric id";
            }
            leaf node-ref {
                type fabrictype:node-ref;
                                description
                                        "node reference";
            }
            leaf role {
                type fabrictype:device-role;
                                description
                                        "role of the node";
            }
        }
    }

    rpc rm-node-from-fabric {
                description "remove nodes from a fabric";
        input {
            leaf fabric-id {
                type fabric-id;
                                description
                                        "fabric id";
            }
            leaf node-ref {
                type fabrictype:node-ref;
                                description
                                        "node reference";
            }
        }
    }

    rpc add-link-to-fabric {
                description "add links to a fabric";
        input {
            leaf fabric-id {
                type fabric-id;
                                description
                                        "fabric id";
            }
            leaf link-ref {
                type fabrictype:link-ref;
                                description
                                        "link reference";
            }
        }
    }
    rpc rm-link-from-fabric {
                description "remove link from a fabric";
        input {
            leaf fabric-id {
                type fabric-id;
                                description
                                        "fabric id";
            }
            leaf link-ref {
                type fabrictype:link-ref;
                                description
                                        "link reference";
            }
        }
    }
}
