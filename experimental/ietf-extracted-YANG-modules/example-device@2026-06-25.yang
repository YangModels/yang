module example-device {
  yang-version 1.1;
  namespace "http://example.com/device";
  prefix "dev";

  description
    "This is a non-normative example module, provided only to
     illustrate coverage analysis in this document.";

  revision 2026-06-25 {
    description "Initial example revision.";
  }

  container device {
    description "Top-level device configuration.";

    leaf hostname {
      type string;
      description "The device hostname.";
    }
    leaf location {
      type string;
      description "Physical location of the device.";
    }
    leaf admin-state {
      type boolean;
      description "Administrative state of the device.";
    }

    list interface {
      key "name";
      description "List of device interfaces.";

      leaf name {
        type string;
        description "Interface name; the list key.";
      }
      leaf enabled {
        type boolean;
        description "Whether the interface is enabled.";
      }
      leaf other {
        type boolean;
        description "An additional example leaf.";
      }
    }
  }
}
