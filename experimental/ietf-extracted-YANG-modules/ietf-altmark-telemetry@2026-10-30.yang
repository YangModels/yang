module ietf-altmark-telemetry {
  yang-version 1.1;
  namespace "urn:ietf:params:xml:ns:yang:ietf-altmark-telemetry";
  prefix "altmark-telemetry";

  import ietf-yang-types {
    prefix yang;
    reference
      "Section 3 of RFC 9911";
  }

  import ietf-altmark {
    prefix altmark;
    reference
      "draft-ietf-bpm-alt-mark-yang";
  }

  import ietf-lime-time-types {
    prefix lime;
    reference
      "RFC 8532: Generic YANG Data Model for the Management of
       Operations, Administration, and Maintenance (OAM) Protocols
       That Use Connectionless Communications";
  }

  organization
    "IETF BPM (Benchmarking & Performance Measurements) Working Group";

  contact
    "WG Web: <https://datatracker.ietf.org/wg/bpm>
     WG List: <bpm@ietf.org>
     Author: giuseppe.fioccola@huawei.com
     Author: zhoutianran@huawei.com
     Author: zhuyq8@chinatelecom.cn
     Author: zhangwq@chinatelecom.cn
     Author: alex.huang-feng@t-systems.com
     Author: zhukeyi@huawei.com";

  description
    "This YANG module specifies vendor-independent data model
     for AltMark Telemetry.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-10-30 {
    description "First revision.";
    reference "RFC XXXX: YANG Data Models for On-path Telemetry";
  }

 /*
  * FEATURES
  */

  feature pathdelay {
    description
      "This feature indicates that the Path Delay is
       supported.";
    reference
      "RFC 9951: Export of Delay Performance Metrics in IPFIX";
  }

 /*
  * GROUP DEFINITIONS
  */

  grouping loss-counters {
    description
      "The set of counters for RFC 9341 and RFC 9342 loss
       calculation.";

    leaf loss-flag {
      type boolean;
      config false;
      description
        "The loss-flag value is defined in RFC 9343 and RFC 9714.
         Note that it corresponds to the altmarkLossFlag parameter
         defined in draft-ietf-opsawg-ipfix-alt-mark.";
    }

    leaf in-traffic-pkts {
      type yang:counter64;
      config false;
      description
        "Total inbound packets of the period according to RFC 9341
         and RFC 9342";
    }

    leaf out-traffic-pkts {
      type yang:counter64;
      config false;
      description
        "Total outbound packets of the period according to RFC 9341
         and RFC 9342";
    }

    leaf in-traffic-bytes {
      type uint64;
      units "bytes";
      config false;
      description
        "Total inbound bytes of the period according to RFC 9341
         and RFC 9342";
    }

    leaf out-traffic-bytes {
      type uint64;
      units "bytes";
      config false;
      description
        "Total outbound bytes of the period according to RFC 9341
         and RFC 9342";
    }
  }

  grouping delay-timestamps {
    description
      "It indicates the set of timestamps for RFC 9341 and RFC 9342
       delay calculation.";

    leaf delay-flag {
      type boolean;
      config false;
      description
        "The delay-flag value is defined in RFC 9343 and RFC 9714.
         Note that it corresponds to the altmarkDelayFlag parameter
         defined in draft-ietf-opsawg-ipfix-alt-mark.";
    }

    container in-pkts-timestamps {
      config false;
      description
        "The list of timestamps of the period according to RFC 9341
         and RFC 9342";

      leaf in-pkt-timestamp {
        type yang:date-and-time;
        description
          "To specify the timestamp of the delay packet for delay
           measurements";
      }

      leaf in-pkt-seq-num {
        type uint32;
        description
          "To specify the sequence number of the delay packet for
           delay measurements";
      }
    }

    container out-pkts-timestamps {
      config false;
      description
        "The list of timestamps of the period according to RFC 9341
         and RFC 9342";

      leaf out-pkt-timestamp {
        type yang:date-and-time;
        description
          "To specify the timestamp of the delay packet for delay
           measurements";
      }

      leaf out-pkt-seq-num {
        type uint32;
        description
          "To specify the sequence number of the delay packet for
           delay measurements";
      }
    }
  }

  grouping path-delay-metrics {
    description
      "It indicates the path delay measurements.";

    leaf path-delay-mean {
      type uint32;
      units "microseconds";
      config false;
      description
        "mean path delay as per RFC 9951";
    }
    leaf path-delay-min {
      type uint32;
      units "microseconds";
      config false;
      description
        "min path delay as per RFC 9951";
    }

    leaf path-delay-max {
      type uint32;
      units "microseconds";
      config false;
      description
        "max path delay as per RFC 9951";
    }

    leaf path-delay-sum {
      type uint64;
      units "microseconds";
      config false;
      description
        "sum of the path delay as per RFC 9951";
    }
  }

 /*
  * DATA NODES
  */

  augment "/altmark:altmark" {
    description "Augments the AltMark with timestamp information";

    container altmark-info {
      config false;
      description
        "Describes information such as units or timestamp format
        that assists monitoring systems in the interpretation of the
        on-path-telemetry data.";

      leaf timestamp-type {
        type identityref {
          base lime:timestamp-type;
        }
        description
          "Type of timestamp, such as Truncated PTP or NTP.";
      }
    }
  }

  augment "/altmark:altmark/altmark:available-interfaces/"
        + "altmark:available-interface/altmark:altmark-profiles/"
        + "altmark:altmark-profile" {
    description "Augments the AltMark with the On-path Telemetry data";

    leaf measurement-period-number {
      type uint32;
      config false;
      description
        "It specifies the On-path Telemetry period number.";
    }

    container altmark-loss-measurement {
      if-feature altmark:altmark;
      presence
        "Present when AltMark loss measurement is enabled.";
      description
        "It reports the loss measurement data.";

      uses loss-counters;
    }

    container altmark-delay-measurement {
      if-feature altmark:altmark;
      presence
        "Present when AltMark delay measurement is enabled.";
      description
        "It reports the delay measurement data.";

      uses delay-timestamps;
    }

    container path-delay-measurement {
      if-feature pathdelay;
      description
        "It reports the path delay measurement data.";

      uses path-delay-metrics;
    }
  }
}
