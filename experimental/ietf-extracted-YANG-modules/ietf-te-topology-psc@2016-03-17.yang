module ietf-te-topology-psc {
  yang-version 1;
  namespace "urn:ietf:params:xml:ns:yang:ietf-te-topology-psc";
  // replace with IANA namespace when assigned

  prefix "tet-psc";

  import ietf-network {
    prefix "nw";
  }

  import ietf-network-topology {
    prefix "nt";
  }

  import ietf-te-topology {
    prefix "tet";
  }

  organization
    "Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editors:  Xufeng Liu
               <mailto:xliu@kuatrotech.com>

               Igor Bryskin
               <mailto:Igor.Bryskin@huawei.com>

               Vishnu Pavan Beeram
               <mailto:vbeeram@juniper.net>

               Tarek Saad
               <mailto:tsaad@cisco.com>

               Himanshu Shah
               <mailto:hshah@ciena.com>

               Oscar Gonzalez De Dios
               <mailto:oscar.gonzalezdedios@telefonica.com>";

  description "TE topology model";

  revision "2016-03-17" {
    description "Initial revision";
    reference "TBD";
  }

  /*
   * Groupings
   */
  grouping packet-switch-capable-container {
    description
      "The container of packet switch capable attributes.";
    container packet-switch-capable {
      description
        "Interface has packet-switching capabilities.";
      leaf minimum-lsp-bandwidth {
        type decimal64 {
          fraction-digits 2;
        }
        description
          "Minimum LSP Bandwidth. Units in bytes per second";
      }
      leaf interface-mtu {
        type uint16;
        description
          "Interface MTU.";
      }
    }
  }

  /*
   * Configuration data nodes
   */
  augment "/nw:networks/tet:te/tet:templates/"
        + "tet:link-template/tet:te-link-attributes/"
        + "tet:interface-switching-capability" {
    when "switching-capability = 'switching-psc1' " {
      description "Valid only for PSC";
    }
    description
      "Parameters for PSC TE topology.";
    uses packet-switch-capable-container;
  }

  augment "/nw:networks/nw:network/nt:link/tet:te/tet:config/"
        + "tet:te-link-attributes/"
        + "tet:interface-switching-capability" {
    when "switching-capability = 'switching-psc1' " {
      description "Valid only for PSC";
    }
    description
      "Parameters for PSC TE topology.";
    uses packet-switch-capable-container;
  }

  /*
   * Operational state data nodes
   */
  augment "/nw:networks/nw:network/nt:link/tet:te/tet:state/"
        + "tet:te-link-attributes/"
        + "tet:interface-switching-capability" {
    when "switching-capability = 'switching-psc1' " {
      description "Valid only for PSC";
    }
    description
      "Parameters for PSC TE topology.";
    uses packet-switch-capable-container;
  }

  augment "/nw:networks/nw:network/nt:link/tet:te/tet:state/"
        + "tet:alt-information-sources/"
        + "tet:interface-switching-capability" {
    when "switching-capability = 'switching-psc1' " {
      description "Valid only for PSC";
    }
    description
      "Parameters for PSC TE topology.";
    uses packet-switch-capable-container;
  }

  /*
   * Notifications
   */
  augment "/tet:te-link-event/tet:te-link-attributes/"
        + "tet:interface-switching-capability" {
    when "switching-capability = 'switching-psc1' " {
      description "Valid only for PSC";
    }
    description
      "Parameters for PSC TE topology.";
    uses packet-switch-capable-container;
  }

  augment "/tet:te-link-event/tet:alt-information-sources/"
        + "tet:interface-switching-capability" {
    when "switching-capability = 'switching-psc1' " {
      description "Valid only for PSC";
    }
    description
      "Parameters for PSC TE topology.";
    uses packet-switch-capable-container;
  }
}
