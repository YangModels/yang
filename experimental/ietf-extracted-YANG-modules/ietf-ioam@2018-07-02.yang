module ietf-ioam {
  yang-version 1.1;
  namespace "urn:ietf:params:xml:ns:yang:ietf-ioam";
  prefix "ioam";
  import ietf-pot-profile {
    prefix "pot";
  }

  import ietf-access-control-list {
    prefix "acl";
  }

  organization
    "IETF IPPM (IP Performance Metrics) Working Group";

  contact
    "WG Web: <http://tools.ietf.org/wg/ippm>
     WG List: <ippm@ietf.org>
     Editor: zhoutianran@huawei.com";

  description
    "This YANG module specifies a vendor-independent data
     model for the in Situ OAM (iOAM).";

  revision 2018-07-02 {
    description "Initial revision.";
    reference "draft-zhou-ippm-ioam-yang";
  }

 /*
  * FEATURES
  */

  feature incremental-trace
  {
    description
      "This feature indicated that the incremental tracing mode is
       supported";
  }

  feature preallocated-trace
  {
    description
      "This feature indicated that the preallocated tracing mode is
       supported";
  }

  feature proof-of-transit
  {
    description
      "This feature indicated that the proof of transit mode is
       supported";
  }

  feature edge-to-edge
  {
    description
      "This feature indicated that the edge to edge mode is
       supported";
  }

 /*
  * IDENTITIES
  */
  identity base-filter {
    description
      "Base identity to represent a filter. A filter is used to
      specify the flow to apply the iOAM profile. ";
  }

  identity acl-filter {
    base base-filter;
    description
      "Apply ACL rule to specify the flow.";
  }

  identity base-protocol {
    description
      "Base identity to represent the carrier protocol. It's used to
       indicate what layer and protocol the iOAM data is embedded.";
  }

  identity ipv6-protocol {
    base base-protocol;
    description
      "The described iOAM data is embedded in ipv6 protocol.";
  }

  identity base-node-action {
    description
      "Base identity to represent the node actions. It's used to
       indicate what action the node will take.";
  }

  identity encapsulate {
    base base-node-action;
    description
      "indicate the node is to encapsulate the iOAM packet";
  }

  identity transit {
    base base-node-action;
    description
      "indicate the node is to transit the iOAM packet";
  }

  identity decapsulate {
    base base-node-action;
    description
      "indicate the node is to decapsulate the iOAM packet";
  }

 /*
  * TYPE DEFINITIONS
  */

  typedef ioam-filter-type {
    type identityref {
      base base-filter;
    }
    description
      "Specifies a known type of filter.";
  }

  typedef ioam-protocol-type {
    type identityref {
      base base-protocol;
    }
    description
      "Specifies a known type of carrier protocol for the iOAM data.";
  }

  typedef ioam-node-action {
    type identityref {
      base base-node-action;
    }
    description
      "Specifies a known type of node action.";
  }

  typedef ioam-trace-types {
    type bits {
      bit ioam-hop-lim-node-id {
        position 0;
        description
          "When set indicates presence of Hop_Lim and node_id in the
          node data.";
      }
      bit ioam-if-id {
        position 1;
        description
          "When set indicates presence of ingress_if_id and
          egress_if_id in the node data.";
      }
      bit ioam-timestamp-seconds {
        position 2;
        description
          "When set indicates presence of time stamp seconds in the
          node data.";
      }
      bit ioam-timestamp-nanoseconds {
        position 3;
        description
          "When set indicates presence of time stamp nanoseconds in
          the node data.";
      }
      bit ioam-transit-delay {
        position 4;
        description
          "When set indicates presence of transit delay in the node
          data.";
      }
      bit ioam-app-data {
        position 5;
        description
          "When set indicates presence of app_data in the node data.";
      }
      bit ioam-queue-depth {
        position 6;
        description
          "When set indicates presence of queue depth in the node
          data.";
      }
      bit ioam-opaque-state-snapshot {
        position 7;
        description
          "When set indicates presence of variable length Opaque
          State Snapshot field.";
      }
      bit ioam-hop-lim-node-id-wide {
        position 8;
        description
          "When set indicates presence of Hop_Lim and node_id wide
           in the node data.";
      }
      bit ioam-if-id-wide {
        position 9;
        description
          "When set indicates presence of ingress_if_id and
          egress_if_id wide in the node data.";
      }
      bit app-data-wide {
        position 10;
        description
          "When set indicates presence of app_data wide in the node
          data.";
      }
    }
    description
      "A 16-bit identifier which specifies which data types are used
       in this node data list.";
  }

  typedef ioam-pot-types {
    type bits {
      bit ioam-bytes-16 {
        position 0;
        description
          "POT data is a 16 Octet field";
      }
    }
    description
      "7-bit identifier of a particular POT variant that dictates
        the POT data that is included.";
  }

  typedef ioam-e2e-types {
    type bits {
      bit ioam-seq-num {
        position 0;
        description
          "A 64-bit sequence number added to a specific tube which is
           used to identify packet loss and reordering for that
           tube.";
      }
    }
    description
      "8-bit identifier of a particular in situ OAM E2E variant.";
  }

 /*
  * GROUP DEFINITIONS
  */

  grouping ioam-filter {
    description "A grouping for iOAM filter definition";

    leaf filter-type {
      type ioam-filter-type;
      description "filter type";
    }

    leaf acl-name {
      when "../filter-type = 'acl-filter'";
      type leafref {
        path "/acl:acls/acl:acl/acl:name";
      }
      description "Access Control List name.";
    }
  }

  grouping ioam-incremental-tracing-profile {
    description
      "A grouping for incremental tracing profile.";

    leaf node-action {
      type ioam-node-action;
      description "node action";
    }

    leaf trace-type {
      when "../node-action = 'encapsulate'";
      type ioam-trace-types;
      description
        "The trace type is only defined at the encapsulation node.";
    }

    leaf enable-loopback-mode {
      when "../node-action = 'encapsulate'";
      type boolean;
      default false;
      description
        "Loopback mode is used to send a copy of a packet back towards
        the source. The loopback mode is only defined at the
        encapsulation node.";
    }

    leaf max-length {
      when "../node-action = 'encapsulate'";
      type uint32;
      description
        "This field specifies the maximum length of the node data list
        in octets. The max-length is only defined at the
        encapsulation node. And it's only used for the incremental
        tracing mode.";
    }
  }

  grouping ioam-preallocated-tracing-profile {
    description
      "A grouping for incremental tracing profile.";

    leaf node-action {
      type ioam-node-action;
      description "node action";
    }

    leaf trace-type {
      when "../node-action = 'encapsulate'";
      type ioam-trace-types;
      description
        "The trace type is only defined at the encapsulation node.";
    }

    leaf enable-loopback-mode {
      when "../node-action = 'encapsulate'";
      type boolean;
      default false;
      description
        "Loopback mode is used to send a copy of a packet back towards
        the source. The loopback mode is only defined at the
        encapsulation node.";
    }
  }

  grouping ioam-e2e-profile {
    description
      "A grouping for tracing profile.";

    leaf node-action {
      type ioam-node-action;
      description
        "indicate how the node act for this profile";
    }

    leaf e2e-type {
      when "../node-action = 'encapsulate'";
      type ioam-e2e-types;
      description
        "The e2e type is only defined at the encapsulation node.";
    }
  }

  grouping ioam-admin-config {
    description
      "IOAM top-level administrative configuration.";

    leaf enabled {
      type boolean;
      default false;
      description
        "When true, IOAM configuration is enabled for the system.
         Meanwhile, the IOAM data-plane functionality is enabled.";
    }
  }

 /*
  * DATA NODES
  */

  container ioam {
    description "iOAM top level container";

    container ioam-profiles {
      description
        "Contains a list of iOAM profiles.";
      container admin-config {
        description
          "Contains all the administrative configurations related to
           the IOAM functionalities and all the IOAM profiles.";

        uses ioam-admin-config;
      }

      list ioam-profile {
        key "profile-name";
        ordered-by user;
        description
          "A list of iOAM profiles that configured on the node.";

        leaf profile-name {
          type string;
          mandatory true;
          description
            "Unique identifier for each iOAM profile";
        }

        container filter {
          uses ioam-filter;
          description
            "The filter which is used to indicate the flow to apply
            iOAM.";
        }

        leaf protocol-type {
          type ioam-protocol-type;
          description
            "This item is used to indicate the carrier protocol where
            the iOAM is applied.";
        }

        container incremental-tracing-profile {
          if-feature incremental-trace;
          description
            "describe the profile for incremental tracing option";

          leaf enabled {
            type boolean;
            default false;
            description
              "When true, apply incremental tracing option to the
               specified flow identified by the filter.";
          }

          uses ioam-incremental-tracing-profile;
        }

        container preallocated-tracing-profile {
          if-feature preallocated-trace;
          description
            "describe the profile for preallocated tracing option";

          leaf enabled {
            type boolean;
            default false;
            description
              "When true, apply preallocated tracing option to the
               specified flow identified by the following filter.";
          }

          uses ioam-preallocated-tracing-profile;
        }

        container pot-profile {
          if-feature proof-of-transit;
          description
            "describe the profile for pot option";

          leaf enabled {
            type boolean;
            default false;
            description
              "When true, apply Proof of Transit option to the
               specified flow identified by the following filter.";
          }

          leaf active-profile-index {
          type pot:profile-index-range;
          description
            "Proof of transit profile index that is currently
             active. Will be set in the first hop of the path
             or chain. Other nodes will not use this field.";
          }

          uses pot:pot-profile;
        }

        container e2e-profile {
          if-feature edge-to-edge;
          description
            "describe the profile for e2e option";

          leaf enabled {
            type boolean;
            default false;
            description
              "When true, apply End to end option to the
               specified flow identified by the following filter.";
          }

          uses ioam-e2e-profile;
        }
      }
    }
  }
}
