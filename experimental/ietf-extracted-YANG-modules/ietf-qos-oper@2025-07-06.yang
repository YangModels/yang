module ietf-qos-oper {
  yang-version 1.1;
  namespace "urn:ietf:params:xml:ns:yang:ietf-qos-oper";
  prefix qos-oper;

  import ietf-yang-types {
    prefix yang;
    reference
      "RFC 6991:Common YANG Data Types.";
  }
  import ietf-interfaces {
    prefix if;
    reference
      "RFC8343: A YANG Data Model for Interface Management.";
  }
  import ietf-qos-types {
    prefix qos-types;
    reference
      "RFC XXXX: YANG Models for Quality of Service (QoS).";
  }

  organization "IETF RTG (Routing Area) Working Group.";

  contact
    "WG Web:   <http://tools.ietf.org/wg/rtgwg/>
     WG List:  <mailto:rtgwg@ietf.org>
     Editor:   Aseem Choudhary
               <mailto:asechoud@cisco.com>
     Editor:   Mahesh Jethanandani
               <mailto:mjethanandani@gmail.com>";
  description
    "This module contains a collection of YANG definitions for
     QoS operational specification.

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2025-07-06 {
    description
      "Initial version.";
    reference
      "RFC XXXX: YANG Models for Quality of Service (QoS).";
  }

  grouping classifier-statistics {
    description
      "Statistics for a classifier.";

    leaf name {
      type string;
      description
        "A unique identifier for Classifier name.";
    }

    leaf classified-pkts {
      type yang:zero-based-counter64;
      description
        "Number of total packets filtered for a classifier.";
    }

    leaf classified-bytes {
      type yang:zero-based-counter64;
      description
        "Number of total bytes filtered for a classifier.";
    }

    leaf classified-rate {
      type yang:gauge64;
      units "bits-per-second";
      description
        "Rate of average data flow through a classifier.";
    }
  }

  grouping queuing-stats {
    description
      "Statistics for a queue.";

    leaf queue-id {
      type string;
      description
        "A unique identifier for the Queue.";
    }

    leaf transmit-pkts {
      type yang:zero-based-counter64;
      description
        "Number of packets transmitted from queue.";
    }

    leaf transmit-bytes {
      type yang:zero-based-counter64;
      description
        "Number of bytes transmitted from queue.";
    }

    leaf queue-current-size-bytes {
      type yang:gauge64;
      description
        "Number of bytes currently buffered.";
    }

    leaf queue-average-size-bytes {
      type yang:gauge64;
      description
        "Average queue size in number of bytes.";
    }

    leaf queue-peak-size-bytes {
      type yang:gauge64;
      description
        "Peak buffer queue size in bytes.";
    }

    leaf tail-drop-pkts {
      type yang:zero-based-counter64;
      description
        "Total number of packets tail-dropped.";
    }

    leaf tail-drop-bytes {
      type yang:zero-based-counter64;
      description
        "Total number of bytes tail-dropped.";
    }

    container red-statistics {
      leaf drop-pkts {
        type yang:zero-based-counter64;
        description
          "Total number of packets dropped because of RED.";
      }

      leaf drop-bytes {
        type yang:zero-based-counter64;
        description
          "Total number of bytes dropped because of RED.";
      }

      leaf ecn-marked-pkts {
        type yang:zero-based-counter64;
        description
          "Total number of packets that were marked with ECN
           because of RED.";
      }

      leaf ecn-marked-bytes {
        type yang:zero-based-counter64;
        description
          "Total number of bytes that were marked with ECN because of
           RED.";
      }

      list wred-stats {
        config false;
        description
          "QoS WRED statistics.";

        leaf profile {
          type uint8;
          description
            "Profile identifier for each color of traffic.";
        }

        leaf drop-pkts {
          type yang:zero-based-counter64;
          description
            "Total number of packets dropped because of WRED.";
        }

        leaf drop-bytes {
          type yang:zero-based-counter64;
          description
            "Total number of bytes dropped because of WRED.";
        }

        leaf ecn-marked-pkts {
          type yang:zero-based-counter64;
          description
            "Total number of packets that were marked with ECN
             because of WRED.";
        }

        leaf ecn-marked-bytes {
          type yang:zero-based-counter64;
          description
            "Total number of bytes that were marked with ECN because
             of WRED.";
        }
      }
      description
        "Container of all RED statistics.";
    }

    container codel-statistics {
      leaf drop-pkts {
        type yang:zero-based-counter64;
        description
          "Total number of packets dropped because of CoDel
           or FQ-CoDel.";
      }

      leaf drop-bytes {
        type yang:zero-based-counter64;
        description
          "Total number of bytes dropped because of CoDel
           or FQ-CoDel.";
      }

      leaf ecn-marked-pkts {
        type yang:zero-based-counter64;
        description
          "Total number of packets that were marked with ECN
           because of CoDel or FQ-CoDel.";
      }

      leaf ecn-marked-bytes {
        type yang:zero-based-counter64;
        description
          "Total number of bytes that were marked with ECN because
           of CoDel or FQ-CoDel.";
      }

      leaf new-flow-count {
        type yang:zero-based-counter64;
        description
          "Total number of flows that FQ-CoDel has identified and is
           managing or has managed.";
      }
      description
        "Container of all CoDel or FQ-CoDel statistics.";
    }
  }

  grouping metering-stats {
    description
      "Statistics for a meter.";

    leaf meter-id {
      type string;
      description
        "A unique identifier that identifies this set of metering
         statistics.";
    }

    leaf conform-pkts {
      type yang:zero-based-counter64;
      description
        "Number of packets that conform to the rate and burst.";
    }

    leaf conform-bytes {
      type yang:zero-based-counter64;
      description
        "Total bytes count that conform to the rate and burst.";
    }

    leaf conform-rate {
      type yang:gauge64;
      units "bits-per-second";
      description
        "Traffic Rate measured as conformimg.";
    }

    leaf exceed-pkts {
      type yang:zero-based-counter64;
      description
        "Number of packets that exceed the peak rate and peak
         burst.";
    }

    leaf exceed-bytes {
      type yang:zero-based-counter64;
      description
        "Total number of bytes which exceed the peak rate and peak
         burst.";
    }

    leaf exceed-rate {
      type yang:gauge64;
      units "bits-per-second";
      description
        "Traffic Rate measured as exceeding.";
    }

    leaf violate-pkts {
      type yang:zero-based-counter64;
      description
        "Number of packets that were beyond peak rate
         and peak burst.";
    }

    leaf violate-bytes {
      type yang:zero-based-counter64;
      description
        "Total number of bytes which were beyond peak rate and
         peak burst.";
    }

    leaf violate-rate {
      type yang:gauge64;
      units "bits-per-second";
      description
        "Traffic Rate measured as violating.";
    }

    leaf drop-pkts {
      type yang:zero-based-counter64;
      description
        "Number of packets dropped by meter.";
    }

    leaf drop-bytes {
      type yang:zero-based-counter64;
      description
        "Number of bytes dropped by meter.";
    }
  }

  augment "/if:interfaces/if:interface" {
    description
      "Augments interface module to add QoS Target entry.";

    container qos-interface-statistics {
      config false;
      description
        "QoS Interface statistics.";

      list stats-per-direction {
        description
          "QoS interface statistics in ingress or egress direction.";

        leaf direction {
          type identityref {
            base qos-types:direction;
          }
          description
            "Direction of the traffic flow. Either ingress or
             egress.";
        }

        leaf policy-name {
          type string;
          description
            "Policy name for single level policy as well as
             for Hierarchical policies. For Hierarchical policies,
             this represent relative path as well as the last level
             policy name.";
        }

        list classifier {
          description
            "Statistics for each Classifier in a
             Policy applied in a particular direction.";
          uses classifier-statistics;
        }

        list named {
          description
            "Statistics for a statistics-name.";

          leaf name {
            type string;
            description
              "A name for statistics.";
          }

          container aggregated {
            description
              "Matched aggregated statistics for a statistics-name.";

            leaf pkts {
              type yang:zero-based-counter64;
              description
                "Number of total matched packets associated
                 with a statistics name.";
            }

            leaf bytes {
              type yang:zero-based-counter64;
              description
                "Number of total matched bytes associated
                 with a statistics name.";
            }

            leaf rate {
              type yang:gauge64;
              units "bits-per-second";
              description
                "Rate of average matched data which is associated
                 to a statistics name.";
            }
          }

          container non-aggregated {
            description
              "Statistics for non-aggregated statistics-name.";

            list classifier {
              description
                "Statistics for each Classifier in a
                 Policy applied in a particular direction.";
              uses classifier-statistics;
            }

            list metering {
              description
                "Statistics for each Meter associated with
                 the Policy.";
              reference
                "RFC2697: A Single Rate Three Color Marker
                 RFC2698: A Two Rate Three Color Marker.";
              uses metering-stats;
            }

            list queueing {
              description
                "Statistics for each Queue associated with
                 the Policy.";
              uses queuing-stats;
            }
          }
        }

        list metering {
          description
            "Statistics for each Meter associated with the Policy.";
          reference
            "RFC2697: A Single Rate Three Color Marker
             RFC2698: A Two Rate Three Color Marker.";
          uses metering-stats;
        }

        list queueing {
          description
            "Statistics for each Queue associated with the Policy.";
          uses queuing-stats;
        }
      }

      action clear {
        description
          "Clear statistics action command. Execution of this command
           should result in all the QoS interface counters to be
           cleared and set to 0.";

        input {
          leaf category {
            type identityref {
              base qos-types:clear-counters-type;
            }
            description
              "Category of counters which is being cleared.";
          }

          leaf started-at {
            type yang:date-and-time;
            description
              "The date and time when the counters should be
               cleared.";
          }
        }

        output {
          leaf finished-at {
            type yang:date-and-time;
            description
              "The date and time when the counters finished
               clearing.";
          }
        }
      }
    }
  }
}
