module ietf-bfd-large {
  yang-version 1.1;
  namespace "urn:ietf:params:xml:ns:yang:ietf-bfd-large";
  prefix "bfdl";

  import ietf-routing {
    prefix rt;
    reference
      "RFC 8349: A YANG Data Model for Routing Management
       (NMDA version)";
  }

  import ietf-bfd {
    prefix bfd;
    reference
      "RFC 9314: YANG Data Model for Bidirectional
       Forwarding Detection.";
  }

  import ietf-bfd-ip-sh {
    prefix bfd-ip-sh;
    reference
      "RFC 9314: YANG Data Model for Bidirectional
       Forwarding Detection.";
  }

  import ietf-bfd-ip-mh {
    prefix bfd-ip-mh;
    reference
      "RFC 9314: YANG Data Model for Bidirectional
       Forwarding Detection.";
  }

  import ietf-bfd-lag {
    prefix bfd-lag;
    reference
      "RFC 9314: YANG Data Model for Bidirectional
       Forwarding Detection.";
  }

  import ietf-bfd-mpls {
    prefix bfd-mpls;
    reference
      "RFC 9314: YANG Data Model for Bidirectional
       Forwarding Detection.";
  }

  organization
    "IETF BFD Working Group";

  contact
    "WG Web:   <http://tools.ietf.org/wg/bfd>
     WG List:  <rtg-bfd@ietf.org>

     Authors: Jeffrey Haas (jhaas@juniper.net)
              Albert Fu (afu14@bloomberg.net).";

  description
    "This YANG module augments the base BFD YANG module to add
     attributes related to support for BFD Encapsulated in Large
     Packets.  In particular, it adds a per-session parameter for the
     BFD Padded PDU Size.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "2024-11-23" {
    description
      "Initial Version.";
    reference
      "RFC XXXX, BFD Encapsulated in Large Packets.";
  }

  feature padding {
    description
      "If supported, the feature allows for BFD sessions to be
       configured with padded PDUs in support of BFD Encapsulated in
       Large Packets.";
  }

  typedef padded-pdu-size {
    type uint16 {
      range "24..65535";
    }
    units "bytes";
    description
      "The size of the padded and encapsulated BFD control packets
       to be transmitted at layer 3.  The BFD minimum control packet
       size is 24 or 26 octets; see Section 6.8.6 of RFC 5880.

       If the configured padded PDU size is smaller than the minimum
       sized packet of a given BFD session, then the minimum sized
       packet for the session will be used.

       The maximum padded PDU size may be limited by the supported
       interface MTU of the system.";
    reference
      "RFC XXXX, BFD Encapsulated in Large Packets.";
  }

  grouping bfd-large-common {
    description
      "Common configuration and operational state for BFD
       Encapsulated in Large Packets.";
    reference
      "RFC XXXX, BFD Encapsulated in Large Packets.";
    leaf pdu-size {
      if-feature "padding";
      type padded-pdu-size;
      description
        "If set, this configures the padded PDU size for the
         Asynchronous mode BFD session. By default, no additional
         padding is added to such packets.";
    }
  }

  augment "/rt:routing/rt:control-plane-protocols/" +
          "rt:control-plane-protocol/bfd:bfd/bfd-ip-sh:ip-sh/" +
          "bfd-ip-sh:sessions/bfd-ip-sh:session" {
    uses bfd-large-common;
    description
      "Augment the 'bfd' container to add attributes related to BFD
       Encapsulated in Large Packets.";
  }

  augment "/rt:routing/rt:control-plane-protocols/" +
          "rt:control-plane-protocol/bfd:bfd/bfd-ip-mh:ip-mh/" +
          "bfd-ip-mh:session-groups/bfd-ip-mh:session-group" {
    uses bfd-large-common;
    description
      "Augment the 'bfd' container to add attributes related to BFD
       Encapsulated in Large Packets.";
  }

  augment "/rt:routing/rt:control-plane-protocols/" +
          "rt:control-plane-protocol/bfd:bfd/bfd-lag:lag/" +
          "bfd-lag:sessions/bfd-lag:session" {
    uses bfd-large-common;
    description
      "Augment the 'bfd' container to add attributes related to BFD
       Encapsulated in Large Packets.";
  }

  augment "/rt:routing/rt:control-plane-protocols/" +
          "rt:control-plane-protocol/bfd:bfd/bfd-mpls:mpls/" +
    "bfd-mpls:session-groups/bfd-mpls:session-group" {
    uses bfd-large-common;
    description
      "Augment the 'bfd' container to add attributes related to BFD
       Encapsulated in Large Packets.";
  }
}
