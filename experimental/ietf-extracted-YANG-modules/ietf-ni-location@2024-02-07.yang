module ietf-ni-location {
  yang-version 1.1;
  namespace "urn:ietf:params:xml:ns:yang:ietf-ni-location";
  prefix nil;

  import ietf-network-inventory {
    prefix nwi;
    reference
      "RFCXXXX: A YANG Data Model for Network Inventory";
  }
  import ietf-geo-location {
    prefix geo;
    reference
      "RFC 9179: A YANG Grouping for Geographic Locations";
  }

  organization
    "IETF Network Inventory YANG (ivy) Working Group";
  contact
    "WG Web:   <https://datatracker.ietf.org/wg/ivy>
     WG List:  <mailto:inventory-yang@ietf.org>

     Editor: Bo Wu
          <lana.wubo@huawei.com>
     Editor: Sergio Belotti
          <sergio.belotti@nokia.com>
     Editor: Jean-Francois Bouquier
          <jeff.bouquier@vodafone.com>
     Editor: Fabio Peruzzini
          <fabio.peruzzini@telecomitalia.it>
     Editor: Phil Bedard
          <phbedard@cisco.com>";
  description
    "This YANG module defines a model for Network Inventory
     location.

     Copyright (c) 2024 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2024-02-07 {
    description
      "Initial version";
    reference
      "RFC XXXX: A YANG Data Model for Network Inventory location.";
    //RFC Editor: Please replace XXXX with actual RFC number,
    //update date information and remove this note
  }

  identity inventory-location-type {
    description
      "Base identity for network inventory location types.";
  }

  identity site {
    base inventory-location-type;
    description
      "Indicates site as location type.";
  }

  identity room {
    base inventory-location-type;
    description
      "Indicates equipment room as location type.";
  }

  identity building {
    base inventory-location-type;
    description
      "Indicates building as location type.";
  }

  grouping locations-grouping {
    description
      "The grouping of the locations.";
    list location {
      key "id";
      description
        "The list of sites within the network.";
      uses nwi:common-entity-attributes;
      leaf location-type {
        type identityref {
          base inventory-location-type;
        }
        description
          "The type of network inventory location, e.g.
           equipment room, building, or site.";
      }
      leaf parent {
        type leafref {
          path "../../location/id";
        }
        description
          "The name of the parent locations.";
      }
      leaf-list child {
        type leafref {
          path "../../location/id";
        }
        description
          "The name of the child locations.";
      }
      uses physical-address-grouping;
      uses geo:geo-location;
    }
  }

  grouping physical-address-grouping {
    description
      "The grouping of the physical address.";
    container physical-address {
      description
        "Top level container for the physical address.";
      leaf address {
        type string;
        description
          "Address (number and street) of the site.";
      }
      leaf postal-code {
        type string;
        description
          "Postal code of the site.";
      }
      leaf state {
        type string;
        description
          "State of the site.  This leaf can also be
           used to describe a region for a country that
           does not have states.";
      }
      leaf city {
        type string;
        description
          "City of the site.";
      }
      leaf country-code {
        type string {
          pattern '[A-Z]{2}';
        }
        description
          "Country of the site.
           Expressed as ISO ALPHA-2 code.";
      }
    }
  }

  grouping rack-grouping {
    description
      "The attributes of the rack.";
    container racks {
      description
        "Top level container for the list of racks.";
      list rack {
        key "id";
        description
          "The list of racks within an equipment room.";
        uses nwi:common-entity-attributes;
        container rack-location {
          description
            "The location information of the rack, which
             comprises the name of the location, row number, and
             column number.";
          leaf location-ref {
            type leafref {
              path "/nil:locations/nil:location/nil:id";
            }
            description
              "Name of location where this rack is located.";
          }
          leaf row-number {
            type uint32;
            description
              "Identifies the row within the equipment room where
               the rack is located.";
          }
          leaf column-number {
            type uint32;
            description
              "Identifies the physical location of the rack within
               the column.";
          }
        }
        leaf height {
          type uint16;
          units "millimeter";
          description
            "Rack height.";
        }
        leaf width {
          type uint16;
          units "millimeter";
          description
            "Rack width.";
        }
        leaf depth {
          type uint16;
          units "millimeter";
          description
            "Rack depth.";
        }
        leaf max-voltage {
          type uint16;
          units "volt";
          description
            "The maximum voltage could be supported by the rack.";
        }
        leaf max-allocated-power {
          type uint16;
          units "watts";
          description
            "The maximum allocated power to the rack.";
        }
        list contained-chassis {
          key "ne-ref component-ref";
          description
            "The list of chassis within a rack.";
          leaf ne-ref {
            type leafref {
              path "/nwi:network-elements/nwi:network-element"
                 + "/nwi:id";
            }
            description
              "The reference to the network element containing
               the chassis component.";
          }
          leaf component-ref {
            type leafref {
              path "/nwi:network-elements/nwi:network-element"
                 + "[nwi:id=current()/../ne-ref]/nwi:components"
                 + "/nwi:component/nwi:id";
            }
            description
              "The reference to the chassis component within
               the network element and contained by the rack.";
          }
          leaf relative-position {
            type uint8;
            description
              "A relative position of chassis within
               the rack";
          }
        }
      }
    }
  }

  grouping locations-ref-grouping {
    description
      "The attributes of the locations.";
    container locations {
      description
        "The container for the location.";
      leaf-list location {
        type leafref {
          path "/nil:locations/nil:location/nil:id";
        }
        description
          "The reference of the location.";
      }
      leaf rack {
        type leafref {
          path "/nil:locations/nil:racks"
             + "/nil:rack/nil:id";
        }
        description
          "The reference to the rack.";
      }
    }
  }

  container locations {
    description
      "The top-level container for the NE location information.";
    uses locations-grouping;
    uses rack-grouping;
  }

  augment "/nwi:network-elements/nwi:network-element" {
    description
      "Provides location information for network inventory.";
    uses locations-ref-grouping;
  }
}
