module acl-ip {
    namespace "urn:cisco:params:xml:ns:yang:acl-ip";
    // replace with IANA namespace when assigned
    prefix acl-ip;

    import acl {
        prefix acl;
    }
    import ietf-inet-types {
        prefix "inet";
    }
    import common-types {
        prefix "c-types";
    }

    organization
       "IETF NETMOD (NETCONF Data Modeling Language) Working Group";

    contact
         "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com

        Editor: Alexander Clemm
        alex@cisco.com

        Editor: Andy Bierman
        andy@yumaworks.com";

     description
        "This YANG module augments the 'acl' module with configuration
        and operational data for IPv4 and IPv6 access control list.

        An ACL is an ordered set of rules and actions used to filter
        traffic.
        Each set of rules and actions is represented as an Access
        Control Entries (ACE). Each ACE is evaluated sequentially.
        When the rule matches then action for that rule is applied
        to the packet.

        IP ACLs are ordered sets of rules that can use to
        filter traffic based on IP information in the Layer 3 header
        of packets.
        The device applies IP ACLs only to IP traffic. IP ACL
        can be IPv4 or IPv6.

        Terms and Acronyms
         ACE (ace): Access Control Entry

         ACL (acl): Access Control List

         AFI (afi): Authority and Format Identifier (Address Field
             Identifier)

         DSCP (dscp): Differentiated Services Code Point

         ICMP (icmp): Internet Control Message Protocol

         IGMP (igmp): Internet Group Management Protocol

         IP (ip): Internet Protocol

         IPv4 (ipv4):Internet Protocol Version 4

         IPv6 (ipv6): Internet Protocol Version 6

         QoS: Quality of Service

         TCP (tcp): Transmission Control Protocol

         ToS (tos): Type of Service

         TTL (ttl): Time to Live

         UDP (udp): User Datagram Protocol

         VLAN (vlan): Virtual Local Area Network

         VRF(vrf) : Virtual Routing and Forwarding
       ";
    reference
        "Access List Commands on Cisco IOS XR Software,
        Cisco Nexus 7000 Series NX-OS Security Configuration Guide,
        Catalyst 6500 Release 12.2SX Software Configuration Guide,
        ACL TCP Flags Filtering";

    revision 2012-10-12 {
        description "Initial revision. ";
    }

    /* Features */

    feature time-to-live {
        description "The ability to filter packets based on their
        time-to-live (TTL) value (0 to 255)";
        reference "ACL Support for Filtering on TTL Value";
    }

    feature flow-label {
        description
            "The ability to filter packets based on flow lable.
            The 20-bit Flow Label field in the IPv6 header
            is used by a source to label packets
            of a flow. This is an IPv6 ACEs option.";
        reference "RFC 3697 IPv6 Flow Label Specification";
    }

    /* Identities */

    identity ip-acl {
        base "acl:acl-type";
        description "layer 3 ACL type";
    }

    /* Groupings */

    grouping IP-SOURCE-NETWORK {
        description "Reusable IP address and mask pair.";

        grouping IP-SOURCE-HOST {
            description
              "Choice within a case not allowed so need
               this grouping.";
            choice ip-src-address-or-name {
                mandatory true;
                leaf ip-source-host-address {
                   type inet:ip-address;
                }
                leaf ip-source-host-name {
                   if-feature acl:host-by-name;
                   type inet:domain-name;
                }
            }
        }

        choice source-address-host-group {
            mandatory true;
            case source-ip {
                description "Used with address and mask couple
                    to express network.";

                leaf ip-source-address {
                    type inet:ip-address;
                    mandatory true;
                }
                leaf ip-source-mask {
                    type inet:ip-address;
                    mandatory true;
                }
            }
            leaf ip-source-any {
                type empty;
                description "To express Any network or address.
                    Use the any keyword as an abbreviation
                    for an address and a mask of 0.0.0.0
                    255.255.255.255. For example:
                    0.0.0.0/255.255.255.255 means 'any'";
            }
            case source-host {
                description "Used with host address to express a
                    single host
                    Use the host address(or name)
                    combination is the same as an address
                    and mask of address 0.0.0.0.
                    For example: '10.1.1.2/0.0.0.0' is the same
                    as 'host 10.1.1.2'";
                uses IP-SOURCE-HOST;
            }
            case source-group {
                if-feature acl:ip-address-groups;
                leaf ip-source-group  {
                    type acl:ip-address-group-ref;
                }
            }
        }
    }

    grouping IP-DESTINATION-NETWORK {
        description
            "Reusable IP address and mask pair for destination.";

        grouping IP-DESTINATION-HOST {
            description
              "Choice within a case not allowed so need
               this grouping.";
            choice ip-dest-address-or-name {
                mandatory true;
                leaf ip-dest-host-address {
                   type inet:ip-address;
                }
                leaf ip-dest-host-name {
                   if-feature acl:host-by-name;
                   type inet:domain-name;
                }
            }
        }

        choice dest-address-host-group {
            mandatory true;
            case dest-ip {
                description "Used with address and mask couple
                    to express network.";
                leaf ip-dest-address {
                    type inet:ip-address;
                    mandatory true;
                }
                leaf ip-dest-mask {
                    type inet:ip-address;
                    mandatory true;
                }
            }
            leaf ip-dest-any {
                type empty;
                description "To express Any network or address.
                    Use the any keyword as an abbreviation
                    for an address and a mask of 0.0.0.0
                    255.255.255.255. For example:
                    0.0.0.0/255.255.255.255 means 'any'";
            }
            case dest-host {
                description "Used with host address to express a
                    single host
                    Use the host address(or name)
                    combination is the same as an address
                    and mask of address 0.0.0.0.
                    For example: '10.1.1.2/0.0.0.0' is the same
                    as 'host 10.1.1.2'";

                uses IP-DESTINATION-HOST;
            }
            case dest-group {
                if-feature acl:ip-address-groups;
                description "Use the group keyword and group name
                   to refer to a pre-defined address object group
                   which is a list of address and mask.";

                leaf ip-dest-group {
                    type acl:ip-address-group-ref;
                }
            }
        }
    }

    grouping DSCP-OR-TOS {
      choice dscp-or-tos {
        leaf dscp {
          type inet:dscp;
          description
            "Match packets with given dscp value";
        }

        case tos {
          leaf tos {
            type c-types:tos;
            description
             "Match packets with given TOS value";
          }
          leaf precedence {
            when "boolean(../tos)" ;
            type c-types:precedence;
            description
              "Match packets with given precedence value";
          }
        }
      }
    }

    grouping IP-ACE-FILTERS {
        leaf protocol {
            type c-types:ip-protocol;
            description "IP protocol number.";
        }

        uses acl:FILTER-COMMON;

        leaf fragments {
            type empty;
            description "Check non-initial fragments";
        }

        leaf time-range {
            type acl:time-range-ref;
            description
                "Refer a time range object by
                name (Max Size 64).";
        }

        choice src-ports {
           when "protocol = '6' or protocol = '17' or " +
                "protocol = '132'";

            description
              "Apply only when the protocol is TCP,
              UDP or SCTP.";

            case port-number-range {
                description
                    "Port group includes all ports between port-lower
                    and port-upper (including those)";
                leaf src-port-lower {
                    type inet:port-number;
                    description "Lower Port number.";
                    mandatory true;
                }
                leaf src-port-upper {
                    type inet:port-number;
                    description "Upper Port number.";
                    mandatory true;
                    must "../src-port-lower <= ../src-port-upper";
                }
            }
            case port-number {
                description
                    "Port group includes all ports that are greater
                    than, greater or equal, less than, less or equal,
                    or not equal the port, per the indicated
                    comparator.  It is possible for the port group
                    to be empty (for example, in case a port group
                    that is less than the minimum port number is
                    specified).";
                leaf src-comparator {
                    type acl:acl-comparator;
                    mandatory true;
                }
                leaf src-port {
                    type inet:port-number;
                    description "Port number.";
                    mandatory true;
                }
            }
            case port-group-ref {
                if-feature acl:port-groups;
                leaf src-port-group-name {
                    type acl:port-group-ref;
                    mandatory true;
                    description
                        "Reference a port group by the Port
                        Group name.";
                }
            }
        }  // choice src-ports

        choice dest-ports {
            when "protocol = '6' or protocol = '17' or " +
                 "protocol = '132'";
            description
                "Apply only when the protocol is TCP,
                UDP or SCTP.";

            case port-number-range {
                description "Port group includes all ports between
                    port-lower and port-upper (including those)";
                leaf des-port-lower {
                    type inet:port-number;
                    description "Lower Port number.";
                    mandatory true;
                }
                leaf des-port-upper {
                    type inet:port-number;
                    description "Upper Port number.";
                    mandatory true;
                    must "../des-port-lower <= ../des-port-upper";
                }
            }
            case port-number {
                description "Port group includes all ports that
                    are greater than, greater or equal, less than,
                    less or equal, or not equal the port, per the
                    indicated comparator.  It is possible for the
                    port group to be empty (for example, in case a
                    port group that is less than the minimum port
                    number is specified).";
                leaf des-comparator {
                    type acl:acl-comparator;
                    mandatory true;
                }
                leaf des-port {
                    type inet:port-number;
                    description "Port number.";
                    mandatory true;
                }
            }
            case port-group-ref {
                if-feature acl:port-groups;
                leaf des-port-group-name {
                    type acl:port-group-ref;
                    mandatory true;
                    description
                    "Reference a port group by the Port Group name.";
                }
            }
        }  // choice dest-ports

        leaf icmp-type {
            when "../protocol = '1'";
            type c-types:icmp-type;
            description
                "ICMP message type number.
                Apply only when the protocol is icmp";
        }

        leaf icmp-code {
            when "boolean(../icmp-type) ";
            type c-types:icmp-code;
            description
            "ICMP subtype for a given icmp type.";
        }

        choice packet-length-or-range {
            if-feature acl:packet-length;
            case length {
                leaf packet-length-comparator {
                    type acl:acl-comparator;
                    description
                        "Operant that compare the packet
                        length. Operands are lt (less than),
                        gt (greater than), eq (equal), and neq
                        (not equal).";
                    mandatory true;
                }
                leaf packet-length {
                    type uint32 {
                        range "20..9210";
                    }
                    description
                        "Packet length value for
                        operation gt, eq, etc, other
                        than range";
                        //TODO need to find out why package is
                        // less than 9210
                    mandatory true;
                }
            }
            case range {
                description
                    "Packet operator 'range' takes
                    both lower and upper value.";

                leaf packet-length-upper {
                    type uint32 {
                        range "20..9210";
                    }
                    mandatory true;
                    description "Upper Packet length";
                }

                leaf packet-length-lower {
                    type uint32 {
                        range "20..9210";
                    }
                    must "number(../packet-length-lower) <= " +
                         "number(../packet-length-upper)";
                    mandatory true;
                    description "Lower packet length";
                }
            }
        }

        leaf tcp-flag-value {
            type c-types:tcp-flag-type ;
            description "TCP flag bits that needs to be checked";
        }

        leaf tcp-flag-mask {
            when "boolean(../tcp-flag-value)" ;
            type c-types:tcp-flag-type ;
            description "TCP flag bit that needs to be checked";
        }

        leaf tcp-flag-operation {
            when "boolean(../tcp-flag-value)" ;
            description
                "TCP flag Match option.
                A match occurs if the TCP
                datagram has certain TCP flags
                set or not set. You use the
                match-any keyword to allow a match
                to occur if any of the specified
                TCP flags are present, or you can
                use the match-all keyword to allow
                a match to occur only if all of
                the specified TCP flags are
                present. You must follow the
                match-any and match-all keywords
                with the + or - keyword and the
                flag-name argument to match on
                one or more TCP flags. ";
            default match-any;
            type enumeration {
                enum match-any {
                    description "match any";
                }
                enum match-all {
                    description "match all";
                }
            }
        }

        choice ttl-value-or-range {
            if-feature time-to-live;
            case value {
                leaf ttl-comparator {
                    type acl:acl-comparator;

                    description
                        "Compares the TTL value in the packet
                        to the TTL value specified in this
                        ACE statement. Operands are lt (less
                        than), gt (greater than), and eq
                        (equal),  neq (not equal).";
                }
                leaf ttl-value {
                    type c-types:time-to-live;
                }
            }
            case range {
                leaf ttl-value-lower {
                    type c-types:time-to-live;
                    description "Lower ttl number.";
                }
                leaf ttl-value--upper {
                    type c-types:time-to-live;
                    description "Upper ttl number.";

                }
            }
        }
    }

    /* Data Nodes */

    augment "/acl:acls/acl:acl" {
        when "acl:acl-type = 'ip-acl'";

        leaf afi {
            type inet:ip-version ;
            default "ipv4";
        }

        container ipv6-aces {
            when "../afi = 'ipv6'" ;

            description
                " The ip-aces container contains a list of ip-ace.
                Each ip-ace is made of a unique ID, an optional
                remark (comment), and a filter. The filter
                requires a mandatory action (permit/deny) and one or
                more options such as source-address with mask,ttl etc";

            list ipv6-ace {
                key "name";
                ordered-by user;
                description "Layer 3 Access Control Element (ACE)";

                leaf name {
                    type acl:acl-name-string;
                    description "Unique ACE identifier.";
                }

                choice remark-or-ipv6-case {
                  leaf remark {
                    type acl:acl-remark;
                    // mandatory true;
                  }
                  case ipv6-ace {
                    container filters {

                      uses IP-SOURCE-NETWORK;
                      uses IP-DESTINATION-NETWORK;
                      uses IP-ACE-FILTERS;
                      uses DSCP-OR-TOS;

                      leaf igmp-type {
                        when "../protocol = '2' ";
                        type c-types:igmp-code;
                        description
                          "IGMP message type (0 to 15) for
                           filtering IGMP packets. Apply only
                           when the protocol is igmp in ipv4";
                      }

                      leaf flow-label {
                        if-feature flow-label;
                        when "../protocol = '17'";
                        type uint64 {
                          range "0..1048575";
                        }
                        description
                          "Flow label value. Apply only when
                           the protocol is UDP in ipv6.";
                        reference
                          "RFC3697 IPv6 Flow Label Specification";
                      }
                    }  // container filters

                    uses acl:ACE-COMMON;
                  }  // case ipv6-ace
                }  // choice remark-or-ipv6-ace
            }  // list ipv6-ace
        }  // container ipv6-aces

        container ipv4-aces {
            when "../afi = 'ipv4'" ;

            description
                "The ip-aces container contains a list of ip-ace.
                Each ip-ace is made of a unique ID, an optional
                remark (comment), and a filter. The filter requires a
                mandatory action (permit/deny) and one or more options
                such as source-address with mask,ttl etc";

            list ipv4-ace {
                key "name";
                ordered-by user;
                description "Layer 3 Access Control Element (ACE)";

                leaf name {
                    type acl:acl-name-string;
                    description "Unique ACE identifier";
                }

                choice remark-or-ipv4-ace {
                    leaf remark {
                      type acl:acl-remark;
                      // mandatory true;
                    }
                    case ipv4-ace {
                        container filters {
                            uses IP-SOURCE-NETWORK;
                            uses IP-DESTINATION-NETWORK;
                            uses IP-ACE-FILTERS;
                            uses DSCP-OR-TOS;
                         }
                         uses acl:ACE-COMMON;
                    }  // case ipv4-ace
                }  // choice remark-or-ipv4-ace
            }  // list ipv4-ace
        }  // container ipv4-aces

        leaf global-fragments {
            default "not-set";
            type enumeration {
                enum not-set;
                enum permit-all {
                    description "Allow all fragments";
                }
                enum deny-all {
                    description "Drop all fragments";
                }
            }
            description
                "Optimizes fragment handling for noninitial fragments.
                When this leaf is set to 'permit-all', noninitial
                fragments will be permitted unless explicitly denied.
                When this leaf is set to 'deny-all', noninitial
                fragments will be denied unless explicitly
                permitted. ";
        }
    }

}
