module ietf-ext-xponder-wdm-if {
  namespace "urn:ietf:params:xml:ns:yang:ietf-ext-xponder-wdm-if";
  prefix ietf-ext-xponder-wdm-if;

  import ietf-interfaces {
    prefix if;
  }
  import ietf-layer0-types {
    prefix "l0-types";
  }

  import ietf-layer0-types-ext {
    prefix "l0-types-ext";
  }

  organization
    "IETF CCAMP
    Working Group";

  contact
    "WG Web:   <http://tools.ietf.org/wg/ccamp/>
     WG List:  <mailto:ccamp@ietf.org>

     Editor:   Dharini Hiremagalur
               <mailto:dharinih@juniper.net>";

  description
    "This module contains a collection of YANG definitions for
     configuring Optical interfaces.

     Copyright (c) 2016 IETF Trust and the persons identified
     as authors of the code.  All rights reserved.

     Redistribution and use in source and binary forms, with or
     without modification, is permitted pursuant to, and
     subject to the license terms contained in, the Simplified
     BSD License set forth in Section 4.c of the IETF Trust's
     Legal Provisions Relating to IETF Documents
     (http://trustee.ietf.org/license-info).";

  revision "2022-01-10" {
    description
      "Revision 1.7";
    reference
      "";
    }

  revision "2021-06-28" {
    description
      "Revision 1.6";
    reference
      "";
    }

  revision "2020-03-09" {
    description
      "Revision 1.5";
    reference
      "";
    }

  revision "2019-11-04" {
    description
      "Revision 1.4";
    reference
      "";
    }

  revision "2019-07-08" {
    description
      "Revision 1.3";
    reference
      "";
    }
    revision "2018-10-22" {
      description
        "Revision 1.2";
      reference
        "";
    }
    revision "2018-03-06" {
      description
        "Revision 1.1";
      reference
        "";
    }
    revision "2017-03-06" {
      description
        "Revision 1.0";
      reference
        "";
    }
    revision "2016-03-17" {
      description
        "Initial revision.";
      reference
        "";
    }

   typedef opt-if-och-tca-types {
      type enumeration {
        enum max-laser-linewdt {
          description "The maximum laser linewidth";
        }
        enum min-tx-power-tca {
          description "The min tx power TCA";
        }
        enum max-tx-power-tca {
          description "The min tx power TCA";
        }
        enum min-rx-power-tca{
          description "The min tx power TCA";
        }
        enum max-rx-power-tca{
          description "The min tx power TCA";
        }
        enum max-pol-power-diff-tca{
          description "The power difference between polarization
          TCA";
        }
        enum max-pol-skew-diff-tca{
          description "The skew between the two polarization TCA";
        }
        enum min-frequency-offset-tca{
          description "Min Frequency offset TCA";
        }
        enum max-frequency-offset-tca{
          description "Max Frequency offset TCA";
        }
        enum min-osnr-tca{
          description "Min OSNR TCA";
        }
        enum max-osnr-tca{
          description "Max OSNR TCA";
        }
        enum min-laser-temperature-tca{
          description "The min tx power TCA";
        }
        enum max-laser-temperature-tca{
          description "Temperature TCA";
        }
        enum min-fec-ber-tca{
          description "Min Pre Fec BER TCA";
        }
        enum max-fec-ber-tca{
          description "Max Pre Fec BER TCA";
        }
        enum min-q-tca{
          description "Min Q TCA";
        }
        enum max-q-tca {
          description "Max Q TCA";
        }
      }
      description "The different types of TCA's";
    }

    grouping opt-if-och-power {
      description "Interface optical Power";

      leaf channel-output-power {
        type dbm-t;
        description "The output power for this interface in .01 dBm.
                     The setting of the output power is optional";
      }

      leaf channel-input-power {
        type dbm-t;
        config false;
        description "The current channel input power of this
        interface";
      }

      leaf total-input-power {
        type dbm-t;
        config false;
        description "The total input power of this interface";
      }
    }

    grouping opt-if-och-tca-thresholds {
      description "Thresholds for TCA's";
      leaf  tca-type {
        type opt-if-och-tca-types;
        description  "type of the TCA eg TX Power";
      }
      leaf  min-threshold {
        type int32;
        description "A TCA is generated if the variable is less than
                     this value";
      }
      leaf  max-threshold {
        type int32;
        description "A TCA is generated if the variable is more than
                     this value";
      }
    }

    grouping opt-if-och-fec {
      description "FEC info";

      leaf fec-info {
        type string { length "1..255"; }
        config false;
        description "FEC Type - eg GFEC";
      }
      leaf fec-bitrate {
        type string { length "1..255"; }
        config false;
        description "FEC Overhead rate ";
      }
      leaf fec-gain {
        type string { length "1..255"; }
        config false;
        description "FEC Overhead rate ";
      }
      leaf  pre-fec-ber-mantissa-threshold {
        type uint32;
        description "Mantissa of the FEC BER threshold";
      }
      leaf  pre-fec-ber-exponent-threshold {
        type int32;
        description "Exponent of the FEC BER threshold";
      }
    }

    grouping opt-if-och-central-frequency {
      description "Interface Central Frequency";
      leaf  central-frequency {
        type layer0-types:frequency-thz;
        description "This parameter indicates the frequency of this
                     interface ";
      }
    }

    grouping opt-if-och-modulation-params {
      description "Optical modulation parameters for the lane";

      leaf modulation-format {
        type string { length "1..255"; }
        config false;
        description "Modulation format for this mode";
      }
      leaf baud-rate {
        type uint32;
        description "Baud-rate or symbol rate";
      }
      leaf  bits-per-symbol {
        type uint32;
        description "This parameter the bits per symbol for this
        mode";
      }
      leaf  num-symbols-in-alphabet {
        type uint32;
        description "This parameter the bits per symbol for this
        mode";
      }
      leaf  symbols-index {
        type uint32;
        description "This parameter is the symbol index this mode";
      }
    }

    grouping opt-if-och-lane-param {
      description "Optical parameters for the lane";

      leaf number-of-lanes {
        type  uint32;
        config false;
        description "Number of optical lanes of this interface";
      }
      leaf min-laser-temperature {
        type  int32;
        units ".01C";
        config false;
        description "Minimum Laser Temperature of this mode for
                     this lane";
      }
      leaf max-laser-temperature {
        type  int32;
        units ".01C";
        config false;
        description "Maximum Laser Temperature of this mode for
                     this lane";
      }
      leaf max-total-rx-optical-power {
        type dbm-t;
        config false;
        description "Maximum rx optical power of this mode for this
                     lane";
      }
      leaf max-chromatic-dispersion {
        type int32;
        config false;
        description "Maximum chromatic dispersion of this mode for
                     this lane";
      }
      leaf max-diff-group-delay  {
        type int32;
        config false;
        description "Maximum Differential group delay of this mode
                     for this lane";
      }
      leaf max-polarization-dependent-loss{
        type decimal64;
        config false;
        description "Maximum max loss between the two carrier
        polarizations";
      }
      uses opt-if-och-modulation-params;
    }

    grouping chromatic-and-polariz-disp-penal {
      description "list of chromatic dispersion and polarization
                   dispersion penalties";
      list cd-and-pmd-penalties {}
        key "penalties"
        description "list of CD and PMD penalties"
      }
      leaf chromatic-dispersion {
        type decimal64;
        config false;
        description "Chromatic Dispersion of this mode for
                     this lane";
      }
      leaf polarization-mode-dispersion {
        type decimal64;
        config false;
        description "Polarization Mode Dispersion";
      }
      leaf penalty {
        type decimal64;
        config false;
        description "penalty given by CD and PMD";
      }
    }
