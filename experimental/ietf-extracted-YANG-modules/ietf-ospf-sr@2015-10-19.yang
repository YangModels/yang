module ietf-ospf-sr {
  namespace "urn:ietf:params:xml:ns:yang:ietf-ospf-sr";

  prefix ospf-sr;

  import ietf-inet-types {
    prefix "inet";
  }

  import ietf-yang-types {
    prefix "yang";
  }

  import ietf-routing {
    prefix "rt";
  }
  import ietf-segment-routing {
    prefix "sr";
  }
  import ietf-ospf {
    prefix "ospf";
  }

  organization
    "Cisco Systems
     170 West Tasman Drive
     San Jose, CA 95134-1706
     USA";

  contact
     "WG Web:   <http://tools.ietf.org/wg/ospf/>
      WG List:  <mailto:ospf@ietf.org>

      WG Chair: Acee Lindem
                <mailto:acee@cisco.com>

      WG Chair: Abhay Roy
                <mailto:akr@cisco.com>

      Editor:   Derek Yeung
                <mailto:myeung@cisco.com>
      Author:   Derek Yeung
                <mailto:myeung@cisco.com>
      Author:   Yingzhen Qu
                <mailto:yiqu@cisco.com>
      Author:   Acee Lindem
                <mailto:acee@cisco.com>
      Author:   Jeffrey Zhang
                <mailto:zzhang@juniper.net>
      Author:   Ing-Wher Chen
                <mailto:ing-wher.chen@ericsson.com>
      Author:   Greg Hankins
                <mailto:greg.hankins@alcatel-lucent.com>";

  description
    "This YANG module defines the generic configuration
     and operational state for OSPF Segment Routing, which is
     common across all of the vendor implementations. It is
     intended that the module will be extended by vendors to
     define vendor-specific OSPF Segment Routing configuration
     and operational parameters and policies.

     Terms and Acronyms

     OSPF (ospf): Open Shortest Path First

     IP (ip): Internet Protocol

     IPv4 (ipv4):Internet Protocol Version 4

     IPv6 (ipv6): Internet Protocol Version 6
    ";

  revision 2015-10-19 {
    description
      "* Add per-protocol SRGB support.
       * Editorial changes.";
    reference
      "RFC XXXX: A YANG Data Model for OSPF Segment Routing.";
  }

  revision 2015-09-02 {
    description
      "* Author list update.
       * Editorial changes.";
    reference
      "RFC XXXX: A YANG Data Model for OSPF Segment Routing.";
  }

  revision 2015-07-06 {
    description
      "Initial revision.";
    reference
      "RFC XXXX: A YANG Data Model for OSPF Segment Routing.";
  }

  feature ti-lfa {
    description
      "Topology-Independent Loop-Free Alternate (TI-LFA)
       computation using segment routing.";
  }

  /* Configuration */

  augment "/rt:routing/rt:routing-instance/rt:routing-protocols"
        + "/rt:routing-protocol/ospf:ospf/ospf:instance" {
    when "../../rt:type = 'ospf:ospfv2' or "
       + "../../rt:type = 'ospf:ospfv3'" {
      description
        "This augments the OSPF routing protocol when used.";
    }
    description
      "This augments the OSPF protocol configuration
       with segment routing.";
    uses sr:controlplane-cfg;
    container protocol-srgb {
      if-feature sr:protocol-srgb;
      uses sr:srgb-cfg;
      description
        "Per-protocol SRGB.";
    }
  }

  augment "/rt:routing/rt:routing-instance/rt:routing-protocols/"
        + "rt:routing-protocol/ospf:ospf/ospf:instance/"
        + "ospf:areas/ospf:area/ospf:interfaces/ospf:interface" {
    when "../../../../../../rt:type = 'ospf:ospfv2' or "
       + "../../../../../../rt:type = 'ospf:ospfv3'" {
      description
        "This augments the OSPF interface configuration
         when used.";
    }
    description
      "This augments the OSPF protocol interface
       configuration with segment routing.";

    uses sr:igp-interface-cfg;
  }

  augment "/rt:routing/rt:routing-instance/rt:routing-protocols/"
        + "rt:routing-protocol/ospf:ospf/ospf:instance/"
        + "ospf:areas/ospf:area/ospf:interfaces/ospf:interface/"
        + "ospf:fast-reroute" {
    when "../../../../../../../rt:type = 'ospf:ospfv2' or "
       + "../../../../../../../rt:type = 'ospf:ospfv3'" {
      description
        "This augments the OSPF routing protocol when used.";
    }
    description
      "This augments the OSPF protocol IP-FRR with TI-LFA.";

    container ti-lfa {
      if-feature ti-lfa;
      leaf enable {
        type boolean;
        description
         "Enables TI-LFA computation.";
      }
      description
        "Topology Independent Loop Free Alternate
         (TI-LFA) support.";
    }
  }

  /* Operational states */

  augment "/rt:routing-state/rt:routing-instance/"
        + "rt:routing-protocols/rt:routing-protocol/"
        + "ospf:ospf/ospf:instance" {
    when "../../rt:type = 'ospf:ospfv2' or "
       + "../../rt:type = 'ospf:ospfv3'" {
      description
        "This augments the OSPF routing protocol when used.";
    }
    description
     "This augments the OSPF protocol operational state
      with segment routing.";

    uses sr:controlplane-cfg;
    container protocol-srgb {
      if-feature sr:protocol-srgb;
      uses sr:srgb-cfg;
      description
        "Per-protocol SRGB.";
    }
  }

  augment "/rt:routing-state/rt:routing-instance/"
        + "rt:routing-protocols/rt:routing-protocol/"
        + "ospf:ospf/ospf:instance/ospf:areas/ospf:area/"
        + "ospf:interfaces/ospf:interface" {
    when "../../../../../../rt:type = 'ospf:ospfv2' or "
       + "../../../../../../rt:type = 'ospf:ospfv3'" {
      description
      "This augments the OSPF routing protocol when used.";
    }
    description
     "This augments the OSPF protocol interface
      operational state with segment routing.";

    uses sr:igp-interface-cfg;
  }

  /* Database */

  grouping sid-sub-tlv {
    description "SID/Label sub-TLV grouping.";
    container sid-sub-tlv {
      description
        "Used to advertise the SID/Label associated with a
         prefix or adjacency.";
      leaf sid {
        type uint32;
        description
          "Segment Identifier (SID) - A 20 bit label or
           32 bit SID.";
      }
    }
  }

  grouping prefix-sid-sub-tlvs {
    description "Prefix Segment ID (SID) sub-TLVs.";
    container perfix-sid-sub-tlvs{
      description "Prefix SID sub-TLV.";
      list prefix-sid-sub-tlv {
        description "Prefix SID sub-TLV.";
        leaf flags {
          type bits {
            bit NP {
              description
                "No-PHP flag.";
            }
            bit M {
              description
                "Mapping server flag.";
            }
            bit E {
              description
                "Explicit-NULL flag.";
            }
            bit V {
              description
                "Value/Index flag.";
            }
            bit L {
              description
                "Local flag.";
            }
          }
          description "Segment Identifier (SID) Flags.";
        }
        leaf mt-id {
          type uint8;
          description "Multi-topology ID.";
        }
        leaf algorithm {
          type uint8;
          description
            "The algorithm associated with the prefix-SID.";
        }
        leaf sid {
          type uint32;
          description "An index or label.";
        }
      }
    }
  }

  grouping sid-binding-sub-tlvs {
    description "SID/Label binding sub-TLV grouping.";
    container sid-binding-sub-tlvs {
      description "SID binding sub-TLVs.";
      list sid-binding-sub-tlv {
        description "SID binding sub-TLV.";
        leaf flags {
          type bits {
            bit M {
              description
                "Mirroring context flag.";
            }
          }
          description "Flags.";
        }
        leaf mt-id {
          type uint8;
          description "Multi-topology ID.";
        }
        leaf weight {
          type uint8;
          description "Weight for load-balancing purposes.";
        }

        uses sid-sub-tlv;

        container ero-metric-sub-tlv {
          description
            "The cost of an Explicit Route Object (ERO) path.";
          leaf metric {
            type uint32;
            description "The aggregate IGP or TE path cost.";
          }
        }

        container ipv4-ero-sub-tlv {
          description
            "The IPv4 ERO sub-TLV describes a path segment
             using IPv4 address.";
          leaf flags {
            type bits {
              bit L {
                description
                  "If set, then the segment path is designated as
                   'loose'. Otherwise, the path is 'strict'.";
              }
            }
            description "ERO Flags.";
          }
          leaf ipv4-address {
            type inet:ipv4-address;
            description "The address of the explicit route hop.";
          }
        }
        container unnumbered-ero-sub-tlv {
          description "The unnumbered interface ID ERO sub-TLV
                       describes a path segment that includes an
                       unnumbered interface.";
          leaf flags {
            type bits {
              bit L {
                description
                  "If set, then the segment path is designated as
                   'loose'. Otherwise as 'strict'.";
              }
            }
            description "ERO Flags.";
          }
          leaf router-id {
            type yang:dotted-quad;
            description "Router-id of the next-hop.";
          }
          leaf interface-id {
            type uint32;
            description
              "The identifier assigned to the link by the
               router specified by the router-id.";
          }
        }
        container ipv4-backup-ero-sub-tlv {
          description
            "The IPv4 backup ERO sub-TLV describes a path
             segment using IPv4 address.";
          leaf flags {
            type bits {
              bit L {
                description
                  "If set, then the segment path is designated as
                   'loose'. Otherwise as 'strict'.";
              }
            }
            description "Flags.";
          }
          leaf ipv4-address {
            type inet:ipv4-address;
            description "The address of the explicit route hop.";
          }
        }
        container unnumbered-backup-ero-sub-tlv {
          description
            "The unnumbered interface ID backup ERO sub-TLV
             describes a path segment that includes an
             unnumbered interface.";
          leaf flags {
            type bits {
              bit L {
                description
                  "If set, then the segment path is designated as
                   'loose'. Otherwise, the path is 'strict'.";
              }
            }
            description "Flags.";
          }
          leaf router-id {
            type yang:dotted-quad;
            description "Router-id of the next-hop.";
          }
          leaf interface-id {
            type uint32;
            description
              "The identifier assigned to the link by the
              router specified by the router-id.";
          }
        }
      }
    }
  }

  grouping extended-prefix-range-tlvs {
    description "Extended prefix range TLV grouping.";

    container extended-prefix-range-tlvs {
      description "The list of range of prefixes.";
      list extended-prefix-range-tlv {    //type=2?
        description "The range of prefixes.";
        leaf range-size {
          type uint16;
          description "The number of prefixes covered by the
                       advertisement.";
        }
        leaf flags {
          type bits {
            bit IA {
              description
                "Inter-Area flag.";
            }
          }
          description "Flags.";
        }
        leaf prefix {
          type inet:ip-prefix;
          description "Address prefix.";
        }
        uses prefix-sid-sub-tlvs;
        uses sid-binding-sub-tlvs;
        uses ospf:unknown-tlvs;
      }
    }
  }

  grouping sr-algorithm-tlv {
    description "SR algorithm TLV grouping.";
    container sr-algorithm-tlv {
      description "All SR algorithm TLVs.";
      leaf-list sr-algorithm {
        type uint8;
        description
          "The Segment Routing (SR) algorithms that the router is
           currently using.";
      }
    }
  }

  grouping sid-range-tlvs {
    description "SID Range TLV grouping.";
    container sid-range-tlvs {
      description "List of SID range TLVs.";
      list sid-range-tlv {
        description "SID range TLV.";
        leaf range-size {
          type ospf:uint24;
          description "The SID range.";
        }
        uses sid-sub-tlv;
      }
    }
  }
  augment "/rt:routing-state/rt:routing-instance/"
        + "rt:routing-protocols/rt:routing-protocol/"
        + "ospf:ospf/ospf:instance/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque/"
        + "ospf:extended-prefix-tlvs/ospf:extended-prefix-tlv" {
    when "../../../../../../../../../../../../../../../../../"
       + "rt:type = 'ospf:ospfv2'" {
      description
        "This augmentation is only valid for OSPFv2.";
    }
    description
      "SR specific TLVs for OSPFv2 extended prefix TLV
       in type 9 opaque LSA.";
    uses prefix-sid-sub-tlvs;
    uses sid-binding-sub-tlvs;
  }

  augment "/rt:routing-state/rt:routing-instance/"
        + "rt:routing-protocols/rt:routing-protocol/"
        + "ospf:ospf/ospf:instance/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-prefix-tlvs/ospf:extended-prefix-tlv" {
    when "../../../../../../../../../../../../../../../"
       + "rt:type = 'ospf:ospfv2'" {
      description
        "This augmentation is only valid for OSPFv2.";
    }
    description
      "SR specific TLVs for OSPFv2 extended prefix TLV
       in type 10 opaque LSA.";
    uses prefix-sid-sub-tlvs;
    uses sid-binding-sub-tlvs;
  }

  augment "/rt:routing-state/rt:routing-instance/"
        + "rt:routing-protocols/rt:routing-protocol/"
        + "ospf:ospf/ospf:instance/ospf:database/"
        + "ospf:as-scope-lsa-type/ospf:as-scope-lsas/"
        + "ospf:as-scope-lsa/ospf:version/ospf:ospfv2/"
        + "ospf:ospfv2/ospf:body/ospf:opaque/"
        + "ospf:extended-prefix-tlvs/ospf:extended-prefix-tlv" {
    when "../../../../../../../../../../../../../"
       + "rt:type = 'ospf:ospfv2'" {
      description
        "This augmentation is only valid for OSPFv2.";
    }
    description
      "SR specific TLVs for OSPFv2 extended prefix TLV
       in type 11 opaque LSA.";
    uses prefix-sid-sub-tlvs;
    uses sid-binding-sub-tlvs;
  }

  augment "/rt:routing-state/rt:routing-instance/"
        + "rt:routing-protocols/rt:routing-protocol/"
        + "ospf:ospf/ospf:instance/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-tlvs/ospf:extended-link-tlv" {
    when "../../../../../../../../../../../../../../../"
       + "rt:type = 'ospf:ospfv2'" {
      description
        "This augmentation is only valid for OSPFv2.";
    }
    description
      "SR specific TLVs for OSPFv2 extended link TLV
       in type 10 opaque LSA.";

    container adj-sid-sub-tlvs {
      description "Adjacency SID optional sub-TLVs.";
      list adj-sid-sub-tlv {
        description "List of Adjacency SID sub-TLVs.";
        leaf flags {
          type bits {
            bit B {
              description
                "Backup flag.";
            }
            bit V {
              description
                "Value/Index flag.";
            }
            bit L {
              description
                "Local/Global flag.";
            }
            bit S {
              description
                "Set flag.";
            }
          }
          description "Flags.";
        }
        leaf mt-id {
          type uint8;
          description "Multi-topology ID.";
        }
        leaf weight {
          type uint8;
          description "Weight used for load-balancing.";
        }
        leaf sid {
          type uint32;
          description "Segment Identifier (SID) index/label.";
        }
      }
    }

    container lan-adj-sid-sub-tlvs {
      description "LAN Adjacency SID optional sub-TLVs.";
      list lan-adj-sid-sub-tlv {
        description "List of LAN adjacency SID sub-TLVs.";
        leaf flags {
          type bits {
            bit B {
              description
                "Backup flag.";
            }
            bit V {
              description
                "Value/Index flag.";
            }
            bit L {
              description
                "Local/Global flag.";
            }
            bit S {
              description
                "Set flag.";
            }
          }
          description "Flags.";
        }
        leaf mt-id {
          type uint8;
          description "Multi-topology ID.";
        }
        leaf weight {
          type uint8;
          description "Weight used for load-balancing.";
        }
        leaf neighbor-router-id {
          type yang:dotted-quad;
          description "Neighbor router ID.";
        }
        leaf sid {
          type uint32;
          description "Segment Identifier (SID) index/label.";
        }
      }
    }
  }

  augment "/rt:routing-state/rt:routing-instance/"
        + "rt:routing-protocols/rt:routing-protocol/"
        + "ospf:ospf/ospf:instance/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque" {
    when "../../../../../../../../../../../../../../../"
       + "rt:type = 'ospf:ospfv2'" {
      description
        "This augmentation is only valid for OSPFv2.";
    }

    description
      "SR specific TLVs for OSPFv2 type 9 opaque LSA.";

    uses extended-prefix-range-tlvs;
    uses sr-algorithm-tlv;
    uses sid-range-tlvs;
  }

  augment "/rt:routing-state/rt:routing-instance/"
        + "rt:routing-protocols/rt:routing-protocol/"
        + "ospf:ospf/ospf:instance/ospf:areas/"
        + "ospf:area/ospf:database/"
        + "ospf:area-scope-lsa-type/ospf:area-scope-lsas/"
        + "ospf:area-scope-lsa/ospf:version/ospf:ospfv2/"
        + "ospf:ospfv2/ospf:body/ospf:opaque" {
    when "../../../../../../../../../../../../../"
       + "rt:type = 'ospf:ospfv2'" {
      description
        "This augmentation is only valid for OSPFv2.";
    }

    description
      "SR specific TLVs for OSPFv2 type 10 opaque LSA.";

    uses extended-prefix-range-tlvs;
    uses sr-algorithm-tlv;
    uses sid-range-tlvs;
  }

  augment "/rt:routing-state/rt:routing-instance/"
        + "rt:routing-protocols/rt:routing-protocol/"
        + "ospf:ospf/ospf:instance/ospf:database/"
        + "ospf:as-scope-lsa-type/ospf:as-scope-lsas/"
        + "ospf:as-scope-lsa/ospf:version/ospf:ospfv2/"
        + "ospf:ospfv2/ospf:body/ospf:opaque" {
    when "../../../../../../../../../../../"
       + "rt:type = 'ospf:ospfv2'" {
      description
        "This augmentation is only valid for OSPFv2.";
    }
    description
      "SR specific TLVs for OSPFv2 type 11 opaque LSA.";

    uses extended-prefix-range-tlvs;
    uses sr-algorithm-tlv;
    uses sid-range-tlvs;
  }
}
