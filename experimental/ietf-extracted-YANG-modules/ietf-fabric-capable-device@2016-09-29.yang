module ietf-fabric-capable-device {
yang-version 1.1;
    namespace "urn:ietf:params:xml:ns:yang:ietf-fabric-capable-device";
    prefix fabric-device;

    import ietf-inet-types { prefix "inet"; revision-date "2013-07-15"; }
    import ietf-network { prefix "nw"; }
        import ietf-network-topology { prefix nt; }
    import ietf-yang-types { prefix "yang"; revision-date "2013-07-15"; }
    import ietf-fabric-types { prefix fabrictype; revision-date "2016-09-29"; }

        organization
    "IETF I2RS (Interface to the Routing System) Working Group";

        contact
    "WG Web:    <http://tools.ietf.org/wg/i2rs/ >
     WG List:   <mailto:i2rs@ietf.org>

     WG Chair:  Susan Hares
                <mailto:shares@ndzh.com>

     WG Chair:  Russ White
                <mailto:russ@riw.us>

     Editor:    Yan Zhuang
                <mailto:zhuangyan.zhuang@huawei.com>

     Editor:    Danian Shi
                <mailto:shidanian@huawei.com>";

    description
        "This module contains a collection of YANG definitions for Fabric.";

    revision "2016-09-29" {
        description
            "Initial revision of faas.";
                reference
                        "draft-zhuang-i2rs-yang-dc-fabric-network-topology-02";
    }

    identity fabric-capable-device-context {
                description
                        "identity of fabric capable device";
    }

    grouping fabric-capable-device-attribute {
                description
                        "attributes of fabric capable device";

        leaf fabric-id {
            type nw:node-id;
                        description "fabric id";
        }
        leaf fabric-ref {
            type fabrictype:node-ref;
                        description "fabric reference";
        }
    }

    grouping fabric-capable-device-config {
                description
                        "fabric service configuration of fabric capable device";

        list bridge-domain {
            key id;
                        description "list of bridge domains";
            leaf id {
                type string;
                                description "id of the device";
            }
            leaf flood {
                type boolean;
                default false;
                                description "flood";
            }
            leaf arp {
                type boolean;
                default false;
                                description "arp";
            }
            leaf segment {
                        type uint32;
                                description "segment";
            }
        }

        list bd-port {
                        key bd-port-id;
            description "bridge port list";
                        leaf bd-port-id {
                type string;
                                description "bridge port id";
            }
            leaf bdid {
                type string;
                                description "bridge id";
            }
            leaf ref-tp-id {
                type nt:tp-id;
                                description "reference of termination port id";
            }
            leaf access-type {
                type fabrictype:access-type;
                                description "access type";
            }
            leaf access-tag {
                type uint32;
                                description "access tag";
            }
            uses fabrictype:acl-list;
        }

        list vrf {
                        key id;
            description "vrf list";
                        leaf id {
                type string;
                                description "vrf id";
            }
            leaf name {
                type string;
                                description "name";
            }
            leaf vrf-ctx {
                type int32;
                                description "context";
            }
        }

        list bdif {
                        key id;
            description "bridge interface list";
                        leaf id {
                type string;
                                description "bridge interface id";
            }
            leaf bdid {
                type string;
                                description "bridge id";
            }
            leaf vrf {
                type int32;
                                description "vrf";
            }
            leaf ip-address {
                type inet:ip-address;
                                description "ip address";
            }
            leaf mask {
                type int32;
                                description "mask";
            }
            leaf mac-address {
                type yang:mac-address;
                                description "mac address";
            }
            uses fabrictype:acl-list;
            uses fabrictype:port-functions;
        }
    }

    augment "/nw:networks/nw:network/nw:node" {
                description "augmentation for fabric capable device nodes";
        leaf-list supported-fabric {
            type identityref {
                base fabrictype:fabric-type;
            }
                        description "supported fabric types";
        }

        leaf-list capability-supported {
                        type fabrictype:service-capabilities;
                        description "service capability list";
        }

        container attributes {
            config false;
                        description "attributes of the device";
            uses fabric-capable-device-attribute;
        }
        container config {
                        description "configuration of the device";
            uses fabric-capable-device-config;
        }
    }

    augment "/nw:networks/nw:network/nw:node/nt:termination-point" {
                description
                        "References a termination point to a tp in a fabric";

        leaf port-role {
            type fabrictype:fabric-port-role;
                        description "role in a fabric";
        }
        leaf port-ref {
            type fabrictype:tp-ref;
                        description "port reference in fabric";
        }
    }

    augment "/nw:networks/nw:network/nw:node/nt:termination-point" {
                description
                        "References a termination point to a tp in bridges";
        leaf-list bd-ids {
            type instance-identifier;
                        description "bridge id list";
        }
    }
}
