module ietf-datastore-push {
  namespace "urn:ietf:params:xml:ns:yang:ietf-datastore-push";
  prefix datastore-push;

  import ietf-yang-types {
    prefix yang;
  }

  organization "IETF";
  contact
    "WG Web:   <http://tools.ietf.org/wg/netconf/>
     WG List:  <mailto:netconf@ietf.org>

     WG Chair: Juergen Schoenwaelder
               <mailto:j.schoenwaelder@jacobs-university.de>

     WG Chair: Kent Watsen
               <mailto:kwatsen@juniper.net>

     WG Chair: Tom Nadeau
               <mailto:tnadeau@lucidvision.com>

     Editor:   Alexander Clemm
               <mailto:alex@cisco.com>

     Editor:   Alberto Gonzalez Prieto
               <mailto:albertgo@cisco.com>

     Editor:   Eric Voit
               <mailto:evoit@cisco.com>";
  description
    "This module contains conceptual YANG specifications
     for datastore push.";

  revision 2015-07-06 {
    description
      "Initial revision.";
    reference "Datastore push.";
  }

  feature custom-streams {
    description
      "This feature allows users to configure datastore update
       streams in addition to the stream provided by default,
       datastore-push.";
  }

  identity subscription-stream-status {
    description
      "Base identity for the status of subscriptions and
       datastreams.";
  }

  identity active {
    base subscription-stream-status;
    description
      "Status is active and healthy.";
  }

  identity inactive {
    base subscription-stream-status;
    description
      "Status is inactive, for example outside the
       interval between start time and stop time.";
  }

  identity in-error {
    base subscription-stream-status;
    description
      "The status is in error or degraded, meaning that
       stream and/or subscription are currently unable to provide
       the negotiated updates.";
  }

  identity subscription-errors {
    description
      "Base identity for subscription errors.";
  }

  identity internal-error {
    base subscription-errors;
    description
      "Subscription failures caused by server internal error.";
  }

  identity no-resources {
    base subscription-errors;
    description
      "Lack of resources, e.g. CPU, memory, bandwidth";
  }

  identity other {
    base subscription-errors;
    description
      "Fallback reason - any other reason";
  }

  identity encodings {
    description
      "Base identity to represent data encodings";
  }

  identity encode-xml {
    base encodings;
    description
      "Encode data using XML";
  }

  identity encode-json {
    base encodings;
    description
      "Encode data using JSON";
  }

  typedef datastore-contents {
    type string;
    description
      "This type is be used to represent datastore contents,
       including a filtered datastore subtree per a set of
       subscription parameters. ";
  }

  typedef subtree-filter {
    type string;
    description
      "This type is used to define a subtree filter.
       Its precise syntax is TBD.";
  }

  typedef subscription-identifier {
    type string {
      length "1 .. max";
    }
    description
      "A client-provided identifier for the subscription.";
  }
  typedef subscription-term-reason {
    type identityref {
      base subscription-errors;
    }
    description
      "Reason for a server to terminate a subscription.";
  }

  typedef subscription-susp-reason {
    type identityref {
      base subscription-errors;
    }
    description
      "Reason for a server to suspend a subscription.";
  }

  typedef encoding {
    type identityref {
      base encodings;
    }
    description
      "Specifies a data encoding, e.g. for a data subscription.";
  }

  typedef change-type {
    type enumeration {
      enum "create" {
        description
          "A new data node was created";
      }
      enum "delete" {
        description
          "A data node was deleted";
      }
      enum "modify" {
        description
          "The value of a data node has changed";
      }
    }
    description
      "Specifies different types of changes that may occur
       to a datastore.";
  }

  grouping subscription-stream-policy {
    description
      "This grouping contains the parameters which describe
       the policy which data is pushed as part of a
       subscription or a data stream.";
    leaf subtree-filter {
      type subtree-filter;
      description
        "Datastore subtree of interest.";
    }
    leaf xpath-filter {
      type yang:xpath1.0;
      description
        "Xpath defining the data items of interest.";
    }
    choice update-trigger {
      description
        "Defines necessary conditions for sending an event  to
         the subscriber.";
      case periodic {
        description
          "The agent is requested to notify periodically the
           current values of the datastore or the subset
           defined by the filter.";
        leaf period {
          type yang:timeticks;
          description
            "Elapsed time between notifications.";
        }
      }
      case on-change {
        description
          "The agent is requested to notify changes in
           values in the datastore or a subset of it defined
           by a filter.";
        leaf dampening-period {
          type yang:timeticks;
          mandatory true;
          description
            "Minimum amount of time that needs to have
             passed since the last time an update was
             provided.";
        }
        leaf-list excluded-change {
          type change-type;
          description
            "Use to restrict which changes trigger an update.
             For example, if modify is excluded, only creation and
             deletion of objects is reported.";
        }
        choice change-policy {
          description
            "Policy describing necessary conditions for
             sending an event to the subscriber.";
          case delta-policy {
            leaf delta {
              type uint32;
              description
                "For modified values of an integer-typed object,
                 minimum difference between current and last
                 report values that can trigger an update.";
            }
          }
        }
      }
    }
  }

  grouping subscription-info {
    description
      "This grouping describes basic information concerning a
       subscription, without the subscription policy which is
       defined separately to be shareable with the definition
       of a datastream.";
    leaf stream {
      type string;
      description
        "The name of the stream subscribed to.";
    }
    leaf encoding {
      type encoding;
      default encode-xml;
      description
        "The type of encoding for the subscribed data.
         Default is XML";
    }
    leaf start-time {
      type yang:date-and-time;
      description
        "Starting time for replays.";
      reference "RFC 5277, Section 2.1.1";
    }
    leaf stop-time {
      type yang:date-and-time;
      description
        "Time limit for events of interest.";
      reference "RFC 5277, Section 2.1.1";
    }
  }

  notification push-update {
    description
      "This notification contains an update from a datastore";
    leaf subscription-id {
      type subscription-identifier;
      mandatory true;
      description
        "This references the subscription because of which the
         notification is sent.";
    }
    leaf datastore-contents {
      type datastore-contents;
      description
        "This contains datastore contents
         per the subscription.";
    }
  }
  notification subscription-suspended {
    description
      "This notification indicates that a suspension of the
       subscription by the server has occurred.  No further
       datastore updates will be sent until subscription
       resumes.";
    leaf subscription-id {
      type subscription-identifier;
      mandatory true;
      description
        "This references the affected subscription.";
    }
    leaf reason {
      type subscription-susp-reason;
      description
        "Provides a reason for why the subscription was
         suspended.";
    }
  }
  notification subscription-resumed {
    description
      "This notification indicates that a subscription that had
       previously been suspended has resumed. Datastore updates
       will once again be sent.";
    leaf subscription-id {
      type subscription-identifier;
      mandatory true;
      description
        "This references the affected subscription.";
    }
  }
  notification subscription-modified {
    description
      "This notification indicates that a subscription has
       been modified.  Datastore updates sent from this point
       on will conform to the modified terms of the
       subscription.";
    leaf subscription-id {
      type subscription-identifier;
      mandatory true;
      description
        "This references the affected subscription.";
    }
    uses subscription-info;
    uses subscription-stream-policy;
  }
  notification subscription-terminated {
    description
      "This notification indicates that a subscription has been
       terminated.";
    leaf subscription-id {
      type subscription-identifier;
      mandatory true;
      description
        "This references the affected subscription.";
    }
    leaf reason {
      type subscription-term-reason;
      description
        "Provides a reason for why the subscription was
         terminated.";
    }
  }
  container streams {
    if-feature custom-streams;
    description
      "This container contains management data for custom streams
       that are configured by a user.";
    list stream {
      key "stream-name";
      description
        "A user-definable stream.";
      leaf stream-name {
        type string;
        mandatory true;
        description
          "The name assigned to the stream.";
      }
      leaf stream-status {
        type identityref {
          base subscription-stream-status;
        }
        config false;
        description
          "The current status of the stream";
      }
      uses subscription-stream-policy;
    }
  }
  container subscriptions {
    description
      "Contains the list of currently active subscription,
       used for subscription management and monitoring purposes.
       Note that this concerns subscriptions that are in-effect.
       Configuration and setup of subscriptions occurs via separate
       primitives, e.g. create-subscription, delete-subscription,
       and modify-subscription.";
    list datastore-push-subscription {
      key "subscription-id";
      config false;
      description
        "Content of a yang-push subscription.
         Subscriptions are created using a dedicated RPC, hence
         they do not constitute configuration information.";
      leaf subscription-id {
        type subscription-identifier;
        description
          "Identifier to use for this subscription.";
      }
      leaf subscription-status {
        type identityref {
          base subscription-stream-status;
        }
        description
          "The status of the subscription.";
      }
      uses subscription-info;
      uses subscription-stream-policy;
    }
  }
}
