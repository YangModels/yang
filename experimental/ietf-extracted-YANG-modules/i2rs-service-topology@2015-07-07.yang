module i2rs-service-topology {
  yang-version 1;
  namespace "urn:ietf:params:xml:ns:yang:i2rs-service-topology";
  prefix "i2rs-st";
  import ietf-network {
    prefix "nw";
  }
  import ietf-network-topology {
    prefix "nt";
  }
  import ietf-inet-types {
    prefix "inet";
  }
  organization "TBD";
  contact "TBD";

  description
    "This module defines a model for the service topology.";

  revision "2015-07-07" {
    description "Initial revision";
    reference "TBD";
  }

     identity svc-topo-flag-identity {
       description "Base type for svc flags";
       }

     identity l3vpn-svc-topo {
       base svc-topo-flag-identity;
       description "L3VPN service type";
      }

     identity l2vpn-svc-topo {
       base svc-topo-flag-identity;
       description "L2VPN service type";
      }

      identity EVPN-svc-topo {
       base svc-topo-flag-identity;
       description "EVPN service type";
      }

       identity Seamless-MPLS-svc-topo {
       base svc-topo-flag-identity;
       description "Seamless MPLS service type";
      }

       identity Etree-svc-topo {
       base svc-topo-flag-identity;
       description "Seamless MPLS service type";
      }

       identity I2rs-svc-topo {
       base svc-topo-flag-identity;
       description "I2RS create service topo";
      }

     identity svc-tp-type {
       description "Base type for service
    termination-point type flags";
       }

     identity svc-tp-type-service {
       base svc-tp-type;
       description "service type";
      }
     identity svc-tp-type-ip {
       base svc-tp-type;
       description "service IP";
      }
     identity svc-tp-type-unnum {
               base svc-tp-type;
       description "service unnumbered link";
      }
     grouping service-topology-types {
      leaf service-type* {
             type identityref {
               base svc-topo-flag-identity;
          }
              description "list of topology type
              supported"

        }
     }

     grouping service-topology attributes {
        description
         "Grouping for the attribute for the
             service topology";
             leaf name {type string;
             description "name of service
                     topology"};
             leaf composite-flag {
               type identityref {
                  base service-topology-types;}
                description "other topologies
                this topology is configured to
         be a composite of
                (L3VPN, L2VPN, I2RS only)"
             }
             leaf service-topo-id {
                     type leafref {
                      path "/nw:network/nw:network-id"
                      }
                      description
                      "An absolute reference to a network topology instance."
               }
              leaf service-id-number {
                 type uint32;
                     description "ID for topology";
             }
             leaf node-node {
                type unint32;
                description "count of service level nodes
                 in the network."
               }
             leaf composite-flag-status {
               type identityref {
                  base svc-topo-flag-identity;}
                description "other topologies
                this topology is currently a
         composite of
                (L3VPN, L2VPN, I2RS only)"
             }
     }

     grouping node-svc-attribute {
         leaf name {
               type inet:domain-name;
               description "Domain name for node";
              }
     leaf composite-flag* {
               type identityref {
                  base svc-topo-flag-identity;}
                description "virtual network
                 node can be composite of the
                topologies list
                (L3VPN, L2VPN, I2RS only)"
               }
              leaf service-node-id {
               type uint32;
               description "ID for node at
                service level";
              }
              leaf node-svc_status {
               type identityref {
                  base service-topology-types;}
                description "other topologies
                this topology is currewntly
         be a composite of
                (L3VPN, L2VPN, I2RS only)"
             }
     }

 grouping service-link-attributes {
       leaf name {type string;
           description "name of
               service link";}
       leaf link-id uint32;
       leaf svc-link-type {
                       type identityref {
                  base service-topology-types;}
                description "other topologies
                this link is current a composite of
                (L3VPN, L2VPN, I2RS only)"
             }
       leaf metric {
           type uint32;
               description "link metric";
   // may need to expand with TE topologies
             }
     }

 grouping service-termination-point-attributes {
        leaf svc-tp-id {
                     type uint32;
                     description "termination point id";
        }
        container supporting-termination-point {
         leaf svc-tp-type {
                type identityref {
                  base svc-tp-type;}
                description "other topologies
                this link termination point is
                part of
                (L3VPN, L2VPN, I2RS only)"

          choice svc-tp-type
                 case svc-tp-type-service {
                      description "network, node,
                       tp that supports this
                       termination point"
                             leaf service-network-id {
                              type uint32; }
                             leaf service-node-id {
                               type unit32;}
                             leaf service-link-id {
                               type uint32;}
                       }
                       case svc-tp-type-inet {
                        leaf ip-address inet:ip-addresss;
                       }
                       case svc-tp-type-unnum {
                        leaf unnumbered-id {
                          type uint32;}}
                       }
               }

     }

        augment /nw:network/nw:node
   +--rw node-svc-attributes
      +--rw name?        inet:domain-name
      +--rw composite_flag*  flag-type
              +--rw service-node-id  uint32
              +--rw node-svc-type service-type
              +--rw next-hop     [next-hop-id]

 augment /nw:network/nw:network-types
       use service-topology-types
 augment /nw:network/nw:network
       use service-topology-attributes

 augment /nw:network/nw:node
       use node-svc-attribute

 augment /nw:network/nt:link:
   uses service-link-attributes

augment /nw:network/nw:node/nt:termination-point:
   uses service-termination-point-attributes
} // module i2rs-service-topology
