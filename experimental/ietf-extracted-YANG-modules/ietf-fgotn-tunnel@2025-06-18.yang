module ietf-fgotn-tunnel {
  /* TODO: FIXME */
  yang-version 1.1;

  namespace "urn:ietf:params:xml:ns:yang:ietf-fgotn-tunnel";
  prefix "fgotn-tnl";

  import ietf-te {
    prefix "te";
    reference
      "RFC KKKK: A YANG Data Model for Traffic Engineering Tunnels,
                 Label Switched Paths and Interfaces";
  }

  /* Note: The RFC Editor will replace KKKK with the number assigned
     to the RFC once draft-ietf-teas-yang-te becomes an RFC.*/

  import ietf-otn-tunnel {
    prefix "otn-tnl";
    reference  "RFC JJJJ: OTN Tunnel YANG Model";
  }

  /* Note: The RFC Editor will replace JJJJ with the number assigned
     to the RFC once draft-ietf-ccamp-otn-tunnel-model becomes
     an RFC.*/

  organization
    "Internet Engineering Task Force (IETF) CCAMP WG";
  contact
    "
      ID-draft editor:
        Yanxia Tan (tanyx11@chinaunicom.cn);
        Yanlei Zheng (zhengyanlei@chinaunicom.cn);
        Italo Busi (italo.busi@huawei.com);
        Chaode Yu (yuchaode@huawei.com);
        Xing Zhao (zhaoxing@caict.ac.cn);
    ";

  description
    "This module defines a YANG data model for fgOTN-specific 
     extension based on existing network topology models. The model 
     fully conforms to the Network Management Datastore Architecture
     (NMDA).

     Copyright (c) 2024 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  // RFC Ed.: replace XXXX with actual RFC number and remove this
  // note.
  // RFC Ed.: update the date below with the date of RFC publication
  // and remove this note.

  revision 2025-06-18 {
    description
      "initial version";
    reference
      "RFC XXXX: YANG Data Models for fine grain Optical Transport
                 Network";
  }  

  augment "/te:te/te:tunnels/te:tunnel/"
        + "te:te-bandwidth/te:technology/otn-tnl:otn" {
    description
      "augmentation of fgOTN tunnel on bandwidth structure";
    leaf fgoduflex-bandwidth {
      type string;
      description 
        "Augment TE bandwidth of the fgOTN tunnel";
    }
  }

  augment "/te:te/te:tunnels/te:tunnel/"
        + "te:primary-paths/te:primary-path/"
        + "te:explicit-route-objects/"
        + "te:route-object-include-exclude/te:type/te:label/"
        + "te:label-hop/te:te-label/te:technology/otn-tnl:otn" + 
          "/otn-tnl:otn-label" {
    description
      "augmentation of fgOTN label";
    leaf fgts-numbers {
      type string;
      description 
        "Augment fgOTN timeslot information of this label hop";
    }
  }

  augment "/te:te/te:tunnels/te:tunnel/te:primary-paths" + 
          "/te:primary-path/te:primary-reverse-path" + 
          "/te:explicit-route-objects" + 
          "/te:route-object-include-exclude/te:type/te:label" + 
          "/te:label-hop/te:te-label/te:technology/otn-tnl:otn" + 
          "/otn-tnl:otn-label" {
    description
      "augmentation of fgOTN label";
    leaf fgts-numbers {
      type string;
      description 
        "Augment fgOTN timeslot information of this label hop";
    }
  }

  augment "/te:te/te:tunnels/te:tunnel/te:secondary-paths" + 
          "/te:secondary-path/te:explicit-route-objects" + 
          "/te:route-object-include-exclude/te:type/te:label" + 
          "/te:label-hop/te:te-label/te:technology/otn-tnl:otn" + 
          "/otn-tnl:otn-label" {
    description
      "augmentation of fgOTN label";
    leaf fgts-numbers {
      type string;
      description 
        "fgOTN timeslot information of this label hop";
    }
  }  

  augment "/te:te/te:tunnels/te:tunnel/te:secondary-reverse-paths" + 
          "/te:secondary-reverse-path/te:explicit-route-objects" + 
          "/te:route-object-include-exclude/te:type/te:label" + 
          "/te:label-hop/te:te-label/te:technology/otn-tnl:otn" + 
          "/otn-tnl:otn-label" {
    description
      "augmentation of fgOTN label";
    leaf fgts-numbers {
      type string;
      description 
        "fgOTN timeslot information of this label hop";
    }
  }

  augment "/te:te/te:lsps/te:lsp/te:lsp-actual-route-information" +
          "/te:lsp-actual-route-information/te:type/te:label" +
          "/te:label-hop/te:te-label/te:technology/otn-tnl:otn" +
          "/otn-tnl:otn-label" {
    description
      "augmentation of fgOTN label";
    leaf fgts-numbers {
      type string;
      description 
        "fgOTN timeslot information of this label hop";
    }
  }
}
