module ietf-power-energy-base {
  yang-version 1.1;

  namespace "urn:ietf:params:xml:ns:yang:ietf-power-energy-base";
  prefix peb;

  import iana-power-and-energy {
    prefix ianaeo;
    reference
      "IANA-defined identities for power and energy class";
  }

  organization
    "IETF GREEN Working Group";

  contact
    "WG Web: <https://datatracker.ietf.org/wg/green/>
     WG List: <mailto:green@ietf.org>";

  description
    "Base identities, typedefs, and reusable power and energy
     attributes.";

  revision 2026-07-02 {
    description
      "Initial revision.";
    reference
      "RFC XXX: Energy Object YANG Data Model";
  }

  identity data-source-accuracy {
    description
      "Base identity for all possible data accuracy types.";
  }

  identity accuracy-unknown {
    base data-source-accuracy;
    description
      "The accuracy of the power data is unknown.";
  }

  identity accuracy-unavailable {
    base accuracy-unknown;
    description
      "A power data is not available for some reason, such as a sensor failure or a component being powered off.";
  }

  identity accuracy-like-parent {
    base data-source-accuracy;
    description
      "The accuracy of the power and energy data is inherited from the parent object.";
  }

  identity accuracy-estimated {
    base data-source-accuracy;
    description
      "The power data is estimated rather than directly measured.";
  }

  identity accuracy-static {
    base accuracy-estimated;
    description
      "Static data such as manufacturer specifications or nameplate ratings.";
  }

  identity accuracy-historic {
    base accuracy-estimated;
    description
      "Historic measurement data for this specific system and usage pattern.";
  }

  identity accuracy-learned {
    base accuracy-estimated;
    description
      "A machine-learning-based prediction.";
  }

  identity accuracy-measured {
    base data-source-accuracy;
    description
      "The power data is a direct, real-time measurement from a sensor.";
  }

  identity accuracy-measured-bronze {
    base accuracy-measured;
    description
      "Direct measurement with bronze accuracy.";
  }

  identity accuracy-measured-bronze-1 {
    base accuracy-measured-bronze;
    description
      "Bronze accuracy with +/-1 absolute unit.";
  }

  identity accuracy-measured-bronze-10 {
    base accuracy-measured-bronze;
    description
      "Bronze accuracy with +/-10 absolute units.";
  }

  identity accuracy-measured-bronze-100 {
    base accuracy-measured-bronze;
    description
      "Bronze accuracy with +/-100 absolute units.";
  }

  identity accuracy-measured-bronze-1000 {
    base accuracy-measured-bronze;
    description
      "Bronze accuracy with +/-1000 absolute units.";
  }

  identity accuracy-measured-silver {
    base accuracy-measured;
    description
      "Direct measurement with silver accuracy.";
  }

  identity accuracy-measured-silver-1 {
    base accuracy-measured-silver;
    description
      "Silver accuracy with +/-1 absolute unit.";
  }

  identity accuracy-measured-silver-10 {
    base accuracy-measured-silver;
    description
      "Silver accuracy with +/-10 absolute units.";
  }

  identity accuracy-measured-silver-100 {
    base accuracy-measured-silver;
    description
      "Silver accuracy with +/-100 absolute units.";
  }

  identity accuracy-measured-silver-1000 {
    base accuracy-measured-silver;
    description
      "Silver accuracy with +/-1000 absolute units.";
  }

  identity accuracy-measured-gold {
    base accuracy-measured;
    description
      "Direct measurement with gold accuracy.";
  }

  identity accuracy-measured-gold-1 {
    base accuracy-measured-gold;
    description
      "Gold accuracy with +/-1 absolute unit.";
  }

  identity accuracy-measured-gold-10 {
    base accuracy-measured-gold;
    description
      "Gold accuracy with +/-10 absolute units.";
  }

  identity accuracy-measured-gold-100 {
    base accuracy-measured-gold;
    description
      "Gold accuracy with +/-100 absolute units.";
  }

  identity accuracy-measured-gold-1000 {
    base accuracy-measured-gold;
    description
      "Gold accuracy with +/-1000 absolute units.";
  }

  identity accuracy-measured-red {
    base accuracy-measured;
    description
      "Direct measurement with red accuracy.";
  }

  identity accuracy-measured-red-1 {
    base accuracy-measured-red;
    description
      "Red accuracy with +/-1 absolute unit.";
  }

  identity accuracy-measured-red-10 {
    base accuracy-measured-red;
    description
      "Red accuracy with +/-10 absolute units.";
  }

  identity accuracy-measured-red-100 {
    base accuracy-measured-red;
    description
      "Red accuracy with +/-100 absolute units.";
  }

  identity accuracy-measured-red-1000 {
    base accuracy-measured-red;
    description
      "Red accuracy with +/-1000 absolute units.";
  }

  identity accuracy-measured-ones {
    base accuracy-measured;
    description
      "All digits are valid except trailing zeros.";
  }

  typedef power-factor {
    type uint8 {
      range "0 .. 100";
    }
    default 100;
    description
      "Percent value of the power factor measurement.";
  }

  identity power-state {
    description
      "Base identity for all possible power states.";
  }

  identity power-state-on {
    base power-state;
    description
      "Full power on.";
  }

  identity power-state-off {
    base power-state;
    description
      "Power off.";
  }

  identity power-state-sleep {
    base power-state;
    description
      "Low-power state.";
  }

  identity energy-relationship-type {
    description
      "Base identity for energy object relationships.";
  }

  identity powered-by {
    base energy-relationship-type;
    description
      "Energy Object A is powered by Energy Object B.";
  }

  identity powering {
    base energy-relationship-type;
    description
      "Energy Object A is powering Energy Object B.";
  }

  identity metered-by {
    base energy-relationship-type;
    description
      "Energy Object A is metered by Energy Object B.";
  }

  identity metering {
    base energy-relationship-type;
    description
      "Energy Object A is metering Energy Object B.";
  }

  identity aggregated-by {
    base energy-relationship-type;
    description
      "Energy Object A is aggregated by Energy Object B.";
  }

  identity aggregating {
    base energy-relationship-type;
    description
      "Energy Object A is aggregating Energy Object B.";
  }

  identity enabled-by {
    base energy-relationship-type;
    description
      "Energy Object A is enabled by Energy Object B.";
  }

  identity enabling {
    base energy-relationship-type;
    description
      "Energy Object A is enabling Energy Object B.";
  }

  grouping power-and-energy-attributes {
    description
      "Reusable power and energy measurement attributes.";

    container power {
      description
        "Container for power measurement attributes.";

      leaf instantaneous-power {
        type int64;
        units "mWatts";
        description
          "Instantaneous power usage for the energy object.";
      }

      leaf nameplate-power {
        type uint32;
        units "Watts";
        description
          "Nameplate power rating of the energy object.";
      }

      leaf data-source-accuracy {
        type identityref {
          base data-source-accuracy;
        }
        default accuracy-like-parent;
        description
          "Accuracy of the power data source.";
      }

      leaf power-factor {
        type power-factor;
        description
          "Percent value of the power factor measurement.";
      }

      leaf measurement-local {
        type boolean;
        description
          "Indicates whether the power measurement is local or remote.";
      }
    }

    container energy {
      description
        "Container for energy measurement attributes.";

      leaf total-energy-consumed {
        type uint64;
        units "Watt-hours";
        description
          "Total cumulative energy consumed since the last reset.";
      }

      leaf total-energy-delivered {
        type uint64;
        units "Watt-hours";
        description
          "Total cumulative energy delivered since the last reset.";
      }

      leaf data-source-accuracy {
        type identityref {
          base data-source-accuracy;
        }
        default accuracy-like-parent;
        description
          "Accuracy of the energy data source.";
      }

      leaf measurement-local {
        type boolean;
        description
          "Indicates whether the energy measurement is local or remote.";
      }

      leaf-list certifications {
        type identityref {
          base ianaeo:certification-type;
        }
        description
          "Certifications applicable to this energy object.";
      }
    }
  }
}
