module ietf-mud-sbom {
  yang-version 1.1;
  namespace "urn:ietf:params:xml:ns:yang:ietf-mud-sbom";
  prefix mud-sbom;

  import ietf-inet-types {
    prefix inet;
  }
  import ietf-mud {
    prefix mud;
  }

  organization
    "IETF OPSAWG (Ops Area) Working Group";
  contact
    "WG
     Web: http://tools.ietf.org/wg/opsawg/
     WG List: opsawg@ietf.org
     Author: Eliot Lear lear@cisco.com
     Author: Scott Rose scott.rose@nist.gov";
  description
    "This YANG module augments the ietf-mud model to provide for
     reporting of SBOMs.

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.  ";

  revision 2021-04-29 {
    description
      "Initial proposed standard.";
    reference
      "RFC XXXX: Extension for MUD SBOM";
  }

  grouping mud-sbom-extension {
    description
      "SBOM extension grouping";
    container sbom {
      description
        "container of methods to get an SBOM.";
      choice sbom-type {
        description
          "SBOM type";
        case cloud {
          list sboms {
            key "version-info";
            description
              "A list of SBOMs tied to different s/w
               or h/w versions.";
            leaf version-info {
              type string;
              description
                "The version to which this SBOM refers.";
            }
            leaf sbom-url {
              type inet:uri;
              description
                "A statically located URI.";
            }
          }
        }
        case local-well-known {
          leaf local-well-known {
            type empty;
            description
              "SBOM information is to be retrieved via
                https from the host on port 443, at
                https://{hostname}/.well-known/sbom, where
                hostname is replaced with the host to which
                this MUD extension refers.";
          }
        }
        case contact-info {
          leaf contact-uri {
            type inet:uri;
            mandatory true;
            description
              "This MUST be either a tel, http, https, or
               mailto uri schema that customers can use to
               contact someone for SBOM information.";
          }
        }
        case openc2 {
          leaf openc2-uri {
            type inet:uri;
            mandatory true;
            description
              "A link to the OpenC2 https RESTful
                 \t mapping.  The OpenC2 protocol is then
                      used to retrieve the SBOM";
          }
        }
      }
    }
  }

  augment "/mud:mud" {
    description
      "Add extension for SBOMs.";
    uses mud-sbom-extension;
  }
}
