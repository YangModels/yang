module ietf-ospfv3-te {
yang-version 1.1;
namespace "urn:ietf:params:xml:ns:yang:ietf-ospfv3-te";

prefix ospfv3-te;

import ietf-inet-types {
  prefix "inet";
  reference "RFC 6991: Common YANG Data Types";
}

import ietf-yang-types {
  prefix "yang";
  reference "RFC 6991: Common YANG Data Types";
}

import ietf-routing-types {
  prefix "rt-types";
  reference "RFC 8294: Common YANG Data Types for the
             Routing Area";
}

import ietf-routing {
  prefix "rt";
}

import ietf-ospf {
  prefix "ospf";
}

organization
  "IETF LSR - Link State Routing Working Group";

contact
   "WG Web:   <http://tools.ietf.org/wg/lsr>
    WG List:  <mailto:lsr@ietf.org>

    Author:   Yingzhen Qu
              <mailto:yqu@futurewei.com>
    Author:   Acee Lindem
              <mailto:acee@cisco.com>";

description
  "This YANG module defines the configuration and operational
  state for OSPFv3 extensions to support intra-area Traffic
  Engineering (TE) as defined in RFC 5329.

   Copyright (c) 2019 IETF Trust and the persons identified as
   authors of the code.  All rights reserved.

   Redistribution and use in source and binary forms, with or
   without modification, is permitted pursuant to, and subject
   to the license terms contained in, the Simplified BSD License
   set forth in Section 4.c of the IETF Trust's Legal Provisions
   Relating to IETF Documents
   (http://trustee.ietf.org/license-info).

   This version of this YANG module is part of RFC XXXX;
   see the RFC itself for full legal notices.";

reference "RFC XXXX";

revision 2019-08-13 {
  description
    "Initial version";
  reference
    "RFC XXXX: A YANG Data Model for OSPFv3 TE.";
}

identity ospfv3-intra-area-te-lsa {
  base ospf:ospfv3-lsa-type;
  description
    "OSPFv3 Intrea-area TE LSA.";
}

grouping ospfv3-intra-area-te {
  description "Grouping for OSPFv3 intra-area-te-lsa.";
  container ospfv3-intra-area-te {
    container router-address-tlv {
      description "The router IPv6 address tlv advertises a reachable
                   IPv6 address.";
      leaf router-address {
        type inet:ipv6-address;
        description
          "Router IPv6 address.";
      }
    }

    container link-tlv {
      description "Describes a singel link, and it is constructed
                   of a set of Sub-TLVs.";
      leaf link-type {
        type ospf:router-link-type;
        mandatory true;
        description "Link type.";
      }
      container local-if-ipv6-addrs {
        description "All local interface IPv6 addresses.";
        leaf-list local-if-ipv6-addr {
          type inet:ipv6-address;
          description
            "List of local interface IPv6 addresses.";
        }
      }

      container remote-if-ipv6-addrs {
        description "All remote interface IPv6 addresses.";
        leaf-list remote-if-ipv6-addr {
          type inet:ipv6-address;
          description
            "List of remote interface IPv6 addresses.";
        }
      }

      leaf te-metric {
        type uint32;
        description "TE metric.";
      }

      leaf max-bandwidth {
        type rt-types:bandwidth-ieee-float32;
        description "Maximum bandwidth.";
      }

      leaf max-reservable-bandwidth {
        type rt-types:bandwidth-ieee-float32;
        description "Maximum reservable bandwidth.";
      }

      container unreserved-bandwidths {
        description "All unreserved bandwidths.";
        list unreserved-bandwidth {
          leaf priority {
            type uint8 {
              range "0 .. 7";
            }
            description "Priority from 0 to 7.";
          }
          leaf unreserved-bandwidth {
            type rt-types:bandwidth-ieee-float32;
            description "Unreserved bandwidth.";
          }
          description
            "List of unreserved bandwidths for different
             priorities.";
        }
      }

      leaf admin-group {
        type uint32;
        description
          "Administrative group/Resource Class/Color.";
      }

      container neighbor-id {
        description "Neighbor link identitification.";
        leaf nbr-interface-id {
          type inet:ipv4-address;
          mandatory true;
          description "The neighbor's interface ID.";
        }
        leaf nbr-router-id {
          type yang:dotted-quad;
          mandatory true;
          description "The neighbor's router ID.";
        }
      }

      uses ospf:unknown-tlvs;
    }

    description "OSPFv3 Intra-Area-TE-LSA.";
    reference "RFC 5329: Traffic Engineering Extensions to OSPF
            :   Version 3.";
  }
}

augment "/rt:routing/"
      + "rt:control-plane-protocols/rt:control-plane-protocol/"
      + "ospf:ospf/ospf:areas/"
      + "ospf:area/ospf:database/"
      + "ospf:area-scope-lsa-type/ospf:area-scope-lsas/"
      + "ospf:area-scope-lsa/ospf:version/ospf:ospfv3/"
      + "ospf:ospfv3/ospf:body" {
  when "../../../../../../../../../"
     + "rt:type = 'ospf:ospfv3'" {
    description
      "This augmentation is only valid for OSPFv3.";
  }
  description
    "OSPFv3 Intrea-Area-TE-LSA.";

  uses ospfv3-intra-area-te;
}
}
