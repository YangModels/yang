module gen-oam {
  namespace "urn:ietf:params:xml:ns:yang:gen-oam";
  prefix goam;

import ietf-interfaces {
prefix if;
}
import ietf-inet-types {
prefix inet;
 }
import ietf-yang-types {

prefix yang;
}

organization "IETF LIME (Layer Independent OAM Management in Multi-Layer Environment) Working Group";
 description
 "This YANG module defines the abstract notification and rpc command for multi-layer OAM management to be used
 within IETF in a protocol independent manner.";

 revision 2014-10-23 {
 description
 "Initial revision.";
 reference " RFC XXXX: A YANG Data Model for Layer independent OAM management";
 }
 /*
 * identity definitions,
 */

 identity technology-types {
 description
  "this is the base identity of technology types which are
 ethernet, bfd, mpls, sfc, ipv4, ipv6";
 }

 identity mpls {
  base technology-types;
 description
 "mpls technology type";
 }

 identity sfc {

 base technology-types;
 description
 "sfc type";
 }

 identity ipv4 {
  base technology-types;
  description
  "technology of ipv4";
  }

 identity ipv6 {
 base technology-types;

 description
 "technology of ipv6";
 }

 /*

  * typedef definitions
 */

 typedef vni {
 type uint32;
 }

 typedef MEP-address {
 type union {
type yang:mac-address
   type inet:ipv4-address;
   type inet:ipv6-address;
   }
   description
   "Defines addresses of different MEP
   types. IPv4, IPv6";
   }

   typedef MEP-id {
   type union{
type uint32 {
   range "1..8191";
}
type yang:mac-address
    type inet:ipv4-address;
    type inet:ipv6-address;
}
   description
   "Defines type for MEPID";
    }

   typedef Context-Identifier {
   type union {
   type vni;
   type uint32;
   }
   description
   "defines context identifier types VNI, etc..";
   }

   typedef oam-counter32 {
   type yang:zero-based-counter32;

    description
    "defines 32 bit counter for OAM";
   }

   /*
   * grouping definitions
   */
grouping context-id {
       description
         "grouping for context id, this will be augmented
          by others who use this component";
       choice context-id {
         default "context-null";
         case context-null {
           description
             "this is a place holder when no context is needed";
           leaf context-null {
             type empty;
             description
               "there is no context define";
           }
         }
       }
     }

grouping maintenance-stats {
       description
         "grouping for maintenance statistics, this will be augmented
          by others who use this component";
       choice maintenance-stats {
         default "maintenance-null";
         case maintenance-null {
           description
             "this is a place holder when no maintenance statis is needed";
           leaf maintenance-null {
             type empty;
             description
               "there is no maintenance statistics to be defined";
           }
         }
       }
     }

grouping interface-status {
       description
         "collection of interface related status";
     leaf list interface-status{
         key " admin-status, oper-status ";
       leaf admin-status {
         config false;
         type leafref {
           path "/if:interfaces-state/if:interface/if:admin-status";
         }
         description
           "oper status from ietf-interface module";
       }

       leaf oper-status {
         config false;
         type leafref {
           path "/if:interfaces-state/if:interface/if:oper-status";
         }
         description
           "oper status from ietf-interface module";
       }
     }
}

leaf oper-status {
           type enumeration{
enum up;
enum down;
}
           description
" This leaf specifies the operational status of the
               Maintenance Domain (MD)";
         }

leaf sub-oper-status {
           type enumeration{
mdDown;
 maDown;
oamAppDown;
pathDown;};
           description
" This leaf specifies the reason why the MD operational
               status as mentioned by the leaf Oper-Status
               is down.

               The mdDown indicates the MD is down.
               The maDown indicates the MA table is
               down.
               The oamAppDown indicates that the
               OAM application has notified that the entity
               monitored by this MEG is down.
               The pathDown indicates that the underlying
               path is down";
         }
 }
