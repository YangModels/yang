submodule ietf-bgp-common-errors {
  yang-version 1.1;
  belongs-to ietf-bgp {
    prefix bgp;
  }

  import iana-bgp-notification {
    prefix bn;
    reference
      "RFC XXXX: YANG Model for Border Gateway Protocol (BGP-4).";
  }
  import ietf-yang-types {
    prefix yang;
    reference
      "RFC 9911: Common YANG Data Types.";
  }

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This sub-module contains common groupings related to BGP errors
     that are common across multiple contexts within the BGP module.
     That is to say that they may be application to a subset of
     global, peer-group, or neighbor contexts.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-03-02 {
    description
      "Initial Version";
    reference
      "RFC XXXX: YANG Model for Border Gateway Protocol (BGP-4).";
  }

  /*
   * Groupings
   */

  grouping bgp-errors-common {
    description
      "BGP NOTIFICATION state that is common in the sent and received
       direction.";

    leaf last-notification {
      type yang:date-and-time;
      description
        "The timestamp indicates the time that a BGP
         NOTIFICATION message was last handled.";
      reference
        "RFC 4271: A Border Gateway Protocol 4 (BGP-4), Section
         4.5.";
    }
    leaf last-error {
      type identityref {
        base bn:bgp-notification;
      }
      description
        "The last NOTIFICATION error for the peer on this
         connection.  If no identity is registered for the
         Error code / Error subcode, this leaf contains the most
         applicable identity for the BGP NOTIFICATION base code.

         The last-error-code and last-error-subcode will always have
         the information received in the NOTIFICATION PDU.";
      reference
        "RFC 4271: A Border Gateway Protocol 4 (BGP-4), Section
         4.5.";
    }
    leaf last-error-code {
      type uint8;
      description
        "The last NOTIFICATION Error code for the peer on
         this connection.";
      reference
        "RFC 4271: A Border Gateway Protocol 4 (BGP-4), Section
         4.5.";
    }
    leaf last-error-subcode {
      type uint8;
      description
        "The last NOTIFICATION Error subcode for the peer on
         this connection.";
      reference
        "RFC 4271: A Border Gateway Protocol 4 (BGP-4), Section
         4.5.";
    }
  }
  grouping bgp-errors-common-data {
    description
      "BGP NOTIFICATION data state that is common in the sent and
       received direction.";

    leaf last-error-data {
      type binary {
        length "0..65535";
      }
      description
        "Content of the BGP NOTIFICATION PDU's Data field.  This data
         is NOTIFICATION Error code / Error subcode specific.";
      reference
        "RFC 4271: A Border Gateway Protocol 4 (BGP-4), Section
         4.5.";
    }
  }

  grouping bgp-encapsulated-errors-common {
    description
      "BGP NOTIFICATION state that is common in the sent and received
       direction that has been encapsulated in a CEASE/HARD RESET
       NOTIFICATION.

       Note that these leafs are only present when carrying the RFC
       8538 encapsulated NOTIFICATION state. In this case,
       the last-error-data leaf will carry the encapsulated Data.";

    leaf last-encapsulated-error {
      type identityref {
        base bn:bgp-notification;
      }
      description
        "The last RFC 8538 encapsulated NOTIFICATION error for the
         peer on this connection.  If no identity is registered for
         the Error code / Error subcode, this leaf contains the most
         applicable identity for the BGP NOTIFICATION base code.

         The last-encapsulated-error-code and
         last-encapsulated-error-subcode will always have the
         encapsulated information received in the CEASE/HARD RESET
         NOTIFICATION PDU's encapsulated ErrCode and Subcode
         fields.";
      reference
        "RFC 8538: Notification Message Support for BGP Graceful
         Restart, Section 3.1.";
    }
    leaf last-encapsulated-error-code {
      type uint8;
      description
        "The last RFC 8538 encapsulated NOTIFICATION Error code for
         the peer on this connection.";
      reference
        "RFC 8538: Notification Message Support for BGP Graceful
         Restart, Section 3.1.";
    }
    leaf last-encapsulated-error-subcode {
      type uint8;
      description
        "The last RFC 8538 encapsulated NOTIFICATION Error subcode
         for the peer on this connection.";
      reference
        "RFC 8538: Notification Message Support for BGP Graceful
         Restart, Section 3.1.";
    }
  }
}
