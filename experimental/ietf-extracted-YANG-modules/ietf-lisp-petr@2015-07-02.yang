module ietf-lisp-petr {
  namespace "urn:ietf:params:xml:ns:yang:ietf-lisp-petr";
  prefix lisp-petr;
  import ietf-lisp {
    prefix lisp;
  }
  import ietf-lisp-address-types {
    prefix lcaf;
  }
  organization
   "IETF LISP (Locator/ID Separation Protocol) Working Group";
  contact
    "lisp@ietf.org";
  description
    "This YANG module defines the generic configuration
     data for a LISP PETR. The module can be extended by vendors to
     define vendor-specific configuration parameters and policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";
  revision 2015-07-02 {
    description
      "Initial revision.";
    reference
      "https://tools.ietf.org/html/rfc6832";
  }
  identity petr {
    base lisp:lisp-device;
    description
      "LISP PETR.";
  }
  augment "/lisp:lisp/lisp:devices/lisp:device" {
    when "lisp:type = lisp-petr:petr" {
      description
        "Augment is valid when LISP device type is PETR.";
    }
    description
      "This augments LISP devices list with PETR specific
       parameters.";
    container proxy-etr-cfg {
      presence "LISP PETR operation enabled";
      description
        "Proxy ETR configuration parameters.";
      container servicing-eids {
        description
          "EIDs serviced by the PETR.";
        list eid {
          key "id";
          description
            "List of EIDs serviced by the PETR.";
          leaf id {
            type lisp:eid-id;
            description
              "Id of serviced EID.";
          }
          container eid-address {
            uses lcaf:lisp-address;
            description
              "Serviced EID in generic LISP address format.";
          }
        }
      }
    }
  }
}
