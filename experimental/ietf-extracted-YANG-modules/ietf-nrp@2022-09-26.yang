module ietf-nrp {
  yang-version 1.1;
  namespace "urn:ietf:params:xml:ns:yang:ietf-nrp";
  prefix nrp;

  import ietf-network {
    prefix nw;
    reference
      "RFC 8345: A YANG Data Model for Network Topologies";
  }
  import ietf-network-topology {
    prefix nt;
    reference
      "RFC 8345: A YANG Data Model for Network Topologies";
  }
  import ietf-routing-types {
    prefix rt-types;
    reference
      "RFC 8294: Common YANG Data Types for the Routing Area";
  }
  import ietf-te-types {
    prefix te-types;
    reference
      "RFC 8776: Traffic Engineering Common YANG Types";
  }
  import ietf-te-packet-types {
    prefix te-packet-types;
    reference
      "RFC 8776: Traffic Engineering Common YANG Types";
  }
  import ietf-inet-types {
    prefix inet;
    reference
      "RFC 6991: Common YANG Data Types";
  }
  import ietf-access-control-list {
    prefix acl;
    reference
      "RFC 8519: YANG Data Model for Network Access Control Lists
       (ACLs)";
  }

  organization
    "IETF TEAS Working Group";
  contact
    "
     WG Web: <http://tools.ietf.org/wg/teas/>
     WG List:<mailto:teas@ietf.org>

     Editor: Bo Wu <lana.wubo@huawei.com>
           : Dhruv Dhody <dhruv.ietf@gmail.com>";
  description
    "This YANG module defines a network data module for
     NRP(Network Resource Partition).

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
        (https://trustee.ietf.org/license-info).

     This version of this YANG module is part of RFC XXXX
     (https://www.rfc-editor.org/info/rfcXXXX); see the RFC itself
     for full legal notices.";

  revision 2022-09-26 {
    description
      "This is the initial version of NRP YANG model.";
    reference
      "RFC XXX: A YANG Data Model for Network Resource Partition";
  }

  typedef srv6-sid {
    type inet:ipv6-prefix;
    description
      "Defines an SRv6 Segment ID (SID). That is,
       an IPv6 address explicitly associated with the segment.";
    reference
      "RFC 8402: Segment Routing Architecture";
  }

  identity nrp-partition-type {
    description
      "Base identity for nrp partition type.";
  }

  identity nrp-control-plane-partition {
    base nrp-partition-type;
    description
      "Identity for control plane partition.";
  }

  identity nrp-data-plane-partition {
    base nrp-partition-type;
    description
      "Identity for data plane partition.";
  }

  identity nrp-hybrid-plane-partition {
    base nrp-partition-type;
    description
      "Identity for both planes partition.";
  }

  identity nrp-link-partition-type {
    description
      "Base identity for interface partition type.";
  }

  identity virtual-sub-interface-partition {
    base nrp-link-partition-type;
    description
      "Identity for virtual interface or sub-interface, e.g. FlexE.";
  }

  identity queue-partition {
    base nrp-link-partition-type;
    description
      "Identity for queue partition type.";
  }

  /*
   * Groupings
   */

  grouping nrp-resource-reservation {
    description
      "Grouping for NRP resource reservation.";
    container resource-reservation {
      description
        "Container for NRP resource reservation.";
      leaf link-partition-type {
        type identityref {
          base nrp-link-partition-type;
        }
        description
          "Indicates the resource reservation type of an NRP link.";
      }
      container bandwidth-reservation {
        description
          "Container for NRP bandwidth reservation.";
        choice bandwidth-type {
          description
            "Choice of bandwidth reservation type.";
          case bandwidth-value {
            leaf bandwidth-value {
              type uint64;
              units "bps";
              description
                "Bandwidth allocation for the NRP as absolute value.";
            }
          }
          case bandwidth-percentage {
            leaf bandwidth-percent {
              type rt-types:percentage;
              description
                "Bandwidth allocation for the NRP as a percentage
                 of a link.";
            }
          }
        }
      }
    }
  }

  grouping nrp-control-plane-attributes {
    description
      "Grouping for NRP control plane attributes.";
    container control-plane {
      description
        "The container of NRP control plane mechanisms.";
      leaf multi-topology-id {
        type uint32;
        description
          "Indicates the MT-id of the NRP distributed control plane.";
      }
      leaf algo-id {
        type uint32;
        description
          "Indicates the algo-id of the NRP distributed control plane.";
      }
      leaf sharing {
        type boolean;
        default "true";
        description
          "'true' if the the NRP distributed control plane
           can be shared with other NRPs;
           'false' if the the NRP distributed control plane
           is dedicated to this NRP.";
      }
      leaf topology-change-is-allowed {
        type boolean;
        description
          "true  - topology change is allowed,
           false - topology change is disallowed.";
      }
    }
  }

  grouping nrp-data-plane-attributes {
    description
      "Grouping for NRP data plane attributes.";
    container data-plane {
      description
        "The data plane mechanisms of an NRP. The forwarding plane
         could be MPLS, IPv6, SRv6, or SR-MPLS.";
      container global-resource-identifier {
        description
          "The container of global NRP data-plane ID.";
        container ipv6 {
          description
            "The container of IPv6 based NRP data-plane identifier.";
          leaf value {
            type inet:ipv6-address;
            description
              "Indicates the IPv6 NRP data-plane identifier.";
          }
        }
        container mpls {
          description
            "The container of MPLS based NRP data-plane identifier.";
          leaf label {
            type uint32;
            description
              "Indicates MPLS metadata values to identify MPLS NRP
               data plane identifier, e.g. Ancillary data.";
          }
        }
      }
      container nrp-aware {
        description
          "The container of SR based NRP data-plane identifier.";
        container srv6 {
          presence "Enables SRv6 data plane type.";
          description
            "The container of SRv6 based NRP data-plane identifier.";
        }
        container sr-mpls {
          presence "Enables SR MPLS data plane type.";
          description
            "The container of SR MPLS based NRP data-plane identifier.";
        }
      }
    }
  }

  grouping nrp-traffic-steering-policy {
    description
      "The grouping of the NRP traffic steering policy.";
    container steering-policy {
      description
        "The container of a policy set
         matching an NRP traffic classifier.";
      leaf-list color-id {
        type uint32;
        description
          "A list of color ID for NRP traffic steering based on
           SR policy.";
      }
      leaf-list acl-ref {
        type leafref {
          path "/acl:acls/acl:acl/acl:name";
        }
        description
          "A list of ACL for NRP traffic classification.";
      }
    }
  }

  grouping nrp-aware-id {
    description
      "The grouping of NRP aware dataplane ID.";
    container data-plane-id {
      config false;
      description
        "The container of NRP data plane identifier.";
      leaf ipv6 {
        type srv6-sid;
        description
          "Indicates the SRv6 SID value as the NRP data plane
           identifier.";
      }
      leaf sr-mpls {
        type rt-types:mpls-label;
        description
          "Indicates the SR MPLS ID value as the NRP data plane
           identifier.";
      }
    }
  }

  grouping nrp-topology {
    description
      "Grouping for NRP topology.";
    list topology-group {
      key "group-id";
      description
        "List of groups for NRP topology elements (node or links)
         that share common attributes.";
      leaf group-id {
        type string;
        description
          "The NRP topology group identifier.";
      }
      container base-topology-ref {
        description
          "Container for the base topology reference.";
        uses nw:network-ref;
      }
      list links {
        key "link-ref";
        description
          "A list of links with common attributes";
        leaf link-ref {
          type leafref {
            path
              "/nw:networks/nw:network[nw:network-id=current()"
            + "/../../base-topology-ref/network-ref]"
            + "/nt:link/nt:link-id";
          }
          description
            "A reference to a link in the base topology.";
        }
      }
      uses nrp-resource-reservation;
    }
  }

  grouping nrp-topology-attributes {
    description
      "NRP global attributes.";
    container nrp {
      description
        "Containing NRP topology attributes.";
      leaf nrp-id {
        type uint32;
        description
          "NRP identifier.";
      }
      leaf nrp-name {
        type string;
        description
          "NRP Name.";
      }
      leaf partition-type {
        type identityref {
          base nrp-partition-type;
        }
        description
          "Indicates the resource partition type of the NRP, such as
           control plane partition, data plane partition,
           or no partition.";
      }
      uses nrp-resource-reservation;
      uses nrp-control-plane-attributes;
      uses nrp-data-plane-attributes;
      uses nrp-traffic-steering-policy;
      uses nrp-topology;
    }
    // nrp
  }

  // nrp-node-attributes

  grouping nrp-node-attributes {
    description
      "NRP node scope attributes.";
    container nrp {
      config false;
      description
        "Containing NRP attributes.";
      uses nrp-aware-id;
    }
  }

  // nrp-node-attributes

  grouping nrp-link-states {
    description
      "NRP link scope states.";
    leaf link-partition-type {
      type identityref {
        base nrp-link-partition-type;
      }
      config false;
      description
        "Indicates the resource partition type of an NRP link.";
    }
    uses nrp-aware-id;
    uses nrp-statistics-per-link;
  }

  // one-way-performance-metrics

  grouping one-way-performance-bandwidth {
    description
      "Grouping for one-way performance bandwidth.";
    leaf one-way-available-bandwidth {
      type rt-types:bandwidth-ieee-float32;
      units "bytes per second";
      default "0x0p0";
      description
        "Available bandwidth that is defined to be NRP link
         bandwidth minus bandwidth utilization. For a
         bundled link, available bandwidth is defined to be the
         sum of the component link available bandwidths.";
    }
    leaf one-way-utilized-bandwidth {
      type rt-types:bandwidth-ieee-float32;
      units "bytes per second";
      default "0x0p0";
      description
        "Bandwidth utilization that represents the actual
         utilization of the link (i.e. as measured in the router).
         For a bundled link, bandwidth utilization is defined to
         be the sum of the component link bandwidth
         utilizations.";
    }
  }

  // nrp-link-statistics

  grouping nrp-statistics-per-link {
    description
      "Statistics attributes per NRP link.";
    container statistics {
      config false;
      description
        "Statistics for NRP link.";
      leaf admin-status {
        type te-types:te-admin-status;
        description
          "The administrative state of the link.";
      }
      leaf oper-status {
        type te-types:te-oper-status;
        description
          "The current operational state of the link.";
      }
      uses one-way-performance-bandwidth;
      uses te-packet-types:one-way-performance-metrics-packet;
    }
  }

  grouping nrp-augment {
    description
      "Augmentation for NRPs.";
    container nrp {
      presence "NRP support";
      description
        "Indicates NRP support.";
    }
    // nrp
  }

  // nrp-augment

  augment "/nw:networks/nw:network/nw:network-types" {
    description
      "Defines the NRP topology type.";
    container nrp {
      presence "Indicates NRP topology";
      description
        "The presence identifies the NRP type.";
    }
  }

  augment "/nw:networks/nw:network" {
    when 'nw:network-types/nrp:nrp' {
      description
        "Augment only for NRP topology.";
    }
    description
      "Augment NRP configuration and state.";
    uses nrp-topology-attributes;
  }

  augment "/nw:networks/nw:network/nw:node" {
    when '../nw:network-types/nrp:nrp' {
      description
        "Augment only for NRP topology.";
    }
    description
      "Augment node configuration and state.";
    uses nrp-node-attributes;
  }

  augment "/nw:networks/nw:network/nt:link" {
    when '../nw:network-types/nrp:nrp' {
      description
        "Augment only for NRP topology.";
    }
    description
      "Augment link configuration and state.";
    container nrp {
      description
        "Containing NRP attributes.";
      leaf bandwidth-value {
        type uint64;
        units "bps";
        description
          "Bandwidth allocation for the NRP as absolute value.";
      }
      uses nrp-link-states;
    }
  }

  augment "/nw:networks/nw:network/nw:node" {
    description
      "Augment node with NRP aware attributes.";
    list nrps {
      key "nrp-id";
      description
        "List of NRPs.";
      leaf nrp-id {
        type uint32;
        description
          "NRP identifier";
      }
      uses nrp-node-attributes;
    }
  }

  augment "/nw:networks/nw:network/nt:link" {
    description
      "Augment link with NRP aware attributes.";
    list nrps {
      key "nrp-id";
      description
        "List of NRPs.";
      leaf nrp-id {
        type uint32;
        description
          "NRP identifier";
      }
      uses nrp-link-states;
    }
  }
}
