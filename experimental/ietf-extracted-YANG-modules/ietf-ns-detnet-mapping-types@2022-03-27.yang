module ietf-ns-detnet-mapping-types {
  yang-version 1.1;
  namespace
    "urn:ietf:params:xml:ns:yang:ietf-ns-detnet-mapping-types";
  prefix nsdmt;

  import ietf-network-slice {
    prefix ietf-ns;
    reference
      "I-D.ietf-teas-ietf-network-slice-nbi-yang-01: A YANG Data Model for the IETF Network Slice";
  }

  organization
    "IETF DetNet Working Group";
  contact
    "WG Web:   <https://datatracker.ietf.org/wg/detnet/>
     WG List:  <mailto:detnet@ietf.org>

     Editor:   Xueyan Song
               <song.xueyan2@zte.com.cn>
     Editor:   Haisheng Wu
               <wu.haisheng@zte.com.cn>";
  description
    "This module contains a YANG module for IETF Network Slice & Detnet mapping
     parameters.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2022-03-27 {
    description
      "Initial revision.";
    reference
      "RFC XXXX:  YANG Data Model for DetNet Mapping with Network Slice";
  }

  /*
   * Features
   */

  feature template {
    description
      "Support Network Slice mapping templates.";
  }

  /*
   * Identity for map-type
   */

  identity map-type {
    description
      "Base identity from which specific map types are derived.";
  }

  identity new {
    base map-type;
    description
      "The new Network Slice are binded to the service.";
  }

  identity select {
    base map-type;
    description
      "The Detnet service selects an existing Network Slice with no
       modification.";
  }

  identity modify {
    base map-type;
    description
      "The Detnet service selects an existing Network Slice and allows to modify
       the properties of the Network Slice (e.g., SLO)";
  }

  identity none {
    base map-type;
    description
      "The Detnet service is not mapped to any underlying Network Slice";
  }

  /*
   * Typedef
   */

  typedef ns-mapping-template-id {
    type string;
    description
      "Identifier for Network Slice mapping template.";
  }

  /*
   * Groupings
   */

  grouping ns-ref {
    description
      "The reference to Network Slice.";

    leaf ns-mapping-slice-id{
            type int;
            description
               "Identifier for a Network Slice.";
         }

    leaf ns-mapping-template-ref {
      if-feature "template";
      type leafref {
        path "/nsdmt:ns-mapping-templates/"
           + "nsdmt:ns-mapping-template/nsdmt:id";
      }
      description
        "An identifier to the Network Slice Mapping Template where the Network Slice
         constraints and optimization criteria are specified.";
    }
  }

  grouping ns-mapping {
    description
      "Mapping between Services and network-slice";
    container ns-mapping {
      description
        "Mapping between Services and network-slice";
      leaf map-type {
        type identityref {
          base map-type;
        }
        description
          "Isolation Requirements";
      }
      uses ns-ref;
    }
  }

  //grouping

  container ns-mapping-templates {
    description
      "The network-slice constraints and optimization criteria";
    list ns-mapping-template {
      key "id";
      leaf id {
        type ns-mapping-template-id;
        description
          "Identification of the Template to be used.";
      }
      leaf description {
        type string;
        description
          "Description of the template.";
      }
      leaf map-type {
        type identityref {
          base map-type;
        }
        must "0 = derived-from-or-self(.,'none')" {
          error-message "The map-type must be other than "
                      + "none";
        }
        description
          "Map type for Network Slice creation/
           selection.";
      }
       leaf ns-slo-ref{
                  type leafref {
                              path "/ns:ns-slo-sle-templates/ns-slo-sle-template/id";
              }

      description
        "List for templates.";
    }
  }
 }
module ietf-ns-detnet-service-mapping {
  yang-version 1.1;
  namespace
    "urn:ietf:params:xml:ns:yang:ietf-ns-detnet-service-mapping";
  prefix detnet-nssm;

  import ietf-ns-detnet-mapping-types {
    prefix nsdmt;
    reference
      "RFC XXXX:  YANG Data Model for DetNet Mapping with Network Slice";
  }
  import ietf-detnet {
    prefix dnet;
    reference
      "draft-ietf-detnet-yang-16.txt: YANG Data Model for Detnet";
  }

  organization
    "IETF DetNet Working Group";

  contact
    "WG Web:   <https://datatracker.ietf.org/wg/detnet/>
     WG List:  <mailto:detnet@ietf.org>

     Editor:   Xueyan Song
               <song.xueyan@zte.com.cn>
     Editor:   Haisheng Wu
               <wu.haisheng@zte.com.cn>";

  description
    "This module contains a YANG module for the mapping of DetNet to the Network Slice.

     Copyright (c) 2022 IETF Trust and the persons identified as
     authors of the code.  All rights reserved.
     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2022-03-27 {
    description
      "Initial revision.";
    reference
      "RFC XXXX:  YANG Data Model for DetNet Mapping with Network Slice";
  }

  /*
   * Augmentation to Detnet
   */

  augment "/dnet:detnet:detnet/service:sub-layer"
        + "/service:sub-layer" {
    description
      "Detnet augmented to include Network Slice parameters and mapping";
    container ns-detnet-mapping {
      presence "Indicates Detnet service to Network Slice mapping";
      description
        "Container to augment detnet to Network Slice parameters and mapping";
      uses nsdmt:ns-mapping;
    }
  }

  //augment

}
