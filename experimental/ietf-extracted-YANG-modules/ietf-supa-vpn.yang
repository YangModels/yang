module ietf-supa-vpn {
  namespace "urn:ietf:params:xml:ns:yang:ietf-supa-vpn";
  // replace with IANA namespace when assigned
  prefix vpn;

  import ietf-inet-types {
    prefix inet;
    //RFC6991
  }

  import ietf-interfaces {
    prefix "if";
  }

  organization "IETF";
  contact
    "Editor: Dacheng Zhang
    dacheng.zdc@alibaba-inc.com

    Ying Cheng
    chengying10@chinaunicom.cn
  ";

  description
    "This YANG module defines a generic VPN
    (Virtual Private Network service)
    configuration model common across all of the
    vendor implementations. ";

  revision 2015-03-24 {
    description
      "Initial revision.";
    reference " RFC 4664, RFC4364, RFC7277";
  }
  typedef vpn-instance-admin-status {
    description
      "Administartive status of a vpn instance.";
    type enumeration {
      enum "unknown";
      enum "up";
      enum "down";
    }
  }

  container vpn-instance {
    list vpn-instance {
      key "instance-name";
      description "Indicates the name of the VPN instance
                   created.";

      leaf instance-name {
        type string;
        description " instance name.";
      }

      leaf connection-type {
        type enumeration {
          enum L2VPN {
            value 0;
            description "L2VPN";
          }
          enum L3VPN {
            value 1;
            description "L3VPN";
          }
        }
        description
          "Indicates the type of VPN, may be L2VPN or L3VPN";
      }

      leaf service-type {
        type enumeration {
          enum full-mesh {
            value "0";
            description "full-mesh";
          }
          enum hub-spoke {
            value "1";
            description "hub-spoke";
          }
        }
        default "full-mesh";
        description "Topology type.";
      }

      container access-management
      {
        leaf user-name {
          type string;
          mandatory true;
          description "User name for this access interface.";
        }

        leaf user-password {
          type string;
          mandatory true;
          description "User password for the access interface.
          User name and password are listed here because VPN
          need the authentication, one typical way is to
          use user name and password, so that in CE dynamic
          migration case, CEs are able to access with
          authentication regardless location.";
        }

      }

      container instance-state {
        description
          "The operational parameters describing the vpn-instance
           state.";
        leaf admin-status {
          type vpn-instance-admin-status;
        }
      }

      list access-interface {
        key "access-interface";
        description "Access interface ID.";

        leaf access-interface {
          type if:interface-ref;
          description "Access interface ID.";
        }

        leaf role {
          type enumeration {
            enum edge-if {
              value "0";
              description "edge interface";
            }
            enum center-if {
              //when "../../service-type = 'hub-spoke'";
              value "1";
              description "center interface";
            }
          }
          mandatory true;
          description
            "center-if is only available in hub-spoke mode;
             center-if is the interface in hub node.";
        }
      }
    }
  }
}
