module alto-service {
  yang-version 1;

  namespace "urn:ietf:params:xml:ns:yang:alto-service";
  // TODO: replace with IANA namespace when assigned

  prefix "as";

  import alto-service-types {
    prefix alto;
  }

  organization "ALTO WG";
  contact "alto@ietf.org";

  description
    "This module defines a semantically equivalent data model
    for the ALTO services defined in RFC7285.";

  revision 2015-03-22 {
    description "Revise according to IETF91.";
  }
  revision 2014-11-01 {
    description "Inherit from alto-service-types.";
  }

  revision 2014-10-24 {
    description "Initial version.";
  }

  /******************************************
    Groupings for ALTO information resource
  *******************************************/

  grouping network-map-data {
    list map {
      key "pid";
      leaf pid {
        type alto:pid-name;
      }
      uses alto:endpoint-address-group;
    }
  }

  /* Network Map Grouping */
  grouping network-map {
    leaf resource-id {
      type alto:resource-id;
      mandatory true;
    }
    leaf tag {
      type alto:tag-string;
      mandatory true;
    }
    uses network-map-data;
  }

  grouping cost-map-data {
    list map {
      leaf src {
        type alto:pid-name;
      }
      key "src";
      list dst-costs {
        leaf dst {
          type alto:pid-name;
        }
        key "dst";
        uses alto:alto-cost;
      }
    }
  }

  /* Cost Map Grouping */
  grouping cost-map {
    leaf resource-id {
      type alto:resource-id;
      mandatory true;
    }
    leaf tag {
      type alto:tag-string;
      mandatory true;
    }
    container meta {
      must "current()";
      uses alto:cost-map-meta;
    }
    uses cost-map-data;
  }

  grouping alto-resources {
    container IRD {
      uses alto:IRD;
    }

    container network-maps {
      list network-map {
        key "resource-id";
        uses network-map;
      }
    }

    container cost-maps {
      list cost-map {
        key "resource-id";
        uses cost-map;
      }
    }

    container endpoint-property-map {
      uses alto:endpoint-property-map;
    }
  }

  /****************************************************
     DATA INSTANCES of all ALTO information resources

     unfiltered network-maps, unfiltered cost-maps are all instances
     of resources. IRD is also modeled as data.

     The design uses augment as the basic approach to implement
     inheritance.
   ****************************************************/

  container resources {
    uses alto-resources;
  }
}
