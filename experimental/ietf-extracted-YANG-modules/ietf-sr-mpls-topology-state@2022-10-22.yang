module ietf-sr-mpls-topology-state {
  yang-version 1.1;
  namespace
    "urn:ietf:params:xml:ns:yang:ietf-sr-mpls-topology-state";
  prefix "srmt-s";

  import ietf-sr-mpls-topology {
    prefix "srmt";
  }
  import ietf-network-state {
    prefix "nw-s";
    reference "RFC 8345: A YANG Data Model for Network Topologies";
  }
  import ietf-network-topology-state {
    prefix "nt-s";
    reference "RFC 8345: A YANG Data Model for Network Topologies";
  }
  import ietf-l3-unicast-topology-state {
    prefix "l3t-s";
    reference "RFC 8346: A YANG Data Model for Layer 3 Topologies";
  }
  import ietf-segment-routing-common {
    prefix "sr-cmn";
    reference "RFC 9020: YANG Data Model for Segment Routing";
  }

  organization
    "IETF Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Igor Bryskin
               <mailto:Igor.Bryskin@huawei.com>

     Editor:   Vishnu Pavan Beeram
               <mailto:vbeeram@juniper.net>

     Editor:   Tarek Saad
               <mailto:tsaad@cisco.com>

     Editor:   Himanshu Shah
               <mailto:hshah@ciena.com>

     Editor:   Stephane Litkowski
               <mailto:stephane.litkowski@orange.com>";

  description
    "YANG data model for representing operational state information
     of Segment Routing Topologies on MPLS data plane, when NMDA is
     not supported.

     Copyright (c) 2022 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2022-10-22 {
    description "Initial revision";
    reference
      "RFC XXXX: YANG Data Model for SR and SR TE Topologies on MPLS
       Data Plane";
  }

  /*
   * Groupings
   */
  grouping sr-mpls-topology-attributes {
    description "SR MPLS topology scope attributes.";
    container sr-mpls {
      description
        "Containing SR attributes.";
      uses sr-cmn:srgb;
    } // sr
  } // sr-mpls-topology-attributes

  /*
   * Augmentations
   */
  augment "/nw-s:networks/nw-s:network/nw-s:network-types/"
    + "l3t-s:l3-unicast-topology" {
    description
      "Defines the SR MPLS topology type.";
    uses srmt:sr-mpls-topology-type;
  }

  augment "/nw-s:networks/nw-s:network/"
    + "l3t-s:l3-topology-attributes" {
    when "../nw-s:network-types/l3t-s:l3-unicast-topology/"
      + "srmt-s:sr-mpls" {
      description "Augment only for SR MPLS topology.";
    }
    description "Augment topology configuration";
    uses srmt:sr-mpls-topology-attributes;
  }

  augment "/nw-s:networks/nw-s:network/nw-s:node/"
    + "l3t-s:l3-node-attributes" {
    when "../../nw-s:network-types/l3t-s:l3-unicast-topology/"
      + "srmt-s:sr-mpls" {
      description "Augment only for SR MPLS topology.";
    }
    description "Augment node configuration.";
    uses srmt:sr-node-attributes;
  }
  augment "/nw-s:networks/nw-s:network/nw-s:node/"
    + "l3t-s:l3-node-attributes/l3t-s:prefix" {
    when "../../../nw-s:network-types/l3t-s:l3-unicast-topology/"
      + "srmt-s:sr-mpls" {
      description "Augment only for SR MPLS topology.";
    }
    description "Augment node prefix.";
    uses srmt:sr-node-prefix-attributes;
  }

  augment "/nw-s:networks/nw-s:network/nt-s:link/"
    + "l3t-s:l3-link-attributes" {
    when "../../nw-s:network-types/l3t-s:l3-unicast-topology/"
      + "srmt-s:sr-mpls" {
      description "Augment only for SR MPLS topology.";
    }
    description "Augment link configuration";
    uses srmt:sr-link-attributes;
  }
}
