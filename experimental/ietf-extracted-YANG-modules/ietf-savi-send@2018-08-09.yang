module ietf-savi-send {
    namespace "urn:ietf:params:xml:ns:yang:ietf-savi-send";
    prefix savi-send;
    import ietf-yang-types {
        prefix yang;
    }
    import ietf-inet-types {
        prefix inet;
    }
    import ietf-interfaces {
        prefix if;
    }
    import ietf-savi {
        prefix savi;
    }
    organization "IETF SAVI Working Group";
    contact
        "
        WG Web:  <http://datatracker.ietf.org/wg/savi/charter>
        Editor:   Changqing An
                  <mailto:acq@tsinghua.edu.cn>
        ";
    description
        "
        The Yang data module defined for SAVI SEND.
        ";

    revision 2018-08-09 {
        description "Initial revision.";
        reference "DRAFT XXX: A YANG Data Model for SAVI Management";
    }

     /* Identities */

    identity savi-send-state {
        base savi:binding-state;
        description "Base identity for the sates definition of SAVI SEND.";
    }
    identity tentative-dad {
        base savi-send-state;
        description "A state defined in SAVI SEND.";
    }
    identity tentative-nud {
        base savi-send-state;
        description "A state defined in SAVI SEND.";
    }
    identity valid {
        base savi-send-state;
        description "A state defined in SAVI SEND.";
    }

    identity testing_vp {
        base savi-send-state;
        description "A state defined in SAVI SEND.";
    }
    identity testing_vp_1 {
        base savi-send-state;
        description "A state defined in SAVI SEND.";
    }

     /* State data */

    augment "/savi:savi-state/savi:savi-instances/savi:savi-instance" {
        when "/savi:savi/savi:savi-instances/savi:savi-instance/savi:savi-method = 'savi-send'";
        description "Binding state table specific for SAVI SEND.";
        container binding-state-table {
            description "Binding state table specific for SAVI SEND.";
            list binding-state-entry {
                key "ifname address";
                description "A binding state entry specific for SAVI SEND.";
                leaf address {
                    type inet:ipv6-address;
                    description "The binding source IP address.";
                }
                uses savi:binding-entry;
                leaf alternative-if {
                    type if:interface-ref;
                    description "Alternative interface is a parameter defined in SAVI SEND.";
                }

                leaf state {
                    type identityref {
                        base savi-send-state;
                    }
                    description "State of the entry as defined in SAVI SEND: TENTATIVE_DAD, TENTATIVE_NUD, VALID, TESTING_VP, TESTING_VP'";
                }
            }
        }
    }

     /* Configuration Data */

    augment "/savi:savi/savi:savi-instances/savi:savi-instance" {
        when "/savi:savi/savi:savi-instances/savi:savi-instance/savi:savi-method = 'savi-send'";
        description "Parameters specific to SAVI SEND.";
        container params {
            description "Parameters specific to SAVI SEND.";
            leaf tent_lt {
                type yang:timeticks;
                default 50;
                description "A default value defined in SAVI SEND.";
                reference "TENT_LT from [RFC7219].";
            }

            leaf default_lt {
                type yang:timeticks;
                default 30000;
                description "A default value defined in SAVI SEND.";
                reference "DEFAULT_LT from [RFC7219]";
            }
            container if-attributes {
                description "Interface attributes specific to SAVI SEND.";
                list if-attribute {
                    key ifname;
                        description "A list of attributes for each interface.";
                    leaf ifname {
                        type if:interface-ref;
                        description "The name of the interface.";
                    }
                    leaf validating {
                        type boolean;
                        must .=not(../trust);
                        default true;
                        description "SAVI SEND processing is performed in the port.";
                    }

                    leaf trust {
                        type boolean;
                        must .=not(../validating);
                        default false;
                        description "SAVI SEND processing is not performed in the port.";
                    }
                } //list
            } //container
        } //container
    } //augment
}
