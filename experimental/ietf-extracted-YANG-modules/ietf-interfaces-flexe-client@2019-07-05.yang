module ietf-interfaces-flexe-client {
  yang-version 1.1;

  namespace
    "urn:ietf:params:xml:ns:yang:ietf-interfaces-flexe-client";

  prefix flexcl;

  import ietf-interfaces {
    prefix if;
  }

  import ietf-yang-types {
    prefix yang;
  }

  import iana-if-type {
    prefix ianaift;
  }

  organization "IETF CCAMP Working Group";
  contact
    "WG Web:   http://tools.ietf.org/wg/ccamp/
     WG List:  <mailto:ccamp@ietf.org>
     Author:   Yuanlong Jiang
               <mailto:jiangyuanlong@huawei.com>
     Author:   Xiang He
               <mailto: hexiang@huawei.com>
     Author:   Weiqiang Cheng
               <mailto: chengweiqiang@chinamobile.com>";

  description
    "This module contains YANG definitions for configuration of
     'FlexE client' interfaces.  FlexE Client is defined in
     OIF Flexible Ethernet 2.0 Implementation Aggreament.";

  revision 2019-07-05 {
    description "Initial revision";
    reference
      "Internet draft: draft-jiang-ccamp-flexe-yang-01";
  }

  identity flexeClient {
    base ianaift:iana-interface-type;
    description
      "FlexE Client.";
  }

  /*
   * Configuration parameters for FlexE client interfaces.
   */
  augment "/if:interfaces/if:interface" {
    when "derived-from-or-self(if:type, 'ianaift:flexeClient')" {
      description "Applies to FlexE client interfaces";
    }
    description
      "Augment the interface model with parameters for
       FlexE client interfaces";

    container flexe-client {
      description
        "Contains parameters for FlexE client interfaces
         which expose an Ethernet MAC layer.";
      leaf mac-address {
        type yang:mac-address;
        config false;
        description
          "The MAC address of the FlexE client.";
      }
      leaf group-number {
        type uint32 {
          range "1..1048574";
        }
        description
          "FlexE Group Number of the FlexE group binding this
           client.";
      }
      // statistics can further be defined for the MAC layer
    }
  }
}
