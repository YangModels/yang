module ietf-yang-push-ext {
  yang-version 1.1;
  namespace "urn:ietf:params:xml:ns:yang:ietf-yang-push-ext";
  prefix ypext;

  import ietf-subscribed-notifications {
    prefix sn;
  }

  import ietf-yang-push {
    prefix yp;
  }

  import ietf-datastores {
    prefix ds;
    reference "RFC 8342: Network Management Datastore Architecture.";
  }

  import ietf-origin {
    prefix or;
    reference "RFC 8342: Network Management Datastore Architecture.";
  }

  organization
    "IETF NETMOD (Network Modeling) Working Group";
  contact
    "WG Web:   <http://tools.ietf.org/wg/netmod/>
     WG List:  <mailto:netmod@ietf.org>
     WG Chair: Kent Watsen
               <mailto:kwatsen@juniper.net>

     Editor:   Rohit Ranade
               <mailto:rohitrranade@huawei.com>";

  description
    "This module defines extensions to subscription mechanism
    to yang-push on operational state datastore.

    Copyright (c) 2019 IETF Trust and the persons identified as
    authors of the code. All rights reserved.

    Redistribution and use in source and binary forms, with or
    without modification, is permitted pursuant to, and subject to
    the license terms contained in, the Simplified BSD License set
    forth in Section 4.c of the IETF Trust's Legal Provisions
    Relating to IETF Documents
    (https://trustee.ietf.org/license-info).

    The key words 'MUST', 'MUST NOT', 'REQUIRED', 'SHALL', 'SHALL
    NOT', 'SHOULD', 'SHOULD NOT', 'RECOMMENDED', 'MAY', and
    'OPTIONAL' in the module text are to be interpreted as described
    in RFC 2119 (https://tools.ietf.org/html/rfc2119).

    This version of this YANG module is part of RFC XXXX
    (https://tools.ietf.org/html/rfcXXXX); see the RFC itself for
    full legal notices.";

  revision 2019-02-01 {
    description
      "Initial revision.";
    reference "RFCXXXX";
  }

  feature origin {
    description
      "Indicates that the server supports the 'origin' annotation.";
    reference
      "RFC 8342: Network Management Datastore Architecture";
  }

  grouping subscription-filter-extension{
    description
      "This grouping describes the extensions to subscription
       conditions.";
    leaf config-filter {
      type boolean;
      description
        "Filter for nodes with the given value for their 'config'
         property.  When this leaf is set to 'true', only 'config
         true' nodes are selected and, when set to 'false', only
         'config false' nodes are selected.  If this leaf is not
         present, this filter is not applied.";
    }

    leaf with-origin {
      when 'derived-from-or-self(../yp:datastore, "ds:operational")';
      if-feature origin;
      type empty;
      description
        "If this parameter is present, the server will return
         the 'origin' annotation for the nodes that has one.";
    }
  }

  augment "/sn:establish-subscription/sn:input/sn:target/ +
              yp:datastore" {
    description
      "This augmentation adds the filter extensions for the
       subscription to RPC input.";
    uses subscription-filter-extension;
  }
}
