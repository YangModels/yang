module iana-timezones {
  namespace "urn:ietf:params:xml:ns:yang:iana-timezones";
  prefix ianatz;

  organization "IANA";
  contact
    "        Internet Assigned Numbers Authority

     Postal: ICANN
             4676 Admiralty Way, Suite 330
             Marina del Rey, CA 90292

     Tel:    +1 310 823 9358
     E-Mail: iana&iana.org";
  description
    "This YANG module defines the iana-timezone typedef, which
     contains YANG definitions for IANA-registered timezones.

     This YANG module is maintained by IANA, and reflects the
     IANA Time Zone Database.
     (http://www.iana.org/time-zones)

     The latest revision of this YANG module can be obtained from
     the IANA web site.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2012-06-27 {
    description
      "Initial revision. Using IANA Time Zone Data v. 2012c
       (Released 2012-03-27)";
    reference "RFC XXXX: TITLE";
  }
  typedef iana-timezone {
    type enumeration {
      enum "Africa/Abidjan" {
        description
          "";
      }
      enum "Africa/Accra" {
        description
          "";
      }
      enum "Africa/Addis_Ababa" {
        description
          "";
      }
      enum "Africa/Algiers" {
        description
          "";
      }
      enum "Africa/Asmara" {
        description
          "";
      }
      enum "Africa/Bamako" {
        description
          "";
      }
      enum "Africa/Bangui" {
        description
          "";
      }
      enum "Africa/Banjul" {
        description
          "";
      }
      enum "Africa/Bissau" {
        description
          "";
      }
      enum "Africa/Blantyre" {
        description
          "";
      }
      enum "Africa/Brazzaville" {
        description
          "";
      }
      enum "Africa/Bujumbura" {
        description
          "";
      }
      enum "Africa/Cairo" {
        description
          "";
      }
      enum "Africa/Casablanca" {
        description
          "";
      }
      enum "Africa/Ceuta" {
        description
          "Ceuta & Melilla";
      }
      enum "Africa/Conakry" {
        description
          "";
      }
      enum "Africa/Dakar" {
        description
          "";
      }
      enum "Africa/Dar_es_Salaam" {
        description
          "";
      }
      enum "Africa/Djibouti" {
        description
          "";
      }
      enum "Africa/Douala" {
        description
          "";
      }
      enum "Africa/El_Aaiun" {
        description
          "";
      }
      enum "Africa/Freetown" {
        description
          "";
      }
      enum "Africa/Gaborone" {
        description
          "";
      }
      enum "Africa/Harare" {
        description
          "";
      }
      enum "Africa/Johannesburg" {
        description
          "";
      }
      enum "Africa/Juba" {
        description
          "";
      }
      enum "Africa/Kampala" {
        description
          "";
      }
      enum "Africa/Khartoum" {
        description
          "";
      }
      enum "Africa/Kigali" {
        description
          "";
      }
      enum "Africa/Kinshasa" {
        description
          "west Dem. Rep. of Congo";
      }
      enum "Africa/Lagos" {
        description
          "";
      }
      enum "Africa/Libreville" {
        description
          "";
      }
      enum "Africa/Lome" {
        description
          "";
      }
      enum "Africa/Luanda" {
        description
          "";
      }
      enum "Africa/Lubumbashi" {
        description
          "east Dem. Rep. of Congo";
      }
      enum "Africa/Lusaka" {
        description
          "";
      }
      enum "Africa/Malabo" {
        description
          "";
      }
      enum "Africa/Maputo" {
        description
          "";
      }
      enum "Africa/Maseru" {
        description
          "";
      }
      enum "Africa/Mbabane" {
        description
          "";
      }
      enum "Africa/Mogadishu" {
        description
          "";
      }
      enum "Africa/Monrovia" {
        description
          "";
      }
      enum "Africa/Nairobi" {
        description
          "";
      }
      enum "Africa/Ndjamena" {
        description
          "";
      }
      enum "Africa/Niamey" {
        description
          "";
      }
      enum "Africa/Nouakchott" {
        description
          "";
      }
      enum "Africa/Ouagadougou" {
        description
          "";
      }
      enum "Africa/Porto-Novo" {
        description
          "";
      }
      enum "Africa/Sao_Tome" {
        description
          "";
      }
      enum "Africa/Tripoli" {
        description
          "";
      }
      enum "Africa/Tunis" {
        description
          "";
      }
      enum "Africa/Windhoek" {
        description
          "";
      }
      enum "America/Adak" {
        description
          "Aleutian Islands";
      }
      enum "America/Anchorage" {
        description
          "Alaska Time";
      }
      enum "America/Anguilla" {
        description
          "";
      }
      enum "America/Antigua" {
        description
          "";
      }
      enum "America/Araguaina" {
        description
          "Tocantins";
      }
      enum "America/Argentina/Buenos_Aires" {
        description
          "Buenos Aires (BA, CF)";
      }
      enum "America/Argentina/Catamarca" {
        description
          "Catamarca (CT), Chubut (CH)";
      }
      enum "America/Argentina/Cordoba" {
        description
          "most locations (CB, CC, CN, ER, FM, MN, SE, SF)";
      }
      enum "America/Argentina/Jujuy" {
        description
          "Jujuy (JY)";
      }
      enum "America/Argentina/La_Rioja" {
        description
          "La Rioja (LR)";
      }
      enum "America/Argentina/Mendoza" {
        description
          "Mendoza (MZ)";
      }
      enum "America/Argentina/Rio_Gallegos" {
        description
          "Santa Cruz (SC)";
      }
      enum "America/Argentina/Salta" {
        description
          "(SA, LP, NQ, RN)";
      }
      enum "America/Argentina/San_Juan" {
        description
          "San Juan (SJ)";
      }
      enum "America/Argentina/San_Luis" {
        description
          "San Luis (SL)";
      }
      enum "America/Argentina/Tucuman" {
        description
          "Tucuman (TM)";
      }
      enum "America/Argentina/Ushuaia" {
        description
          "Tierra del Fuego (TF)";
      }
      enum "America/Aruba" {
        description
          "";
      }
      enum "America/Asuncion" {
        description
          "";
      }
      enum "America/Atikokan" {
        description
          "Eastern Standard Time - Atikokan, Ontario and Southampton I, Nunavut";
      }
      enum "America/Bahia" {
        description
          "Bahia";
      }
      enum "America/Bahia_Banderas" {
        description
          "Mexican Central Time - Bahia de Banderas";
      }
      enum "America/Barbados" {
        description
          "";
      }
      enum "America/Belem" {
        description
          "Amapa, E Para";
      }
      enum "America/Belize" {
        description
          "";
      }
      enum "America/Blanc-Sablon" {
        description
          "Atlantic Standard Time - Quebec - Lower North Shore";
      }
      enum "America/Boa_Vista" {
        description
          "Roraima";
      }
      enum "America/Bogota" {
        description
          "";
      }
      enum "America/Boise" {
        description
          "Mountain Time - south Idaho & east Oregon";
      }
      enum "America/Cambridge_Bay" {
        description
          "Mountain Time - west Nunavut";
      }
      enum "America/Campo_Grande" {
        description
          "Mato Grosso do Sul";
      }
      enum "America/Cancun" {
        description
          "Central Time - Quintana Roo";
      }
      enum "America/Caracas" {
        description
          "";
      }
      enum "America/Cayenne" {
        description
          "";
      }
      enum "America/Cayman" {
        description
          "";
      }
      enum "America/Chicago" {
        description
          "Central Time";
      }
      enum "America/Chihuahua" {
        description
          "Mexican Mountain Time - Chihuahua away from US border";
      }
      enum "America/Costa_Rica" {
        description
          "";
      }
      enum "America/Creston" {
        description
          "Mountain Standard Time - Creston, British Columbia";
      }
      enum "America/Cuiaba" {
        description
          "Mato Grosso";
      }
      enum "America/Curacao" {
        description
          "";
      }
      enum "America/Danmarkshavn" {
        description
          "east coast, north of Scoresbysund";
      }
      enum "America/Dawson_Creek" {
        description
          "Mountain Standard Time - Dawson Creek & Fort Saint John, British Columbia";
      }
      enum "America/Dawson" {
        description
          "Pacific Time - north Yukon";
      }
      enum "America/Denver" {
        description
          "Mountain Time";
      }
      enum "America/Detroit" {
        description
          "Eastern Time - Michigan - most locations";
      }
      enum "America/Dominica" {
        description
          "";
      }
      enum "America/Edmonton" {
        description
          "Mountain Time - Alberta, east British Columbia & west Saskatchewan";
      }
      enum "America/Eirunepe" {
        description
          "W Amazonas";
      }
      enum "America/El_Salvador" {
        description
          "";
      }
      enum "America/Fortaleza" {
        description
          "NE Brazil (MA, PI, CE, RN, PB)";
      }
      enum "America/Glace_Bay" {
        description
          "Atlantic Time - Nova Scotia - places that did not observe DST 1966-1971";
      }
      enum "America/Godthab" {
        description
          "most locations";
      }
      enum "America/Goose_Bay" {
        description
          "Atlantic Time - Labrador - most locations";
      }
      enum "America/Grand_Turk" {
        description
          "";
      }
      enum "America/Grenada" {
        description
          "";
      }
      enum "America/Guadeloupe" {
        description
          "";
      }
      enum "America/Guatemala" {
        description
          "";
      }
      enum "America/Guayaquil" {
        description
          "mainland";
      }
      enum "America/Guyana" {
        description
          "";
      }
      enum "America/Halifax" {
        description
          "Atlantic Time - Nova Scotia (most places), PEI";
      }
      enum "America/Havana" {
        description
          "";
      }
      enum "America/Hermosillo" {
        description
          "Mountain Standard Time - Sonora";
      }
      enum "America/Indiana/Indianapolis" {
        description
          "Eastern Time - Indiana - most locations";
      }
      enum "America/Indiana/Knox" {
        description
          "Central Time - Indiana - Starke County";
      }
      enum "America/Indiana/Marengo" {
        description
          "Eastern Time - Indiana - Crawford County";
      }
      enum "America/Indiana/Petersburg" {
        description
          "Eastern Time - Indiana - Pike County";
      }
      enum "America/Indiana/Tell_City" {
        description
          "Central Time - Indiana - Perry County";
      }
      enum "America/Indiana/Vevay" {
        description
          "Eastern Time - Indiana - Switzerland County";
      }
      enum "America/Indiana/Vincennes" {
        description
          "Eastern Time - Indiana - Daviess, Dubois, Knox & Martin Counties";
      }
      enum "America/Indiana/Winamac" {
        description
          "Eastern Time - Indiana - Pulaski County";
      }
      enum "America/Inuvik" {
        description
          "Mountain Time - west Northwest Territories";
      }
      enum "America/Iqaluit" {
        description
          "Eastern Time - east Nunavut - most locations";
      }
      enum "America/Jamaica" {
        description
          "";
      }
      enum "America/Juneau" {
        description
          "Alaska Time - Alaska panhandle";
      }
      enum "America/Kentucky/Louisville" {
        description
          "Eastern Time - Kentucky - Louisville area";
      }
      enum "America/Kentucky/Monticello" {
        description
          "Eastern Time - Kentucky - Wayne County";
      }
      enum "America/Kralendijk" {
        description
          "";
      }
      enum "America/La_Paz" {
        description
          "";
      }
      enum "America/Lima" {
        description
          "";
      }
      enum "America/Los_Angeles" {
        description
          "Pacific Time";
      }
      enum "America/Lower_Princes" {
        description
          "";
      }
      enum "America/Maceio" {
        description
          "Alagoas, Sergipe";
      }
      enum "America/Managua" {
        description
          "";
      }
      enum "America/Manaus" {
        description
          "E Amazonas";
      }
      enum "America/Marigot" {
        description
          "";
      }
      enum "America/Martinique" {
        description
          "";
      }
      enum "America/Matamoros" {
        description
          "US Central Time - Coahuila, Durango, Nuevo Leon, Tamaulipas near US border";
      }
      enum "America/Mazatlan" {
        description
          "Mountain Time - S Baja, Nayarit, Sinaloa";
      }
      enum "America/Menominee" {
        description
          "Central Time - Michigan - Dickinson, Gogebic, Iron & Menominee Counties";
      }
      enum "America/Merida" {
        description
          "Central Time - Campeche, Yucatan";
      }
      enum "America/Metlakatla" {
        description
          "Metlakatla Time - Annette Island";
      }
      enum "America/Mexico_City" {
        description
          "Central Time - most locations";
      }
      enum "America/Miquelon" {
        description
          "";
      }
      enum "America/Moncton" {
        description
          "Atlantic Time - New Brunswick";
      }
      enum "America/Monterrey" {
        description
          "Mexican Central Time - Coahuila, Durango, Nuevo Leon, Tamaulipas away from US border";
      }
      enum "America/Montevideo" {
        description
          "";
      }
      enum "America/Montreal" {
        description
          "Eastern Time - Quebec - most locations";
      }
      enum "America/Montserrat" {
        description
          "";
      }
      enum "America/Nassau" {
        description
          "";
      }
      enum "America/New_York" {
        description
          "Eastern Time";
      }
      enum "America/Nipigon" {
        description
          "Eastern Time - Ontario & Quebec - places that did not observe DST 1967-1973";
      }
      enum "America/Nome" {
        description
          "Alaska Time - west Alaska";
      }
      enum "America/Noronha" {
        description
          "Atlantic islands";
      }
      enum "America/North_Dakota/Beulah" {
        description
          "Central Time - North Dakota - Mercer County";
      }
      enum "America/North_Dakota/Center" {
        description
          "Central Time - North Dakota - Oliver County";
      }
      enum "America/North_Dakota/New_Salem" {
        description
          "Central Time - North Dakota - Morton County (except Mandan area)";
      }
      enum "America/Ojinaga" {
        description
          "US Mountain Time - Chihuahua near US border";
      }
      enum "America/Panama" {
        description
          "";
      }
      enum "America/Pangnirtung" {
        description
          "Eastern Time - Pangnirtung, Nunavut";
      }
      enum "America/Paramaribo" {
        description
          "";
      }
      enum "America/Phoenix" {
        description
          "Mountain Standard Time - Arizona";
      }
      enum "America/Port-au-Prince" {
        description
          "";
      }
      enum "America/Port_of_Spain" {
        description
          "";
      }
      enum "America/Porto_Velho" {
        description
          "Rondonia";
      }
      enum "America/Puerto_Rico" {
        description
          "";
      }
      enum "America/Rainy_River" {
        description
          "Central Time - Rainy River & Fort Frances, Ontario";
      }
      enum "America/Rankin_Inlet" {
        description
          "Central Time - central Nunavut";
      }
      enum "America/Recife" {
        description
          "Pernambuco";
      }
      enum "America/Regina" {
        description
          "Central Standard Time - Saskatchewan - most locations";
      }
      enum "America/Resolute" {
        description
          "Central Standard Time - Resolute, Nunavut";
      }
      enum "America/Rio_Branco" {
        description
          "Acre";
      }
      enum "America/Santa_Isabel" {
        description
          "Mexican Pacific Time - Baja California away from US border";
      }
      enum "America/Santarem" {
        description
          "W Para";
      }
      enum "America/Santiago" {
        description
          "most locations";
      }
      enum "America/Santo_Domingo" {
        description
          "";
      }
      enum "America/Sao_Paulo" {
        description
          "S & SE Brazil (GO, DF, MG, ES, RJ, SP, PR, SC, RS)";
      }
      enum "America/Scoresbysund" {
        description
          "Scoresbysund / Ittoqqortoormiit";
      }
      enum "America/Shiprock" {
        description
          "Mountain Time - Navajo";
      }
      enum "America/Sitka" {
        description
          "Alaska Time - southeast Alaska panhandle";
      }
      enum "America/St_Barthelemy" {
        description
          "";
      }
      enum "America/St_Johns" {
        description
          "Newfoundland Time, including SE Labrador";
      }
      enum "America/St_Kitts" {
        description
          "";
      }
      enum "America/St_Lucia" {
        description
          "";
      }
      enum "America/St_Thomas" {
        description
          "";
      }
      enum "America/St_Vincent" {
        description
          "";
      }
      enum "America/Swift_Current" {
        description
          "Central Standard Time - Saskatchewan - midwest";
      }
      enum "America/Tegucigalpa" {
        description
          "";
      }
      enum "America/Thule" {
        description
          "Thule / Pituffik";
      }
      enum "America/Thunder_Bay" {
        description
          "Eastern Time - Thunder Bay, Ontario";
      }
      enum "America/Tijuana" {
        description
          "US Pacific Time - Baja California near US border";
      }
      enum "America/Toronto" {
        description
          "Eastern Time - Ontario - most locations";
      }
      enum "America/Tortola" {
        description
          "";
      }
      enum "America/Vancouver" {
        description
          "Pacific Time - west British Columbia";
      }
      enum "America/Whitehorse" {
        description
          "Pacific Time - south Yukon";
      }
      enum "America/Winnipeg" {
        description
          "Central Time - Manitoba & west Ontario";
      }
      enum "America/Yakutat" {
        description
          "Alaska Time - Alaska panhandle neck";
      }
      enum "America/Yellowknife" {
        description
          "Mountain Time - central Northwest Territories";
      }
      enum "Antarctica/Casey" {
        description
          "Casey Station, Bailey Peninsula";
      }
      enum "Antarctica/Davis" {
        description
          "Davis Station, Vestfold Hills";
      }
      enum "Antarctica/DumontDUrville" {
        description
          "Dumont-d'Urville Station, Terre Adelie";
      }
      enum "Antarctica/Macquarie" {
        description
          "Macquarie Island Station, Macquarie Island";
      }
      enum "Antarctica/Mawson" {
        description
          "Mawson Station, Holme Bay";
      }
      enum "Antarctica/McMurdo" {
        description
          "McMurdo Station, Ross Island";
      }
      enum "Antarctica/Palmer" {
        description
          "Palmer Station, Anvers Island";
      }
      enum "Antarctica/Rothera" {
        description
          "Rothera Station, Adelaide Island";
      }
      enum "Antarctica/South_Pole" {
        description
          "Amundsen-Scott Station, South Pole";
      }
      enum "Antarctica/Syowa" {
        description
          "Syowa Station, E Ongul I";
      }
      enum "Antarctica/Vostok" {
        description
          "Vostok Station, Lake Vostok";
      }
      enum "Arctic/Longyearbyen" {
        description
          "";
      }
      enum "Asia/Aden" {
        description
          "";
      }
      enum "Asia/Almaty" {
        description
          "most locations";
      }
      enum "Asia/Amman" {
        description
          "";
      }
      enum "Asia/Anadyr" {
        description
          "Moscow+08 - Bering Sea";
      }
      enum "Asia/Aqtau" {
        description
          "Atyrau (Atirau, Gur'yev), Mangghystau (Mankistau)";
      }
      enum "Asia/Aqtobe" {
        description
          "Aqtobe (Aktobe)";
      }
      enum "Asia/Ashgabat" {
        description
          "";
      }
      enum "Asia/Baghdad" {
        description
          "";
      }
      enum "Asia/Bahrain" {
        description
          "";
      }
      enum "Asia/Baku" {
        description
          "";
      }
      enum "Asia/Bangkok" {
        description
          "";
      }
      enum "Asia/Beirut" {
        description
          "";
      }
      enum "Asia/Bishkek" {
        description
          "";
      }
      enum "Asia/Brunei" {
        description
          "";
      }
      enum "Asia/Choibalsan" {
        description
          "Dornod, Sukhbaatar";
      }
      enum "Asia/Chongqing" {
        description
          "central China - Sichuan, Yunnan, Guangxi, Shaanxi, Guizhou, etc.";
      }
      enum "Asia/Colombo" {
        description
          "";
      }
      enum "Asia/Damascus" {
        description
          "";
      }
      enum "Asia/Dhaka" {
        description
          "";
      }
      enum "Asia/Dili" {
        description
          "";
      }
      enum "Asia/Dubai" {
        description
          "";
      }
      enum "Asia/Dushanbe" {
        description
          "";
      }
      enum "Asia/Gaza" {
        description
          "Gaza Strip";
      }
      enum "Asia/Harbin" {
        description
          "Heilongjiang (except Mohe), Jilin";
      }
      enum "Asia/Hebron" {
        description
          "West Bank";
      }
      enum "Asia/Ho_Chi_Minh" {
        description
          "";
      }
      enum "Asia/Hong_Kong" {
        description
          "";
      }
      enum "Asia/Hovd" {
        description
          "Bayan-Olgiy, Govi-Altai, Hovd, Uvs, Zavkhan";
      }
      enum "Asia/Irkutsk" {
        description
          "Moscow+05 - Lake Baikal";
      }
      enum "Asia/Jakarta" {
        description
          "Java & Sumatra";
      }
      enum "Asia/Jayapura" {
        description
          "west New Guinea (Irian Jaya) & Malukus (Moluccas)";
      }
      enum "Asia/Jerusalem" {
        description
          "";
      }
      enum "Asia/Kabul" {
        description
          "";
      }
      enum "Asia/Kamchatka" {
        description
          "Moscow+08 - Kamchatka";
      }
      enum "Asia/Karachi" {
        description
          "";
      }
      enum "Asia/Kashgar" {
        description
          "west Tibet & Xinjiang";
      }
      enum "Asia/Kathmandu" {
        description
          "";
      }
      enum "Asia/Kolkata" {
        description
          "";
      }
      enum "Asia/Krasnoyarsk" {
        description
          "Moscow+04 - Yenisei River";
      }
      enum "Asia/Kuala_Lumpur" {
        description
          "peninsular Malaysia";
      }
      enum "Asia/Kuching" {
        description
          "Sabah & Sarawak";
      }
      enum "Asia/Kuwait" {
        description
          "";
      }
      enum "Asia/Macau" {
        description
          "";
      }
      enum "Asia/Magadan" {
        description
          "Moscow+08 - Magadan";
      }
      enum "Asia/Makassar" {
        description
          "east & south Borneo, Sulawesi (Celebes), Bali, Nusa Tengarra, west Timor";
      }
      enum "Asia/Manila" {
        description
          "";
      }
      enum "Asia/Muscat" {
        description
          "";
      }
      enum "Asia/Nicosia" {
        description
          "";
      }
      enum "Asia/Novokuznetsk" {
        description
          "Moscow+03 - Novokuznetsk";
      }
      enum "Asia/Novosibirsk" {
        description
          "Moscow+03 - Novosibirsk";
      }
      enum "Asia/Omsk" {
        description
          "Moscow+03 - west Siberia";
      }
      enum "Asia/Oral" {
        description
          "West Kazakhstan";
      }
      enum "Asia/Phnom_Penh" {
        description
          "";
      }
      enum "Asia/Pontianak" {
        description
          "west & central Borneo";
      }
      enum "Asia/Pyongyang" {
        description
          "";
      }
      enum "Asia/Qatar" {
        description
          "";
      }
      enum "Asia/Qyzylorda" {
        description
          "Qyzylorda (Kyzylorda, Kzyl-Orda)";
      }
      enum "Asia/Rangoon" {
        description
          "";
      }
      enum "Asia/Riyadh" {
        description
          "";
      }
      enum "Asia/Sakhalin" {
        description
          "Moscow+07 - Sakhalin Island";
      }
      enum "Asia/Samarkand" {
        description
          "west Uzbekistan";
      }
      enum "Asia/Seoul" {
        description
          "";
      }
      enum "Asia/Shanghai" {
        description
          "east China - Beijing, Guangdong, Shanghai, etc.";
      }
      enum "Asia/Singapore" {
        description
          "";
      }
      enum "Asia/Taipei" {
        description
          "";
      }
      enum "Asia/Tashkent" {
        description
          "east Uzbekistan";
      }
      enum "Asia/Tbilisi" {
        description
          "";
      }
      enum "Asia/Tehran" {
        description
          "";
      }
      enum "Asia/Thimphu" {
        description
          "";
      }
      enum "Asia/Tokyo" {
        description
          "";
      }
      enum "Asia/Ulaanbaatar" {
        description
          "most locations";
      }
      enum "Asia/Urumqi" {
        description
          "most of Tibet & Xinjiang";
      }
      enum "Asia/Vientiane" {
        description
          "";
      }
      enum "Asia/Vladivostok" {
        description
          "Moscow+07 - Amur River";
      }
      enum "Asia/Yakutsk" {
        description
          "Moscow+06 - Lena River";
      }
      enum "Asia/Yekaterinburg" {
        description
          "Moscow+02 - Urals";
      }
      enum "Asia/Yerevan" {
        description
          "";
      }
      enum "Atlantic/Azores" {
        description
          "Azores";
      }
      enum "Atlantic/Bermuda" {
        description
          "";
      }
      enum "Atlantic/Canary" {
        description
          "Canary Islands";
      }
      enum "Atlantic/Cape_Verde" {
        description
          "";
      }
      enum "Atlantic/Faroe" {
        description
          "";
      }
      enum "Atlantic/Madeira" {
        description
          "Madeira Islands";
      }
      enum "Atlantic/Reykjavik" {
        description
          "";
      }
      enum "Atlantic/South_Georgia" {
        description
          "";
      }
      enum "Atlantic/Stanley" {
        description
          "";
      }
      enum "Atlantic/St_Helena" {
        description
          "";
      }
      enum "Australia/Adelaide" {
        description
          "South Australia";
      }
      enum "Australia/Brisbane" {
        description
          "Queensland - most locations";
      }
      enum "Australia/Broken_Hill" {
        description
          "New South Wales - Yancowinna";
      }
      enum "Australia/Currie" {
        description
          "Tasmania - King Island";
      }
      enum "Australia/Darwin" {
        description
          "Northern Territory";
      }
      enum "Australia/Eucla" {
        description
          "Western Australia - Eucla area";
      }
      enum "Australia/Hobart" {
        description
          "Tasmania - most locations";
      }
      enum "Australia/Lindeman" {
        description
          "Queensland - Holiday Islands";
      }
      enum "Australia/Lord_Howe" {
        description
          "Lord Howe Island";
      }
      enum "Australia/Melbourne" {
        description
          "Victoria";
      }
      enum "Australia/Perth" {
        description
          "Western Australia - most locations";
      }
      enum "Australia/Sydney" {
        description
          "New South Wales - most locations";
      }
      enum "Europe/Amsterdam" {
        description
          "";
      }
      enum "Europe/Andorra" {
        description
          "";
      }
      enum "Europe/Athens" {
        description
          "";
      }
      enum "Europe/Belgrade" {
        description
          "";
      }
      enum "Europe/Berlin" {
        description
          "";
      }
      enum "Europe/Bratislava" {
        description
          "";
      }
      enum "Europe/Brussels" {
        description
          "";
      }
      enum "Europe/Bucharest" {
        description
          "";
      }
      enum "Europe/Budapest" {
        description
          "";
      }
      enum "Europe/Chisinau" {
        description
          "";
      }
      enum "Europe/Copenhagen" {
        description
          "";
      }
      enum "Europe/Dublin" {
        description
          "";
      }
      enum "Europe/Gibraltar" {
        description
          "";
      }
      enum "Europe/Guernsey" {
        description
          "";
      }
      enum "Europe/Helsinki" {
        description
          "";
      }
      enum "Europe/Isle_of_Man" {
        description
          "";
      }
      enum "Europe/Istanbul" {
        description
          "";
      }
      enum "Europe/Jersey" {
        description
          "";
      }
      enum "Europe/Kaliningrad" {
        description
          "Moscow-01 - Kaliningrad";
      }
      enum "Europe/Kiev" {
        description
          "most locations";
      }
      enum "Europe/Lisbon" {
        description
          "mainland";
      }
      enum "Europe/Ljubljana" {
        description
          "";
      }
      enum "Europe/London" {
        description
          "";
      }
      enum "Europe/Luxembourg" {
        description
          "";
      }
      enum "Europe/Madrid" {
        description
          "mainland";
      }
      enum "Europe/Malta" {
        description
          "";
      }
      enum "Europe/Mariehamn" {
        description
          "";
      }
      enum "Europe/Minsk" {
        description
          "";
      }
      enum "Europe/Monaco" {
        description
          "";
      }
      enum "Europe/Moscow" {
        description
          "Moscow+00 - west Russia";
      }
      enum "Europe/Oslo" {
        description
          "";
      }
      enum "Europe/Paris" {
        description
          "";
      }
      enum "Europe/Podgorica" {
        description
          "";
      }
      enum "Europe/Prague" {
        description
          "";
      }
      enum "Europe/Riga" {
        description
          "";
      }
      enum "Europe/Rome" {
        description
          "";
      }
      enum "Europe/Samara" {
        description
          "Moscow+00 - Samara, Udmurtia";
      }
      enum "Europe/San_Marino" {
        description
          "";
      }
      enum "Europe/Sarajevo" {
        description
          "";
      }
      enum "Europe/Simferopol" {
        description
          "central Crimea";
      }
      enum "Europe/Skopje" {
        description
          "";
      }
      enum "Europe/Sofia" {
        description
          "";
      }
      enum "Europe/Stockholm" {
        description
          "";
      }
      enum "Europe/Tallinn" {
        description
          "";
      }
      enum "Europe/Tirane" {
        description
          "";
      }
      enum "Europe/Uzhgorod" {
        description
          "Ruthenia";
      }
      enum "Europe/Vaduz" {
        description
          "";
      }
      enum "Europe/Vatican" {
        description
          "";
      }
      enum "Europe/Vienna" {
        description
          "";
      }
      enum "Europe/Vilnius" {
        description
          "";
      }
      enum "Europe/Volgograd" {
        description
          "Moscow+00 - Caspian Sea";
      }
      enum "Europe/Warsaw" {
        description
          "";
      }
      enum "Europe/Zagreb" {
        description
          "";
      }
      enum "Europe/Zaporozhye" {
        description
          "Zaporozh'ye, E Lugansk / Zaporizhia, E Luhansk";
      }
      enum "Europe/Zurich" {
        description
          "";
      }
      enum "Indian/Antananarivo" {
        description
          "";
      }
      enum "Indian/Chagos" {
        description
          "";
      }
      enum "Indian/Christmas" {
        description
          "";
      }
      enum "Indian/Cocos" {
        description
          "";
      }
      enum "Indian/Comoro" {
        description
          "";
      }
      enum "Indian/Kerguelen" {
        description
          "";
      }
      enum "Indian/Mahe" {
        description
          "";
      }
      enum "Indian/Maldives" {
        description
          "";
      }
      enum "Indian/Mauritius" {
        description
          "";
      }
      enum "Indian/Mayotte" {
        description
          "";
      }
      enum "Indian/Reunion" {
        description
          "";
      }
      enum "Pacific/Apia" {
        description
          "";
      }
      enum "Pacific/Auckland" {
        description
          "most locations";
      }
      enum "Pacific/Chatham" {
        description
          "Chatham Islands";
      }
      enum "Pacific/Chuuk" {
        description
          "Chuuk (Truk) and Yap";
      }
      enum "Pacific/Easter" {
        description
          "Easter Island & Sala y Gomez";
      }
      enum "Pacific/Efate" {
        description
          "";
      }
      enum "Pacific/Enderbury" {
        description
          "Phoenix Islands";
      }
      enum "Pacific/Fakaofo" {
        description
          "";
      }
      enum "Pacific/Fiji" {
        description
          "";
      }
      enum "Pacific/Funafuti" {
        description
          "";
      }
      enum "Pacific/Galapagos" {
        description
          "Galapagos Islands";
      }
      enum "Pacific/Gambier" {
        description
          "Gambier Islands";
      }
      enum "Pacific/Guadalcanal" {
        description
          "";
      }
      enum "Pacific/Guam" {
        description
          "";
      }
      enum "Pacific/Honolulu" {
        description
          "Hawaii";
      }
      enum "Pacific/Johnston" {
        description
          "Johnston Atoll";
      }
      enum "Pacific/Kiritimati" {
        description
          "Line Islands";
      }
      enum "Pacific/Kosrae" {
        description
          "Kosrae";
      }
      enum "Pacific/Kwajalein" {
        description
          "Kwajalein";
      }
      enum "Pacific/Majuro" {
        description
          "most locations";
      }
      enum "Pacific/Marquesas" {
        description
          "Marquesas Islands";
      }
      enum "Pacific/Midway" {
        description
          "Midway Islands";
      }
      enum "Pacific/Nauru" {
        description
          "";
      }
      enum "Pacific/Niue" {
        description
          "";
      }
      enum "Pacific/Norfolk" {
        description
          "";
      }
      enum "Pacific/Noumea" {
        description
          "";
      }
      enum "Pacific/Pago_Pago" {
        description
          "";
      }
      enum "Pacific/Palau" {
        description
          "";
      }
      enum "Pacific/Pitcairn" {
        description
          "";
      }
      enum "Pacific/Pohnpei" {
        description
          "Pohnpei (Ponape)";
      }
      enum "Pacific/Port_Moresby" {
        description
          "";
      }
      enum "Pacific/Rarotonga" {
        description
          "";
      }
      enum "Pacific/Saipan" {
        description
          "";
      }
      enum "Pacific/Tahiti" {
        description
          "Society Islands";
      }
      enum "Pacific/Tarawa" {
        description
          "Gilbert Islands";
      }
      enum "Pacific/Tongatapu" {
        description
          "";
      }
      enum "Pacific/Wake" {
        description
          "Wake Island";
      }
      enum "Pacific/Wallis" {
        description
          "";
      }
    }
  }
}
