module ietf-sr-policy {

  namespace "urn:ietf:params:xml:ns:yang:ietf-sr-policy";

  prefix "sr-policy";

  import ietf-inet-types {
    prefix "inet";
  }

  import ietf-interfaces {
    prefix if;
  }

  import ietf-routing {
    prefix "rt";
  }

  import ietf-routing-types {
    prefix "rt-types";
  }

  import ietf-yang-types {
    prefix "yang";
  }

  import ietf-srv6-types {
    prefix "srv6-types";
  }

  import ietf-sr-policy-types {
    prefix "sr-policy-types";
  }

  import ietf-te-types {
    prefix "te-types";
  }

  organization "IETF SPRING Working Group";
  contact
    "WG Web:   <http://tools.ietf.org/wg/spring/>
     WG List:  <mailto:spring@ietf.org>
     Editor:   Kamran Raza
     <mailto:skraza@cisco.com>
     Editor:   Tarik Saleh
     <mailto:tasaleh@cisco.com>
     Editor:   Robert Sawaya
     <mailto:rsawaya@cisco.com>
     Editor:   Zhuang Shunwan
     <mailto:zhuangshunwan@huawei.com>
     Editor:   Daniel Voyer
     <mailto:danvoyerwork@gmail.com>
     Editor:   Muhammad Durrani
     <mailto:Muahmmad.durrani@oracle.com>
     Editor:   Satoru Matsushima
     <mailto:satoru.matsushima@g.softbank.co.jp>
     Editor:   Pavan Vishnu Beeram
     <mailto:vbeeram@juniper.net>
    ";

  description
    "This module contains a collection of YANG definitions
    for SR policy module.

     Copyright (c) 2024 IETF Trust and the persons identified as
     authors of the code.  All rights reserved.
     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

    // RFC Editor: replace XXXX with actual RFC number and remove
    // this note
  revision "2025-05-22" {
    // RFC Editor: replace the above date 2024-11-22 with the date of
    // publication and remove this note.

    description
      "Update the SR policy YANG model with more alignment with SR
       policy architecture";
    reference
      "RFC XXXX: YANG Data Model for Segment-routing Policy";
     // RFC Editor: replace XXXX with actual RFC number and remove
     // this note
  }

  revision "2024-11-22" {
    // RFC Editor: replace the above date 2024-11-22 with the date of
    // publication and remove this note.

    description
      "Fix SR policy YANG model";
    reference
      "RFC XXXX: YANG Data Model for Segment-routing Policy";
     // RFC Editor: replace XXXX with actual RFC number and remove
     // this note
  }

  revision "2024-03-04" {
    // RFC Editor: replace the above date 2024-03-04 with the date of
    // publication and remove this note.

    description
      "Alignment with SR policy architecture RFC9256";
    reference
      "RFC XXXX: YANG Data Model for Segment-routing Policy";
     // RFC Editor: replace XXXX with actual RFC number and remove
     // this note
  }

  revision "2022-03-28" {
    description
      "Alignment with SR policy architecture";
    reference
      "draft-ietf-spring-sr-policy-yang";
  }

  revision "2019-11-04" {
    description
      "Changes in keys for policy and its candidate paths";
    reference
      "draft-raza-spring-sr-policy-yang";
  }

  revision "2019-07-08" {
    description
      "Dynamic TE candidate-path support";
    reference
      "draft-raza-spring-sr-policy-yang";
  }

  revision "2018-07-01" {
    description
      "Initial version";
    reference
      "draft-raza-spring-sr-policy-yang";
  }

  //TBD: To be moved to srv6-base model when the model is ready
  grouping srv6-sid-info {
    description "Define an SRv6 SID";

    leaf value {
      type srv6-types:srv6-sid;
      description "SRv6 SID value";
    }

    leaf sid-behavior {
      type identityref {
        base srv6-types:srv6-endpoint-type;
      }
      description "SRv6 BSID behavior";
    }

    container sid-structure {
      description "SRv6 BSID structure";
      uses srv6-types:srv6-sid-structure;
    }
  }

  grouping srv6-bsid-type-b-config {
    description "SRv6 BSID Type-B config grouping";

    leaf sid-behavior {
      type identityref {
        base srv6-types:srv6-endpoint-type;
      }
      description "SRv6 BSID behavior";
    }

    container sid-structure {
      description "SRv6 BSID structure";
      uses srv6-types:srv6-sid-structure;
    }
  }

  grouping segment_config {
    description "Segment properties grouping";
    leaf index {
      type uint32;
      description "Segment index";
    }
    leaf type {
      type identityref {
        base sr-policy-types:segment-type;
      }
      mandatory true;
      description "Segment type";
    }

    container sr-mpls {
      description "SR-MPLS specific types";

      container Type-A {
        description
          "Segment declared by MPLS label";
        leaf value {
          type rt-types:mpls-label;
          description "MPLS label value";
        }
      }

      container Type-C {
        description
          "Segment declared by IPv4 Prefix with optional SR Algorithm
          for SR-MPLS";
        leaf ipv4-address {
          type inet:ipv4-address;
          description "Segment IPv4 address";
        }
        leaf algorithm {
          type uint8;
          description "Prefix SID algorithm identifier";
        }
      }

      container Type-D {
        description
          "Segment declared by IPv6 Global Prefix with optional
          SR Algorithm for SR-MPLS";
        leaf ipv6-address {
          type inet:ipv6-address;
          description "Segment IPv6 address";
        }
        leaf algorithm {
          type uint8;
          description "Prefix SID algorithm identifier";
        }
      }

      container Type-E {
        description
          "Segment declared by IPv4 Prefix with Local Interface ID -
          SR-MPLS";
        leaf ipv4-address {
          type inet:ipv4-address;
          description "Node IPv4 address";
        }
        leaf interface-identifier {
          type uint32;
          description "local interface identifier";
        }
      }

      container Type-F {
        description
          "Segment declared by IPv4 Addresses for link endpoints
          as Local, Remote pair - SR-MPLS";
        leaf local-ipv4-address {
          type inet:ipv4-address;
          description "Segment local IPv4 adjacency address";
        }
        leaf remote-ipv4-address {
          type inet:ipv4-address;
          description "Segment remote IPv4 adjacency address";
        }
      }

      container Type-G {
        description
          "Segment declared by IPv6 Prefix and Interface ID for
          link endpoints as Local, Remote pair for SR-MPLS";
        leaf local-ipv6-address {
          type inet:ipv6-address;
          description "Local link IPv6 address";
        }
        leaf local-interface-identifier {
          type uint32;
          description "Local interface identifier";
        }
        leaf remote-ipv6-address {
          type inet:ipv6-address;
          description "Remote link IPv6 address";
        }
        leaf remote-interface-identifier {
          type uint32;
          description "Remote interface identifier";
        }
      }

      container Type-H {
        description
          "Segment declared by IPv6 Addresses for link endpoints as
          Local, Remote pair for SR-MPLS";
        leaf local-ipv6-address {
          type inet:ipv6-address;
          description "Segment local IPv6 adjacency address";
        }
        leaf remote-ipv6-address {
          type inet:ipv6-address;
          description "Segment remote IPv6 adjacency address";
        }
      }
    } // sr-mpls

    container srv6 {
      description "SRv6 specific types";

      container Type-B {
        description
          "Segment declared by SRv6 SID value";
        leaf value {
          type srv6-types:srv6-sid;
          description "SRv6 SID value";
        }

        uses srv6-bsid-type-b-config;
      }

      container Type-I {
        description
          "Segment declared by IPv6 Global Prefix with optional
          SR Algorithm for SRv6";
        leaf ipv6-address {
          type inet:ipv6-address;
          description "Segment IPv6 prefix";
        }
        leaf algorithm {
          type uint8;
          description "Prefix SID algorithm identifier";
        }
      }
      container Type-J {
        description
          "Segment declared by IPv6 Prefix and Interface ID for
          link endpoints as Local, Remote pair for SRv6";
        leaf local-ipv6-address {
          type inet:ipv6-address;
          description "Local link IPv6 address";
        }
        leaf local-interface-identifier {
          type uint32;
          description "Local interface identifier";
        }
        leaf remote-ipv6-address {
          type inet:ipv6-address;
          description "Remote link IPv6 address";
        }
        leaf remote-interface-identifier {
          type uint32;
          description "Remote interface identifier";
        }
      }
      container Type-K {
        description
          "Segment declared by IPv6 Addresses for link endpoints as
          Local, Remote pair for SRv6";
        leaf local-ipv6-address {
          type inet:ipv6-address;
          description "Segment local IPv6 adjacency address";
        }
        leaf remote-ipv6-address {
          type inet:ipv6-address;
          description "Segment remote IPv6 adjacency address";
        }
      }
    } // srv6

    leaf validate {
      type boolean;
      default 'false';
      description
        "Indicates whether the segment should be validated.
        The default applies to all segments other than the first
        segment. For the first segment, validation is always done.";
    }
  }

  grouping segment-properties {
    description
      "SR segment properties grouping";
    uses segment_config;
  }

  grouping optimization-template-constraints {
    description "Constraints of optimization template";

      container srlg { // the rule applies per link
        description "SRLG constraints on the computed dynamic path";

        leaf-list exclude-any {
          type string;
          description
            "The link is excluded if it has any of these SRLG.";
        }
      }

      container affinity {  // the rule applies per link
        description
          "Affinity constraints on the computed dynamic path";

        leaf-list exclude-any {
          type string;
          description
            "The link is excluded if it has any of these affinities."
            ;
        }

        leaf-list include-any {
          type string;
          description
            "The link is accepted if it has any of these affinities";
        }
        leaf-list include-all {
          type string;
          description
            "The link is accepted if it has all these affinities";
        }
      }

      container ip-address {
        // the rule applies to e2e path and not per link
        description
          "IP address constraints on the computed dynamic path";

        leaf-list exclude {
          type inet:ip-address;
          description
            "Must exclude the links that has any of these IP
            addresses.";
        }
      }

      container upper-bounds {
        description
          "Upper-bound constraints on the computed dynamic path";

        container cumulative-metric {
          description
            "Path is invalid if its metric exceeds this value";

          leaf metric-type {
            type sr-policy-types:metric-type;
            description "Metric type";
          }

          leaf value { type uint32; description "Cumulative value"; }
        }

        leaf max-sids {
          type uint32;
          description
            "Path is invalid if it has more SIDs than this value";
        }
      }

      container segment-rules {
        description
          "Constraints on the segments to be used in the path";

        leaf sid-protection-eligibility {
          // currently applies to adj-sid segments only
          type sr-policy-types:sid-protection-eligibility-type;
          description "SID protection eligibility";
        }
      }

      leaf max-sids {
        type uint32;
        description "Maximum number of SIDs in a segment-list";
      }
  }

  grouping optimization-templates {
    description
      "Path optimization templates properties";

    container optimization-templates {
      description "Path optimization templates";

      list optimization-template {
        key "color";
        description "Path optimization template";

        leaf color {
          type uint32;
          description "Template identifier as a policy color";
        }

        container candidate-paths {
          description "A list of candidate paths representing the
                       optimization objectives and constraints";

          list candidate-path {
            key "discriminator";
            description "Candidate paths representing the
                         optimization objectives and constraints";
            leaf discriminator {
              type uint32;
              description "Candidate path distinguisher";
            }
            uses cpath-optimization-objs;
            container constraints {
              description "Constraints of a path optimization template";

              uses optimization-template-constraints;
            }
          }
        }
      }
    }
  }

  grouping attributes {
    description
      "Grouping containing attributes applicable to all SR policies";

    container attributes {
      description
        "Attributes applicable to SR policies";

      /*      uses srlg;
              uses affinity-mapping;
       */ // TODO: Beyond the scope of this model
      uses segment-lists;
      uses explicit-binding-sid-rules;
    }
  }

  grouping forwarding-counters {
    description
      "Grouping for counters";
    container counters {
      config false;
      description
        "Counters containing stats related to forwarding";

      leaf pkts {
        type yang:counter64;
        description "Number of packets forwarded";
      }
      leaf octets {
        type yang:counter64;
        units "byte";
        description "Number of bytes forwarded";
      }
    }
  }

  grouping segment-lists {
    description
      "Segment lists grouping";
    container segment-lists {
      description "Segment-lists properties";

      list segment-list {
        key "name";
        description "Segment-list properties";
        leaf name {
          type string;
          description "Segment-list name";
        }
        container segments {
          description
            "Segments for given segment list";

          list segment {
            key "index";
            description "Configure Segment/hop at the index";
            uses segment-properties;
          }
        }
      }
    }
  }

  grouping binding-sid_config {
    description
      "Binding SID configuration properties grouping";
    container mpls-sid {
      description "MPLS binding SIDs";
      leaf value {
        type sr-policy-types:mpls-sid-value-type;
        description "MPLS binding SID value";
      }
    }

    container srv6-sids {
      description "SRv6 binding SIDs";

      list srv6-sid {
        key "index";
        description "Configure an SRv6 binding-sid";
        leaf index {
          type uint32;
          description "Binding SID index";
        }

        leaf locator-name {
          type srv6-types:srv6-locator-name-type;
          description "Locator name used to allocate SRv6 binding SID";
        }
        uses srv6-sid-info;
      }
    }
  }

  grouping binding-sid_state {
    description
      "Binding SID state properties grouping";
    leaf alloc-mode {
      type sr-policy-types:binding-sid-alloc-mode;
      config false;
      description "Binding SID allocation mode";
    }
    leaf allocated-sid {
      type sr-policy-types:sid-value-type;
      config false;
      description "Allocated SID value for the Binding SID";
    }
    leaf oper-state {
      type sr-policy-types:binding-sid-oper-state;
      config false;
      description
        "Binding SID operational state";
    }
  }

  grouping binding-sid-properties {
    description
      "Binding SID properties grouping";
    container binding-sid {
      description "Binding Segment ID";
      uses binding-sid_config;
    }
  }

  grouping path-forwarding_state {
    description "Policy Forwarding path information";
    leaf path-id {
      type uint8;
      description "Primary path id";
    }
    leaf next-hop-address {
      type inet:ip-address;
      description "Nexthop address";
    }
    leaf next-hop-table-id {
      type uint32;
      description "Table ID for nexthop address";
    }
    leaf interface {
      type if:interface-ref;
      description "Outgoing interface handle";
    }
    leaf is-protected {
      type boolean;
      description "Is this path protected ?";
    }
    leaf backup-path-id {
      type uint8;
      description "Backup path id";
    }
    leaf is-pure-backup {
      type boolean;
      description "Is this path a pure backup ?";
    }
    leaf weight {
      type uint32;
      description "Path's weight for W-ECMP balancing";
    }
    container sid-list {
      description "Outgoing sid stack";

      uses sid-list-grouping;
    }
  }

  grouping cpath-cmn-properties {
    description
      "Common properties of the candidate path";

    leaf is-active {
      type boolean;
      config false;
      description
        "True if the candidate path is valid and used to forward
        traffic, False otherwise";
    }
    leaf is-valid {
      type boolean;
      config false;
      description
        "True if at least one segment-list is valid,
        False otherwise";
    }

    container computed-sid-list {
      config false;
      description "Computed SID list which could be different from
                   outgoing SID list";

      uses sid-list-grouping;
    }

    container forwarding-paths {
      config false;
      description
        "Forwarding state of paths";
      list forwarding-path {
        key "path-id";
        description "Forwarding path";
        uses path-forwarding_state;
        uses forwarding-counters;
      }
    }
  }

  grouping explicit-path-properties {
    description
      "Explicit path properties of the candidate path";
    container segment-lists {
      description
        "Path segment list(s) properties";
      list segment-list {
        key "name-ref";
        description "SR policy candidate path segment lists";

        leaf name-ref {
          type leafref {
            path "/rt:routing/"
              + "sr-policy:segment-routing/"
              + "sr-policy:traffic-engineering/"
              + "sr-policy:attributes/"
              + "sr-policy:segment-lists/"
              + "sr-policy:segment-list/"
              + "sr-policy:name";
          }
          description "Reference to segment-list name";
        }
        leaf weight {
          type uint32;
          default 1;
          description "Segment-list weighted loadshare";
        }
        leaf is-valid {
          type boolean;
          config false;
          description
            "True if the segment-list is valid, False otherwise";
        }
        uses forwarding-counters;
      }
    }
  }

  grouping affinity-mapping {
    description "Affinity-map grouping";

    container affinity-map {
      description
        "Mapping of affinity names to bit position";
      list affinity {
        key "name";
        unique "bit-position";
        leaf name {
          type string;
          description
            "Name of the affinity";
        }
        leaf bit-position {
          type uint16;
          description
            "The affinity entry in this list is mapped to the this
            bit-position in the affinity bitmap";
        }

        description "Affinity";
      }
    }
  }

  grouping srlg {
    description "SRLG grouping";

    container srlgs {
      description "SRLG";
      list srlg {
        key "name";

        leaf name {
          type string;
          description
            "Name of the SRLG";
        }

        leaf description {
          type string;
          description
            "Description of the SRLG";
        }
        leaf value {
          type uint32;
          mandatory true;
          description
            "The associated value (for advertisements etc.) ";
        }

        description "SRLG";
      }
    }
  }

  grouping cpath-optimization-objs {
    description "Candidate-path optimization objective grouping";

    container optimization-objectives {
      description
        "Optimization objectives for the dynamic path computation";
      container minimize-metric {
        description "The metric for which the path is optimized";
        leaf metric-type {
          type sr-policy-types:metric-type;
          description "Metric type";
        }

        container margin {
          description
            "The margin by which two paths with similar metric-type
            would be considered equal";
          leaf type {
            type sr-policy-types:margin-type;
            description "Margin type";
          }
          leaf value {
            type uint32;
            description "Margin value";
          }
          leaf computed-value {
            type uint32;
            config false;
            description "Computed metric value";
          }
        }
      }
    }
  }

  grouping cpath-constraints {
    description "Candidate-path constraints grouping";

    container constraints {
      description "Constraints for the dynamic path computation";

      container srlg { // the rule applies per link
        description "SRLG constraints on the computed dynamic path";

        leaf-list exclude-any {
          type string;
          description
            "The link is excluded if it has any of these SRLG.";
        }
        leaf-list include-any {
          type string;
          description
            "The link is accepted if it has any of these SRLG";
        }

        leaf-list include-all {
          type string;
          description
            "The link is accepted if it has all these SRLG";
        }
      }

      container affinity {  // the rule applies per link
        description
          "Affinity constraints on the computed dynamic path";

        leaf-list exclude-any {
          type string;
          description
            "The link is excluded if it has any of these affinities."
            ;
        }

        leaf-list include-any {
          type string;
          description
            "The link is accepted if it has any of these affinities";
        }
        leaf-list include-all {
          type string;
          description
            "The link is accepted if it has all these affinities";
        }
      }

      container ip-address {
        // the rule applies to e2e path and not per link
        description
          "IP address constraints on the computed dynamic path";

        leaf-list exclude {
          type inet:ip-address;
          description
            "Must exclude the links that has any of these IP
            addresses.";
        }
        leaf-list include-any {
          type inet:ip-address;
          description
            "Must include atleast 1 link (or possibly more) with any
            of these IP addresses.";
        }
        leaf-list include-all {
          type inet:ip-address;
          description
            "Must include all the links that have any of these IP
            addresses.";
        }
      }

      container upper-bounds {
        description
          "Upper-bound constraints on the computed dynamic path";

        container cumulative-metric {
          description
            "Path is invalid if its metric exceeds this value";

          leaf metric-type {
            type sr-policy-types:metric-type;
            description "Metric type";
          }

          leaf value { type uint32; description "Cumulative value"; }
        }

        leaf max-sids {
          type uint32;
          description
            "Path is invalid if it has more SIDs than this value";
        }
      }

      container segment-rules {
        description
          "Constraints on the segments to be used in the path";
        leaf sid-algorithm {
          type sr-policy-types:sid-algorithm-type;
          description
            "The prefix-sid algorithm to be used in

            path calculation";
        }

        leaf sid-protection-eligibility {
          // currently applies to adj-sid segments only
          type sr-policy-types:sid-protection-eligibility-type;
          description "SID protection eligibility";
        }
      }

      container disjoint-path {
        description "Path disjointness constraints";

        leaf disjointness-type {
          type te-types:te-path-disjointness;
          description
            "Type of disjointness computation used to find the path";
        }

        leaf association-group-id {
          type uint16;
          mandatory true;
          description "Association group Id";
        }

        leaf association-source {
          type inet:ip-address;
          mandatory true;
          description "Association source address";
        }

        leaf association-extended-id {
          type yang:hex-string;
          description
            "Association extended identifier.";
          reference
            "RFC6780";
        }
      }

      leaf max-sids {
        type uint32;
        description "Maximum number of SIDs in a segment-list";
      }
    }
  }

  grouping dynamic-path-properties {
    description
      "Dynamic path properties of the candidate path";
    container segment-list {
      description
        "Segment-list properties";
      leaf segment-list-dataplane-type {
        type sr-policy-types:dataplane-type;
        mandatory true;
        description
          "The dataplane type for the segment-list";
      }
      leaf is-valid {
        type boolean;
        config false;
        description
          "True if the segment-list is valid, False otherwise";
      }
      uses forwarding-counters;
    }

    uses cpath-optimization-objs;
    uses cpath-constraints;
  }
  grouping composite-path-properties {
    description
      "Composite path properties of the candidate path";

    container constituent-policies {
      description "Constituent SR policies";

      list constituent-policy {
        key "color";
        description "List of constituent SR policies";

        leaf color {
          type sr-policy-types:color-type;
          description
            "Color associated with the constituent policy
            (the endpoint is same as the parent policy)";
        }
        leaf weight {
          type uint32;
          default 1;
          description "Constituent policy weighted loadshare";
        }
      }
    }
  }

  grouping mpls-label-stack {
    description
      "Grouping for MPLS label stack";

    list labels {
      key "index";
      description
        "Stack containing MPLS labels";

      leaf index {
        type uint32;
        description "A unique ID of an MPLS label in labels list";
      }
      leaf label {
        type rt-types:mpls-label;
        description
          "MPLS label value";
      }
    }
  }

  grouping srv6-sid-stack {
    description
      "Grouping for SRv6 label stack";

    list sids {
      key "index";
      description
        "Stack containing SRv6 SIDs";

      leaf index {
        type uint32;
        description "A unique ID of an SRv6 sid in sid list";
      }
      leaf sid {
        type srv6-types:srv6-sid;
        description
          "SRv6 sid value";
      }
    }
  }

  grouping sid-list-grouping {
    description "Grouping for SID list";

    choice dataplane-type {
      description
        "Outgoing sids dataplane choice";
      case mpls {
        uses mpls-label-stack;
      }
      case srv6 {
        uses srv6-sid-stack;
      }
    }
  }

  grouping candidate-path_state {
    description
      "Candidate path state properties grouping";
    leaf is-best-candidate-path {
      type boolean;
      default 'false';
      config false;
      description
        "True if the candidate path is the best candidate path,
        False otherwise";
    }
    leaf non-selection-reason {
      type identityref {
        base sr-policy-types:candidate-path-not-selected-reason;
      }
      config false;
      description
        "Candidate path not selected reason";
    }
  }

  grouping policy-properties_config {
    description
      "SR policy configuration grouping";
    leaf name {
      type sr-policy-types:name-type;
      description "SR policy name";
    }
    leaf color {
      type sr-policy-types:color-type;
      description "Color associated with the policy";
    }
    leaf endpoint {
      type inet:ip-address;
      description "Policy end point IP address";
    }
    leaf description {
      type string;
      description "Description of the policy";
    }
    leaf admin-state {
      type sr-policy-types:policy-admin-state;
      default 'UP';
      description
        "SR policy administrative state, true for
        enabled, false for disabled";
    }
    leaf priority {
      type uint8;
      default 128;
      description
        "Priority considered when policy is recomputed due to
        topology changes";
    }
    leaf profile-id {
      type uint32;
      description "A profile represents a set of configuration knobs
                   specifying a policy or candidate-path attributes.
                   The profile-ID feature allows usage of
                   vendor/implementation specific functionality per
                   policy without requiring  explicit support by
                   controller.";
    }
    container bandwidth {
      description "Bandwidth constraints";

      leaf requested {
        type uint64;
        description
          "Requested bandwidth expressed in bytes per second";
      }
      leaf reserved {
        type uint64;
        config false;
        description
          "Reserved bandwidth expressed in bytes per second";
      }
    }
  }

  grouping policy-properties_state {
    description
      "SR policy property grouping";
    leaf oper-state {
      type sr-policy-types:policy-oper-state;
      config false;
      description
        "SR policy operational state";
    }
    leaf transition-count {
      type uint32;
      config false;
      description "Indicates number of up/down transitions";
    }
    leaf up-time {
      type yang:date-and-time;
      config false;
      description "Policy up time in seconds";
    }
    leaf down-time {
      type yang:date-and-time;
      config false;
      description "Policy down time in seconds";
    }
  }

  grouping policy-properties {
    description
      "SR policy properties";
    uses policy-properties_config;
    uses policy-properties_state;
    uses binding-sid-properties;
    uses forwarding-counters;
  }

  grouping candidate-path-type {
    description "Candidate path type grouping";
    choice type {
      description
        "Type of candidate paths";
      case explicit {
        description
          "Candidate path with explicitly defined set/s of
          segment-lists";
        uses explicit-path-properties;
      }
      case dynamic {
        description
          "Candidate path with dynamic computed segment-lists";
        uses dynamic-path-properties;
      }
      case composite {
        description
          "Candidate path that groups SR policies each with explicit
          and/or dynamic candidate path with potentially different
          optimization objectives and constraints";
        uses composite-path-properties;
      }

    }
  }

  grouping candidate-paths {
    description "SR policy candidate path grouping";
    container candidate-paths {
      description "SR policy candidate path(s) ";

      list candidate-path {
        key "protocol-origin originator-asn originator-node-address
          discriminator";
        unique "preference";

        description "SR policy Candidate path(s) list entry";

        leaf protocol-origin {
          type identityref {
            base sr-policy-types:protocol-origin-type;
          }
          description
            "Instantiation mechanism used to create the candidate
            path";
        }
        leaf originator-asn {
          type uint32;
          description
            "The autonomous system number (ASN) of the provisioning
            node. If 2-byte ASNs are in use, the low-order 16 bits
            MUST be used, and the high-order bits MUST be set to 0";
        }
        leaf originator-node-address {
          type sr-policy-types:node-address-type;
          description
            "represented as a 128-bit value. IPv4 addresses MUST be
            encoded in the lowest 32 bits, and the high-order bits
            MUST be set to 0";
        }
        leaf discriminator {
          type uint32;
          description "Candidate path distinguisher";
        }
        leaf preference {
          type uint32 {
            range "1..65535";
          }
          mandatory true;
          description "Candidate path preference";
        }
        leaf name {
          type string;
          description "Candidate path name";
        }
        leaf description {
          type string;
          description "Candidate path description";
        }
        leaf drop-upon-invalid {
          type boolean;
          description "Enable traffic dropping when LSP is invalid";
        }
        leaf admin-state {
          type boolean;
          description "Shutdown the candidate-path";
        }
        container binding-sid {
          if-feature capability-candidate-path-binding-sid;
          description
            "Binding segment ID";
          uses binding-sid_config;
        }

        uses candidate-path-type;
        uses candidate-path_state;
        uses cpath-cmn-properties;
      }
    }
  }

  grouping policies {
    description "SR policy grouping";
    container policies {
      description "SR Policy container";

      list policy {
        key "color endpoint";
        unique "name";
        description "SR Policy properties";

        uses policy-properties;
        uses candidate-paths;
      }
    }
  }

  grouping explicit-binding-sid-rules {
    description
      "Grouping for explicit binding sid rules";

    list explicit-binding-sid-rules {
      key "index";
      description
        "Explicit binding sid rules applicable for all policies";
      leaf index {
        type uint32;
        description "Explicit binding SID rules list index";
      }
      leaf rule {
        type sr-policy-types:explicit-binding-sid-rule-type;
        mandatory true;
        description "Explicit binding sid rule";
      }
    }
  }

  augment "/rt:routing" {
    description
      "This augments routing-instance configuration with
      segment-routing sr-policy.";
    container segment-routing {
      description "Main segment routing container";
      container traffic-engineering {
        description "Traffic-engineering container";

        uses optimization-templates;
        uses attributes;
        uses policies;
      }
    }
  }

  augment "/rt:routing/"
    + "sr-policy:segment-routing/"
    + "sr-policy:traffic-engineering/"
    + "sr-policy:policies/"
    + "sr-policy:policy/"
    + "sr-policy:binding-sid/"
    + "sr-policy:mpls-sid" {
    description
      "Augments binding-sid state with MPLS binding-sid";
    uses binding-sid_state;
  }

  augment "/rt:routing/"
    + "sr-policy:segment-routing/"
    + "sr-policy:traffic-engineering/"
    + "sr-policy:policies/"
    + "sr-policy:policy/"
    + "sr-policy:binding-sid/"
    + "sr-policy:srv6-sids/"
    + "sr-policy:srv6-sid" {
    description
      "Augments binding-sid state with SRv6 binding-sid";
    uses binding-sid_state;
  }

  /* Notifications */

  notification sr-policy-oper-state-change-event {
    description
      "Notification event when the operational state of the SR policy
      changes";

    leaf policy-name-ref {
      type leafref {
        path "/rt:routing/"
          + "sr-policy:segment-routing/"
          + "sr-policy:traffic-engineering/"
          + "sr-policy:policies/"
          + "sr-policy:policy/"
          + "sr-policy:name";
      }
      description "Reference to sr-policy name";
    }

    leaf policy-color-ref {
      type leafref {
        path "/rt:routing/"
          + "sr-policy:segment-routing/"
          + "sr-policy:traffic-engineering/"
          + "sr-policy:policies/"
          + "sr-policy:policy/"
          + "sr-policy:color";
      }
      description "Reference to sr-policy color";
    }

    leaf policy-endpoint-ref {
      type leafref {
        path "/rt:routing/"
          + "sr-policy:segment-routing/"
          + "sr-policy:traffic-engineering/"
          + "sr-policy:policies/"
          + "sr-policy:policy/"
          + "sr-policy:endpoint";
      }
      description "Reference to sr-policy endpoint";
    }

    leaf policy-new-oper-state  {
      type sr-policy-types:policy-oper-state;
      description "New operational state of the SR policy";
    }

    leaf policy-down-reason {
      type identityref {
        base sr-policy-types:policy-down-reason;
      }
      description
        "Down reason if the SR policy's new operational state is
        down";
    }
  }

  notification sr-policy-candidate-path-change-event {
    description
      "Notification event when candidate path changes for SR policy";

    leaf policy-name-ref {
      type leafref {
        path "/rt:routing/"
          + "sr-policy:segment-routing/"
          + "sr-policy:traffic-engineering/"
          + "sr-policy:policies/"
          + "sr-policy:policy/"
          + "sr-policy:name";
      }
      description "Reference to sr-policy name";
    }

    leaf policy-color-ref {
      type leafref {
        path "/rt:routing/"
          + "sr-policy:segment-routing/"
          + "sr-policy:traffic-engineering/"
          + "sr-policy:policies/"
          + "sr-policy:policy/"
          + "sr-policy:color";
      }
      description "Reference to sr-policy color";
    }

    leaf policy-endpoint-ref {
      type leafref {
        path "/rt:routing/"
          + "sr-policy:segment-routing/"
          + "sr-policy:traffic-engineering/"
          + "sr-policy:policies/"
          + "sr-policy:policy/"
          + "sr-policy:endpoint";
      }
      description "Reference to sr-policy endpoint";
    }

    leaf existing-preference {
      type uint32;
      description "Existing candidate path preference";
    }

    leaf new-preference {
      type uint32;
      description "New candidate path preference";
    }
  }

  notification sr-policy-binding-sid-unavailable-event {
    description
      "Notification event when the binding sid of sr-policy is
      unavailable";

    leaf policy-name-ref {
      type leafref {
        path "/rt:routing/"
          + "sr-policy:segment-routing/"
          + "sr-policy:traffic-engineering/"
          + "sr-policy:policies/"
          + "sr-policy:policy/"
          + "sr-policy:name";
      }
      description "Reference to sr-policy name";
    }

    leaf policy-color-ref {
      type leafref {
        path "/rt:routing/"
          + "sr-policy:segment-routing/"
          + "sr-policy:traffic-engineering/"
          + "sr-policy:policies/"
          + "sr-policy:policy/"
          + "sr-policy:color";
      }
      description "Reference to sr-policy color";
    }

    leaf policy-endpoint-ref {
      type leafref {
        path "/rt:routing/"
          + "sr-policy:segment-routing/"
          + "sr-policy:traffic-engineering/"
          + "sr-policy:policies/"
          + "sr-policy:policy/"
          + "sr-policy:endpoint";
      }
      description "Reference to sr-policy endpoint";
    }

    choice dataplane-type {
      description
        "Binding SID dataplane choice";
      case mpls {
        leaf policy-mpls-binding-sid-value-ref {
          if-feature capability-candidate-path-binding-sid;
          type leafref {
            path "/rt:routing/"
              + "sr-policy:segment-routing/"
              + "sr-policy:traffic-engineering/"
              + "sr-policy:policies/"
              + "sr-policy:policy/"
              + "sr-policy:binding-sid/"
              + "sr-policy:mpls-sid/"
              + "sr-policy:value";
          }
          description "Reference to sr-policy MPLS binding SID value";
        }
      }
      case srv6 {
        leaf policy-srv6-binding-sid-value-ref {
          if-feature capability-candidate-path-binding-sid;
          type leafref {
            path "/rt:routing/"
              + "sr-policy:segment-routing/"
              + "sr-policy:traffic-engineering/"
              + "sr-policy:policies/"
              + "sr-policy:policy/"
              + "sr-policy:binding-sid/"
              + "sr-policy:srv6-sids/"
              + "sr-policy:srv6-sid/"
              + "sr-policy:value";
          }
          description "Reference to sr-policy SRv6 binding SID value";
        }
      }
    }

    leaf reason {
      type identityref {
        base sr-policy-types:binding-sid-unavailable-reason;
      }
      description
        "Reason why the binding sid is unavailable";
    }
  }

  notification sr-policy-candidate-path-binding-sid-mismatch-event {
    description
      "Notification event when binding sid of requested candidate
      path is different from the binding sid of the existing
      candidate path";

    leaf policy-color-ref {
      type leafref {
        path "/rt:routing/"
          + "sr-policy:segment-routing/"
          + "sr-policy:traffic-engineering/"
          + "sr-policy:policies/"
          + "sr-policy:policy/"
          + "sr-policy:color";
      }
      description "Reference to sr-policy color";
    }

    leaf policy-endpoint-ref {
      type leafref {
        path "/rt:routing/"
          + "sr-policy:segment-routing/"
          + "sr-policy:traffic-engineering/"
          + "sr-policy:policies/"
          + "sr-policy:policy/"
          + "sr-policy:endpoint";
      }
      description "Reference to sr-policy endpoint";
    }

    leaf existing-candidate-path-protocol-origin-ref {
      type leafref {
        path "/rt:routing/"
          + "sr-policy:segment-routing/"
          + "sr-policy:traffic-engineering/"
          + "sr-policy:policies/"
          + "sr-policy:policy/"
          + "sr-policy:candidate-paths/"
          + "sr-policy:candidate-path/"
          + "sr-policy:protocol-origin";
      }
      description
        "Reference to existing candidate path protocol origin";
    }

    leaf existing-candidate-path-preference-ref {
      type leafref {
        path "/rt:routing/"
          + "sr-policy:segment-routing/"
          + "sr-policy:traffic-engineering/"
          + "sr-policy:policies/"
          + "sr-policy:policy/"
          + "sr-policy:candidate-paths/"
          + "sr-policy:candidate-path/"
          + "sr-policy:preference";
      }
      description "Reference to existing candidate path preference";
    }

    choice dataplane-type {
      description
        "Binding SID dataplane choice";
      case mpls {
        leaf existing-candidate-path-mpls-binding-sid-value-ref {
          if-feature capability-candidate-path-binding-sid;
          type leafref {
            path "/rt:routing/"
              + "sr-policy:segment-routing/"
              + "sr-policy:traffic-engineering/"
              + "sr-policy:policies/"
              + "sr-policy:policy/"
              + "sr-policy:candidate-paths/"
              + "sr-policy:candidate-path/"
              + "sr-policy:binding-sid/"
              + "sr-policy:mpls-sid/"
              + "sr-policy:value";
          }
          description
            "Reference to existing candidate path MPLS binding SID value";
        }
      }
      case srv6 {
        leaf existing-candidate-path-srv6-binding-sid-value-ref {
          if-feature capability-candidate-path-binding-sid;
          type leafref {
            path "/rt:routing/"
              + "sr-policy:segment-routing/"
              + "sr-policy:traffic-engineering/"
              + "sr-policy:policies/"
              + "sr-policy:policy/"
              + "sr-policy:candidate-paths/"
              + "sr-policy:candidate-path/"
              + "sr-policy:binding-sid/"
              + "sr-policy:srv6-sids/"
              + "sr-policy:srv6-sid/"
              + "sr-policy:value";
          }
          description
            "Reference to existing candidate path SRv6 binding SID value";
        }
      }
    }

    leaf conflicting-candidate-path-protocol-origin {
      type uint8;
      description "Conflicting candidate path protocol origin";
    }

    leaf conflicting-candidate-path-preference {
      type uint32;
      description "Conflicting candidate path preference";
    }

    leaf conflicting-candidate-path-binding-sid-dataplane {
      type sr-policy-types:dataplane-type;
      description
        "Conflicting candidate path binding sid dataplane type";
    }

    leaf conflicting-candidate-path-binding-sid-value {
      type sr-policy-types:sid-value-type;
      description "Conflicting candidate path binding sid value";
    }
  }

  /* Features */

  feature capability-candidate-path-binding-sid {
    description
      "This feature enables the capability of specifying binding-sid
      for a candidate path.";
  }
}
