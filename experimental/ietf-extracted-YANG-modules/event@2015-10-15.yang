submodule event {
  belongs-to sfc-control-planes {
    prefix sfc-e;
  }
  organization "ETRI.";
  contact
  "M-K. Shin mkshin@etri.re.kr
   M-J Choi mjchoi@kangwon.ac.kr";
  description
  "Events such as loops detection, long unavailable
   forwarding path time, out of service of SFIs.";
  revision 2015-10-15 {
     reference
     "draft-shin-sfc-control-plane-yang-00 -
     Yang Data Model for Service Function Chaining Control Plane";
  }
  notification event {
    description
    "Events such as loops detection, long unavailable forwarding
     path time, out of service of SFIs.";
    leaf event-type {
      type string;
      description
      "Event type.";
    }
    leaf severity {
      type string;
      description
      "The severity of the event.";
    }
    leaf event-explanation {
      type string;
      description
      "The detailed explanation of the event.";
    }
 }
}
