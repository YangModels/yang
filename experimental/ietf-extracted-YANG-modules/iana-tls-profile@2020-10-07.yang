module iana-tls-profile {
  yang-version 1.1;
  namespace "urn:ietf:params:xml:ns:yang:iana-tls-profile";
  prefix ianatp;

  organization
    "IANA";
  contact
    "        Internet Assigned Numbers Authority

     Postal: ICANN
             12025 Waterfront Drive, Suite 300
             Los Angeles, CA  90094-2536
             United States

     Tel:    +1 310 301 5800
     E-Mail: iana@iana.org>";
  description
    "This module contains YANG definition for the (D)TLS profile.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2020-10-07 {
    description
      "Initial revision";
    reference
      "RFC XXXX: Manufacturer Usage Description (MUD) (D)TLS Profiles
                 for IoT Devices";
  }

  typedef extension-type {
    type uint16;
    description
      "Extension type";
  }

  typedef supported-group {
    type uint16;
    description
      "Named group (DHE or ECDHE)";
  }

  typedef SPKI-pin-set {
    type binary;
    description
      "Subject Public Key Info pin set";
  }

  typedef signature-algorithm {
    type uint16;
    description
      "Signature algorithm";
  }

  typedef psk-key-exchange-mode {
    type uint8;
    description
      "pre-shared key exchange mode";
  }

  typedef application-protocol {
    type string;
    description
      "application protocol";
  }

  typedef cert-compression-algorithm {
    type uint16;
    description
      "certificate compression algorithm";
  }

  typedef certificate_authority {
    type string;
    description
      "Distinguished Name of Certificate authority";
  }

  typedef cipher-algorithm {
    type uint8;
    description
      "Cipher Algorithm";
  }

  typedef aead-algorithm {
    type uint8;
    description
      "AEAD Algorithm";
  }

  typedef tls-version {
    type enumeration {
      enum tls-1.2 {
        value 1;
        description
          "TLS Protocol Version 1.2.";
        reference
          "RFC 5246: The Transport Layer Security (TLS) Protocol
                     Version 1.2";
      }
      enum tls-1.3 {
        value 2;
        description
          "TLS Protocol Version 1.3.";
        reference
          "RFC 8446: The Transport Layer Security (TLS) Protocol
                     Version 1.3";
      }
    }
    description
      "Indicates the TLS version.";
  }

  typedef dtls-version {
    type enumeration {
      enum dtls-1.2 {
        value 1;
        description
          "DTLS Protocol Version 1.2.";
        reference
          "RFC 6346: Datagram Transport Layer Security 1.2";
      }
      enum dtls-1.3 {
        value 2;
        description
          "DTLS Protocol Version 1.3.";
        reference
          "RFC DDDD: Datagram Transport Layer Security 1.3";
      }
    }
    description
      "Indicates the DTLS version.";
  }
}
