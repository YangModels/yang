module ietf-http-server {
  yang-version 1.1;
  namespace "urn:ietf:params:xml:ns:yang:ietf-http-server";
  prefix https;

  organization
    "IETF NETCONF (Network Configuration) Working Group";

  contact
    "WG Web:   <http://datatracker.ietf.org/wg/netconf/>
     WG List:  <mailto:netconf@ietf.org>
     Author:   Kent Watsen <mailto:kent+ietf@watsen.net>";

  description
    "This module defines reusable groupings for HTTP servers that
     can be used as a basis for specific HTTP server instances.

     Copyright (c) 2019 IETF Trust and the persons identified
     as authors of the code. All rights reserved.

     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.;

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2019-04-07 {
    description
      "Initial version";
    reference
      "RFC XXXX: YANG Groupings for HTTP Clients and HTTP Servers";
  }

  // Groupings

  grouping http-server-grouping {
    description
      "A reusable grouping for configuring an HTTP server.";

    container http-server-parameters {
      description
        "A container that holds HTTP server configuration.  As HTTP
         servers vary wildly, it is expected that this container will
         be augmented by application-level modules as needed.";

      leaf server-name {
        type string;
        description
          "The value of the 'Server' header field.  If not set, then
           underlying software's default value is used.  Set to the
           empty string to disable.";
      }

      container protocol-versions {
        description
          "A list of HTTP protocol versions supported by this
           server.";
        leaf-list protocol-version {
          type enumeration {
            enum "HTTP/1.0" {
              description
                "The server supports the 'HTTP/1.0' protocol.";
            }
            enum "HTTP/1.1" {
              description
                "The server supports the 'HTTP/1.1' protocol.";
            }
            enum "HTTP/2.0" {
              description
                "The server supports the 'HTTP/2.0' protocol.";
            }
          }
          description
            "An HTTP protocol version supported by this server.";
        }
      }
    }
  }
}
