module ietf-platform-manifest {
  yang-version 1.1;
  namespace "urn:ietf:params:xml:ns:yang:ietf-platform-manifest";
  prefix p-mf;

  import ietf-yang-library {
    prefix yanglib;
    reference
      "RFC 8525: YANG Library";
  }
  import ietf-inet-types {
    prefix inet;
    reference
      "RFC 9911: Common YANG Data Types";
  }

  organization
    "IETF OPSAWG (Operations and Management Area Working Group)";
  contact
    "WG Web:   <https://datatracker.ietf.org/wg/opsawg/>
     WG List:  <mailto:opsawg@ietf.org>
     Author:   Benoit Claise   <mailto:benoit@everything-ops.net>
     Author:   Jean Quilbeuf   <mailto:jean.quilbeuf@huawei.com>
     Author:   Diego R. Lopez  <mailto:diego.r.lopez@telefonica.com>
     Author:   Ignacio Dominguez Martinez-Casanueva
     <mailto:i.domingumar@gmail.com>
     Author:   Thomas Graf     <mailto:thomas.graf@swisscom.com>";
  description
    "This module describes the platform information to be used as
     context of data collection from a given network element. The
     contents of this model must be streamed and stored along with
     the data streamed and stored from the network element so that
     the platform context of the data collection can be retrieved
     when the data is used for analysis.

     The data content of this model should not change except on
     software upgrade of the device, which might modify the
     software or os version or the YANG library.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     An implementation of this module MUST support at least one of
     the features 'yang-catalog' or 'ietf-system'.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.";

  revision 2026-06-27 {
    description
      "Initial revision";
    reference
      "RFC XXXX: A Data Manifest for Contextualized Telemetry Data";
  }

  feature yang-catalog {
    description
      "The implementation provides platform details following the
       YANG Catalog conventions (name, vendor, vendor-pen,
       software-version, software-flavor, os-version, os-type).";
  }

  feature ietf-system {
    description
      "The implementation provides platform details sourced from
       the RFC 7317 ietf-system system-state/platform container
       (os-name, os-release, os-version, machine).";
    reference
      "RFC 7317: A YANG Data Model for System Management";
  }

  grouping platform-yang-catalog {
    description
      "Platform details as stored in the YANG Catalog.
       Used when feature yang-catalog is supported.";
    leaf name {
      type string;
      description
        "Model of the platform from which data is collected.";
    }
    leaf vendor {
      type string;
      description
        "Organization that implements that platform.";
    }
    leaf vendor-pen {
      type uint32;
      description
        "Vendor's registered Private Enterprise Number";
      reference
        "RFC9371: Registration Procedures for Private Enterprise
         Numbers (PENs)";
    }
    leaf software-version {
      type string;
      description
        "Name of the version of software. With respect to most
         network device appliances, this will be the operating system
         version. But for other YANG module implementation, this
         would be a version of appliance software. Ultimately, this
         should correspond to a version string that will be
         recognizable by the consumers of the platform.";
    }
    leaf software-flavor {
      type string;
      description
        "A variation of a specific version where YANG model support
         may be different.  Depending on the vendor, this could be a
         license, additional software component, or a feature set.";
    }
    leaf os-version {
      type string;
      description
        "Version of the operating system using this module. This is
         primarily useful if the software implementing the module is
         an application that requires a specific operating system
         version.";
    }
    leaf os-type {
      type string;
      description
        "Type of the operating system using this module. This is
         primarily useful if the software implementing the module is
         an application that requires a specific operating system
         type.";
    }
  }

  grouping platform-ietf-system {
    description
      "Platform details sourced from the RFC 7317 ietf-system
       module: system/contact, system/hostname, system/location,
       and system-state/platform.";
    reference
      "RFC 7317: A YANG Data Model for System Management";
    container system {
      description
        "System group configuration.";
      reference
        "RFC 7317: A YANG Data Model for System Management,
         Section 3.1";
      leaf contact {
        type string;
        description
          "The administrator contact information for the system.";
        reference
          "RFC 7317: A YANG Data Model for System Management,
           Section 3.1";
      }
      leaf hostname {
        type inet:domain-name;
        description
          "The name of the host. This name can be a single domain
           label or the fully qualified domain name of the host.";
        reference
          "RFC 7317: A YANG Data Model for System Management,
           Section 3.1";
      }
      leaf location {
        type string;
        description
          "The system location.";
        reference
          "RFC 7317: A YANG Data Model for System Management,
           Section 3.1";
      }
    }
    container system-state {
      config false;
      description
        "System group operational state.";
      reference
        "RFC 7317: A YANG Data Model for System Management,
         Section 3.1";
      container platform {
        description
          "Contains vendor-specific information for identifying
           the system platform and operating system.";
        reference
          "RFC 7317: A YANG Data Model for System Management,
           Section 3.1";
        leaf os-name {
          type string;
          description
            "The name of the operating system in use.";
          reference
            "RFC 7317: A YANG Data Model for System Management,
             Section 3.1";
        }
        leaf os-release {
          type string;
          description
            "The current release level of the operating system.";
          reference
            "RFC 7317: A YANG Data Model for System Management,
             Section 3.1";
        }
        leaf os-version {
          type string;
          description
            "The current version level within the release of the
             operating system.";
          reference
            "RFC 7317: A YANG Data Model for System Management,
             Section 3.1";
        }
        leaf machine {
          type string;
          description
            "A vendor-specific identifier string for the hardware
             of the managed device.";
          reference
            "RFC 7317: A YANG Data Model for System Management,
             Section 3.1";
        }
      }
    }
  }

  container platforms {
    config false;
    description
      "Top container including all platforms in scope. If this model
       is hosted on a single device, it should contain a single entry
       in the list. At the network level, it should contain an entry
       for every monitored platform.";
    list platform {
      key "id";
      description
        "Contains information about the platform that allows
         identifying and understanding the individual data collection
         information.";
      leaf id {
        type string;
        description
          "Identifies a given platform on the network, for instance
           the 'sysName' of the platform. The 'id' has to be unique
           within the network scope at every point in time. The same
           id can point to different platform if they are not
           simultaneously part of the network, e.g., when a device
           associated to a particular id is replaced.";
      }
      uses platform-yang-catalog {
        if-feature "yang-catalog";
      }
      uses platform-ietf-system {
        if-feature "ietf-system";
      }
      uses yanglib:yang-library-parameters;
    }
  }
}
