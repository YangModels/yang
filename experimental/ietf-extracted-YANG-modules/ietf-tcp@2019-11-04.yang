module ietf-tcp {
  yang-version "1.1";
  namespace "urn:ietf:params:xml:ns:yang:ietf-tcp";
  prefix "tcp";

  import ietf-tcp-client {
    prefix "tcpc";
  }
  import ietf-tcp-server {
    prefix "tcps";
  }
  import ietf-tcp-common {
    prefix "tcpcmn";
  }
  import ietf-inet-types {
    prefix "inet";
  }

  organization
    "IETF TCPM Working Group";

  contact
    "WG Web:   <http://tools.ietf.org/wg/tcpm>
     WG List:  <tcpm@ietf.org>

     Authors: Michael Scharf (michael.scharf at hs-esslingen dot de)
              Vishal Murgai (vmurgai at cisco dot com)
              Mahesh Jethanandani (mjethanandani at gmail dot com)";

  description
    "This module focuses on fundamental and standard TCP functions
     that widely implemented. The model can be augmented to address
     more advanced or implementation specific TCP features.";

  revision "2019-11-04" {
    description
      "Initial Version";
    reference
      "RFC XXX, TCP Configuration.";
  }

  // Features
  feature server {
    description
      "TCP Server configuration supported.";
  }

  feature client {
    description
      "TCP Client configuration supported.";
  }

  // TCP-AO Groupings

  grouping mkt {
    leaf options {
      type binary;
      description
        "This flag indicates whether TCP options other than TCP-AO
         are included in the MAC calculation. When options are
         included, the content of all options, in the order present,
         is included in the MAC, with TCP-AO's MAC field zeroed out.
         When the options are not included, all options other than
         TCP-AO are excluded from all MAC calculations (skipped over,
         not zeroed).

         Note that TCP-AO, with its MAC field zeroed out, is always
         included in the MAC calculation, regardless of the setting
         of this flag; this protects the indication of the MAC length
         as well as the key ID fields (KeyID, RNextKeyID). The option
         flag applies to TCP options in both directions
         (incoming and outgoing segments).";
      reference
        "RFC 5925: The TCP Authentication Option.";
    }

    leaf key-id {
      type uint8;
      description
        "TBD";
    }

    leaf rnext-key-id {
      type uint8;
      description
        "TBD";
    }
    description
      "A Master Key Tuple (MKT) describes TCP-AO properties to be
       associated with one or more connections.";
  }

  grouping ao {
    leaf enable {
      type boolean;
      default "false";
      description
        "Enable support of TCP-Authentication Option (TCP-AO).";
    }

    leaf current-key {
      type binary;
      description
        "The Master Key Tuple (MKT) currently used to authenticate
         outgoing segments, whose SendID is inserted in outgoing
         segments as KeyID. Incoming segments are authenticated
         using the MKT corresponding to the segment and its TCP-AO
         KeyID as matched against the MKT TCP connection identifier
         and the MKT RecvID. There is only one current-key at any
         given time on a particular connection.

         Every TCP connection in a non-IDLE state MUST have at most
         one current_key specified.";
      reference
        "RFC 5925: The TCP Authentication Option.";
    }

    leaf rnext-key {
      type binary;
      description
        "The MKT currently preferred for incoming (received)
         segments, whose RecvID is inserted in outgoing segments as
         RNextKeyID.

         Each TCP connection in a non-IDLE state MUST have at most
         one rnext_key specified.";
      reference
        "RFC 5925: The TCP Authentication Option.";
    }

    leaf-list sne {
      type uint32;
      min-elements 1;
      max-elements 2;
      description
        "A pair of Sequence Number Extensions (SNEs). SNEs are used
         to prevent replay attacks. Each SNE is initialized to zero
         upon connection establishment.";
      reference
        "RFC 5925: The TCP Authentication Option.";
    }

    leaf-list mkt {
      type binary;
      min-elements 1;
      description
        "One or more MKTs. These are the MKTs that match this
         connection's socket pair.";
      reference
        "RFC 5925: The TCP Authentication Option.";
    }
    description
      "Authentication Option (AO) for TCP.";
    reference
      "RFC 5925: The TCP Authentication Option.";
  }

  // TCP general configuration groupings

  grouping tcp-mss-grouping {
    description "Maximum Segment Size (MSS) parameters";

    leaf tcp-mss {
      type uint16;
      description
        "Sets the max segment size for TCP connections.";
    }
  } // grouping tcp-mss-grouping

  grouping tcp-mtu-grouping {
    description "Maximum Transfer Unit (MTU) discovery parameters";

    leaf tcp-mtu-discovery {
      type boolean;
      default false;
      description
        "Turns path mtu discovery for TCP connections on (true) or
         off (false)";
    }
  } // grouping tcp-mtu-grouping

  grouping tcp-sack-grouping {
    description "Selective Acknowledgements (SACK) parameters";

    leaf sack-enable {
      type boolean;

      description
        "Enable support of Selective Acknowledgements (SACK)";
    }
  } // grouping tcp-sack-grouping

  grouping tcp-timestamps-grouping {
    description "Timestamp parameters";

    leaf timestamps-enable {
      type boolean;

      description
        "Enable support of timestamps";
    }
  } // grouping tcp-timestamps-grouping

  grouping tcp-fin-timeout-grouping {
    description "TIME WAIT timeout parameters";

    leaf fin-timeout {
      type uint16;
      units "seconds";
      description
        "When a connection is closed actively, it must linger in
         TIME-WAIT state for a time 2xMSL (Maximum Segment Lifetime).
         This parameter sets the TIME-WAIT timeout duration in
         seconds.";
    }
  } // grouping tcp-fin-timeout-grouping

  grouping tcp-ecn-grouping {
    description "Explicit Congestion Notification (ECN) parameters";

    leaf ecn-enable {
      type enumeration {
        enum disable;
        enum passive;
        enum active;
      }
      description
        "Enabling of ECN.";
    }
  } // grouping tcp-ecn-grouping

  // augment statements

  container tcp {
    presence "The container for TCP configuration.";

    description
      "TCP container.";

    container connections {
      list connection {
        key "local-address remote-address local-port remote-port";

        leaf local-address {
          type inet:ip-address;
          description
            "Local address that forms the connection identifier.";
        }

        leaf remote-address {
          type inet:ip-address;
          description
            "Remote address that forms the connection identifier.";
        }

        leaf local-port {
          type inet:port-number;
          description
            "Local TCP port that forms the connection identifier.";
        }

        leaf remote-port {
          type inet:port-number;
          description
            "Remote TCP port that forms the connection identifier.";
        }

        container common {
          uses tcpcmn:tcp-common-grouping;
          uses ao;
          description
            "Common definitions of TCP configuration. This includes
             parameters such as keepalives and idle time, that can
             be part of either the client or server.";
        }

        container server {
          if-feature server;
          uses tcps:tcp-server-grouping;
          description
            "Definitions of TCP server configuration.";
        }

        container client {
          if-feature client;
          uses tcpc:tcp-client-grouping;
          description
            "Definitions of TCP client configuration.";
        }
        description
          "Connection related parameters.";
      }
      description
        "A container of all TCP connections.";
    }
  }
}
