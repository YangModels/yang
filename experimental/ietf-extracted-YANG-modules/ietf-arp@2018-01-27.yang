module ietf-arp {
  yang-version 1.1;
  namespace "urn:ietf:params:xml:ns:yang:ietf-arp";
  prefix arp;

  import ietf-inet-types {
    prefix inet;
        reference "RFC 6991: INET Types Model";
  }

  import ietf-yang-types {
    prefix yang;
        reference "RFC 6991: yang Types Model";
  }

  import ietf-interfaces {
    prefix if;
    description
      "A Network Management Datastore Architecture (NMDA)
       compatible version of the ietf-interfaces module
       is required.";
  }
  import ietf-ip {
    prefix ip;
    description
      "A Network Management Datastore Architecture (NMDA)
       compatible version of the ietf-ip module is
       required.";
  }

  organization
    "IETF Routing Area Working Group (rtgwg)";
  contact
    "WG Web: <http://tools.ietf.org/wg/rtgwg/>
     WG List: <mailto: rtgwg@ietf.org>
     Editor: Xiaojian Ding
         dingxiaojian1@huawei.com
     Editor: Feng Zheng
         habby.zheng@huawei.com
     Editor: Robert Wilton
         rwilton@cisco.com";
  description
    "Address Resolution Protocol (ARP) management, which includes
     static ARP configuration, dynamic ARP learning, ARP entry query,
     and packet statistics collection.";

  revision 2018-01-27 {
    description
      "Init revision";
       //   NOTE TO RFC EDITOR:
     // Please replace the following reference
     // to draft-ding-rtgwg-arp-yang-model-02 with
     // RFC number when published (i.e. RFC xxxx).
    reference
         "draft-ding-rtgwg-arp-yang-model-02";
  }

      /*
      * Features
      */

    feature global-static-entries {
    description
      "This feature indicates that the device allows static entries
       to be configured globally.";
  }

  container arp {
    description
      "Address Resolution Protocol (ARP) management, which includes
        static ARP configuration, dynamic ARP learning, ARP entry
        query, and packet statistics collection.";

    container global-static-entries {
      if-feature "global-static-entries";
      description
        "Set a global static ARP entry, which is independent of the interface.";
      list static-entry {
        key "ip-address";
        description
          "List of ARP static entries that can be configured globally.";
        leaf ip-address {
          type inet:ipv4-address-no-zone;
          description
            "IP address, in dotted decimal notation.";
        }
        leaf mac-address {
          type yang:mac-address;
          mandatory true;
          description
            "MAC address in the format of H-H-H, in which H is
                        a hexadecimal number of 1 to 4 bits.";
        }
      }
    }
    container global-control {
      description
        "Set global control parameters, which are independent of interface.";
        leaf enable-learning {
          type boolean;
                  default "true";
          description
            "Enables or disables global dynamic ARP learning.
                        If 'true', then enforcement is enabled.
                        If 'false', then enforcement is disabled.";
        }
        leaf enable-proxy {
          type boolean;
          default "true";
          description
            "Proxy ARP is enabled by default; perform this
                        task to globally disable proxy ARP on all interfaces.";
        }
    }
        }
   augment "/if:interfaces/if:interface" {
    description
      "Augment interface configuration with parameters of ARP.";
    container arp-dynamic-learning {
      description
        "Support for ARP configuration on interfaces.";
      leaf expire-time {
        type yang:timeticks {
          range "60..86400";
        }
        units "second";
        description
          "Aging time of a dynamic ARP entry.";
      }
      leaf learn-disable {
        type boolean;
        default "false";
        description
          "Whether dynamic ARP learning is disabled on an interface.
                  If the value is True, dynamic ARP learning is disabled.
                  If the value is False, dynamic ARP learning is enabled.";
      }

      container proxy {
        description
          "Configuration parameters for proxy ARP";
                leaf mode {
                  type enumeration {
                        enum DISABLE {
                          description
                                "The system should not respond to ARP requests that
                                do not specify an IP address configured on the local
                                subinterface as the target address.";
                        }
                        enum REMOTE_ONLY {
                          description
                                "The system responds to ARP requests only when the
                                sender and target IP addresses are in different
                                subnets.";
                        }
                        enum ALL {
                          description
                                "The system responds to ARP requests where the sender
                                and target IP addresses are in different subnets, as well
                                as those where they are in the same subnet.";
                        }
                  }
                  default "DISABLE";
                  description
                        "When set to a value other than DISABLE, the local system should
                        respond to ARP requests that are for target addresses other than
                        those that are configured on the local subinterface using its own
                        MAC address as the target hardware address. If the REMOTE_ONLY
                        value is specified, replies are only sent when the target address
                        falls outside the locally configured subnets on the interface,
                        whereas with the ALL value, all requests, regardless of their
                        target address are replied to.";
                  reference "RFC1027: Using ARP to Implement Transparent Subnet Gateways";
       }
      }

      container probe {
        description
          "Common configuration parameters for all ARP probe.";
        leaf interval {
          type uint8 {
            range "1..5";
          }
          units "second";
          description
            "Interval for detecting dynamic ARP entries.";
        }
        leaf times {
          type uint8 {
            range "0..10";
          }
          description
            "Number of aging probe attempts for a dynamic ARP entry.
             If a device does not receive an ARP reply message after
             the number of aging probe attempts reaches a specified
             number,thedynamic ARP entry is deleted.";
        }
        leaf unicast {
          type boolean;
          default "false";
          description
            "Send unicast ARP aging probe messages for a dynamic ARP
             entry.";
        }
      }

      container gratuitous {
        description
          "Configure gratuitous ARP.";
        leaf enable {
          type boolean;
          default "false";
          description
            "Enable or disable sending gratuitous-arp packet on
             interface.";
        }
        leaf interval {
          type uint32 {
            range "1..86400";
          }
          units "second";
          description
            "The interval of sending gratuitous-arp packet on the
             interface.";
        }
        leaf drop {
          type boolean;
          default "false";
          description
            "Drop the receipt of gratuitous ARP packets on the interface.";
        }
      }

      container statistics {
        config false;
        description
          "IP ARP Statistics information on interfaces";
        leaf in-requests-pkts {
          type uint16;
          description
            "Total ARP requests received";
        }
        leaf in-replies-pkts {
          type uint16;
          description
            "Total ARP replies received";
        }
        leaf in-gratuitous-pkts {
          type uint16;
          description
            "Total gratuitous ARP received";
        }
        leaf out-requests-pkts {
          type uint16;
          description
            "Total ARP requests sent";
        }
        leaf out-replies-pkts {
          type uint16;
          description
            "Total ARP replies sent";
        }
        leaf out-gratuitous-pkts {
          type uint16;
          description
            "Total gratuitous ARP sent";
        }
      }
    }
  }

  augment "/if:interfaces/if:interface/ip:ipv4/ip:neighbor" {
    description
      "Augment neighbor list with parameters of ARP,
       eg., support for remaining expire time query on interfaces.";
    leaf remaining-expire-time {
      type uint32;
      config false;
      description
        "Remaining expire time of a dynamic ARP entry. ";
    }
   }

}
