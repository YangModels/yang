module ietf-restconf-client {
  yang-version 1.1;
  namespace "urn:ietf:params:xml:ns:yang:ietf-restconf-client";
  prefix rcc;

  import ietf-yang-types {
    prefix yang;
    reference
      "RFC 6991: Common YANG Data Types";
  }

  import ietf-tcp-client {
    prefix tcpc;
    reference
      "RFC AAAA: YANG Groupings for TCP Clients and TCP Servers";
  }

  import ietf-tcp-server {
    prefix tcps;
    reference
      "RFC AAAA: YANG Groupings for TCP Clients and TCP Servers";
  }

  import ietf-tls-client {
    prefix tlsc;
    reference
      "RFC BBBB: YANG Groupings for TLS Clients and TLS Servers";
  }

  import ietf-http-client {
    prefix httpc;
    reference
      "RFC CCCC: YANG Groupings for HTTP Clients and HTTP Servers";
  }

  organization
    "IETF NETCONF (Network Configuration) Working Group";

  contact
    "WG Web:   <http://datatracker.ietf.org/wg/netconf/>
     WG List:  <mailto:netconf@ietf.org>
     Author:   Kent Watsen <mailto:kent+ietf@watsen.net>
     Author:   Gary Wu <mailto:garywu@cisco.com>";

  description
    "This module contains a collection of YANG definitions
     for configuring RESTCONF clients.

     Copyright (c) 2019 IETF Trust and the persons identified
     as authors of the code. All rights reserved.

     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.;

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2019-04-29 {
    description
      "Initial version";
    reference
      "RFC XXXX: RESTCONF Client and Server Models";
  }
  // Features

  feature https-initiate {
    description
      "The 'https-initiate' feature indicates that the RESTCONF
       client supports initiating HTTPS connections to RESTCONF
       servers. This feature exists as HTTPS might not be a
       mandatory to implement transport in the future.";
    reference
      "RFC 8040: RESTCONF Protocol";
  }

  feature https-listen {
    description
      "The 'https-listen' feature indicates that the RESTCONF client
       supports opening a port to listen for incoming RESTCONF
       server call-home connections.  This feature exists as not
       all RESTCONF clients may support RESTCONF call home.";
    reference
      "RFC 8071: NETCONF Call Home and RESTCONF Call Home";
  }

  // Groupings

  grouping restconf-client-grouping {
    description
      "Top-level grouping for RESTCONF client configuration.";
    container initiate {
      if-feature "https-initiate";
      presence "Enables client to initiate TCP connections";
      description
        "Configures client initiating underlying TCP connections.";
      list restconf-server {
        key "name";
        min-elements 1;
        description
          "List of RESTCONF servers the RESTCONF client is to
           initiate connections to in parallel.";
        leaf name {
          type string;
          description
            "An arbitrary name for the RESTCONF server.";
        }
        container endpoints {
          description
            "Container for the list of endpoints.";
          list endpoint {
            key "name";
            min-elements 1;
            ordered-by user;
            description
              "A non-empty user-ordered list of endpoints for this
               RESTCONF client to try to connect to in sequence.
               Defining more than one enables high-availability.";
            leaf name {
              type string;
              description
                "An arbitrary name for this endpoint.";
            }
            choice transport {
              mandatory true;
              description
                "Selects between available transports. This is a
                 'choice' statement so as to support additional
                 transport options to be augmented in.";
              case https {
                if-feature "https-initiate";
                container https {
                  description
                    "Specifies HTTPS-specific transport
                     configuration.";
                  container tcp-client-parameters {
                    description
                      "A wrapper around the TCP client parameters
                       to avoid name collisions.";
                    uses tcpc:tcp-client-grouping {
                      refine "remote-port" {
                        default "443";
                        description
                          "The RESTCONF client will attempt to
                           connect to the IANA-assigned well-known
                           port value for 'https' (443) if no value
                           is specified.";
                      }
                    }
                  }
                  container tls-client-parameters {
                    description
                      "A wrapper around the TLS client parameters
                       to avoid name collisions.";
                    uses tlsc:tls-client-grouping {
                      refine "client-identity/auth-type" {
                        mandatory true;
                        description
                          "RESTCONF clients MUST pass some
                           authentication credentials.";
                      }
                    }
                  }
                  container http-client-parameters {
                    description
                      "A wrapper around the HTTP client parameters
                       to avoid name collisions.";
                    uses httpc:http-client-grouping;
                  }
                }
              } // https
            } // transport
          } // endpoint
        } // endpoints
        container connection-type {
          description
            "Indicates the RESTCONF client's preference for how
             the RESTCONF connection is maintained.";
          choice connection-type {
            mandatory true;
            description
              "Selects between available connection types.";
            case persistent-connection {
              container persistent {
                presence "Indicates that a persistent connection
                          is to be maintained.";
                description
                  "Maintain a persistent connection to the
                   RESTCONF server. If the connection goes down,
                   immediately start trying to reconnect to the
                   RESTCONF server, using the reconnection strategy.

                   This connection type minimizes any RESTCONF server
                   to RESTCONF client data-transfer delay, albeit
                   at the expense of holding resources longer.";
              }
            }
            case periodic-connection {
              container periodic {
                presence "Indicates that a periodic connection is
                          to be maintained.";
                description
                  "Periodically connect to the RESTCONF server.

                   This connection type increases resource
                   utilization, albeit with increased delay
                   in RESTCONF server to RESTCONF client
                   interactions.
                   The RESTCONF client SHOULD gracefully close
                   the underlying TLS connection upon completing
                   planned activities.

                   In the case that the previous connection is
                   still active, establishing a new connection
                   is NOT RECOMMENDED.";

                leaf period {
                  type uint16;
                  units "minutes";
                  default "60";
                  description
                    "Duration of time between periodic
                     connections.";
                }
                leaf anchor-time {
                  type yang:date-and-time {
                    // constrained to minute-level granularity
                    pattern '\d{4}-\d{2}-\d{2}T\d{2}:\d{2}'
                          + '(Z|[\+\-]\d{2}:\d{2})';
                  }
                  description
                    "Designates a timestamp before or after which
                     a series of periodic connections are
                     determined.  The periodic connections occur
                     at a whole multiple interval from the anchor
                     time.  For example, for an anchor time is 15
                     minutes past midnight and a period interval
                     of 24 hours, then a periodic connection will
                     occur 15 minutes past midnight everyday.";
                }
                leaf idle-timeout {
                  type uint16;
                  units "seconds";
                  default 120; // two minutes
                  description
                    "Specifies the maximum number of seconds
                     that the underlying TCP session may remain
                     idle. A TCP session will be dropped if it
                     is idle for an interval longer than this
                     number of seconds If set to zero, then the
                     RESTCONF client will never drop a session
                     because it is idle.";
                }
              }
            } // periodic-connection
          } // connection-type
        } // connection-type
        container reconnect-strategy {
          description
            "The reconnection strategy directs how a RESTCONF
             client reconnects to a RESTCONF server, after
             discovering its connection to the server has
             dropped, even if due to a reboot.  The RESTCONF
             client starts with the specified endpoint and
             tries to connect to it max-attempts times before
             trying the next endpoint in the list (round
             robin).";
          leaf start-with {
            type enumeration {
              enum first-listed {
                description
                  "Indicates that reconnections should start
                   with the first endpoint listed.";
              }
              enum last-connected {
                description
                  "Indicates that reconnections should start
                   with the endpoint last connected to.  If
                   no previous connection has ever been
                   established, then the first endpoint
                   configured is used.   RESTCONF clients
                   SHOULD be able to remember the last
                   endpoint connected to across reboots.";
              }
              enum random-selection {
                description
                  "Indicates that reconnections should start with
                   a random endpoint.";
              }
            }
            default "first-listed";
            description
              "Specifies which of the RESTCONF server's
               endpoints the RESTCONF client should start
               with when trying to connect to the RESTCONF
               server.";
          }
          leaf max-attempts {
            type uint8 {
              range "1..max";
            }
            default "3";
            description
              "Specifies the number times the RESTCONF client
               tries to connect to a specific endpoint before
               moving on to the next endpoint in the list
               (round robin).";
          }
        } // reconnect-strategy
      } // restconf-server
    } // initiate

    container listen {
      if-feature "https-listen";
      presence "Enables client to accept call-home connections";
      description
        "Configures client accepting call-home TCP connections.";
      leaf idle-timeout {
        type uint16;
        units "seconds";
        default 3600; // one hour
        description
          "Specifies the maximum number of seconds that an
           underlying TCP session may remain idle. A TCP session
           will be dropped if it is idle for an interval longer
           then this number of seconds.  If set to zero, then
           the server will never drop a session because it is
           idle.  Sessions that have a notification subscription
           active are never dropped.";
      }
      list endpoint {
        key "name";
        min-elements 1;
        description
          "List of endpoints to listen for RESTCONF connections.";
        leaf name {
          type string;
          description
            "An arbitrary name for the RESTCONF listen endpoint.";
        }
        choice transport {
          mandatory true;
          description
            "Selects between available transports. This is a
             'choice' statement so as to support additional
             transport options to be augmented in.";
          case https {
            if-feature "https-listen";
            container https {
              description
                "HTTPS-specific listening configuration for inbound
                 connections.";
              container tcp-server-parameters {
                description
                  "A wrapper around the TCP client parameters
                   to avoid name collisions.";
                uses tcps:tcp-server-grouping {
                  refine "local-port" {
                    default "4336";
                    description
                      "The RESTCONF client will listen on the IANA-
                       assigned well-known port for 'restconf-ch-tls'
                       (4336) if no value is specified.";
                  }
                }
              }
              container tls-client-parameters {
                description
                  "A wrapper around the TLS client parameters
                   to avoid name collisions.";
                uses tlsc:tls-client-grouping {
                  refine "client-identity/auth-type" {
                    mandatory true;
                    description
                      "RESTCONF clients MUST pass some authentication
                       credentials.";
                  }
                }
              }
              container http-client-parameters {
                description
                  "A wrapper around the HTTP client parameters
                   to avoid name collisions.";
                uses httpc:http-client-grouping;
              }
            }
          } // case https
        } // transport
      } // endpoint
    } // listen
  } // restconf-client

  // Protocol accessible node, for servers that implement this
  // module.

  container restconf-client {
    uses restconf-client-grouping;
    description
      "Top-level container for RESTCONF client configuration.";
  }
}
