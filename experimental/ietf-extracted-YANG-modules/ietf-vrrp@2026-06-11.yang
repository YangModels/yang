module ietf-vrrp {
  yang-version 1.1;
  namespace "urn:ietf:params:xml:ns:yang:ietf-vrrp";
  prefix vrrp;

  import ietf-inet-types {
    prefix inet;
    reference
      "RFC 9911: Common YANG Data Types, Section 4";
  }
  import ietf-yang-types {
    prefix yang;
    reference
      "RFC 9911: Common YANG Data Types, Section 3";
  }
  import ietf-interfaces {
    prefix if;
    reference
      "RFC 8343: A YANG Data Model for Interface Management";
  }
  import ietf-ip {
    prefix ip;
    reference
      "RFC 8344: A YANG Data Model for IP Management";
  }

  organization
    "IETF Routing Area Working Group (RTGWG)";
  contact
    "WG Web:   <https://datatracker.ietf.org/wg/rtgwg/>
     WG List:  <mailto:rtgwg@ietf.org>

     Editor:   Acee Lindem
               <mailto:acee.ietf@gmail.com>

     Editor:   Xufeng Liu
               <mailto:xufeng.liu.ietf@gmail.com>

     Editor:   Athanasios Kyparlis
               <mailto:Athanasios_Kyparlis@jabil.com>

     Editor:   Ravi Parikh
               <mailto:parikh_ravi@ymail.com>

     Editor:   Mingui Zhang
               <mailto:zhangmingui@huawei.com>";
  description
    "This YANG module defines a model for managing Virtual Router
     Redundancy Protocol (VRRP) versions 2 and 3.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).
     All revisions of IETF and IANA published modules can be found
     at the YANG Parameters registry group
     (https://www.iana.org/assignments/yang-parameters).

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     This version of this YANG module is part of RFC XXXX; see
     the RFC itself for full legal notices.";

  revision 2026-06-11 {
    description
      "This revision includes the following changes:
       - Update some identifiers and descriptions to conform
         to the changes in RFC 9568
       - Add a new effective-priority leaf
       - Update some reference statements";
    reference
      "RFC XXXX: A YANG Data Model for the Virtual Router Redundancy
                 Protocol (VRRP)";
  }
  revision 2018-03-13 {
    description
      "Initial revision.";
    reference
      "RFC 8347: A YANG Data Model for the Virtual Router Redundancy
                 Protocol (VRRP)";
  }

  /*
   * Features
   */

  feature validate-interval-errors {
    description
      "This feature indicates that the system validates that the
       advertisement interval from advertisement packets received
       is the same as the interval configured for the local
       VRRP router.";
  }

  feature validate-address-list-errors {
    description
      "This feature indicates that the system validates that
       the address list from received packets matches the
       locally configured list for the VRRP router.";
  }

  /*
   * Typedefs
   */

  typedef new-active-reason-type {
    type enumeration {
      enum not-active {
        description
          "The virtual router has never transitioned to active
           state.";
      }
      enum priority {
        description
          "Priority was higher.";
      }
      enum preempted {
        description
          "The active virtual router was preempted.";
      }
      enum no-response {
        description
          "Previous active virtual router did not respond.";
      }
    }
    description
      "Indicates why the virtual router has transitioned to
       active state.

       The identifier of this typedef is changed to reflect
       the updated terminology used in RFC 9568.";
  } // new-active-reason-type

  /*
   * Identities
   */
  /* vrrp-event-type identity and its derivatives. */

  identity vrrp-event-type {
    description
      "Indicates the type of a VRRP protocol event.";
  }

  identity vrrp-event-none {
    base vrrp-event-type;
    description
      "Indicates a non-meaningful event.";
  }

  identity vrrp-event-startup {
    base vrrp-event-type;
    description
      "Indicates that a VRRP router has initiated the protocol.";
  }

  identity vrrp-event-shutdown {
    base vrrp-event-type;
    description
      "Indicates that a VRRP router has closed down the protocol.";
  }

  identity vrrp-event-higher-priority-backup {
    base vrrp-event-type;
    description
      "Indicates that a backup router has a higher priority than
       the current active.";
  }

  identity vrrp-event-active-timeout {
    base vrrp-event-type;
    description
      "Indicates that the current active virtual router has not sent
       an advertisement within the limit of active-down-interval.

       The identity is changed to reflect the updated terminology
       used in RFC 9568.";
  }

  identity vrrp-event-interface-up {
    base vrrp-event-type;
    description
      "Indicates that the VRRP-enabled interface has become
       'operational up'.";
  }

  identity vrrp-event-interface-down {
    base vrrp-event-type;
    description
      "Indicates that the VRRP-enabled interface has become
       'operational down'.";
  }

  identity vrrp-event-no-primary-ip-address {
    base vrrp-event-type;
    description
      "Indicates that the primary IP address on the VRRP-enabled
       interface has become unavailable.";
  }

  identity vrrp-event-primary-ip-address {
    base vrrp-event-type;
    description
      "Indicates that the primary IP address on the VRRP-enabled
       interface has become available.";
  }

  identity vrrp-event-no-virtual-ip-addresses {
    base vrrp-event-type;
    description
      "Indicates that there are no virtual IP addresses on the
       virtual router.";
  }

  identity vrrp-event-virtual-ip-addresses {
    base vrrp-event-type;
    description
      "Indicates that there are virtual IP addresses on the
       virtual router.";
  }

  identity vrrp-event-preempt-hold-timeout {
    base vrrp-event-type;
    description
      "Indicates that the configured preemption hold time has
       passed.";
  }

  identity vrrp-event-lower-priority-active {
    base vrrp-event-type;
    description
      "Indicates that there is a lower-priority VRRP active router.

       The identity is changed to reflect the updated terminology
       used in RFC 9568.";
  }

  identity vrrp-event-owner-preempt {
    base vrrp-event-type;
    description
      "Indicates that the owner has preempted another virtual router
       to become the active virtual router.";
  }
  /* vrrp-error-global identity and its derivatives. */

  identity vrrp-error-global {
    description
      "Indicates the type of a VRRP error that occurred
       for a packet before it reaches a VRRP router.";
  }

  identity checksum-error {
    base vrrp-error-global;
    description
      "A packet has been received with an invalid VRRP checksum
       value.";
  }

  identity ip-ttl-error {
    base vrrp-error-global;
    description
      "A packet has been received with IP TTL (Time-To-Live)
       not equal to 255.";
  }

  identity version-error {
    base vrrp-error-global;
    description
      "A packet has been received with an unknown or unsupported
       version number.";
  }

  identity vrid-error {
    base vrrp-error-global;
    description
      "A packet has been received with a Virtual Router Identifier
       (VRID) that is not valid for any virtual router on this
       router.";
  }

  /* vrrp-error-virtual-router identity and its derivatives. */

  identity vrrp-error-virtual-router {
    description
      "Indicates the type of a VRRP error that occurred
       after a packet reaches a VRRP router.";
  }

  identity address-list-error {
    base vrrp-error-virtual-router;
    description
      "A packet has been received with an address list that
       does not match the locally configured address list for
       the virtual router.";
  }

  identity interval-error {
    base vrrp-error-virtual-router;
    description
      "A packet has been received with an advertisement interval
       different than the interval configured for the local
       virtual router.";
  }

  identity packet-length-error {
    base vrrp-error-virtual-router;
    description
      "A packet has been received with a packet length less
       than the length of the VRRP header.";
  }

  /* vrrp-state-type identity and its derivatives. */

  identity vrrp-state-type {
    description
      "Indicates the state of a virtual router.";
  }

  identity initialize {
    base vrrp-state-type;
    description
      "Indicates that the virtual router is waiting
       for a startup event.";
  }

  identity backup {
    base vrrp-state-type;
    description
      "Indicates that the virtual router is monitoring the
       availability of the active virtual router.";
  }

  identity active {
    base vrrp-state-type;
    description
      "Indicates that the virtual router is forwarding
       packets for IP addresses that are associated with
       this virtual router.

       The identity is changed to reflect the updated terminology
       used in RFC 9568.";
  }

  /* vrrp-version identity and its derivatives. */

  identity vrrp-version {
    description
      "The version of VRRP.";
  }

  identity vrrp-v2 {
    base vrrp-version;
    description
      "Indicates version 2 of VRRP.";
  }

  identity vrrp-v3 {
    base vrrp-version;
    description
      "Indicates version 3 of VRRP.";
  }

  /*
   * Groupings
   */

  grouping vrrp-common-attributes {
    description
      "Group of VRRP attributes common to versions 2 and 3.";
    leaf vrid {
      type uint8 {
        range "1..255";
      }
      description
        "Virtual Router ID (i.e., VRID).";
    }
    leaf version {
      type identityref {
        base vrrp:vrrp-version;
      }
      mandatory true;
      description
        "Version 2 or 3 of VRRP.";
    }
    leaf log-state-change {
      type boolean;
      default "false";
      description
        "Generates VRRP state change messages each time the
         VRRP instance changes state from one VRRP state
         ('initialize', 'backup', or 'active') to another
         VRRP state.";
    }
    container preempt {
      description
        "Enables a higher-priority VRRP backup router to preempt a
         lower-priority VRRP active router.";
      leaf enabled {
        type boolean;
        default "true";
        description
          "'true' if preemption is enabled.";
      }
      leaf hold-time {
        type uint16;
        units "seconds";
        default "0";
        description
          "Hold time, in seconds, for which a higher-priority VRRP
           backup router must wait before preempting a lower-priority
           VRRP active router.";
      }
    }
    leaf priority {
      type uint8 {
        range "1..254";
      }
      default "100";
      description
        "Configures the VRRP election priority for the backup
         virtual router.";
    }
    leaf accept-mode {
      when "derived-from-or-self(current()/../version, "
         + "'vrrp:vrrp-v3')" {
        description
          "Applicable only to version 3.";
      }
      type boolean;
      default "false";
      description
        "Controls whether a virtual router in active state will
         accept packets addressed to the address owner's IPvX address
         as its own if it is not the IPvX address owner.  The default
         is 'false'.  Deployments that rely on, for example, pinging
         the address owner's IPvX address may wish to configure
         accept-mode to 'true'.

         Note: IPv6 Neighbor Solicitations and Neighbor
         Advertisements MUST NOT be dropped when accept-mode
         is 'false'.";
    }
  } // vrrp-common-attributes

  grouping vrrp-ipv4-attributes {
    description
      "Group of VRRP attributes for IPv4.";
    uses vrrp-common-attributes;
    choice advertise-interval-choice {
      description
        "The options for the advertisement interval at which VRRPv2
         or VRRPv3 advertisements are sent from the specified
         interface.";
      case v2 {
        when "derived-from-or-self(version, 'vrrp:vrrp-v2')" {
          description
            "Applicable only to version 2.";
        }
        leaf advertise-interval-sec {
          type uint8 {
            range "1..254";
          }
          units "seconds";
          default "1";
          description
            "Configures the interval that VRRPv2 advertisements
             are sent from the specified interface.";
        }
      }
      case v3 {
        when "derived-from-or-self(version, 'vrrp:vrrp-v3')" {
          description
            "Applicable only to version 3.";
        }
        leaf advertise-interval-centi-sec {
          type uint16 {
            range "1..4095";
          }
          units "centiseconds";
          default "100";
          description
            "Configures the interval that VRRPv3 advertisements
             are sent from the specified interface.";
        }
      }
    } // advertise-interval-choice
    container track {
      description
        "Enables the specified VRRP instance to track interfaces
         or networks.";
      container interfaces {
        description
          "Enables the specified VRRPv2 or VRRPv3 instance to track
           interfaces.  Interface tracking prevents traffic loss by
           detecting the availability of interfaces.  The operational
           states of other interfaces are associated with the
           priority of a VRRP router.  When a tracked interface
           becomes unavailable (or 'operational down'), the priority
           of the VRRP router decrements.  When an unavailable
           interface becomes available again, the priority of the
           VRRP router is incremented by the same amount.";
        list interface {
          key "interface";
          description
            "Interface to track.";
          leaf interface {
            type if:interface-ref;
            must '/if:interfaces/if:interface[if:name=current()]/'
               + 'ip:ipv4' {
              description
                "Interface is IPv4.";
            }
            description
              "Interface to track.";
          }
          leaf priority-decrement {
            type uint8 {
              range "1..254";
            }
            default "10";
            description
              "Specifies how much to decrement the priority of the
               VRRP instance if the interface goes down.";
          }
        } // interface
      } // interfaces
      container networks {
        description
          "Enables the VRRPv2 or VRRPv3 router instance to track the
           specified networks through their IPv4 network prefixes.
           Network tracking prevents traffic loss by detecting
           network connectivity failure.  The states of
           connectivity to some networks are associated with the
           priority of a VRRP router.  When connectivity to a
           tracked network represented by its prefix is lost, the
           priority of the VRRP router decrements.  When an
           unavailable network is again reachable, the priority of
           the VRRP router is incremented by the same amount.";
        list network {
          key "prefix";
          description
            "Enables the specified VRRPv2 or VRRPv3 instance to
             track an IPv4 network by specifying the prefix of the
             IPv4 network.";
          leaf prefix {
            type inet:ipv4-prefix;
            description
              "The IPv4 prefix of the network to track.";
          }
          leaf priority-decrement {
            type uint8 {
              range "1..254";
            }
            default "10";
            description
              "Specifies how much to decrement the priority of the
               VRRP router if there is a failure in the IPv4
               network.";
          }
        } // network
      } // networks
    } // track
    container virtual-ipv4-addresses {
      description
        "Configures the virtual IPv4 address for the
         VRRP interface.";
      list virtual-ipv4-address {
        key "ipv4-address";
        max-elements 16;
        description
          "Virtual IPv4 addresses for a single VRRP instance.  For a
           VRRP owner router, the virtual address must match one
           of the IPv4 addresses configured on the interface
           corresponding to the virtual router.";
        leaf ipv4-address {
          type inet:ipv4-address;
          description
            "An IPv4 address associated with a virtual router.";
          reference
            "RFC 9568: Virtual Router Redundancy Protocol (VRRP)
                       Version 3 for IPv4 and IPv6,  Section 1.3";
        }
      } // virtual-ipv4-address
    } // virtual-ipv4-addresses
  } // vrrp-ipv4-attributes

  grouping vrrp-ipv6-attributes {
    description
      "Group of VRRP attributes for IPv6.";
    uses vrrp-common-attributes;
    leaf advertise-interval-centi-sec {
      type uint16 {
        range "1..4095";
      }
      units "centiseconds";
      default "100";
      description
        "Includes the interval that VRRPv3 advertisements
         are sent from the specified interface.";
    }
    container track {
      description
        "Enables the specified VRRP instance to track interfaces
         or networks.";
      container interfaces {
        description
          "Enables the specified VRRPv3 instance to track
           interfaces.  Interface tracking prevents traffic loss by
           detecting the availability of interfaces.  The operational
           states of other interfaces are associated with the
           priority of a VRRP router.  When a tracked interface
           becomes unavailable (or 'operational down'), the priority
           of the VRRP router decrements.  When an unavailable
           interface becomes available again, the priority of the
           VRRP router is incremented by the same amount.";
        list interface {
          key "interface";
          description
            "Interface to track.";
          leaf interface {
            type if:interface-ref;
            must '/if:interfaces/if:interface[if:name=current()]/'
               + 'ip:ipv6' {
              description
                "Interface is IPv6.";
            }
            description
              "Interface to track.";
          }
          leaf priority-decrement {
            type uint8 {
              range "1..254";
            }
            default "10";
            description
              "Specifies how much to decrement the priority of the
               VRRP instance if the interface goes down.";
          }
        } // interface
      } // interfaces
      container networks {
        description
          "Enables the VRRPv3 router instance to track the
           specified networks through their IPv6 network prefixes.
           Network tracking prevents traffic loss by detecting
           network connectivity failure.  The states of
           connectivity to some networks are associated with the
           priority of a VRRP router.  When connectivity to a
           tracked network represented by its prefix is lost, the
           priority of the VRRP router decrements.  When an
           unavailable network is again reachable, the priority of
           the VRRP router is incremented by the same amount.";
        list network {
          key "prefix";
          description
            "Enables the specified VRRPv3 instance to track an
             IPv6 network by specifying the prefix of the
             IPv6 network.";
          leaf prefix {
            type inet:ipv6-prefix;
            description
              "The IPv6 prefix of the network to track.";
          }
          leaf priority-decrement {
            type uint8 {
              range "1..254";
            }
            default "10";
            description
              "Specifies how much to decrement the priority of the
               VRRP router if there is a failure in the IPv6
               network.";
          }
        } // network
      } // networks
    } // track
    container virtual-ipv6-addresses {
      description
        "Configures the virtual IPv6 address for the
         VRRP interface.";
      list virtual-ipv6-address {
        key "ipv6-address";
        max-elements 16;
        description
          "Virtual IPv6 addresses for a single VRRP instance.  The
           first configured virtual address must be an IPv6
           link-local address. Subsequent IPv6 addresses can be
           IPv6 link-local or global addresses. For a VRRP owner
           router, the virtual address must match one of the IPv6
           global or link-local addresses associated with the
           interface corresponding to the virtual router.";
        leaf ipv6-address {
          type inet:ipv6-address;
          description
            "An IPv6 address associated with a virtual router.";
          reference
            "RFC 9568: Virtual Router Redundancy Protocol (VRRP)
                       Version 3 for IPv4 and IPv6, Section 1.4";
        }
      } // virtual-ipv6-address
    } // virtual-ipv6-addresses
  } // vrrp-ipv6-attributes

  grouping vrrp-state-attributes {
    description
      "Group of VRRP state attributes.";
    leaf state {
      type identityref {
        base vrrp:vrrp-state-type;
      }
      config false;
      description
        "Operational state.";
    }
    leaf is-owner {
      type boolean;
      config false;
      description
        "Set to 'true' if this virtual router is the owner.";
    }
    leaf effective-priority {
      type uint8 {
        range "1..255";
      }
      config false;
      description
        "The effective priority of the virtual router taking
         account address ownership and any modifications due to
         local policy. The priority 255 is reserved the virtual
         router owning the address.";
    }
    leaf last-adv-source {
      type inet:ip-address;
      config false;
      description
        "Last advertised IPv4/IPv6 source address.";
    }
    leaf up-datetime {
      type yang:date-and-time;
      config false;
      description
        "The date and time when this virtual router
         transitioned out of 'initialize' state.";
    }
    leaf active-down-interval {
      type uint32;
      units "centiseconds";
      config false;
      description
        "Time interval for the backup virtual router to declare
         'active down'.

         The identifier of this leaf is changed to reflect
         the updated terminology used in RFC 9568.";
    }
    leaf skew-time {
      type uint32;
      units "microseconds";
      config false;
      description
        "Calculated based on the priority and advertisement
         interval configuration command parameters. Note that
         the units are microseconds rather than centiseconds units
         as configured for advertisement-interval.";
      reference
        "RFC 9568: Virtual Router Redundancy Protocol (VRRP)
         Version 3 for IPv4 and IPv6, Section 6.1";
    }
    leaf last-event {
      type identityref {
        base vrrp:vrrp-event-type;
      }
      config false;
      description
        "Last reported event.";
    }
    leaf new-active-reason {
      type new-active-reason-type;
      config false;
      description
        "Indicates why the virtual router has transitioned to
         active state.

         The identifier of this leaf is changed to reflect
         the updated terminology used in RFC 9568.";
    }
    container statistics {
      config false;
      description
        "VRRP statistics.";
      leaf discontinuity-datetime {
        type yang:date-and-time;
        description
          "The time on the most recent occasion at which any one or
           more of the VRRP statistics counters suffered a
           discontinuity.  If no such discontinuities have occurred
           since the last re-initialization of the local management
           subsystem, then this node contains the time that the
           local management subsystem re-initialized itself.";
      }
      leaf active-transitions {
        type yang:counter64;
        description
          "The total number of times that this virtual router's
           state has transitioned to 'Active'.

           The identifier of this leaf is changed to reflect
           the updated terminology used in RFC 9568. The leaf type
           has also been updated to a 64-bit counter consistent
           with other VRRP counters.";
      }
      leaf advertisement-rcvd {
        type yang:counter64;
        description
          "The total number of VRRP advertisements received by
           this virtual router.";
      }
      leaf advertisement-sent {
        type yang:counter64;
        description
          "The total number of VRRP advertisements sent by
           this virtual router.";
      }
      leaf interval-errors {
        if-feature "validate-interval-errors";
        type yang:counter64;
        description
          "The total number of VRRP advertisement packets received
           with an advertisement interval different than the
           interval configured for the local virtual router.";
      }
      leaf priority-zero-pkts-rcvd {
        type yang:counter64;
        description
          "The total number of VRRP packets received by the
           virtual router with a priority of 0.";
      }
      leaf priority-zero-pkts-sent {
        type yang:counter64;
        description
          "The total number of VRRP packets sent by the
           virtual router with a priority of 0.";
      }
      leaf invalid-type-pkts-rcvd {
        type yang:counter64;
        description
          "The number of VRRP packets received by the virtual
           router with an invalid value in the 'type' field.";
      }
      leaf address-list-errors {
        if-feature "validate-address-list-errors";
        type yang:counter64;
        description
          "The total number of packets received with an
           address list that does not match the locally
           configured address list for the virtual router.";
      }
      leaf packet-length-errors {
        type yang:counter64;
        description
          "The total number of packets received with a packet
           length less than the length of the VRRP header.";
      }
    } // statistics
  } // vrrp-state-attributes

  grouping vrrp-global-state-attributes {
    description
      "Group of VRRP global state attributes.";
    leaf virtual-routers {
      type uint32;
      description
        "Number of configured virtual routers.";
    }
    leaf interfaces {
      type uint32;
      description
        "Number of interfaces with VRRP configured.";
    }
    container statistics {
      description
        "VRRP global statistics.";
      leaf discontinuity-datetime {
        type yang:date-and-time;
        description
          "The time on the most recent occasion at which any
           one or more of checksum-errors, version-errors,
           vrid-errors, or ip-ttl-errors suffered a
           discontinuity.

           If no such discontinuities have occurred since the last
           re-initialization of the local management subsystem,
           then this node contains the time that the local management
           subsystem re-initialized itself.";
      }
      leaf checksum-errors {
        type yang:counter64;
        description
          "The total number of VRRP packets received with an invalid
           VRRP checksum value.";
        reference
          "RFC 9568: Virtual Router Redundancy Protocol (VRRP)
           Version 3 for IPv4 and IPv6, Section 5.2.8.";
      }
      leaf version-errors {
        type yang:counter64;
        description
          "The total number of VRRP packets received with an unknown
           or unsupported version number.";
        reference
          "RFC 9568: Virtual Router Redundancy Protocol (VRRP)
           Version 3 for IPv4 and IPv6, Section 5.2.1.";
      }
      leaf vrid-errors {
        type yang:counter64;
        description
          "The total number of VRRP packets received with a VRID that
           is not valid for any virtual router on this router.";
        reference
          "RFC 9568: Virtual Router Redundancy Protocol (VRRP)
                     Version 3 for IPv4 and IPv6, Section 5.2.3.";
      }
      leaf ip-ttl-errors {
        type yang:counter64;
        description
          "The total number of VRRP packets received by the
           virtual router with IP TTL (IPv4) or Hop Limit (IPv6)
           not equal to 255.";
        reference
          "RFC 9568: Virtual Router Redundancy Protocol (VRRP)
                     Version 3 for IPv4 and IPv6,
                     Sections 5.1.1.3 and 5.1.2.3";
      }
    } // statistics
  } // vrrp-global-state-attributes

  /*
   * Configuration data and operational state data nodes
   */

  augment "/if:interfaces/if:interface/ip:ipv4" {
    description
      "Augments IPv4 interface.";
    container vrrp {
      description
        "Configures VRRP version 2 or 3 for IPv4.";
      list vrrp-instance {
        key "vrid";
        description
          "Defines a virtual router, identified by a VRID, within the
           IPv4 address space.";
        uses vrrp-ipv4-attributes;
        uses vrrp-state-attributes;
      }
    }
  } // augments ipv4

  augment "/if:interfaces/if:interface/ip:ipv6" {
    description
      "Augments IPv6 interface.";
    container vrrp {
      description
        "Configures VRRP version 3 for IPv6.";
      list vrrp-instance {
        must "derived-from-or-self(version, 'vrrp:vrrp-v3')" {
          description
            "IPv6 is only supported by version 3.";
        }
        key "vrid";
        description
          "Defines a virtual router, identified by a VRID, within the
           IPv6 address space.";
        uses vrrp-ipv6-attributes;
        uses vrrp-state-attributes;
      }
    }
  } // augments ipv6

  container vrrp {
    config false;
    description
      "VRRP data at the global level.";
    uses vrrp-global-state-attributes;
  }

  /*
   * Notifications
   */

  notification vrrp-new-active-event {
    description
      "Notification event for the election of a new VRRP
       active router.

       The identifier of the notification is changed to
       reflect the updated terminology used in RFC 9568.";
    leaf active-ip-address {
      type inet:ip-address;
      mandatory true;
      description
        "IPv4 or IPv6 address of the new VRRP active router.

         The identifier of the leaf is changed to
         reflect the updated terminology used in RFC 9568.";
    }
    leaf new-active-reason {
      type new-active-reason-type;
      mandatory true;
      description
        "Indicates why the virtual router has transitioned to
         active state.
         The identifier of the leaf is changed to
         reflect the updated terminology used in RFC 9568.";
    }
  }

  notification vrrp-protocol-error-event {
    description
      "Notification event for a VRRP protocol error.";
    leaf protocol-error-reason {
      type identityref {
        base vrrp:vrrp-error-global;
      }
      mandatory true;
      description
        "Indicates the reason for the protocol error.";
    }
  }

  notification vrrp-virtual-router-error-event {
    description
      "Notification event for an error that happened on a
       virtual router.";
    leaf interface {
      type if:interface-ref;
      mandatory true;
      description
        "Indicates the interface on which the event has occurred.";
    }
    choice ip-version {
      mandatory true;
      description
        "The error may have happened on either an IPv4 virtual
         router or an IPv6 virtual router.  The information
         related to a specific IP version is provided by one of
         the following cases.";
      case ipv4 {
        description
          "IPv4.";
        container ipv4 {
          description
            "Error information for IPv4.";
          leaf vrid {
            type leafref {
              path "/if:interfaces/if:interface"
                 + "[if:name = current()/../../vrrp:interface]/"
                 + "ip:ipv4/vrrp:vrrp/vrrp:vrrp-instance/vrrp:vrid";
            }
            mandatory true;
            description
              "Indicates the virtual router on which the event has
               occurred.";
          }
        }
      }
      case ipv6 {
        description
          "IPv6.";
        container ipv6 {
          description
            "Error information for IPv6.";
          leaf vrid {
            type leafref {
              path "/if:interfaces/if:interface"
                 + "[if:name = current()/../../vrrp:interface]/"
                 + "ip:ipv6/vrrp:vrrp/vrrp:vrrp-instance/vrrp:vrid";
            }
            mandatory true;
            description
              "Indicates the virtual router on which the event has
               occurred.";
          }
        }
      }
    }
    leaf virtual-router-error-reason {
      type identityref {
        base vrrp:vrrp-error-virtual-router;
      }
      mandatory true;
      description
        "Indicates the reason for the virtual router error.";
    }
  }
}
