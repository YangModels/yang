module ietf-multicast-service {

 namespace "urn:ietf:params:xml:ns:yang:ietf-multicast-service";

 prefix multicast-service;

 import ietf-routing {
     prefix "rt";
 }
 import ietf-yang-types {
     prefix "yang";
 }
 import ietf-inet-types {
     prefix "inet";
 }

 organization " IETF MBONED( MBONE Deployment ) Working Group";
 contact
     "WG List:  <mailto:bier@ietf.org>
      WG Chair: Greg Shepherd
                <mailto:gjshep@gmail.com>
      WG Chair: Leonard Giuliano
                <mailto:lenny@juniper.net>

      Editor:   Zheng Zhang
                <mailto:zhang.zheng@zte.com.cn>
      Editor:   Cui Wang
                <mailto:wang.cui1@zte.com.cn>
     ";

 description
     "This module contains a collection of YANG definitions for
      managing multicast service.";

 revision 2016-02-29 {
     description
     "Initial version.";
     reference "https://tools.ietf.org/html/draft-zhang-mboned-mservice-yang";
 }
/*feature*/
    grouping general-multicast {
        description "The general multicast address information.";
        leaf source-address {
            type inet:ip-address;
            mandatory true;
            description "The address of multicast source. The value set to zero
              means that the receiver interests in all source that relevant to
              one group.";
        }
        leaf source-wildcard {
            type uint8;
            description "The wildcard information of source.";
        }
        leaf group-address {
            type inet:ip-address;
            mandatory true;
            description "The address of multicast group.";
        }
        leaf group-wildcard {
            type uint8;
            description "The wildcard information of group.";
        }
    }

        grouping m-addr {
        description "The vpn multicast information.";
        leaf vpn-id {
            type uint32;
            mandatory true;
            description "The vpn-id of the multicast flow.
              If there is global instance, the vpnid value should be zero.";
        }
        uses general-multicast;
    }

    typedef virtual-type {
        type enumeration {
            enum "vxlan" {
                description "The vxlan type.";
            }
            enum "virtual subnet" {
                description "The nvgre type";
            }
            enum "vni" {
                description "The geneve type";
            }
        }
        description "The collection of virtual network type.";
    }

    grouping multicast-nvo3 {
        description "The nvo3 multicast information.";
        leaf vni-type {
            type virtual-type;
            mandatory true;
            description "The type of virtual network identifier. Such as the Vxlan
              NVGRE and Geneve.";
        }
        leaf vni-value {
            type uint32;
            mandatory true;
            description "The value of Vxlan network identifier, virtual subnet ID
            or virtual net identifier.";
        }
    }

    grouping multicast-feature {
        description
          "This group describes the different multicast information
           in various deployments.";
        choice feature-type {
            mandatory true;
            case pure-multicast {
                uses m-addr;
            }
            case nvo3 {
                uses multicast-nvo3;
            }
            description "The collection of all possible multicast feature.";
        }
    }

    grouping ip-node {
        description "The IP information of multicast nodes.";
        leaf ingress-node {
            type inet:ip-address;
            mandatory true;
            description "The ingress node of multicast flow. Or the ingress
              node of MVPN and BIER. In MVPN, this is the address of ingress
              PE; in BIER, this is the BFR-prefix of ingress node.";
        }

        list egress-node {
            key "number";
            description "This ID information of one adjacency.";
            leaf number {
                type uint32;
                mandatory true;
                description "The number of egress nodes.";
            }
            leaf egress-node {
                type inet:ip-address;
                mandatory true;
                description
                  "The egress multicast node of multicast flow.
                  Or the egress node of MVPN and BIER. In MVPN, this is the
                  address of egress PE; in BIER, this is the BFR-prefix of
                  egress node.";
            }
        }
    }
    /* should import from BIER yang */
    typedef bfr-id {
        type uint16;
        description "The BFR id of node.";
    }

    typedef si {
        type uint16;
        description
          "The type for set identifier";
    }

    typedef sub-domain-id {
        type uint16;
        description
          "The type for sub-domain-id";
    }

    typedef bit-string {
        type uint16;
        description
          "The bit mask of one bitstring.";
    }

    grouping bier-node {
        description "The BIER information of multicast nodes.";
        leaf sub-domain {
            type sub-domain-id;
            mandatory true;
            description "The sub-domain that this multicast flow belongs to.";
        }
        leaf ingress-node {
            type bfr-id;
            mandatory true;
            description "The ingress node of multicast flow. This is the
              BFR-id of ingress node.";
        }
        list egress-node {
            key "number";
            description "This ID information of one adjacency.";
            leaf number {
                type uint32;
                mandatory true;
                description "The number of egress nodes.";
            }
            leaf egress-node {
                type bfr-id;
                mandatory true;
                description
                  "The egress multicast node of multicast flow.
                  This is the BFR-id of egress node.";
            }
        }
    }

    grouping overlay-tech {
        description "The possible overlay technologies for multicast service.";
        choice overlay-tech-type {
            mandatory true;
            case mld {
                description "MLD technology is used for multicast overlay";
            }
            case mvpn {
                description "MVPN technology is used for multicast overlay";
            }
            description "The collection of multicast overlay technology";
        }
    }

    grouping multicast-overlay {
        description "The node information that connect the ingress multicast
          flow, and the nodes information that connect the egress multicast
          flow.";
        uses multicast-feature;
        container nodes-information {
            description "The ingress and egress nodes information.";
            uses ip-node;
        }
        container bier-information {
            description "The ingress and egress BIER nodes information.";
            uses bier-node;
        }
        container overlay-technology {
            description "The possible overlay technologies for multicast service.";
            uses overlay-tech;
        }
    }

/*transport*/

    typedef bier-encap-type {
        type enumeration {
            enum "mpls" {
                description "The mpls forwarding function is used in BIER.";
            }
        }
        description "The encapsulation type of BIER transportion.";
    }
    grouping transport-bier {
        description "The BIER transport information.";
        leaf sub-domain {
            type sub-domain-id;
            mandatory true;
            description "The subdomain id that this multicast flow belongs to.";
        }
        choice encap-type {
            mandatory true;
            case mpls {
                description "The BIER forwarding depends on mpls.";
            }
            description "The encapsulation type in BIER.";
        }
         leaf bitstringlength {
            type uint16;
            description "The bitstringlength used by BIER forwarding.";
        }
        leaf set-identifier {
            type si;
            description "The set identifier used by this multicast flow, especially in BIER TE.";
        }
        leaf ecmp {
            type boolean;
            description "The capability of ECMP.";
        }
        leaf frr {
            type boolean;
            description "The capability of fast re-route.";
        }
    }

    grouping transport-pim {
        description "The requirement information of pim transportion.";
        leaf graceful-restart {
            type boolean;
            description "The capability of graceful restart.";
        }
        leaf bfd {
            type boolean;
            description "The capability of bfd.";
        }
    }

    grouping tunnel-feature {
        description "The tunnel feature.";
        leaf tunnel-id {
            type uint32;
            description "The tunnel id that corresponds this flow.";
        }
        leaf frr {
            type boolean;
            description "The capability of fast re-route.";
        }
        leaf backup-tunnel {
            type boolean;
            description "The capability of backup tunnel.";
        }
    }

    grouping transport-mpls {
        description "The mpls transportion information.";
        choice mpls-tunnel-type {
            case mldp {
                uses tunnel-feature;
                description "The mldp tunnel.";
            }
            case p2mp-te {
                uses tunnel-feature;
                description "The p2mp te tunnel.";
            }
            description "The collection types of mpls tunnels";
        }
    }

    grouping cisco-multicast {
        description "The Cisco MDT multicast information in RFC6037.";
        leaf p-group {
            type inet:ip-address;
            mandatory true;
            description "The address of p-group.";
        }
    }
        grouping transport-cisco-mode {
        description "The transport information of Cisco mode, RFC6037.";
        uses cisco-multicast;
        uses transport-pim;
    }

    grouping multicast-transport {
        description "The transport information of multicast service.";
        choice transport-type {
            mandatory true;
            case bier {
                uses transport-bier;
            }
            case cisco-mode {
                uses transport-cisco-mode;
            }
            case mpls {
                uses transport-mpls;
            }
            case pim {
                uses transport-pim;
            }
            description "The collection of all possible multicast transport technology.";
        }
    }

/*underlay*/
    grouping underlay-bgp {
        description "Underlay information of BGP.";
    }

    grouping underlay-ospf {
        description "Underlay information of OSPF.";
        leaf topology-id {
            type uint16;
            description "The topology id of ospf instance.";
        }
    }

    grouping underlay-isis {
        description "Underlay information of ISIS.";
        leaf topology-id {
            type uint16;
            description "The topology id of isis instance.";
        }
    }

    grouping underlay-pim {
        description "Underlay information of PIM.";
        /* If there are some necessary information should be defined? */
    }

    grouping multicast-underlay {
        description "The underlay information relevant multicast service.";
        leaf underlay-requirement {
            type boolean;
            description "Whether the underlay technology should be required.";
        }
        choice underlay-type {
            mandatory true;
            case bgp {
                uses underlay-bgp;
            }
            case ospf {
                uses underlay-ospf;
            }
            case isis {
                uses underlay-isis;
            }
            case pim {
                uses underlay-pim;
            }
            description "The collection of all possible multicast underlay technology.";
        }
    }

    container multicast-service {
        description "The model of multicast service. Include overlay, transport and underlay.";
        container multicast-overlay {
            description "The overlay information of multicast service.";
            uses multicast-overlay;
        }
        container multicast-transport {
            description "The transportion of multicast service.";
            uses multicast-transport;
        }
        container multicast-underlay {
            description "The underlay of multicast service.";
            uses multicast-underlay;
        }
    }

}
