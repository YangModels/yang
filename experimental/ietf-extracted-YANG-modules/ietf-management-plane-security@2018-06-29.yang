module ietf-management-plane-security {
  yang-version 1.1;
  namespace "urn:ietf:params:xml:ns:yang:ietf-management-plane-security";
  prefix mp-sec;

  import ietf-inet-types {
    prefix inet;
      reference "RFC 6991 - Common YANG Data Types.";
  }
  import ietf-yang-types {
    prefix yang;
    reference
      "RFC 6991 - Common YANG Data Types.";
  }

  import ietf-tls-server {
    prefix tlss;
      reference "draft-ietf-netconf-tls-client-server";
    }

  import ietf-ssh-server {
    prefix sshs;
      reference "draft-ietf-netconf-ssh-client-server";
    }

  organization
    "IETF SACM (Security Automation and Continuous Monitoring) Working Group";

  contact
    "WG Web: http://tools.ietf.org/wg/sacm/
    WG List: sacm@ietf.org

    Editor: Qiushi Lin
            linqiushi@huawei.com;
    Editor: Liang Xia
            frank.xialiang@huawei.com
        Editor: Henk Birkholz
            henk.birkholz@sit.fraunhofer.de";

  description
    "This YANG module defines groupings that are used by ietf-management-plane-security YANG module. Their usage is not limited to ietf-management-plane-security and can be used anywhere as applicable.";

  revision 2018-06-29 {
    description "Initial version.";
        reference "draft-lin-sacm-nid-mp-security-baseline-03";
  }

  /*
  * features
  */
  feature web-interface {
    description "The network device supports web interface for administrator to manage itself.";
  }

  feature ip-block-config {
    description "Whether the network device supports the configuration of ip block function.";
  }
  feature display-online-info {
    description "Whether the device supports providing a list of online administrators.";
  }

  /*
  * typedefs
  */
  typedef auth-mode-type {
    type enumeration {
      enum "none" {
        description "Authentication mode: none.";
      }
      enum "password" {
        description "Authentication mode: password.";
      }
      enum "aaa" {
         description "Authentication mode: aaa.";
      }
    }
    description "The Authentication mode of console and vty interface.";
   }

  typedef aaa-authen-mode {
    type enumeration {
      enum "invalid" {
        description "Invalid authentication mode.";
      }
      enum "local" {
        description "Local authentication mode.";
      }
      enum "tacacs" {
        description "TACACS authentication mode. ";
      }
      enum "radius" {
        description "RADIUS authentication mode. ";
       }
      enum "none" {
        description "In this mode, users can pass with authentication.";
      }
      enum "radius-proxy" {
        description "RADIUS proxy authentication mode.";
      }
    }
    description "Diffrent types of authentication modes.";
  }

  typedef radius-authen-type {
    type enumeration {
      enum "pap" {
        description "PAP authentication";
      }
      enum "chap" {
        description "CHAP authentication.";
      }
    }
    description "Different authentication types of RADIUS authentication.";
  }

  typedef aaa-author-mode {
    type enumeration {
      enum "invalid" {
        description "Invalid authorization mode.";
      }
      enum "local" {
        description "Local authorization mode.";
      }
      enum "tacacs" {
        description "TACACS authorization mode.";
      }
      enum "if-authenticated" {
        description "If-authenticated mode: If users pass the authentication and the authentication is not in this mode, it indicates that the user authorization is passed. Otherwise, the authorization is not passed.";
      }
      enum "none" {
        description "Users can pass without authorization.";
      }
    }
    description "Different types of AAA authorization modes.";
  }

  typedef aaa-cmd-author-mode {
    type enumeration {
      enum "invalid" {
        description "Invalid command line authorization mode.";
      }
      enum "local" {
        description "Local command line authorization mode.";
      }
      enum "tacacs" {
        description "Specifies that the TACACS mode is applied.";
      }
    }
    description "Different types of command line authorization modes.";
  }

  typedef aaa-account-mode {
    type enumeration {
      enum "invalid" {
        description "invalid accounting mode.";
      }
      enum "radius" {
        description "RADIUS accounting mode. ";
      }
      enum "tacacs" {
        description "TACACS accounting mode. ";
      }
      enum "none" {
        description "In this mode, users do not be accounting.";
      }
    }
    description "Different types of accounting modes.";
  }

  typedef ip-block-state-type {
    type enumeration {
      enum "authenfail" {
        description "Authentication fialed State";
      }
      enum "blocked" {
        description "BLOCKED State";
      }
    }
    description "The status of an login failed IP address";
  }

  /*
  * groupings
  */
  grouping ssh-security-hardening {
    leaf ssh-server-port {
      type inet:port-number;
      description "The port number of SSH server.";
    }
    leaf ssh-rekey-interval {
      type uint32;
      description "The interval for updating the key pair of the SSH server.";
    }
    leaf ssh-timeout {
      type uint32;
      description "The authentication timeout period of SSH.";
    }
    leaf ssh-retry-times {
      type uint32;
      description "The authentication retry times.";
    }
    leaf ssh-compatible-ssh1x-enable {
      type boolean;
      description "The status of version-compatible function on the SSH server: enabled, disabled.";
    }
    leaf ssh-server-interface {
      type string;
      description "The source interface of SSH server.";
    }
    leaf ip-block-enable {
      type boolean;
      description "The status of ip block function: enabled, or disabled.";
    }
    container ip-block-limit {
      if-feature ip-block-config;
      leaf failed-times {
        type uint64;
                description "The failed times in a certain perid.";
      }
      leaf peroid {
        type uint64;
                description "The certain period in which the failed times are counted.";
      }
      leaf reactive-time {
        type uint64;
                description "The reactive time after which the address is not blocked.";
      }
      description "If the login from an address failed several times in a certain period, this address will be blocked for a certain time range.";
    }
        description "A set of SSH configuration status to enhance security.";
  }

  /*
  * admin-security-policy
  */
  container admin-security-policy {
    container account-sec-policy {
      leaf security-policy {
        type boolean;
        description "The status of account security policy: enabled, or disabled.";
      }
      leaf account-aging-period {
        type uint64;
        description "The aging period of an administrator.";
      }
      leaf account-name-minlen {
        type uint64;
        description "The minimum length of an administrator account name";
      }
      description "Get configuration data about administrator account security policy.";
    }
    container pwd-sec-policy {
      leaf expire-days {
        type uint64;
        description "The password validity period.";
      }
      leaf prompt-days {
        type uint64;
        description "The period for advance warning before the password expires.";
      }
      leaf change-check {
        type boolean;
        description "The status of mandatory password change when a password is used for the first time: enabled, or disabled.";
      }
      leaf complexity-check {
        type boolean;
        description "The status of password complexity check: enable, or disable.";
      }
      leaf history-pwd-num {
        type uint64;
        description "The newly configured password should not be the same as the several past passwords.";
      }
      leaf pwd-minlen {
        type uint64;
        description "The minimum length of a password.";
      }
      description "Get configuration data about password security policy.";
    }
    container forbidden-word-rules {
      list forbidden-word-rule {
        key "forbidden-word";
        leaf forbidden-word {
          type string;
          description "A forbidden word in password.";
        }
        description "A list of forbidden words that are not allowed to be used in password.";
      }
      description "Password blacklist.";
    }
    container login-failed-limit {
      leaf failed-times {
        type uint64;
                description "The failed time in a certain period.";
      }
      leaf peroid {
        type uint64;
                description "The certain period in which the failed times are counted.";
      }
      leaf reactive-time {
        type uint64;
                description "The reactive time after which the account is not blocked.";
      }
      description "If an account login failed several times in a certain period, this account will be blocked for a certain time range.";
    }
    description "Get configuration data about administrator security policy.";
  }

  /*
  * admin-login-security
  */
  grouping admin-login-security {
    container console {
      leaf auth-mode {
        type auth-mode-type;
        description "The authentication mode used when administrator login through console interface: none, password, AAA.";
      }
      leaf privilege-level {
        type uint8;
        description "User privilege level.";
      }
      description "Status of security contorls for console interface.";
    }
    container vtys {
      list vty {
        key "vty-number";
        leaf vty-number {
          type uint8;
          description "The number of the vty interface.";
        }
        leaf auth-mode {
          type auth-mode-type;
          description "The authentication mode used when administrator login through vty interface: none, password, AAA.";
        }
        leaf privilege-level {
          type uint8;
          description "User privilege level.";
        }
        leaf-list acl-name-list {
          type string;
          description "The name of the acl.";
        }
        leaf ip-block-enable {
          type boolean;
          description "The status of ip block function: enabled, or disabled.";
        }
        container ip-block-limit {
          if-feature ip-block-config;
                  leaf failed-times {
            type uint64;
                    description "The failed times in a certain perid.";
          }
          leaf peroid {
            type uint64;
                    description "The certain period in which the failed times are counted.";
          }
          leaf reactive-time {
            type uint64;
                    description "The reactive time after which the address is not blocked.";
          }
          description "If the login from an address failed several times in a certain period, this address will be blocked for a certain time range.";
        }
                description "A list of vty interface configuration status.";
      }
      description "Configuration status of security contorls for vty interface.";
    }
    container telnet {
      leaf telnet-ipv4-enable {
        type boolean;
        description "The status of ipv4 telnet server: enabled, or disabled.";
      }
      leaf telnet-ipv4-server-port {
        type inet:port-number;
        description "The port number of ipv4 telnet server.";
      }
      leaf telnet-ipv6-enable {
        type boolean;
        description "The status of ipv6 telnet server: enabled, or disabled.";
      }
      leaf telnet-ipv6-server-port {
        type inet:port-number;
        description "The port number of ipv6 telnet server.";
      }
      leaf telnet-server-interface {
        type string;
        description "The source interface of telnet server.";
      }
      leaf-list acl-name-list {
        type string;
        description "The name of the acl.";
      }
      leaf ip-block-enable {
        type boolean;
        description "Whether the ip block function is enabled: enabled, disabled.";
      }
      container ip-block-limit {
        if-feature ip-block-config;
        leaf failed-times {
          type uint64;
                  description "The failed times in a certain perid.";
        }
        leaf peroid {
          type uint64;
                  description "The certain period in which the failed times are counted.";
        }
        leaf reactive-time {
          type uint64;
                  description "The reactive time after which the address is not blocked.";
        }
        description "If the login from an address failed several times in a certain period, this address will be blocked for a certain time range.";
      }
      description "Configuration status of security contorls for telnet login.";
    }
    container ssh {
      leaf ssh-enable {
        type boolean;
        description "The status of SSH server: enabled, or disabled.";
      }
      uses sshs:ssh-server-grouping;
      uses ssh-security-hardening;
      description "Configuration status of security contorls for SSH login.";
    }
    container web {
      if-feature web-interface;
      uses tlss:tls-server-grouping;
      leaf auth-mode {
        type auth-mode-type;
        description "The authentication mode used when administrator login through web interface: none, password, AAA.";
      }
      leaf privilege-level {
        type uint8;
        description "User privilege level.";
      }
      leaf http-server-interface {
        type string;
        description "The source interface of web server.";
      }
      leaf https-ipv4-enable {
        type boolean;
        description "The status of ipv4 https server: enabled, disabled.";
      }
      leaf https-ipv6-enable {
        type boolean;
        description "The status of ipv6 https server: enabled, disabled.";
      }
      leaf https-source-port {
        type inet:port-number;
        description "The port number of web server.";
      }
      leaf https-timeout {
        type uint32;
        description "The authentication timeout period of https.";
      }
      leaf ip-block-enable {
        type boolean;
        description "The status of ip block function: enabled, or disabled.";
      }
      container ip-block-limit {
        if-feature ip-block-config;
        leaf failed-times {
          type uint64;
                  description "The failed times in a certain perid.";
        }
        leaf peroid {
          type uint64;
                  description "The certain period in which the failed times are counted.";
        }
        leaf reactive-time {
          type uint64;
                  description "The reactive time after which the address is not blocked.";
        }
        description "If the login from an address failed several times in a certain period, this address will be blocked for a certain time range.";
      }
      description "If the network device supports web interface. The configuration status of the web server.";
    }
    description "Configuration status of different types of login interfaces.";
  }

  container aaa-security {
    list authentication-scheme {
      key "authen-scheme-name";
      leaf authen-scheme-name {
        type string;
        description "The name of the authentication scheme.";
      }
      leaf-list authen-mode {
        type aaa-authen-mode;
        description "A list of authentication modes with different preference level. The second, third, and the following authentication mode is used only when the first authentication mode does not respond.";
      }
      leaf authen-type {
        type radius-authen-type;
        description "Authentication type of RADIUS: PAP, CHAP.";
      }
      leaf authen-fail-policy {
        type boolean;
        description "The policy to be adopted after user authentication fail: force the user to be offline, allow user login to a domain with access control.";
      }
      description "Authentication scheme list.";
    }
    list authorization-scheme {
      key "author-scheme-name";
      leaf author-scheme-name {
        type string;
        description "The name of the authorization scheme.";
      }
      leaf-list auhtor-mode {
        type aaa-author-mode;
        description "A list of authorization modes with different preference level. The second, third, and the following authorization mode is used only when the first authorization mode does not respond.";
      }
      leaf-list cmd-auhtor-mode {
        type aaa-cmd-author-mode;
        description "A list of command line authorization modes with different preference level. The second, third, and the following command line authorization mode is used only when the first command line authorization mode does not respond.";
      }
      description "Authorization scheme list.";
    }
    list accounting-scheme {
      key "account-scheme-name";
      leaf account-scheme-name {
        type string;
        description "The name of the accounting scheme.";
      }
      leaf account-mode {
        type aaa-account-mode;
        description "Accounting mode.";
      }
      description "Accounting scheme list.";
    }
    container radius-security {
      list radius-authen-servers {
        key "address";
        leaf address {
          type inet:host;
          description "The ip address of the authentication server.";
        }
        leaf port {
          type inet:port-number;
          description "The port number of the authentication server.";
        }
                description "A list of RADIUS authentication servers";
      }
      list radius-author-servers {
        key "address";
        leaf address {
          type inet:host;
          description "The ip address of the authorization server.";
        }
        leaf port {
          type inet:port-number;
          description "The port number of the authorization server.";
        }
                description "A list of RADIUS authorization servers";
      }
      list radius-account-servers {
        key "address";
        leaf address {
          type inet:host;
          description "The ip address of the accounting server.";
        }
        leaf port {
          type inet:port-number;
          description "The port number of the accounting server.";
        }
                description "A list of RADIUS accounting servers";
      }
      description "RADIUS authentication servers, authorization servers and accounting servers.";
    }
    container tacacs-security {
      list tacacs-authen-servers {
        key "address";
        leaf address {
          type inet:host;
          description "The ip address of the authentication server.";
        }
        leaf port {
          type inet:port-number;
          description "The port number of the authentication server.";
        }
        description "A list of TACACS+ and TACACS+ compatible authentication servers";
      }
      list tacacs-author-servers {
        key "address";
        leaf address {
          type inet:host;
          description "The ip address of the authorization server.";
        }
        leaf port {
          type inet:port-number;
          description "The port number of the authorization server.";
        }
        description "A list of TACACS+ and TACACS+ compatible authorization servers";
      }
      list tacacs-account-servers {
        key "address";
        leaf address {
          type inet:host;
          description "The ip address of the accounting server.";
        }
        leaf port {
          type inet:port-number;
          description "The port number of the accounting server.";
        }
                description "A list of TACACS+ and TACACS+ compatible accounting servers";
      }
      description "TACACS+ and TACACS+ compatible authentication servers, authorization servers, and accounting servers.";
    }
    description "Configuration status of AAA.";
  }

  container admin-access-statistics {
    config false;
    leaf total-online-users {
      type uint32;
      config false;
      description "The number of administrators that are current online.";
    }
    container online-admin-list {
      if-feature display-online-info;
      config false;
      list online-users {
        key "account-name";
        leaf account-name {
          type string;
          config false;
          description "The account name of the online account.";
        }
        leaf ip-address {
          type inet:ip-address-no-zone;
          config false;
                  description "The ip address of the online account.";
        }
        leaf mac-address {
          type yang:mac-address;
          config false;
                  description "The MAC address of the online account.";
        }
        description "Online adminstrator list.";
      }
      description "If the device supports providing information of online administrators, a list of account details are provided.";
    }
    description "online administrator lists, ip addresses authentication failure or blocked ip addresses. ";
  }
}
