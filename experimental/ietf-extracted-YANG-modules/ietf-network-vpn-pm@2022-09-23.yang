module ietf-network-vpn-pm {
  yang-version 1.1;
  namespace "urn:ietf:params:xml:ns:yang:ietf-network-vpn-pm";
  prefix nvp;

  import ietf-yang-types {
    prefix yang;
    reference
      "RFC 6991: Common YANG Types";
  }
  import ietf-vpn-common {
    prefix vpn-common;
    reference
      "RFC 9181: A Common YANG Data Model for Layer 2 and
       Layer 3 VPNs.";
  }
  import ietf-network {
    prefix nw;
    reference
      "RFC 8345: A YANG Data Model for Network
       Topologies, Section 6.1";
  }
  import ietf-network-topology {
    prefix nt;
    reference
      "RFC 8345: A YANG Data Model for Network
       Topologies, Section 6.2";
  }
  import ietf-lime-time-types {
    prefix lime;
    reference
      "RFC 8532: Generic YANG Data Model for the Management of
       Operations, Administration, and Maintenance (OAM) Protocols
       That Use Connectionless Communications";
  }

  organization
    "IETF OPSAWG (Operations and Management Area Working Group)";
  contact
    "WG Web:   <https://datatracker.ietf.org/wg/opsawg/>
     WG List:  <mailto:opsawg@ietf.org>

     Editor: Bo Wu
          <lana.wubo@huawei.com>
     Editor: Mohamed Boucadair
          <mohamed.boucadair@orange.com>
     Editor: Qin Wu
          <bill.wu@huawei.com>
     Author: Oscar Gonzalez de Dios
          <oscar.gonzalezdedios@telefonica.com>
     Author: Bin Wen
          <bin_wen@comcast.com>";
  description
    "This module defines a model for Network and VPN Service
     Performance monitoring.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
        (https://trustee.ietf.org/license-info).

     This version of this YANG module is part of RFC XXXX
     (https://www.rfc-editor.org/info/rfcXXXX); see the RFC itself
     for full legal notices.";

  // RFC Ed.: update the date below with the date of RFC
  // publication and remove this note.
  // RFC Ed.: replace XXXX with actual RFC number and remove
  // this note.

  revision 2022-09-23 {
    description
      "Initial revision.";
    reference
      "RFC XXXX: A YANG Model for Network and VPN Service
       Performance Monitoring";
  }

  identity node-type {
    description
      "Base identity for node type";
  }

  identity pe {
    base node-type;
    description
      "Provider Edge (PE) node type. A PE is the device
       or set of devices at the edge of the provider network with the
       functionality that is needed to interface with the customer.";
  }
  identity p {
    base node-type;
    description
      "Provider router node type. That is, a router
       in the core network that does not have interfaces
       directly toward a customer.";
  }

  identity asbr {
    base node-type;
    description
      "Autonomous System Border Router (ASBR) node type.";
    reference
      "RFC 4364: BGP/MPLS IP Virtual Private Networks (VPNs)";
  }

  identity pm-source-type {
    description
      "Base identity from which specific performance monitoring
       mechanism types are derived.";
  }

  identity pm-source-bgpls {
    base pm-source-type;
    description
      "Indicates BGP-LS as the performance monitoring metric source";
    reference
      "RFC 8571: BGP - Link State (BGP-LS) Advertisement of
        IGP Traffic Engineering Performance Metric Extensions";
  }

  identity pm-source-owamp {
    base pm-source-type;
    description
      "Indicates One-Way Active Measurement Protocol(OWAMP)
       as the performance monitoring metric source.";
    reference
      "RFC 4656: A One-Way Active Measurement Protocol (OWAMP)";
  }

  identity pm-source-twamp {
    base pm-source-type;
    description
      "Indicates Two-Way Active Measurement Protocol(TWAMP)
       as the performance monitoring metric source.";
    reference
      "RFC 5357: A Two-Way Active Measurement Protocol (TWAMP)";
  }
  identity pm-source-stamp {
    base pm-source-type;
    description
      "Indicates Simple Two-way Active Measurement Protocol(STAMP)
       as the performance monitoring metric source.";
    reference
      "RFC 8762: Simple Two-Way Active Measurement Protocol";
  }

  identity pm-source-y-1731 {
    base pm-source-type;
    description
      "Indicates Ethernet OAM Y.1731 as the performance monitoring
       metric source.";
    reference
      "ITU-T Y.1731: Operations, administration and
       maintenance (OAM) functions and mechanisms
       for Ethernet-based networks";
  }

  identity pm-type {
    description
      "Base identity for PM type.";
  }

  identity pm-type-network-link {
    base pm-type;
    description
      "Indicates that the PM type is for the link in
       the network topology.";
  }

  identity pm-type-vpn-inter-access {
    base pm-type;
    description
      "Indicates that the PM type is for logical point-to-point VPN
       connections between a source and a destination VPN access
       interfaces.";
  }

  identity pm-type-vpn-tunnel {
    base pm-type;
    description
      "Indicates that the PM type is for VPN tunnels.";
  }

  typedef percentage {
    type decimal64 {
      fraction-digits 5;
      range "0..100";
    }
    description
      "Percentage to 5 decimal places.";
  }

  typedef percentile {
    type decimal64 {
      fraction-digits 3;
      range "0..100";
    }
    description
      "The percentile is a value between 0 and 100
       to 2 decimal places, e.g. 10.00, 99.90 ,99.99 etc..
       For example, for a given one-way delay measurement,
       if the percentile is set to 95.00 and the 95th percentile
       one-way delay is 2 milliseconds, then the 95 percent of
       the sample value is less than or equal to 2 milliseconds.";
  }

  grouping entry-summary {
    description
      "Entry summary grouping used for network topology
       augmentation.";
    container entry-summary {
      config false;
      description
        "Container for VPN or network entry summary.";
      container ipv4-num {
        leaf maximum-routes {
          type uint32;
          description
            "Indicates the maximum number of IPv4 routes
             for the VPN or network.";
        }
        leaf total-active-routes {
          type uint32;
          description
            "Indicates total active IPv4 routes
             for the VPN or network.";
        }
        description
          "IPv4-specific parameters.";
      }
      container ipv6-num {
        leaf maximum-routes {
          type uint32;
          description
            "Indicates the maximum number of IPv6 routes
             for the VPN or network.";
        }
        leaf total-active-routes {
          type uint32;
          description
            "Indicates total active IPv6 routes
             for the VPN or network.";
        }
        description
          "IPv6-specific parameters.";
      }
      container mac-num {
        leaf mac-num-limit {
          type uint32;
          description
            "Indicates the maximum number of MAC entries
             for the VPN or network.";
        }
        leaf total-active-mac-num {
          type uint32;
          description
            "Indicates the total active MAC entries
             for the VPN or network.";
        }
        description
          "MAC statistics.";
      }
    }
  }

  grouping link-loss-statistics {
    description
      "Grouping for per link error statistics.";
    container loss-statistics {
      description
        "One-way link loss summarized information.";
      reference
        "RFC 4656: A One-way Active Measurement Protocol (OWAMP)
         ITU-T Y.1731: Operations, administration and
         maintenance (OAM) functions and mechanisms
         for Ethernet-based networks";
      leaf packet-loss-count {
        type yang:counter64;
        description
          "Total number of lost packets.";
      }
      leaf loss-ratio {
        type percentage;
        description
          "Loss ratio of the packets. Express as percentage
           of packets lost with respect to packets sent.";
      }
    }
  }

  grouping link-delay-statistics {
    description
      "Grouping for per link delay statistics.";
    container delay-statistics {
      description
        "One-way link delay summarized information.";
      reference
        "RFC 4656: A One-way Active Measurement Protocol (OWAMP)
         ITU-T Y.1731: Operations, administration and
         maintenance (OAM) functions and mechanisms
         for Ethernet-based networks";
      leaf unit-value {
        type identityref {
          base lime:time-unit-type;
        }
        default "lime:milliseconds";
        description
          "Time units, where the options are hours, minutes, seconds,
           milliseconds, microseconds, and nanoseconds.";
      }
      leaf min-delay-value {
        type yang:gauge64;
        description
          "Minimum observed one-way delay.";
      }
      leaf max-delay-value {
        type yang:gauge64;
        description
          "Maximum observed one-way delay.";
      }
      leaf low-delay-percentile {
        type yang:gauge64;
        description
          "Low percentile of observed one-way delay with
           specific measurement method.";
      }
      leaf intermediate-delay-percentile {
        type yang:gauge64;
        description
          "Intermediate percentile of observed one-way delay with
           specific measurement method.";
      }
      leaf high-delay-percentile {
        type yang:gauge64;
        description
          "High percentile of observed one-way delay with
           specific measurement method.";
      }
    }
  }

  grouping link-jitter-statistics {
    description
      "Grouping for per link jitter statistics.";
    container jitter-statistics {
      description
        "One-way link jitter summarized information.";
      reference
        "RFC 3393: IP Packet Delay Variation Metric
         for IP Performance Metrics (IPPM)
         RFC 4656: A One-way Active Measurement Protocol (OWAMP)
         ITU-T Y.1731: Operations, administration and
         maintenance (OAM) functions and mechanisms
         for Ethernet-based networks";
      leaf unit-value {
        type identityref {
          base lime:time-unit-type;
        }
        default "lime:milliseconds";
        description
          "Time units, where the options are hours, minutes, seconds,
           milliseconds, microseconds, and nanoseconds.";
      }
      leaf min-jitter-value {
        type yang:gauge64;
        description
          "Minimum observed one-way jitter.";
      }
      leaf max-jitter-value {
        type yang:gauge64;
        description
          "Maximum observed one-way jitter.";
      }
      leaf low-jitter-percentile {
        type yang:gauge64;
        description
          "Low percentile of observed one-way jitter.";
      }
      leaf intermediate-jitter-percentile {
        type yang:gauge64;
        description
          "Intermediate percentile of observed one-way jitter.";
      }
      leaf high-jitter-percentile {
        type yang:gauge64;
        description
          "High percentile of observed one-way jitter.";
      }
    }
  }

  grouping tp-svc-telemetry {
    leaf last-updated {
      type yang:date-and-time;
      config false;
      description
        "Indicates the time when the counters were last updated.";
    }
    leaf inbound-octets {
      type yang:counter64;
      description
        "The total number of octets received on the
         interface, including framing characters.";
    }
    leaf inbound-unicast {
      type yang:counter64;
      description
        "The total number of inbound unicast packets.";
    }
    leaf inbound-non-unicast {
      type yang:counter64;
      description
        "The total number of inbound non-unicast
         (i.e., broadcast or multicast) packets.";
    }
    leaf inbound-discards {
      type yang:counter64;
      description
        "The number of inbound packets that were chosen to be
         discarded even though no errors had been detected.
         Possible reasons for discarding such a packet could
         be to free up buffer space, not enough buffer for
         too much data, etc.";
    }
    leaf inbound-errors {
      type yang:counter64;
      description
        "The number of inbound packets that contained errors.";
    }
    leaf inbound-unknown-protocol {
      type yang:counter64;
      description
        "The number of packets received via the interface
         which were discarded because of an unknown or
         unsupported protocol.";
    }
    leaf outbound-octets {
      type yang:counter64;
      description
        "The total number of octets transmitted out of the
         interface, including framing characters.";
    }
    leaf outbound-unicast {
      type yang:counter64;
      description
        "The total number of outbound unicast packets.";
    }
    leaf outbound-non-unicast {
      type yang:counter64;
      description
        "The total number of outbound non unicast
         (i.e., broadcast or multicast) packets.";
    }
    leaf outbound-discards {
      type yang:counter64;
      description
        "The number of outbound packets which were chosen
         to be discarded even though no errors had been
         detected to prevent their being transmitted.
         Possible reasons for discarding such a packet could
         be to free up buffer space, not enough buffer for
         too much data, etc.";
    }
    leaf outbound-errors {
      type yang:counter64;
      description
        "The number of outbound packets that contained
         errors.";
    }
    description
      "Grouping for interface service telemetry.";
  }

  augment "/nw:networks/nw:network/nw:network-types" {
    description
      "Defines the service topologies types.";
    container service {
      presence
        "Presence of the container indicates performance monitoring
         of the VPN service, and absence of the container indicates
         performance monitoring of the network itself.";
      description
        "Container for VPN service.";
      leaf service-type {
        type identityref {
          base vpn-common:service-type;
        }
        mandatory true;
        description
          "This indicates the network service type,
           e.g., L3VPN, VPLS, etc.";
      }
      leaf vpn-id {
        type vpn-common:vpn-id;
        description
          "VPN identifier.";
      }
      leaf vpn-service-topology {
        type identityref {
          base vpn-common:vpn-topology;
        }
        description
          "VPN service topology, e.g., hub-spoke, any-to-any,
           hub-spoke-disjoint.";
      }
    }
  }

  augment "/nw:networks/nw:network/nw:node" {
    description
      "Augments the network node with other general attributes.";
    leaf node-type {
      type identityref {
        base node-type;
      }
      description
        "Node type, e.g., PE, P, ASBR.";
    }
    uses entry-summary;
  }

  augment "/nw:networks/nw:network/nw:node" {
    when '../nw:network-types/nvp:service' {
      description
        "Augments for VPN service PM.";
    }
    description
      "Augments the network node with VPN service attributes.";
    leaf role {
      type identityref {
        base vpn-common:role;
      }
      default "vpn-common:any-to-any-role";
      description
        "Role of the node in the VPN service topology.";
    }
  }

  augment "/nw:networks/nw:network/nt:link" {
    description
      "Augments the network topology link with performance
       monitoring attributes.";
    container perf-mon {
      description
        "Container for PM attributes.";
      leaf low-percentile {
        type percentile;
        default "10.00";
        description
          "Low percentile to report. Setting low-percentile
           into 0.00 indicates the client is not interested
           in receiving low percentile.";
      }
      leaf intermediate-percentile {
        type percentile;
        default "50.00";
        description
          "Intermediate percentile to report. Setting
           intermediate-percentile into 0.00 indicates the client
           is not interested in receiving intermediate percentile.";
      }
      leaf high-percentile {
        type percentile;
        default "95.00";
        description
          "High percentile to report. Setting high-percentile
           into 0.00 indicates the client is not interested in
           receiving high percentile.";
      }
      leaf measurement-interval {
        type uint32 {
          range "1..max";
        }
        units "seconds";
        default "60";
        description
          "Indicates the time interval to perform PM
           measurement over.";
      }
      list pm {
        key "pm-type";
        config false;
        description
          "The list of PM based on PM type";
        leaf pm-type {
          type identityref {
            base pm-type;
          }
          config false;
          description
            "The PM type of the measured PM attributes";
        }
        container pm-attributes {
          description
            "Container for PM attributes.";
          leaf start-time {
            type yang:date-and-time;
            config false;
            description
              "The date and time the measurement last started.";
          }
          leaf end-time {
            type yang:date-and-time;
            config false;
            description
              "The date and time the measurement last ended.";
          }
          leaf pm-source {
            type identityref {
              base pm-source-type;
            }
            config false;
            description
              "The OAM tool used to collect the PM data.";
          }
          container one-way-pm-statistics {
            config false;
            description
              "Container for link telemetry attributes.";
            uses link-loss-statistics;
            uses link-delay-statistics;
            uses link-jitter-statistics;
          }
          list one-way-pm-statistics-per-class {
            key "class-id";
            config false;
            description
              "The list of PM data based on class of service.";
            leaf class-id {
              type string;
              description
                "The class-id is used to identify the
                 class of service. This identifier is internal
                 to the administration.";
            }
            uses link-loss-statistics;
            uses link-delay-statistics;
            uses link-jitter-statistics;
          }
        }
      }
    }
  }

  augment "/nw:networks/nw:network/nt:link/perf-mon" {
    when '../../nw:network-types/nvp:service' {
      description
        "Augments for VPN service PM.";
    }
    description
      "Augments the network topology link with VPN service
       performance monitoring attributes.";
    container vpn-pm-type {
      description
        "The VPN PM type of this logical point-to-point
         unidirectional VPN link.";
      container inter-vpn-access-interface {
        description
          "Indicates inter-vpn-access-interface PM, which is to
           monitor the performance of logical point-to-point VPN
           connections between a source and a destination
           VPN access interfaces.";
        leaf inter-vpn-access-interface {
          type empty;
          description
            "This is a placeholder for inter-vpn-access-interface PM,
             which is not bound to a specific VPN access interface.
             The source or destination VPN access interface
             of the measurement can be augmented as needed.";
        }
      }
      container vpn-tunnel {
        presence "Enables VPN tunnel PM";
        description
          "Indicates VPN tunnel PM, which is to monitor
           the performance of VPN tunnels.";
        leaf vpn-tunnel-type {
          type identityref {
            base vpn-common:protocol-type;
          }
          config false;
          description
            "The leaf indicates the VPN tunnel type, e.g.,
             Generic Routing Encapsulation (GRE),
             Generic Network Virtualization Encapsulation (Geneve),
             etc.";
        }
      }
    }
  }

  augment
    "/nw:networks/nw:network/nw:node/nt:termination-point" {
      description
        "Augments the network topology termination point with
         performance monitoring attributes.";
      container pm-statistics {
        config false;
        description
          "Container for termination point PM attributes.";
        uses tp-svc-telemetry;
      }
  }

  augment "/nw:networks/nw:network/nw:node"
        + "/nt:termination-point/pm-statistics" {
    when '../../../nw:network-types/nvp:service' {
      description
        "Augments for VPN service PM.";
    }
    description
      "Augments the network topology termination-point with
       VPN service performance monitoring attributes";
    list vpn-network-access {
      key "network-access-id";
      description
        "The list of PM based on VPN network accesses.";
      leaf network-access-id {
        type vpn-common:vpn-id;
        description
          "The reference to an identifier for the VPN network
           access.";
      }
      uses tp-svc-telemetry;
    }
  }
}
