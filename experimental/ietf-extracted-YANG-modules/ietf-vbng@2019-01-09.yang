module ietf-vbng{
namespace "urn:ietf:params:xml:ns:yang:ietf-vbng";
prefix "vbng";

import ietf-inet-types {
   prefix "inet";
 }

import ietf-interfaces {
  prefix if;
 }

import ietf-logical-network-element {
  prefix lne;
}

organization
  "IETF NETCONF Working Group";

  contact
   "
     WG List:  <mailto:netconf@ietf.org>

     Editor:   Guangping Huang
               <mailto:huang.Guangping@zte.com.cn>
    ";

description
   "The YANG module defines a generic configuration
     model for vbng";

revision 2019-01-09{
  description "Initial a new vbng control and user plane separation
      yang data model, the yang data model includes ietf-vbng, ietf-vbng-cp,and ietf-vbng-up,
      this module is ietf-vbng";
  reference
     "draft-cuspdt-rtgwg-cu-separation-yang-model-02";
}

/* Typedefs  */

  typedef vlan-id {
   type uint16 {
     range "0..4094";
   }
   description
     "Typedef for VLAN ID.";
 }

 typedef vxlan-id {
   type uint32;
   description
     "Typedef for VxLAN ID.";
 }

  typedef address-family-type {
    type enumeration {
      enum ipv4 {
        description
          "IPv4";
      }
      enum ipv6 {
        description
          "IPv6";
      }
    }
    description
      "Typedef for address family type.";
  }

 /* Configuration Data */

 augment /lne:logical-network-elements/lne:logical-network-element {
 container ietf-vbng{
     container interfaces {
       list interface {
         key name;
         leaf name {
            type if:interface-ref;
            description "interface name";
           }
         container ethernet {
           leaf lacp {
            type boolean;
            description "enable lacp function";
            }
            description "configure ethernet interface";
           }
         leaf mac-offset {
            type uint32;
            description "configure mac offset";
           }
         container vlans {
             list tag {
                 key index;
                 max-elements 2;
                 leaf index {
                    type uint8 {
                      range "0..1";
                  }
                  must ". = 0 or
                    count(../../tag[index = 0]/index) > 0" {
                    error-message "An inner tag can only be specified if an
                             outer tag has also been specified";
                   description "Ensure that an inner tag cannot be
                           specified without an outer tag'";
                   }

                  description "The index into the tag stack, outermost tag
                         assigned index 0";
                 }

                 container tag{
                   leaf tag-type {
                      type string;
                      description "tag type";
                      }
                   leaf vlan-id {
                     type vlan-id;
                     description "vlan id value";
                    }

                description "tag";
                }
               description "tag list";
             }
           description "vlans";
         }
        description "interfaces list";
       }
      description "interface container";
     }

     container control-channel {
       leaf name {
         type string;
         description "control channel protocol logical name";
       }
       leaf id {
         type uint32;
         description "the cusp session id";
       }
       leaf port {
         type uint32;
         description "cusp tcp connection port number";
       }
       leaf version {
         type uint8;
         description "cusp version number";
       }
       leaf hellointerval {
         type uint32;
         description "cusp hello interval";
       }
       leaf deadtime {
         type uint32;
         description "cusp dead time";
       }
       leaf keepalivetime {
         type uint32;
         description "cusp keepalive time";
       }

       description "configure cusp parameters";
     }

     list service-channel{
         key vxlan-tunnel-id;
         leaf vxlan-tunnel-id {
            type uint32;
            description
                  "Static VxLAN tunnel ID.";
         }

         leaf vxlan-tunnel-name {
            type string;
            description
            "Name of the static VxLAN tunnel.";
         }

         list address-family {
            key "af";
            leaf af {
              type address-family-type;
              description
              "Address family type value.";
            }

            leaf tunnel-source-ip {
              type inet:ip-address;
              description
              "Source IP address for the static VxLAN tunnel";
            }

            leaf tunnel-destination-ip {
               type inet:ip-address;
               description
                "Destination IP address for the static VxLAN tunnel";
            }

            list bind-vxlan-id {
               key vxlan-id;
               leaf vxlan-id {
                 type vxlan-id;
                 description
                    "VxLAN ID.";
               }
               description
                  "VxLAN ID list for the VTEP.";
            }

             description
                "Per-af params.";
          }
         description
           "Configure VxLAN channel";
     }
    description "ietf-bng configuration!";
 }
description "augment lne model";
}
}
