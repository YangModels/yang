module ietf-vni-mng {
  yang-version 1.1;
  namespace "urn:ietf:params:xml:ns:yang:ietf-vni-mng";
  prefix vni-mng;

  organization
    "XXX";
  contact
    "WG Web: <http://tools.ietf.org/wg/neotec/>
     WG List: <mailto: neotec@ietf.org>

     Author:  Fan Zhang
              <zhangf52@chinatelecom.cn>
     Author:  Yongqing Zhu
              <zhuyq8@chinatelecom.cn>";
  description
    "This document defines a YANG data model for the management
     of VNIs (Virtual Network Interfaces), including vNIC and CNI,
     depending on the different ways of virtualization. It exposes
     the real-time VNI resources to network controller and service
     orchestrator in order to supervise the cloud resource states
     for dynamic adjustment of service function placement and
     load-balancing of service instances to ensure the
     SLO (Service Level Objective).

     The model is based on YANG 1.1 as defined in RFC 7950 and
     conforms to Network Management Datastore Architecture (NMDA)
     as defined in RFC 8342.

     Copyright (c) 2025 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see the
     RFC itself for full legal notices.";

  revision 2025-07-07 {
    description
      "Init revision";
    reference
      "YANG Data Model for Virtual Network Interfaces Management";
  }

  /* Data nodes */

  container dc {
    description
      "Datacenter";
    leaf dc-id {
      type string;
      description
        "Identifier for the datacenter";
    }
    container nodes {
      description
        "Virtualized nodes (VMs or containers)";
      list node {
        key "node-id";
        description
          "List of virtualized nodes.";
        leaf node-id {
          type string;
          description
            "Identifier for the virtualized node.";
        }
        leaf node-type {
          type enumeration {
            enum vm {
              description
                "Indicates that the node is a Virtual
                 Machine (VM) instance.";
            }
            enum container {
              description
                "Indicates that the node is a Container instance.";
            }
          }
          description
            "Specifies the type of the node.";
        }
        leaf allocatable-bandwidth {
          type uint64;
          units "bps";
          description
            "The maximum allocatable bandwidth for the
             node's virtualized interface.";
        }
        leaf allocated-bandwidth {
          type uint64;
          units "bps";
          description
            "The allocated bandwidth for the node's
             virtualized interface.";
        }
        leaf bandwidth-usage {
          type uint64;
          units "bps";
          description
            "The current bandwidth usage on the node's
             virtualized interface.";
        }
        leaf priority {
          type uint8;
          description
            "Priority level of the node or its traffic,
             with lower values indicating higher priority.";
        }
        leaf latency {
          type uint64;
          units "ms";
          description
            "Average one-way latency experienced by the
             node.";
        }
        leaf packet-loss-rate {
          type uint64;
          units "%";
          description
            "The average packet loss rate observed on the
             node's virtualized interface.";
        }
        leaf ingress-bytes {
          type uint64;
          units "bytes";
          description
            "Total number of bytes received by the node.";
        }
        leaf egress-bytes {
          type uint64;
          units "bytes";
          description
            "Total number of bytes transmitted from the
             node.";
        }
        list policy {
          key "policy-id";
          description
            "The service deployed on the node and its
             related policy.";
          leaf policy-id {
            type string;
            description
              "Identifier for the policy of the service
               deployed on the node.";
          }
          leaf service-id {
            type string;
            description
              "Identifier for the service deployed on the
               node.";
          }
        }
      }
    }
  }
}
