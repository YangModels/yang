module iana-timezones {
  namespace "urn:ietf:params:xml:ns:yang:iana-timezones";
  prefix ianatz;

  organization "IANA";
  contact
    "        Internet Assigned Numbers Authority

     Postal: ICANN
             4676 Admiralty Way, Suite 330
             Marina del Rey, CA 90292

     Tel:    +1 310 823 9358
     E-Mail: iana&iana.org";
  description
    "This YANG module defines the iana-timezone typedef, which
     contains YANG definitions for IANA-registered timezones.

     This YANG module is maintained by IANA, and reflects the
     IANA Time Zone Database.
     (http://www.iana.org/time-zones)

     The latest revision of this YANG module can be obtained from
     the IANA web site.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2013-11-19 {
    description
      "Initial revision using IANA Time Zone Data v. 2013h
       (Released 2013-10-25)";
    reference "RFC XXXX: TITLE";
  }

  typedef iana-timezone {
    description
      "A timezone location as defined by the IANA timezone
       database (http://www.iana.org/time-zones)";
    type enumeration {
      enum "Europe/Andorra" {
        value 0;
      }
      enum "Asia/Dubai" {
        value 1;
      }
      enum "Asia/Kabul" {
        value 2;
      }
      enum "America/Antigua" {
        value 3;
      }
      enum "America/Anguilla" {
        value 4;
      }
      enum "Europe/Tirane" {
        value 5;
      }
      enum "Asia/Yerevan" {
        value 6;
      }
      enum "Africa/Luanda" {
        value 7;
      }
      enum "Antarctica/McMurdo" {
        value 8;
        description
          "McMurdo, South Pole, Scott (New Zealand time)";
      }
      enum "Antarctica/Rothera" {
        value 9;
        description
          "Rothera Station, Adelaide Island";
      }
      enum "Antarctica/Palmer" {
        value 10;
        description
          "Palmer Station, Anvers Island";
      }
      enum "Antarctica/Mawson" {
        value 11;
        description
          "Mawson Station, Holme Bay";
      }
      enum "Antarctica/Davis" {
        value 12;
        description
          "Davis Station, Vestfold Hills";
      }
      enum "Antarctica/Casey" {
        value 13;
        description
          "Casey Station, Bailey Peninsula";
      }
      enum "Antarctica/Vostok" {
        value 14;
        description
          "Vostok Station, Lake Vostok";
      }
      enum "Antarctica/DumontDUrville" {
        value 15;
        description
          "Dumont-d'Urville Station, Terre Adelie";
      }
      enum "Antarctica/Syowa" {
        value 16;
        description
          "Syowa Station, E Ongul I";
      }
      enum "America/Argentina/Buenos_Aires" {
        value 17;
        description
          "Buenos Aires (BA, CF)";
      }
      enum "America/Argentina/Cordoba" {
        value 18;
        description
          "most locations (CB, CC, CN, ER, FM, MN, SE, SF)";
      }
      enum "America/Argentina/Salta" {
        value 19;
        description
          "(SA, LP, NQ, RN)";
      }
      enum "America/Argentina/Jujuy" {
        value 20;
        description
          "Jujuy (JY)";
      }
      enum "America/Argentina/Tucuman" {
        value 21;
        description
          "Tucuman (TM)";
      }
      enum "America/Argentina/Catamarca" {
        value 22;
        description
          "Catamarca (CT), Chubut (CH)";
      }
      enum "America/Argentina/La_Rioja" {
        value 23;
        description
          "La Rioja (LR)";
      }
      enum "America/Argentina/San_Juan" {
        value 24;
        description
          "San Juan (SJ)";
      }
      enum "America/Argentina/Mendoza" {
        value 25;
        description
          "Mendoza (MZ)";
      }
      enum "America/Argentina/San_Luis" {
        value 26;
        description
          "San Luis (SL)";
      }
      enum "America/Argentina/Rio_Gallegos" {
        value 27;
        description
          "Santa Cruz (SC)";
      }
      enum "America/Argentina/Ushuaia" {
        value 28;
        description
          "Tierra del Fuego (TF)";
      }
      enum "Pacific/Pago_Pago" {
        value 29;
      }
      enum "Europe/Vienna" {
        value 30;
      }
      enum "Australia/Lord_Howe" {
        value 31;
        description
          "Lord Howe Island";
      }
      enum "Antarctica/Macquarie" {
        value 32;
        description
          "Macquarie Island";
      }
      enum "Australia/Hobart" {
        value 33;
        description
          "Tasmania - most locations";
      }
      enum "Australia/Currie" {
        value 34;
        description
          "Tasmania - King Island";
      }
      enum "Australia/Melbourne" {
        value 35;
        description
          "Victoria";
      }
      enum "Australia/Sydney" {
        value 36;
        description
          "New South Wales - most locations";
      }
      enum "Australia/Broken_Hill" {
        value 37;
        description
          "New South Wales - Yancowinna";
      }
      enum "Australia/Brisbane" {
        value 38;
        description
          "Queensland - most locations";
      }
      enum "Australia/Lindeman" {
        value 39;
        description
          "Queensland - Holiday Islands";
      }
      enum "Australia/Adelaide" {
        value 40;
        description
          "South Australia";
      }
      enum "Australia/Darwin" {
        value 41;
        description
          "Northern Territory";
      }
      enum "Australia/Perth" {
        value 42;
        description
          "Western Australia - most locations";
      }
      enum "Australia/Eucla" {
        value 43;
        description
          "Western Australia - Eucla area";
      }
      enum "America/Aruba" {
        value 44;
      }
      enum "Europe/Mariehamn" {
        value 45;
      }
      enum "Asia/Baku" {
        value 46;
      }
      enum "Europe/Sarajevo" {
        value 47;
      }
      enum "America/Barbados" {
        value 48;
      }
      enum "Asia/Dhaka" {
        value 49;
      }
      enum "Europe/Brussels" {
        value 50;
      }
      enum "Africa/Ouagadougou" {
        value 51;
      }
      enum "Europe/Sofia" {
        value 52;
      }
      enum "Asia/Bahrain" {
        value 53;
      }
      enum "Africa/Bujumbura" {
        value 54;
      }
      enum "Africa/Porto-Novo" {
        value 55;
      }
      enum "America/St_Barthelemy" {
        value 56;
      }
      enum "Atlantic/Bermuda" {
        value 57;
      }
      enum "Asia/Brunei" {
        value 58;
      }
      enum "America/La_Paz" {
        value 59;
      }
      enum "America/Kralendijk" {
        value 60;
      }
      enum "America/Noronha" {
        value 61;
        description
          "Atlantic islands";
      }
      enum "America/Belem" {
        value 62;
        description
          "Amapa, E Para";
      }
      enum "America/Fortaleza" {
        value 63;
        description
          "NE Brazil (MA, PI, CE, RN, PB)";
      }
      enum "America/Recife" {
        value 64;
        description
          "Pernambuco";
      }
      enum "America/Araguaina" {
        value 65;
        description
          "Tocantins";
      }
      enum "America/Maceio" {
        value 66;
        description
          "Alagoas, Sergipe";
      }
      enum "America/Bahia" {
        value 67;
        description
          "Bahia";
      }
      enum "America/Sao_Paulo" {
        value 68;
        description
          "S & SE Brazil (GO, DF, MG, ES, RJ, SP, PR, SC, RS)";
      }
      enum "America/Campo_Grande" {
        value 69;
        description
          "Mato Grosso do Sul";
      }
      enum "America/Cuiaba" {
        value 70;
        description
          "Mato Grosso";
      }
      enum "America/Santarem" {
        value 71;
        description
          "W Para";
      }
      enum "America/Porto_Velho" {
        value 72;
        description
          "Rondonia";
      }
      enum "America/Boa_Vista" {
        value 73;
        description
          "Roraima";
      }
      enum "America/Manaus" {
        value 74;
        description
          "E Amazonas";
      }
      enum "America/Eirunepe" {
        value 75;
        description
          "W Amazonas";
      }
      enum "America/Rio_Branco" {
        value 76;
        description
          "Acre";
      }
      enum "America/Nassau" {
        value 77;
      }
      enum "Asia/Thimphu" {
        value 78;
      }
      enum "Africa/Gaborone" {
        value 79;
      }
      enum "Europe/Minsk" {
        value 80;
      }
      enum "America/Belize" {
        value 81;
      }
      enum "America/St_Johns" {
        value 82;
        description
          "Newfoundland Time, including SE Labrador";
      }
      enum "America/Halifax" {
        value 83;
        description
          "Atlantic Time - Nova Scotia (most places), PEI";
      }
      enum "America/Glace_Bay" {
        value 84;
        description
          "Atlantic Time - Nova Scotia - places that did not observe DST
           1966-1971";
      }
      enum "America/Moncton" {
        value 85;
        description
          "Atlantic Time - New Brunswick";
      }
      enum "America/Goose_Bay" {
        value 86;
        description
          "Atlantic Time - Labrador - most locations";
      }
      enum "America/Blanc-Sablon" {
        value 87;
        description
          "Atlantic Standard Time - Quebec - Lower North Shore";
      }
      enum "America/Toronto" {
        value 88;
        description
          "Eastern Time - Ontario & Quebec - most locations";
      }
      enum "America/Nipigon" {
        value 89;
        description
          "Eastern Time - Ontario & Quebec - places that did not observe
           DST 1967-1973";
      }
      enum "America/Thunder_Bay" {
        value 90;
        description
          "Eastern Time - Thunder Bay, Ontario";
      }
      enum "America/Iqaluit" {
        value 91;
        description
          "Eastern Time - east Nunavut - most locations";
      }
      enum "America/Pangnirtung" {
        value 92;
        description
          "Eastern Time - Pangnirtung, Nunavut";
      }
      enum "America/Resolute" {
        value 93;
        description
          "Central Standard Time - Resolute, Nunavut";
      }
      enum "America/Atikokan" {
        value 94;
        description
          "Eastern Standard Time - Atikokan, Ontario and Southampton I,
           Nunavut";
      }
      enum "America/Rankin_Inlet" {
        value 95;
        description
          "Central Time - central Nunavut";
      }
      enum "America/Winnipeg" {
        value 96;
        description
          "Central Time - Manitoba & west Ontario";
      }
      enum "America/Rainy_River" {
        value 97;
        description
          "Central Time - Rainy River & Fort Frances, Ontario";
      }
      enum "America/Regina" {
        value 98;
        description
          "Central Standard Time - Saskatchewan - most locations";
      }
      enum "America/Swift_Current" {
        value 99;
        description
          "Central Standard Time - Saskatchewan - midwest";
      }
      enum "America/Edmonton" {
        value 100;
        description
          "Mountain Time - Alberta, east British Columbia & west
           Saskatchewan";
      }
      enum "America/Cambridge_Bay" {
        value 101;
        description
          "Mountain Time - west Nunavut";
      }
      enum "America/Yellowknife" {
        value 102;
        description
          "Mountain Time - central Northwest Territories";
      }
      enum "America/Inuvik" {
        value 103;
        description
          "Mountain Time - west Northwest Territories";
      }
      enum "America/Creston" {
        value 104;
        description
          "Mountain Standard Time - Creston, British Columbia";
      }
      enum "America/Dawson_Creek" {
        value 105;
        description
          "Mountain Standard Time - Dawson Creek & Fort Saint John,
           British Columbia";
      }
      enum "America/Vancouver" {
        value 106;
        description
          "Pacific Time - west British Columbia";
      }
      enum "America/Whitehorse" {
        value 107;
        description
          "Pacific Time - south Yukon";
      }
      enum "America/Dawson" {
        value 108;
        description
          "Pacific Time - north Yukon";
      }
      enum "Indian/Cocos" {
        value 109;
      }
      enum "Africa/Kinshasa" {
        value 110;
        description
          "west Dem. Rep. of Congo";
      }
      enum "Africa/Lubumbashi" {
        value 111;
        description
          "east Dem. Rep. of Congo";
      }
      enum "Africa/Bangui" {
        value 112;
      }
      enum "Africa/Brazzaville" {
        value 113;
      }
      enum "Europe/Zurich" {
        value 114;
      }
      enum "Africa/Abidjan" {
        value 115;
      }
      enum "Pacific/Rarotonga" {
        value 116;
      }
      enum "America/Santiago" {
        value 117;
        description
          "most locations";
      }
      enum "Pacific/Easter" {
        value 118;
        description
          "Easter Island & Sala y Gomez";
      }
      enum "Africa/Douala" {
        value 119;
      }
      enum "Asia/Shanghai" {
        value 120;
        description
          "east China - Beijing, Guangdong, Shanghai, etc.";
      }
      enum "Asia/Harbin" {
        value 121;
        description
          "Heilongjiang (except Mohe), Jilin";
      }
      enum "Asia/Chongqing" {
        value 122;
        description
          "central China - Sichuan, Yunnan, Guangxi, Shaanxi, Guizhou,
           etc.";
      }
      enum "Asia/Urumqi" {
        value 123;
        description
          "most of Tibet & Xinjiang";
      }
      enum "Asia/Kashgar" {
        value 124;
        description
          "west Tibet & Xinjiang";
      }
      enum "America/Bogota" {
        value 125;
      }
      enum "America/Costa_Rica" {
        value 126;
      }
      enum "America/Havana" {
        value 127;
      }
      enum "Atlantic/Cape_Verde" {
        value 128;
      }
      enum "America/Curacao" {
        value 129;
      }
      enum "Indian/Christmas" {
        value 130;
      }
      enum "Asia/Nicosia" {
        value 131;
      }
      enum "Europe/Prague" {
        value 132;
      }
      enum "Europe/Berlin" {
        value 133;
        description
          "most locations";
      }
      enum "Europe/Busingen" {
        value 134;
        description
          "Busingen";
      }
      enum "Africa/Djibouti" {
        value 135;
      }
      enum "Europe/Copenhagen" {
        value 136;
      }
      enum "America/Dominica" {
        value 137;
      }
      enum "America/Santo_Domingo" {
        value 138;
      }
      enum "Africa/Algiers" {
        value 139;
      }
      enum "America/Guayaquil" {
        value 140;
        description
          "mainland";
      }
      enum "Pacific/Galapagos" {
        value 141;
        description
          "Galapagos Islands";
      }
      enum "Europe/Tallinn" {
        value 142;
      }
      enum "Africa/Cairo" {
        value 143;
      }
      enum "Africa/El_Aaiun" {
        value 144;
      }
      enum "Africa/Asmara" {
        value 145;
      }
      enum "Europe/Madrid" {
        value 146;
        description
          "mainland";
      }
      enum "Africa/Ceuta" {
        value 147;
        description
          "Ceuta & Melilla";
      }
      enum "Atlantic/Canary" {
        value 148;
        description
          "Canary Islands";
      }
      enum "Africa/Addis_Ababa" {
        value 149;
      }
      enum "Europe/Helsinki" {
        value 150;
      }
      enum "Pacific/Fiji" {
        value 151;
      }
      enum "Atlantic/Stanley" {
        value 152;
      }
      enum "Pacific/Chuuk" {
        value 153;
        description
          "Chuuk (Truk) and Yap";
      }
      enum "Pacific/Pohnpei" {
        value 154;
        description
          "Pohnpei (Ponape)";
      }
      enum "Pacific/Kosrae" {
        value 155;
        description
          "Kosrae";
      }
      enum "Atlantic/Faroe" {
        value 156;
      }
      enum "Europe/Paris" {
        value 157;
      }
      enum "Africa/Libreville" {
        value 158;
      }
      enum "Europe/London" {
        value 159;
      }
      enum "America/Grenada" {
        value 160;
      }
      enum "Asia/Tbilisi" {
        value 161;
      }
      enum "America/Cayenne" {
        value 162;
      }
      enum "Europe/Guernsey" {
        value 163;
      }
      enum "Africa/Accra" {
        value 164;
      }
      enum "Europe/Gibraltar" {
        value 165;
      }
      enum "America/Godthab" {
        value 166;
        description
          "most locations";
      }
      enum "America/Danmarkshavn" {
        value 167;
        description
          "east coast, north of Scoresbysund";
      }
      enum "America/Scoresbysund" {
        value 168;
        description
          "Scoresbysund / Ittoqqortoormiit";
      }
      enum "America/Thule" {
        value 169;
        description
          "Thule / Pituffik";
      }
      enum "Africa/Banjul" {
        value 170;
      }
      enum "Africa/Conakry" {
        value 171;
      }
      enum "America/Guadeloupe" {
        value 172;
      }
      enum "Africa/Malabo" {
        value 173;
      }
      enum "Europe/Athens" {
        value 174;
      }
      enum "Atlantic/South_Georgia" {
        value 175;
      }
      enum "America/Guatemala" {
        value 176;
      }
      enum "Pacific/Guam" {
        value 177;
      }
      enum "Africa/Bissau" {
        value 178;
      }
      enum "America/Guyana" {
        value 179;
      }
      enum "Asia/Hong_Kong" {
        value 180;
      }
      enum "America/Tegucigalpa" {
        value 181;
      }
      enum "Europe/Zagreb" {
        value 182;
      }
      enum "America/Port-au-Prince" {
        value 183;
      }
      enum "Europe/Budapest" {
        value 184;
      }
      enum "Asia/Jakarta" {
        value 185;
        description
          "Java & Sumatra";
      }
      enum "Asia/Pontianak" {
        value 186;
        description
          "west & central Borneo";
      }
      enum "Asia/Makassar" {
        value 187;
        description
          "east & south Borneo, Sulawesi (Celebes), Bali, Nusa Tengarra,
           west Timor";
      }
      enum "Asia/Jayapura" {
        value 188;
        description
          "west New Guinea (Irian Jaya) & Malukus (Moluccas)";
      }
      enum "Europe/Dublin" {
        value 189;
      }
      enum "Asia/Jerusalem" {
        value 190;
      }
      enum "Europe/Isle_of_Man" {
        value 191;
      }
      enum "Asia/Kolkata" {
        value 192;
      }
      enum "Indian/Chagos" {
        value 193;
      }
      enum "Asia/Baghdad" {
        value 194;
      }
      enum "Asia/Tehran" {
        value 195;
      }
      enum "Atlantic/Reykjavik" {
        value 196;
      }
      enum "Europe/Rome" {
        value 197;
      }
      enum "Europe/Jersey" {
        value 198;
      }
      enum "America/Jamaica" {
        value 199;
      }
      enum "Asia/Amman" {
        value 200;
      }
      enum "Asia/Tokyo" {
        value 201;
      }
      enum "Africa/Nairobi" {
        value 202;
      }
      enum "Asia/Bishkek" {
        value 203;
      }
      enum "Asia/Phnom_Penh" {
        value 204;
      }
      enum "Pacific/Tarawa" {
        value 205;
        description
          "Gilbert Islands";
      }
      enum "Pacific/Enderbury" {
        value 206;
        description
          "Phoenix Islands";
      }
      enum "Pacific/Kiritimati" {
        value 207;
        description
          "Line Islands";
      }
      enum "Indian/Comoro" {
        value 208;
      }
      enum "America/St_Kitts" {
        value 209;
      }
      enum "Asia/Pyongyang" {
        value 210;
      }
      enum "Asia/Seoul" {
        value 211;
      }
      enum "Asia/Kuwait" {
        value 212;
      }
      enum "America/Cayman" {
        value 213;
      }
      enum "Asia/Almaty" {
        value 214;
        description
          "most locations";
      }
      enum "Asia/Qyzylorda" {
        value 215;
        description
          "Qyzylorda (Kyzylorda, Kzyl-Orda)";
      }
      enum "Asia/Aqtobe" {
        value 216;
        description
          "Aqtobe (Aktobe)";
      }
      enum "Asia/Aqtau" {
        value 217;
        description
          "Atyrau (Atirau, Gur'yev), Mangghystau (Mankistau)";
      }
      enum "Asia/Oral" {
        value 218;
        description
          "West Kazakhstan";
      }
      enum "Asia/Vientiane" {
        value 219;
      }
      enum "Asia/Beirut" {
        value 220;
      }
      enum "America/St_Lucia" {
        value 221;
      }
      enum "Europe/Vaduz" {
        value 222;
      }
      enum "Asia/Colombo" {
        value 223;
      }
      enum "Africa/Monrovia" {
        value 224;
      }
      enum "Africa/Maseru" {
        value 225;
      }
      enum "Europe/Vilnius" {
        value 226;
      }
      enum "Europe/Luxembourg" {
        value 227;
      }
      enum "Europe/Riga" {
        value 228;
      }
      enum "Africa/Tripoli" {
        value 229;
      }
      enum "Africa/Casablanca" {
        value 230;
      }
      enum "Europe/Monaco" {
        value 231;
      }
      enum "Europe/Chisinau" {
        value 232;
      }
      enum "Europe/Podgorica" {
        value 233;
      }
      enum "America/Marigot" {
        value 234;
      }
      enum "Indian/Antananarivo" {
        value 235;
      }
      enum "Pacific/Majuro" {
        value 236;
        description
          "most locations";
      }
      enum "Pacific/Kwajalein" {
        value 237;
        description
          "Kwajalein";
      }
      enum "Europe/Skopje" {
        value 238;
      }
      enum "Africa/Bamako" {
        value 239;
      }
      enum "Asia/Rangoon" {
        value 240;
      }
      enum "Asia/Ulaanbaatar" {
        value 241;
        description
          "most locations";
      }
      enum "Asia/Hovd" {
        value 242;
        description
          "Bayan-Olgiy, Govi-Altai, Hovd, Uvs, Zavkhan";
      }
      enum "Asia/Choibalsan" {
        value 243;
        description
          "Dornod, Sukhbaatar";
      }
      enum "Asia/Macau" {
        value 244;
      }
      enum "Pacific/Saipan" {
        value 245;
      }
      enum "America/Martinique" {
        value 246;
      }
      enum "Africa/Nouakchott" {
        value 247;
      }
      enum "America/Montserrat" {
        value 248;
      }
      enum "Europe/Malta" {
        value 249;
      }
      enum "Indian/Mauritius" {
        value 250;
      }
      enum "Indian/Maldives" {
        value 251;
      }
      enum "Africa/Blantyre" {
        value 252;
      }
      enum "America/Mexico_City" {
        value 253;
        description
          "Central Time - most locations";
      }
      enum "America/Cancun" {
        value 254;
        description
          "Central Time - Quintana Roo";
      }
      enum "America/Merida" {
        value 255;
        description
          "Central Time - Campeche, Yucatan";
      }
      enum "America/Monterrey" {
        value 256;
        description
          "Mexican Central Time - Coahuila, Durango, Nuevo Leon,
           Tamaulipas away from US border";
      }
      enum "America/Matamoros" {
        value 257;
        description
          "US Central Time - Coahuila, Durango, Nuevo Leon, Tamaulipas
           near US border";
      }
      enum "America/Mazatlan" {
        value 258;
        description
          "Mountain Time - S Baja, Nayarit, Sinaloa";
      }
      enum "America/Chihuahua" {
        value 259;
        description
          "Mexican Mountain Time - Chihuahua away from US border";
      }
      enum "America/Ojinaga" {
        value 260;
        description
          "US Mountain Time - Chihuahua near US border";
      }
      enum "America/Hermosillo" {
        value 261;
        description
          "Mountain Standard Time - Sonora";
      }
      enum "America/Tijuana" {
        value 262;
        description
          "US Pacific Time - Baja California near US border";
      }
      enum "America/Santa_Isabel" {
        value 263;
        description
          "Mexican Pacific Time - Baja California away from US border";
      }
      enum "America/Bahia_Banderas" {
        value 264;
        description
          "Mexican Central Time - Bahia de Banderas";
      }
      enum "Asia/Kuala_Lumpur" {
        value 265;
        description
          "peninsular Malaysia";
      }
      enum "Asia/Kuching" {
        value 266;
        description
          "Sabah & Sarawak";
      }
      enum "Africa/Maputo" {
        value 267;
      }
      enum "Africa/Windhoek" {
        value 268;
      }
      enum "Pacific/Noumea" {
        value 269;
      }
      enum "Africa/Niamey" {
        value 270;
      }
      enum "Pacific/Norfolk" {
        value 271;
      }
      enum "Africa/Lagos" {
        value 272;
      }
      enum "America/Managua" {
        value 273;
      }
      enum "Europe/Amsterdam" {
        value 274;
      }
      enum "Europe/Oslo" {
        value 275;
      }
      enum "Asia/Kathmandu" {
        value 276;
      }
      enum "Pacific/Nauru" {
        value 277;
      }
      enum "Pacific/Niue" {
        value 278;
      }
      enum "Pacific/Auckland" {
        value 279;
        description
          "most locations";
      }
      enum "Pacific/Chatham" {
        value 280;
        description
          "Chatham Islands";
      }
      enum "Asia/Muscat" {
        value 281;
      }
      enum "America/Panama" {
        value 282;
      }
      enum "America/Lima" {
        value 283;
      }
      enum "Pacific/Tahiti" {
        value 284;
        description
          "Society Islands";
      }
      enum "Pacific/Marquesas" {
        value 285;
        description
          "Marquesas Islands";
      }
      enum "Pacific/Gambier" {
        value 286;
        description
          "Gambier Islands";
      }
      enum "Pacific/Port_Moresby" {
        value 287;
      }
      enum "Asia/Manila" {
        value 288;
      }
      enum "Asia/Karachi" {
        value 289;
      }
      enum "Europe/Warsaw" {
        value 290;
      }
      enum "America/Miquelon" {
        value 291;
      }
      enum "Pacific/Pitcairn" {
        value 292;
      }
      enum "America/Puerto_Rico" {
        value 293;
      }
      enum "Asia/Gaza" {
        value 294;
        description
          "Gaza Strip";
      }
      enum "Asia/Hebron" {
        value 295;
        description
          "West Bank";
      }
      enum "Europe/Lisbon" {
        value 296;
        description
          "mainland";
      }
      enum "Atlantic/Madeira" {
        value 297;
        description
          "Madeira Islands";
      }
      enum "Atlantic/Azores" {
        value 298;
        description
          "Azores";
      }
      enum "Pacific/Palau" {
        value 299;
      }
      enum "America/Asuncion" {
        value 300;
      }
      enum "Asia/Qatar" {
        value 301;
      }
      enum "Indian/Reunion" {
        value 302;
      }
      enum "Europe/Bucharest" {
        value 303;
      }
      enum "Europe/Belgrade" {
        value 304;
      }
      enum "Europe/Kaliningrad" {
        value 305;
        description
          "Moscow-01 - Kaliningrad";
      }
      enum "Europe/Moscow" {
        value 306;
        description
          "Moscow+00 - west Russia";
      }
      enum "Europe/Volgograd" {
        value 307;
        description
          "Moscow+00 - Caspian Sea";
      }
      enum "Europe/Samara" {
        value 308;
        description
          "Moscow+00 - Samara, Udmurtia";
      }
      enum "Asia/Yekaterinburg" {
        value 309;
        description
          "Moscow+02 - Urals";
      }
      enum "Asia/Omsk" {
        value 310;
        description
          "Moscow+03 - west Siberia";
      }
      enum "Asia/Novosibirsk" {
        value 311;
        description
          "Moscow+03 - Novosibirsk";
      }
      enum "Asia/Novokuznetsk" {
        value 312;
        description
          "Moscow+03 - Novokuznetsk";
      }
      enum "Asia/Krasnoyarsk" {
        value 313;
        description
          "Moscow+04 - Yenisei River";
      }
      enum "Asia/Irkutsk" {
        value 314;
        description
          "Moscow+05 - Lake Baikal";
      }
      enum "Asia/Yakutsk" {
        value 315;
        description
          "Moscow+06 - Lena River";
      }
      enum "Asia/Khandyga" {
        value 316;
        description
          "Moscow+06 - Tomponsky, Ust-Maysky";
      }
      enum "Asia/Vladivostok" {
        value 317;
        description
          "Moscow+07 - Amur River";
      }
      enum "Asia/Sakhalin" {
        value 318;
        description
          "Moscow+07 - Sakhalin Island";
      }
      enum "Asia/Ust-Nera" {
        value 319;
        description
          "Moscow+07 - Oymyakonsky";
      }
      enum "Asia/Magadan" {
        value 320;
        description
          "Moscow+08 - Magadan";
      }
      enum "Asia/Kamchatka" {
        value 321;
        description
          "Moscow+08 - Kamchatka";
      }
      enum "Asia/Anadyr" {
        value 322;
        description
          "Moscow+08 - Bering Sea";
      }
      enum "Africa/Kigali" {
        value 323;
      }
      enum "Asia/Riyadh" {
        value 324;
      }
      enum "Pacific/Guadalcanal" {
        value 325;
      }
      enum "Indian/Mahe" {
        value 326;
      }
      enum "Africa/Khartoum" {
        value 327;
      }
      enum "Europe/Stockholm" {
        value 328;
      }
      enum "Asia/Singapore" {
        value 329;
      }
      enum "Atlantic/St_Helena" {
        value 330;
      }
      enum "Europe/Ljubljana" {
        value 331;
      }
      enum "Arctic/Longyearbyen" {
        value 332;
      }
      enum "Europe/Bratislava" {
        value 333;
      }
      enum "Africa/Freetown" {
        value 334;
      }
      enum "Europe/San_Marino" {
        value 335;
      }
      enum "Africa/Dakar" {
        value 336;
      }
      enum "Africa/Mogadishu" {
        value 337;
      }
      enum "America/Paramaribo" {
        value 338;
      }
      enum "Africa/Juba" {
        value 339;
      }
      enum "Africa/Sao_Tome" {
        value 340;
      }
      enum "America/El_Salvador" {
        value 341;
      }
      enum "America/Lower_Princes" {
        value 342;
      }
      enum "Asia/Damascus" {
        value 343;
      }
      enum "Africa/Mbabane" {
        value 344;
      }
      enum "America/Grand_Turk" {
        value 345;
      }
      enum "Africa/Ndjamena" {
        value 346;
      }
      enum "Indian/Kerguelen" {
        value 347;
      }
      enum "Africa/Lome" {
        value 348;
      }
      enum "Asia/Bangkok" {
        value 349;
      }
      enum "Asia/Dushanbe" {
        value 350;
      }
      enum "Pacific/Fakaofo" {
        value 351;
      }
      enum "Asia/Dili" {
        value 352;
      }
      enum "Asia/Ashgabat" {
        value 353;
      }
      enum "Africa/Tunis" {
        value 354;
      }
      enum "Pacific/Tongatapu" {
        value 355;
      }
      enum "Europe/Istanbul" {
        value 356;
      }
      enum "America/Port_of_Spain" {
        value 357;
      }
      enum "Pacific/Funafuti" {
        value 358;
      }
      enum "Asia/Taipei" {
        value 359;
      }
      enum "Africa/Dar_es_Salaam" {
        value 360;
      }
      enum "Europe/Kiev" {
        value 361;
        description
          "most locations";
      }
      enum "Europe/Uzhgorod" {
        value 362;
        description
          "Ruthenia";
      }
      enum "Europe/Zaporozhye" {
        value 363;
        description
          "Zaporozh'ye, E Lugansk / Zaporizhia, E Luhansk";
      }
      enum "Europe/Simferopol" {
        value 364;
        description
          "central Crimea";
      }
      enum "Africa/Kampala" {
        value 365;
      }
      enum "Pacific/Johnston" {
        value 366;
        description
          "Johnston Atoll";
      }
      enum "Pacific/Midway" {
        value 367;
        description
          "Midway Islands";
      }
      enum "Pacific/Wake" {
        value 368;
        description
          "Wake Island";
      }
      enum "America/New_York" {
        value 369;
        description
          "Eastern Time";
      }
      enum "America/Detroit" {
        value 370;
        description
          "Eastern Time - Michigan - most locations";
      }
      enum "America/Kentucky/Louisville" {
        value 371;
        description
          "Eastern Time - Kentucky - Louisville area";
      }
      enum "America/Kentucky/Monticello" {
        value 372;
        description
          "Eastern Time - Kentucky - Wayne County";
      }
      enum "America/Indiana/Indianapolis" {
        value 373;
        description
          "Eastern Time - Indiana - most locations";
      }
      enum "America/Indiana/Vincennes" {
        value 374;
        description
          "Eastern Time - Indiana - Daviess, Dubois, Knox & Martin
           Counties";
      }
      enum "America/Indiana/Winamac" {
        value 375;
        description
          "Eastern Time - Indiana - Pulaski County";
      }
      enum "America/Indiana/Marengo" {
        value 376;
        description
          "Eastern Time - Indiana - Crawford County";
      }
      enum "America/Indiana/Petersburg" {
        value 377;
        description
          "Eastern Time - Indiana - Pike County";
      }
      enum "America/Indiana/Vevay" {
        value 378;
        description
          "Eastern Time - Indiana - Switzerland County";
      }
      enum "America/Chicago" {
        value 379;
        description
          "Central Time";
      }
      enum "America/Indiana/Tell_City" {
        value 380;
        description
          "Central Time - Indiana - Perry County";
      }
      enum "America/Indiana/Knox" {
        value 381;
        description
          "Central Time - Indiana - Starke County";
      }
      enum "America/Menominee" {
        value 382;
        description
          "Central Time - Michigan - Dickinson, Gogebic, Iron & Menominee
           Counties";
      }
      enum "America/North_Dakota/Center" {
        value 383;
        description
          "Central Time - North Dakota - Oliver County";
      }
      enum "America/North_Dakota/New_Salem" {
        value 384;
        description
          "Central Time - North Dakota - Morton County (except Mandan
           area)";
      }
      enum "America/North_Dakota/Beulah" {
        value 385;
        description
          "Central Time - North Dakota - Mercer County";
      }
      enum "America/Denver" {
        value 386;
        description
          "Mountain Time";
      }
      enum "America/Boise" {
        value 387;
        description
          "Mountain Time - south Idaho & east Oregon";
      }
      enum "America/Phoenix" {
        value 388;
        description
          "Mountain Standard Time - Arizona (except Navajo)";
      }
      enum "America/Los_Angeles" {
        value 389;
        description
          "Pacific Time";
      }
      enum "America/Anchorage" {
        value 390;
        description
          "Alaska Time";
      }
      enum "America/Juneau" {
        value 391;
        description
          "Alaska Time - Alaska panhandle";
      }
      enum "America/Sitka" {
        value 392;
        description
          "Alaska Time - southeast Alaska panhandle";
      }
      enum "America/Yakutat" {
        value 393;
        description
          "Alaska Time - Alaska panhandle neck";
      }
      enum "America/Nome" {
        value 394;
        description
          "Alaska Time - west Alaska";
      }
      enum "America/Adak" {
        value 395;
        description
          "Aleutian Islands";
      }
      enum "America/Metlakatla" {
        value 396;
        description
          "Metlakatla Time - Annette Island";
      }
      enum "Pacific/Honolulu" {
        value 397;
        description
          "Hawaii";
      }
      enum "America/Montevideo" {
        value 398;
      }
      enum "Asia/Samarkand" {
        value 399;
        description
          "west Uzbekistan";
      }
      enum "Asia/Tashkent" {
        value 400;
        description
          "east Uzbekistan";
      }
      enum "Europe/Vatican" {
        value 401;
      }
      enum "America/St_Vincent" {
        value 402;
      }
      enum "America/Caracas" {
        value 403;
      }
      enum "America/Tortola" {
        value 404;
      }
      enum "America/St_Thomas" {
        value 405;
      }
      enum "Asia/Ho_Chi_Minh" {
        value 406;
      }
      enum "Pacific/Efate" {
        value 407;
      }
      enum "Pacific/Wallis" {
        value 408;
      }
      enum "Pacific/Apia" {
        value 409;
      }
      enum "Asia/Aden" {
        value 410;
      }
      enum "Indian/Mayotte" {
        value 411;
      }
      enum "Africa/Johannesburg" {
        value 412;
      }
      enum "Africa/Lusaka" {
        value 413;
      }
      enum "Africa/Harare" {
        value 414;
      }
    }
  }
}
