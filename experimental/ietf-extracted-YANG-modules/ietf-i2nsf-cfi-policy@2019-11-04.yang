module ietf-i2nsf-cfi-policy {
yang-version 1.1;
  namespace
    "urn:ietf:params:xml:ns:yang:ietf-i2nsf-cfi-policy";
  prefix
    cfi-policy;

  import ietf-yang-types{
    prefix yang;
    reference
    "Section 3 of RFC 6991";
  }

  import ietf-inet-types{
    prefix inet;
    reference
    "Section 4 of RFC 6991";
  }

  import ietf-netconf-acm {
    prefix nacm;
  }

  organization
    "IETF I2NSF (Interface to Network Security Functions)
     Working Group";

  contact
    "WG Web: <http://tools.ietf.org/wg/i2nsf>
     WG List: <mailto:i2nsf@ietf.org>

     WG Chair: Linda Dunbar
     <mailto:Linda.duhbar@huawei.com>

     WG Chair: Yoav Nir
     <mailto:ynir.ietf@gmail.com>

     Editor: Jaehoon Paul Jeong
     <mailto:pauljeong@skku.edu>

     Editor: Chaehong Chung
     <mailto:darkhong@skku.edu>";

  description
   "This module is a YANG module for Consumer-Facing Interface.
   Copyright (c) 2018 IETF Trust and the persons identified as
   authors of the code. All rights reserved.
   Redistribution and use in source and binary forms, with or
   without modification, is permitted pursuant to, and subject
   to the license terms contained in, the Simplified BSD License
   set forth in Section 4.c of the IETF Trust's Legal Provisions
   Relating to IETF Documents
   (http://trustee.ietf.org/license-info).
   This version of this YANG module is part of RFC XXXX; see
   the RFC itself for full legal notices.";

  revision "2019-11-04"{
    description "The latest revision";
    reference
      "draft-ietf-consumer-facing-interface-dm-07";
  }

  identity malware-file-type {
    description
      "Base identity for malware file types.";
  }
  identity executable-file {
    base malware-file-type;
    description
      "Identity for executable file types.";
  }
  identity doc-file {
    base malware-file-type;
    description
      "Identity for Microsoft document file types.";
  }
  identity html-app-file {
    base malware-file-type;
    description
      "Identity for html application file types.";
  }
  identity javascript-file {
    base malware-file-type;
    description
      "Identity for Javascript file types.";
  }
  identity pdf-file {
    base malware-file-type;
    description
      "Identity for pdf file types.";
  }
  identity dll-file {
    base malware-file-type;
    description
      "Identity for dll file types.";
  }
  identity msi-file {
    base malware-file-type;
    description
      "Identity for Microsoft installer file types.";
  }

  identity security-event-type {
    description
      "Base identity for security event types.";
  }
  identity ddos {
    base malware-file-type;
    description
      "Identity for DDoS event types.";
  }
  identity spyware {
    base malware-file-type;
    description
      "Identity for spyware event types.";
  }
  identity trojan {
    base malware-file-type;
    description
      "Identity for Trojan infection event types.";
  }
  identity ransomware {
    base malware-file-type;
    description
      "Identity for ransomware infection event types.";
  }

  identity i2nsf-ipsec {
    description
      "Base identity for IPsec method types.";
  }
  identity ipsec-ike {
    base i2nsf-ipsec;
    description
      "Identity for ipsec-ike.";
  }

  identity ipsec-ikeless {
    base i2nsf-ipsec;
    description
      "Identity for ipsec-ikeless.";
  }

  identity continent {
    description
    "Base Identity for continent types.";
  }

  identity africa {
    base continent;
    description
    "Identity for africa.";
  }
  identity asia {
    base continent;
    description
    "Identity for asia.";
  }
  identity europe {
    base continent;
    description
    "Identity for europe.";
  }
  identity north-america {
    base continent;
    description
    "Identity for north-america.";
  }
  identity south-america {
    base continent;
    description
    "Identity for south-america.";
  }
  identity oceania {
    base continent;
    description
    "Identity for Oceania";
  }
  identity enforce-type {
    description
    "This identity represents the event of
    policy enforcement trigger type.";
  }
  identity admin {
    base enforce-type;
    description
    "The identity for policy enforcement by admin.";
  }
  identity time {
    base enforce-type;
    description
    "The identity for policy enforcement based on time.";
  }

  identity protocol-type {
    description
    "This identity represents the protocol types.";
  }
  identity ftp {
    base protocol-type;
    description
    "The identity for ftp protocol.";
  }
  identity ssh {
    base protocol-type;
    description
    "The identity for ssh protocol.";
  }
  identity telnet {
    base protocol-type;
    description
    "The identity for telnet.";
  }
  identity smtp {
    base protocol-type;
    description
    "The identity for smtp.";
  }
  identity sftp {
    base protocol-type;
    description
    "The identity for sftp.";
  }
  identity http {
    base protocol-type;
    description
    "The identity for http.";
  }
  identity https {
    base protocol-type;
    description
    "The identity for https.";
  }
  identity pop3 {
    base protocol-type;
    description
    "The identity for pop3.";
  }
  identity nat {
    base protocol-type;
    description
    "The identity for nat.";
  }

  identity primary-action {
    description
    "This identity represents the primary actions, such as
    PASS, DROP, ALERT, RATE-LIMIT, and MIRROR.";
  }
  identity pass {
    base primary-action;
    description
    "The identity for pass.";
  }
  identity drop {
    base primary-action;
    description
    "The identity for drop.";
  }
  identity alert {
    base primary-action;
    description
    "The identity for alert.";
  }
  identity rate-limit {
    base primary-action;
    description
    "The identity for rate-limit.";
  }
  identity mirror {
    base primary-action;
    description
    "The identity for mirroring.";
  }
  identity secondary-action {
    description
    "This field identifies additional actions if a rule is
    matched. This could be one of 'LOG', 'SYSLOG',
    'SESSION-LOG', etc.";
  }
  identity log {
    base secondary-action;
    description
    "The identity for logging.";
  }
  identity syslog {
    base secondary-action;
    description
    "The identity for system logging.";
  }
  identity session-log {
    base secondary-action;
    description
    "The identity for session logging.";
  }

  identity owner {
    description
    "This is the base identity for the owner";
  }
  identity dept-head {
    base owner;
    description
    "This represents the identity of the head of department.";
  }
  identity manager {
    base owner;
    description
    "This represents the identity of the manager of the department.";
  }
  identity employee {
    base owner;
    description
    "This represents the identity of department employees.";
  }
  identity sec-head {
    base owner;
    description
    "This represents the identity of the head of security.";
  }
  identity sec-admin {
    base owner;
    description
    "This represents the identity of security admin.";
  }

  identity signature-type {
    description
    "This represents the base identity for signature types.";
  }
  identity signature-yara {
    base signature-type;
    description
    "This represents the YARA signatures.";
  }
  identity signature-snort {
    base signature-type;
    description
    "This represents the SNORT signatures.";
  }
  identity signature-suricata {
    base signature-type;
    description
    "This represents the SURICATA signatures.";
  }

  identity threat-feed-type {
    description
    "This represents the base identity for threat-feed.";
  }
  identity palo-alto {
    base threat-feed-type;
    description
    "This represents Palo-Alto threat-feed.";
  }
  identity rsa-netwitness {
    base threat-feed-type;
    description
    "This represents RSA-netwitness threat-feed.";
  }
  identity fireeye {
    base threat-feed-type;
    description
    "This represents FireEye threat-feed.";
  }
  identity alienvault {
    base threat-feed-type;
    description
    "This represents Alienvault threat-feed.";
  }
/*
 * Groupings
 */

grouping ipv4-list {
  description
  "Grouping for ipv4 based ip-addresses.";
  leaf-list ipv4 {
    type inet:ipv4-address;
    description
    "This is the entry for the ipv4 ip-addresses.";
  }
}

grouping ipv6-list {
  description
  "Grouping for ipv6 based ip-addresses.";
  leaf-list ipv6 {
    type inet:ipv6-address;
    description
    "This is the entry for the ipv6 ip-addresses.";
  }
}

grouping ipv4 {
  description
  "Grouping for ipv4 based ip-address.";
  leaf ipv4 {
    type inet:ipv4-address;
    description
    "This is the entry for the ipv4 ip-address.";
  }
}

grouping ipv6 {
  description
  "Grouping for ipv6 based ip-address.";
  leaf ipv6 {
    type inet:ipv6-address;
    description
    "This is the entry for the ipv6 ip-address.";
  }
}

grouping ip-address-info {
  description
  "There are two types to configure a security policy
    for IPv4 address, such as exact match and range match.";
  choice match-type {
    description
      "User can choose between 'exact match' and 'range match'.";
    case exact-match-ipv4 {
      uses ipv4;
      description
      "Exact ip-address match for ipv4 type addresses";
    }
    case exact-match-ipv6 {
      uses ipv6;
      description
      "Exact ip-address match for ipv6 type addresses";
    }
    case range-match-ipv4 {
      list range-ipv4-address {
        key "start-ipv4-address end-ipv4-address";
        leaf start-ipv4-address {
          type inet:ipv4-address;
          description
            "Start IPv4 address for a range match.";
        }
        leaf end-ipv4-address {
          type inet:ipv4-address;
          description
            "End IPv4 address for a range match.";
        }
        description
          "Range match for an IP-address.";
      }
    }
    case range-match-ipv6 {
      list range-ipv6-address {
        key "start-ipv6-address end-ipv6-address";
        leaf start-ipv6-address {
          type inet:ipv6-address;
          description
            "Start IPv6 address for a range match.";
        }
        leaf end-ipv6-address {
          type inet:ipv6-address;
          description
            "End IPv6 address for a range match.";
        }
        description
          "Range match for an IP-address.";
      }
    }
  }
}

grouping ipsec-based-method {
  description
  "This represents the ipsec-based method.";
  list ipsec-method {
    key "method";
    description
    "This represents the list of IPsec method types.";

    leaf method {
      type identityref {
        base i2nsf-ipsec;
      }
      description
      "This represents IPsec IKE and IPsec IKEless cases.";
    }
  }
}

grouping user-group {
  description
  "The grouping for user-group entities, and
    contains information such as name & ip-address.";
  leaf-list name {
    type leafref {
      path /nacm:nacm/nacm:groups/nacm:group/nacm:user-name;
    }
    description
    "This represents the name of a user.";
  }
  uses ip-address-info;
}

grouping device-group {
  description
  "This group represents device group information
  such as ip-address protocol.";
  leaf name {
    type string;
    description
    "This represents the name of a device.";
  }
  uses ip-address-info;
  leaf-list protocol {
    type identityref {
      base protocol-type;
    }
    description
    "This represents the communication protocols of devices.";
  }
}

grouping location-group {
  description
  "This group represents location-group information
  such as geo-ip and continent.";
  leaf name {
    type string;
    description
    "This represents the name of a location.";
  }
  leaf geo-ip-ipv4 {
    type inet:ipv4-address;
    description
    "This represents the IPv4 geo-ip of a location.";
  }
  leaf geo-ip-ipv6 {
    type inet:ipv6-address;
    description
    "This represents the IPv6 geo-ip of a location.";
  }
  leaf continent {
    type identityref {
      base continent;
        }
    description
      "location-group-based on geo-ip of
      respective continent.";
  }
}

grouping threat-feed-info {
  description
  "This is the grouping for the threat-feed-list";

  leaf feed-name {
    type identityref {
      base threat-feed-type;
    }
    description
    "This represents the name of the a threat-feed.";
  }
  leaf feed-server-ipv4 {
    type inet:ipv4-address;
    description
    "The IPv4 ip-address for the threat-feed server.";
  }
  leaf feed-server-ipv6 {
    type inet:ipv6-address;
    description
    "The IPv6 ip-address for the threat-feed server.";
  }
  leaf feed-description {
    type string;
    description
    "This represents the descriptions of a threat-feed.
    The description should include information, such as
    the type, related threat, method, and file type.";
  }
}

grouping payload-string {
  description
    "The grouping for payload-string content.
    It contains information such as name and string content.";
  leaf payload-description {
    type string;
    description
    "This represents the description of a payload.";
  }
  leaf-list content {
    type string;
    description
    "This represents the payload string content.";
  }
}

grouping owners-ref {
  description
    "This grouping is for owners reference using Network configuration Access Control Model (NACM).";
  leaf-list owners {
    type leafref {
      path /nacm:nacm/nacm:groups/nacm:group/nacm:name;
    }
    description
      "This leaf-list names the owner groups of the
      list instace it sits on. Only the owners and
      super users are authorized to modify the contents.";
  }
}

list i2nsf-cfi-policy {
  key "policy-name";
  description
  "This is the security policy list. Each policy in the list
  contains a list of security rules, and is a policy instance
  to have complete information such as where and when a
  policy needs to be applied.";
  leaf policy-name {
    type string;
    mandatory true;
    description
    "The name which identifies the policy.";
  }
  uses owners-ref;

  container rule{
    description
    "This container is for rules.";
    nacm:default-deny-write;
    list rule {
      leaf rule-name {
        type string;
        mandatory true;
        description
        "This represents the name for the rule.";
      }
      key "rule-name";
      description
      "There can be a single or multiple number of rules.";
      uses owners-ref;

      container event {
        description
        "This represents the event (e.g., a security event,
        which a security rule is made for.)";
        leaf security-event {
          type identityref {
            base security-event-type;
          }
          mandatory true;
          description
          "This contains the description of security events.";
        }
        choice enforce-type {
          description
          "There are three different enforcement types; admin, and time.";
          case enforce-admin {
            leaf admin {
              type identityref {
                base enforce-type;
              }
              description
              "This represents the enforcement type based on admin's
              decision.";
            }
          }
          case time {
            container time-information {
              description
              "The begin-time and end-time information
              when the security rule should be applied.";
              leaf enforce-time {
                type identityref {
                  base enforce-type;
                }
                description
                "The enforcement type is time-enforced.";
              }
              leaf begin-time {
                type yang:date-and-time;
                description
                "This is start time for time zone";
              }
              leaf end-time {
                type yang:date-and-time;
                description
                "This is end time for time zone";
              }
            }
          }
        }
        leaf frequency {
          type enumeration {
            enum only-once {
              description
              "This represents the rule is enforced only once.";
            }
            enum daily {
              description
              "This represents the rule is enforced on a daily basis.";
            }
            enum weekly {
              description
              "This represents the rule is enforced on a weekly basis.";
            }
            enum monthly {
              description
              "This represents the rule is enforced on a monthly basis.";
            }
          }
          default only-once;
          description
          "This represents how frequent the rule should be enforced.";
          }
        }
        container condition {
          description
          "The conditions for general security policies.";
          choice condition {
            description
            "This choice condition is for general firewall.";
            case firewall-condition {
              description
              "The general firewall condition.";
              container firewall-source {
                description
                "This represents the source.";
                leaf src-target {
                  type leafref {
                    path /nacm:nacm/nacm:groups/nacm:group/nacm:user-name;
                  }
                  mandatory true;
                  description
                  "This describes the paths to
                  the source reference.";
                }
              }
              container firewall-destination {
                description
                "This represents the destination.";
                leaf-list dest-target {
                  type leafref {
                    path /nacm:nacm/nacm:groups/nacm:group/nacm:user-name;
                  }
                description
                "This describes the paths to the
                destination target reference.";
                }
              }
            }
            case ddos-condition {
              description
              "The condition for DDoS mitigation.";
              container ddos-source {
                description
                "This represents the source.";
                leaf-list src-target {
                  type leafref {
                  path "/i2nsf-cfi-policy/endpoint-group/device-group/name";
                  }
                description
                "This describes the path to the
                source target references.";
                }
              }
              container ddos-destination {
                description
                "This represents the target.";
                leaf-list dest-target {
                  type leafref {
                  path "/i2nsf-cfi-policy/endpoint-group/device-group/name";
                  }
                  description
                  "This describes the path to the
                  destination target references.";
                }
              }
              container rate-limit {
                description "This describes the rate-limit.";
                leaf packet-per-second {
                  type uint16;
                  description
                  "The rate-limit limits the amount of incoming packets.";
                }
              }
            }
            case custom-condition {
              description
              "The condition based on packet contents.";
              container custon-source {
                description
                "This represents the source.";
                leaf-list src-target {
                  type leafref {
                    path "/i2nsf-cfi-policy/threat-prevention/payload-content/name";
                  }
                description
                "Describes the payload string
                content condition source.";
                }
              }
              container custom-destination {
                description
                "This represents the destination.";
                leaf dest-target {
                  type leafref {
                    path "/i2nsf-cfi-policy/threat-prevention/payload-content/name";
                  }
                mandatory true;
                description
                "Describes the payload string
                content condition destination.";
                }
              }
            }
            case threat-feed-condition {
            description
            "The condition based on the threat-feed information.";
              container threat-feed-source {
                description
                "This represents the source.";
                leaf-list src-target {
                  type leafref {
                  path "/i2nsf-cfi-policy/threat-prevention/threat-feed-list/feed-name";
                  }
                description "Describes the threat-feed
                condition source.";
                }
              }
              container threat-feed-destination {
              description
              "This represents the destination.";
                leaf dest-target {
                  type leafref {
                  path "/i2nsf-cfi-policy/threat-prevention/threat-feed-list/feed-name";
                  }
                mandatory true;
                description "Describes the threat-feed
                condition destination.";
                }
              }
            }
          }
        }
        container action {
        description
          "This is the action container.";
        leaf primary-action {
          type identityref {
            base primary-action;
          }
          mandatory true;
          description
          "This represent the primary actions (e.g., PASS, DROP,
          ALERT, and MIRROR) to be applied a condition.";
        }
        leaf secondary-action {
          type identityref {
            base secondary-action;
          }
          description
          "This represents the secondary actions (e.g., log
          and syslog) to be applied if needed.";
          }
        }
        container ipsec-method {
        description
        "This container represents the IPsec IKE and IKEless cases.";
        leaf method {
          type identityref {
          base i2nsf-ipsec;
          }
          description
          "This references the IPsec method types,
           which includes IPsec IKE and IPsec IKEless cases.";
          }
        }
        leaf owner {
          type identityref {
          base owner;
          }
        mandatory true;
        description
        "This field defines the owner of this
        rule. Only the owner is authorized to
        modify the contents of the rule.";
        }
      }
    }
    container endpoint-group {
    description
    "A logical entity in their business
    environment, where a security policy
    is to be applied.";
    uses user-group;
    list device-group {
    key "name";
    uses device-group;
    description
    "This represents the device group.";
    }
      list location-group{
      key "name";
      uses location-group;
      description
      "This represents the location group.";
      }
    }

    container threat-prevention {
    description
    "this describes the list of threat-prevention.";

    list threat-feed-list {
      key "feed-name";
      description
      "This represents the threat feed list.";
      uses threat-feed-info;

      leaf-list threat-file-types {
        type identityref {
        base malware-file-type;
        }
        default executable-file;
        description
        "This contains a list of file types needed to
        be scanned for the virus.";
      }
      leaf-list signatures {
        type identityref {
          base signature-type;
          }
        default signature-suricata;
        description
        "This contains a list of signatures or hash
        of the threats.";
        }
      }
    list payload-content {
      key "name";
      leaf name {
        type string;
        description
        "This represents the name of payload-content.
        It should give an idea of why specific payload
        content is marked as threat. For example, the name
        'backdoor' indicates the payload content is related
        to backdoor attack.";
        }
      description
      "This represents the payload-string group.";
      uses payload-string;
      }
    }
  }
}
