module ietf-ospf-lls-local-id {
  yang-version 1.1;
  namespace "urn:ietf:params:xml:ns:yang:ietf-ospf-lls-local-id";

  prefix ospf-lls-localid;

  import ietf-routing {
    prefix "rt";
    reference "RFC 8349: A YANG Data Model for Routing
               Management (NMDA Version)";
  }

  import ietf-ospf {
    prefix "ospf";
    reference "RFC 9129: YANG Data Model for the OSPF
               Protocol";
  }

  organization
    "IETF LSR - Link State Routing Working Group";
  contact
     "WG Web:   <https://datatracker.ietf.org/wg/lsr/>
      WG List:  <mailto:lsr@ietf.org>

      Author:   Yingzhen Qu
                <mailto:yingzhen.ietf@gmail.com>
      Author:   Acee Lindem
                <mailto:acee.ietf@gmail.com>";

  description
    "This YANG module defines the configuration and operational
    state for OSPF Link-Local Signaling (LLS) Extensions for Local
    Interface ID Advertisement feature as defined in RFC 8510.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.";

  revision 2024-07-01 {
    description
      "Initial version";
    reference
      "RFC XXXX: OSPF YANG Model Augmentations for Additional
                 Features - Version 1.";
  }

  augment "/rt:routing/rt:control-plane-protocols"
        + "/rt:control-plane-protocol/ospf:ospf" {
    when "../rt:type = 'ospf:ospfv2' or "
       + "../rt:type = 'ospf:ospfv3'" {
      description
        "This augments the OSPF routing protocol when used.";
    }
    description
      "This augments the OSPF protocol configuration
       to support LLS extesnions for interfacde ID as
       defined in RFC 8510.";
    container lls-int-id {
      leaf enable {
        type boolean;
        default false;
        description
          "Enable LLS to advertise local interface ID.";
      }
      description
        "OSPF LLS Extensions for interface ID.";
    }
  }
}
