module abstract-policy{
     yang-version 1;

     namespace "urn:TBD:params:xml:ns:yang:abstract-policy";
     prefix aplc;
     import ietf-complex-types {prefix "ct"; }

     organization "IETF I2RS Working Group";
     contact
       "wangzitao@huawei.com";
     description
       "This module defines common core-network-policy yang data model";

     typedef bnp-group-type {
   type string;
       description "basic network group type";
     }
    typedef bnp-rule-type {
    type string;
       description "basic network policy rule type";
     }
    typedef role-type {
    type string;
       description "basic network policy role type";
     }

grouping bnp-role{
leaf role{
description
"A role is an administratively specified characteristic of a managed element.
As a selector for policies, it determines the applicability of the policy to
a particular managed element.";
type role-type;
}
}

grouping ietf-policy-rule{
ct:complex-type PolicyRule{
list policy-rule{
description
"defines a list of policy rules.";
key "rule-name";
leaf rule-name{
      type string;
      description
      "The entry-index is the identification of the policy-rule-entry list";
  }
leaf rule-type{
description
"The rule-type is used to indicate the type of the policy rule.";
type bnp-rule-type;
}
leaf priority{
description
"The priority leaf indicate the priority of the policy rule.
And it will be used when a single client is sending operations
to accomplish multiple tasks.";
type uint32;
}
leaf sequenced-actions{
description
"This leaf gives a policy administrator a way of specifying
the ordering of the policy actions.";
type enumeration{
enum mandatory{
description
"Do the actions in the indicated order, or don't do them at all.";}
enum recommended{
description
"Do the actions in the indicated order if you can,
but if you can't do them in this order, do them in another order if you can.";}
enum dontCare{
description
"I don't care about the order.";}
}
}

leaf  execution-strategy{
description
"This leaf defines the execution strategy to be used
upon the sequenced actions is this policy-rule.";
type enumeration{
enum DoUntilSuccess {
description
"execute actions according to predefined order,
until successful execution of a single action.";}
enum DoAll{
description
"execute ALL actions which are part of the modeled set,
according to their predefined order. Continue doing this,
even if one or more of the actions fails.";}
enum DoUntilFailure{
description
"execute actions according to predefined order,
until the first failure in execution of a single sub-action.";}
}
}
}
}
}

grouping ietf-role-collection{
container PolicyRoleCollection{
uses bnp-role;
}
}

grouping ietf-filter{
list FilterList{
key "list-name";
leaf list-name{
type string;
}
}
}

grouping ietf-policy-group{
ct:complex-type PolicyGroup{
list policy-group{
key "group-name";
leaf group-name{
description
"The group-name is the identification of the policy-group.";
type string;
}
leaf group-type{
description
"The group-type is used to indicate the type of the policy group.";
type bnp-group-type;
}
}
}
}
ct:complex-type Policy{ct:abstract true;}

ct:complex-type PolicySet{
ct:abstract true;
uses bnp-role;
leaf policy-decision-strategy {
description
"The match-strategy leaf is used to specify
the matching strategy for the policies of the policy rule.
There are two matching strategy: First-Matching and All-Matching.";
type enumeration{
enum First-Matching {
description "The First-Matching strategy is used to cause
the evaluation of the rules in a set such that the only actions
enforced on a given examination of the Policy Set are those for
the first rule that has its conditions evaluate to TRUE.";}
enum All-Matching {
description " The All-Matching strategy is used to cause the
evaluation of all rules in a set; for all of the rules whose
conditions evaluate to TRUE, the actions are enforced.";}
}
}
}

ct:complex-type PolicyCondition{
ct:abstract true;
}
ct:complex-type PolicyAction{
ct:abstract true;
}
ct:complex-type PolicyVariable{
ct:abstract true;
}
ct:complex-type PolicyValue{
ct:abstract true;
}
ct:complex-type Collection{
ct:abstract true;
}

ct:complex-type ManagedSystemElement{
ct:abstract true;
ct:complex-type LogicalElement{
ct:abstract true;
ct:complex-type System{
ct:abstract true;
ct:complex-type AdminDomain{
ct:abstract true;
}
}
ct:complex-type FilterEntryBase{
ct:abstract true;
}

   ct:complex-type PolicyTimePeriodCondition{
      ct:extends PolicyCondition;
  leaf TimePeriod{type string;}
      leaf TimeMask{type yang:date-and-time;}
      leaf LocalOrUtcTime{
  type enumeration{
  enum localTime;
  enum utcTime;
  }
  }
   }

   ct:complex-type PolicyImplicitVariable{
      ct:extends PolicyVariable;
  container PolicySourceIPv4Variable;
      container PolicySourceIPv6Variable;
      container PolicyDestinationIPv4Variable;
      container PolicyDestinationIPv6Variable;
      container PolicySourcePortVariable;
  container PolicyDestinationPortVariable;
      container PolicyIPProtocolVariable;
      container PolicyIPToSVariable;
  container PolicyDSCPVariable;
      container PolicyFlowIdVariable;
      container PolicySourceMACVariable;
      container PolicyDestinationMACVariable;
  container PolicyVLANVariable;
  container PolicyCoSVariable;
      container PolicyEthertypeVariable;
      container PolicySourceSAPVariable;
  container PolicyDestinationSAPVariable;
  container PolicySNAPOUIVariable;
      container PolicySNAPTypeVariable;
      container PolicyFlowDirectionVariable;

   }
   ct:complex-type IpHeadersFilter{
      ct:extends FilterEntryBase;
  container HdrIpVersion;
  container HdrSrcAddress;
  container HdrSrcAddressEndOfRange;
  container HdrSrcMask;
  container HdrDestAddress;
  container HdrDestAddressEndOfRange;
  container HdrDestMask;
  container HdrProtocolID;
  container HdrSrcPortStart;
  container HdrSrcPortEnd;
  container HdrDestPortStart;
  container HdrDestPortEnd;
  container HdrDSCP;
  container HdrFlowLabel;
   }

   ct:complex-type 8021Filter{
      ct:extends FilterEntryBase;
  container 8021HdrSrcMACAddr;
  container 8021HdrSrcMACMask;
  container 8021HdrDestMACAddr;
  container 8021HdrDestMACMask;
  container 8021HdrProtocolID;
  container 8021HdrPriorityValue;
  container 8021HDRVLANID;
   }

}
}
}
