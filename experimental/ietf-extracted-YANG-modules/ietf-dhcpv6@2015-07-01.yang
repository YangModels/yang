module ietf-dhcpv6 {
    namespace "urn:ietf:params:xml:ns:yang:dhc:dhcpv6";
    prefix "dhcpv6";

    import ietf-inet-types {
        prefix inet;
        revision-date "2013-07-15";
    }
    import ietf-yang-types {
        prefix yang;
        revision-date "2013-07-15";
    }

    organization "dhc wg";
    contact "yong@csnet1.cs.tsinghua.edu.cn
            wangh13@mails.tsinghua.edu.cn
            lh.sunlinh@gmail.com
            Ted.Lemon@nominum.com
            ian.farrer@telekom.de";

    description "This model defines a YANG data model that can be used to configure and manage DHCPv6 server, DHCPv6 relay and DHCPv6 client.";

    revision 2015-07-01 { description "version03: Correct grammar errors."; }
    revision 2015-04-13 { description "version02: Correct grammar errors."; }
    revision 2015-04-02 { description "version01: Correct grammar errors, Reuse groupings, Update 'dhcpv6-realy' feature, Add notifications.";}
    revision 2015-03-04 { description "Initial revision."; }

/*
 * Features
 */

    feature dhcpv6-server {
        description
            "Server in DHCPv6.";
        reference
            "RFC3315";
    }

    feature dhcpv6-relay {
        description
            "Relay agent in DHCPv6.";
        reference
            "RFC3315";
    }

    feature dhcpv6-client {
        description
             "Client in DHCPv6.";
        reference
               "RFC3315";
    }
/*
 * Typedef
 */

    typedef threshold {
        description "Threshold value in percent";
        type union {
            type uint16 {
                range 0..100;
            }
            type enumeration {
                enum "disabled" {
                    description "No threshold";
                }
            }
        }
    }
/*
 * Grouping
 */

    grouping vendor-infor {
        container vendor-info {
            description "";
            leaf ent-num {
                mandatory true;
                type uint32;
            }
            leaf-list data {
                type string;
            }
        }
    }

    grouping portset-para {
        container port-parameter {
            leaf offset {
                mandatory true;
                type uint8;
            }
            leaf psid-len {
                mandatory true;
                type uint8;
            }
            leaf psid {
                mandatory true;
                type uint16;
            }
        }
    }

    grouping duid-para {
        container duid {
            leaf duid-type {
                mandatory true;
                type uint16;
            }
            leaf duid-high-1 {
                mandatory true;
                type uint32;
            }
            leaf duid-high-2 {
                mandatory true;
                type uint32;
            }
            leaf duid-low-1 {
                mandatory true;
                type uint32;
            }
            leaf duid-low-2 {
                mandatory true;
                type uint32;
            }
        }
    }

/*
 * Data Nodes
 */

    container server {
        if-feature dhcpv6-server;
        container serv-attributes {
            description "This container contains basic attributes of a DHCPv6 server such as DUID, server name and so on. Some optional functions that can be provided by the server is also included.";
            leaf name {
                mandatory true;
                type string;
            }
            container duid {
                leaf duid-type {
                    mandatory true;
                    type uint16;
                }
                leaf duid-high-1 {
                    mandatory true;
                    type uint32;
                }
                leaf duid-high-2 {
                    mandatory true;
                    type uint32;
                }
                leaf duid-low-1 {
                    mandatory true;
                    type uint32;
                }
                leaf duid-low-2 {
                    mandatory true;
                    type uint32;
                }
                leaf enable {
                    mandatory true;
                    type boolean;
                }
                leaf ipv6-address {
                    mandatory true;
                    type inet:ipv6-address;
                }
                leaf description {
                    type string;
                }
                leaf pd-function {
                    description "Whether the server can act as a delegating router to perform prefix delegation ([RFC3633]).";
                    mandatory true;
                    type boolean;
                }
                leaf stateless-service {
                    description "A boolean value specifies whether the server support client-server exchanges involving two messages defined in ([RFC3315]).";
                    mandatory true;
                    type boolean;
                }
                leaf rapid-commit {
                    description "A boolean value specifies whether the server support client-server exchanges involving two messages defined in ([RFC3315]).";
                    mandatory true;
                    type boolean;
                }
                leaf store-client-link-layer {
                    description ".";
                    type boolean;
                }
                uses vendor-infor;
            }
            container option-sets {
                list option-set {
                    key option-set-id;
                    leaf option-set-id {
                        mandatory true;
                        type uint8;
                    }
                    leaf user-class-value {
                        type string;
                    }
                    leaf enterprise-number {
                        type uint32;
                    }
                    leaf store-client-link-layer {
                        type boolean;
                    }
                    container preference-option {
                        leaf enable {
                            mandatory true;
                            type boolean;
                        }
                        leaf preference-value {
                            mandatory true;
                            type uint8;
                        }
                    }
                    container sip-server-option {
                        leaf enable {
                            mandatory true;
                            type boolean;
                        }
                        list sip-server {
                            key sip-serv-id;
                            leaf sip-serv-id {
                                mandatory true;
                                type uint8;
                            }
                            leaf sip-serv-domain-name {
                                mandatory true;
                                type string;
                            }
                            leaf sip-serv-addr {
                                mandatory true;
                                type inet:ipv6-address;
                            }
                        }
                    }
                    container dns-config-option {
                        leaf enable {
                            mandatory true;
                            type boolean;
                        }
                        list dns-server {
                            key dns-serv-id;
                            leaf dns-serv-id {
                                mandatory true;
                                type uint8;
                            }
                            leaf dns-serv-addr {
                                mandatory true;
                                type inet:ipv6-address;
                            }
                        }
                        leaf domain-search-list {
                            mandatory true;
                            type string;
                        }
                    }
                    container nis-config-option {
                        leaf enable {
                            mandatory true;
                            type boolean;
                        }
                        list nis-server {
                            key nis-serv-id;
                            leaf nis-serv-id {
                                mandatory true;
                                type uint8;
                            }
                            leaf nis-serv-addr {
                                mandatory true;
                                type inet:ipv6-address;
                            }
                        }
                    }
                    container nis-plus-config-option {
                        leaf enable {
                            mandatory true;
                            type boolean;
                        }
                        list nis-plus-server {
                            key nis-plus-serv-id;
                            leaf nis-plus-serv-id {
                                mandatory true;
                                type uint8;
                            }
                            leaf nis-plus-serv-addr {
                                mandatory true;
                                type inet:ipv6-address;
                            }
                        }
                    }
                    container info-refresh-time-option {
                        leaf enable {
                            mandatory true;
                            type boolean;
                        }
                        leaf info-refresh-time {
                            mandatory true;
                            type yang:timeticks;
                        }
                    }
                    container cli-fqdn-option {
                        leaf enable {
                            mandatory true;
                            type boolean;
                        }
                        leaf server-initiate-update {
                            mandatory true;
                            type boolean;
                        }
                        leaf client-initiate-update {
                            mandatory true;
                            type boolean;
                        }
                        leaf modify-name-from-cli {
                            mandatory true;
                            type boolean;
                        }
                    }
                    container timezone-option {
                        leaf enable {
                            mandatory true;
                            type boolean;
                        }
                        leaf tz-posix {
                            mandatory true;
                            type string;
                        }
                        leaf tz-database {
                            mandatory true;
                            type string;
                        }
                    }
                    container ntp-server-option {
                        leaf enable {
                            mandatory true;
                            type boolean;
                        }
                        list ntp-server {
                            key ntp-serv-id;
                            leaf ntp-serv-id {
                                mandatory true;
                                type uint8;
                            }
                            leaf ntp-serv-addr {
                                mandatory true;
                                type inet:ipv6-address;
                            }
                            leaf ntp-serv-mul-addr {
                                mandatory true;
                                type inet:ipv6-address;
                            }
                            leaf ntp-serv-fqdn {
                                mandatory true;
                                type string;
                            }
                        }
                    }
                    container sntp-server-option {
                        leaf enable {
                            mandatory true;
                            type boolean;
                        }
                        list sntp-server {
                            key sntp-serv-id;
                            leaf sntp-serv-id {
                                mandatory true;
                                type uint8;
                            }
                            leaf sntp-serv-addr {
                                mandatory true;
                                type inet:ipv6-address;
                            }
                        }
                    }
                    container network-boot-option {
                        leaf enable {
                            mandatory true;
                            type boolean;
                        }
                        list boot-file {
                            key boot-file-id;
                            leaf boot-file-id {
                                mandatory true;
                                type uint8;
                            }
                            leaf-list suitable-arch-type {
                                type uint16;
                            }
                            leaf-list suitable-net-if {
                                type uint32;
                            }
                             leaf boot-file-url {
                                mandatory true;
                                type string;
                            }
                            list boot-file-paras {
                                key para-id;
                                leaf id {
                                    mandatory true;
                                    type uint8;
                                }
                                    leaf parameter {
                                    mandatory true;
                                    type string;
                                    }
                            }
                        }
                    }
                    container dslite-option {
                        leaf enable {
                            mandatory true;
                            type boolean;
                        }
                        leaf dslite-aftr-name {
                            mandatory true;
                            type string;
                        }
                    }
                    container kerveros-option {
                        leaf enable {
                            mandatory true;
                            type boolean;
                        }
                        leaf default-realm-name {
                            mandatory true;
                            type string;
                        }
                        list kdc-info {
                            key kdc-id;
                            leaf kdc-id {
                                mandatory true;
                                type uint8;
                            }
                            leaf priority {
                                mandatory true;
                                type uint16;
                            }
                            leaf weight {
                                mandatory true;
                                type uint16;
                            }
                            leaf transport-type {
                                mandatory true;
                                type uint8;
                            }
                            leaf port-number {
                                mandatory true;
                                type uint16;
                            }
                            leaf kdc-ipv6-addr {
                                mandatory true;
                                type inet:ipv6-address;
                            }
                            leaf realm-name {
                                mandatory true;
                                type string;
                            }
                        }
                    }
                    container addr-selection-option {
                        leaf enable {
                            mandatory true;
                            type boolean;
                        }
                        leaf a-bit-set {
                            description "";
                            mandatory true;
                            type boolean;
                        }
                        leaf p-bit-set {
                            mandatory true;
                            type boolean;
                        }
                        list policy-table {
                            key policy-id;
                            leaf policy-id {
                                mandatory true;
                                type uint8;
                            }
                            leaf label {
                                mandatory true;
                                type uint8;
                            }
                            leaf precedence {
                                mandatory true;
                                type uint8;
                            }
                            leaf prefix-len {
                                mandatory true;
                                type uint8;
                            }
                            leaf prefix {
                                mandatory true;
                                type inet:ipv6-prefix;
                            }
                        }
                    }
                    container sol-max-rt-option {
                        leaf enable {
                            mandatory true;
                            type boolean;
                        }
                        leaf sol-max-rt-value {
                            mandatory true;
                            type yang:timeticks;
                        }
                    }
                    container inf-max-rt-option {
                        leaf enable {
                            mandatory true;
                            type boolean;
                        }
                        leaf inf-max-rt-value {
                            mandatory true;
                            type yang:timeticks;
                        }
                    }
                    container pcp-server-option {
                        leaf enable {
                            mandatory true;
                            type boolean;
                        }
                        list pcp-server {
                            key pcp-serv-id;
                            leaf pcp-serv-id {
                                mandatory true;
                                type uint8;
                            }
                            leaf pcp-serv-addr {
                                mandatory true;
                                type inet:ipv6-address;
                            }
                        }
                    }
                    container s46-rule-option {
                        leaf enable {
                            mandatory true;
                            type boolean;
                        }
                        list s46-rule {
                            key rule-id;
                            leaf rule-id {
                                mandatory true;
                                type uint8;
                            }
                            leaf rule-type {
                                mandatory true;
                                type enumeration {
                                enum "BMR";
                                enum "FMR";
                                }
                            }
                            leaf prefix4-len {
                                mandatory true;
                                type uint8;
                            }
                            leaf ipv4-prefix {
                                mandatory true;
                                type inet:ipv4-prefix;
                            }
                            leaf prefix6-len {
                                mandatory true;
                                type uint8;
                            }
                            leaf ipv6-prefix {
                                mandatory true;
                                type inet:ipv6-prefix;
                            }
                            uses portset-para;
                        }
                    }
                    container s46-br-option {
                        leaf enable {
                            mandatory true;
                            type boolean;
                        }
                        list br {
                            key br-id;
                            leaf br-id {
                                mandatory true;
                                type uint8;
                            }
                            leaf br-ipv6-addr {
                                mandatory true;
                                type inet:ipv6-address;
                            }
                        }
                    }
                    container s46-dmr-option {
                        leaf enable {
                            description "";
                            mandatory true;
                            type boolean;
                        }
                        list dmr {
                            key dmr-id;
                            leaf dmr-id {
                                mandatory true;
                                type uint8;
                            }
                            leaf dmr-prefix-len {
                                mandatory true;
                                type uint8;
                            }
                            leaf dmr-ipv6-prefix {
                                mandatory true;
                                type inet:ipv6-prefix;
                            }
                        }
                    }
                    container s46-v4-v6-binding-option {
                        leaf enable {
                            mandatory true;
                            type boolean;
                        }
                        list ce {
                            key ce-id;
                            leaf ce-id {
                                mandatory true;
                                type uint8;
                            }
                            leaf ipv4-addr {
                                mandatory true;
                                type inet:ipv4-address;
                            }
                            leaf bind-prefix6-len {
                                mandatory true;
                                type uint8;
                            }
                            leaf bind-ipv6-prefix {
                                mandatory true;
                                type inet:ipv6-prefix;
                            }
                            uses portset-para;
                        }
                    }
                 }
            }
            container network-range {
                leaf-list option-set {
                    type uint8;
                }
                list network-range {
                    key network-range-id;
                    leaf network-range-id {
                        mandatory true;
                        type uint8;
                    }
                    leaf network-description {
                        mandatory true;
                        type string;
                    }
                    leaf network-prefix {
                        mandatory true;
                        type inet:ipv6-prefix;
                    }
                    leaf inherit-option-set {
                        mandatory true;
                        type boolean;
                    }
                    leaf-list option-set {
                        type uint8;
                    }
                    container address-pools {
                        description "A container describes the DHCPv6 server's address pools.";
                        list address-pool {
                            description "A DHCPv6 server can be configured with several address pools. This list defines such address pools which are distinguish by the key called 'pool-name'.";
                            key pool-id;
                            leaf pool-id {
                                mandatory true;
                                type uint8;
                            }
                            leaf pool-prefix {
                                mandatory true;
                                type inet:ipv6-prefix;
                            }
                            leaf start-address {
                                mandatory true;
                                type inet:ipv6-address-no-zone;
                            }
                            leaf end-address {
                                mandatory true;
                                type inet:ipv6-address-no-zone;
                            }
                            leaf preferred-lifetime {
                                mandatory true;
                                type yang:timeticks;
                            }
                            leaf valid-lifetime {
                                mandatory true;
                                type yang:timeticks;
                            }
                            leaf total-ipv6-count {
                                config "false";
                                mandatory true;
                                type uint64;
                            }
                            leaf used-ipv6-count {
                                config "false";
                                mandatory true;
                                type uint64;
                            }
                            leaf utilization-ratio {
                                mandatory true;
                                type threshold;
                            }
                            leaf inherit-option-set {
                                mandatory true;
                                type boolean;
                            }
                            leaf-list option-set {
                                type uint8;
                            }
                            container reserved-addresses {
                                list static-binding {
                                    key cli-id;
                                    leaf cli-id {
                                        mandatory true;
                                        type uint32;
                                    }
                                    uses duid-para;
                                    leaf-list reserv-addr {
                                        type inet:ipv6-address;
                                    }
                                }
                                leaf-list other-reserv-addr {
                                    type inet:ipv6-address;
                                }
                            }
                        }
                        list binding-info {
                            config "false";
                            description "A list records a binding information for each DHCPv6 client that has already been allocated IPv6 addresses.";
                            key cli-id;
                            leaf cli-id {
                                mandatory true;
                                type uint32;
                            }
                            uses duid-para;
                            list cli-ia {
                                key iaid;
                                leaf ia-type {
                                    mandatory true;
                                    type string;
                                }
                                leaf iaid {
                                    mandatory true;
                                    type string;
                                }
                                leaf-list cli-addr {
                                    type inet:ipv6-address;
                                }
                                leaf pool-id {
                                    mandatory true;
                                    type uint8;
                                }
                            }
                        }
                    }
                    container prefix-pools {
                        description "If a server supports prefix delegation function, this container will be used to define the delegating router's refix pools.";
                        list prefix-pool {
                            description "Similar to server's address pools, a delegating router can also be configured with multiple prefix pools specified by a list called 'prefix-pool'.";
                            key pool-id;
                            leaf pool-id {
                                mandatory true;
                                type uint8;
                            }
                            leaf prefix {
                                mandatory true;
                                type inet:ipv6-prefix;
                            }
                            leaf prefix-length {
                                mandatory true;
                                type uint8;
                            }
                            leaf preferred-lifetime {
                                mandatory true;
                                type yang:timeticks;
                            }
                            leaf valid-lifetime {
                                mandatory true;
                                type yang:timeticks;
                            }
                            leaf utilization-ratio {
                                mandatory true;
                                type threshold;
                            }
                            leaf inherit-option-set {
                                mandatory true;
                                type boolean;
                            }
                            leaf-list option-set {
                                type uint8;
                            }
                            container reserved-prefixes {
                                list static-binding {
                                    key cli-id;
                                    leaf cli-id {
                                        mandatory true;
                                        type uint32;
                                    }
                                    uses duid-para;
                                    leaf reserv-prefix-len {
                                        mandatory true;
                                        type uint8;
                                    }
                                    leaf reserv-prefix {
                                        mandatory true;
                                        type inet:ipv6-prefix;
                                    }
                                }
                                leaf exclude-prefix-len {
                                    mandatory true;
                                    type uint8;
                                }
                                leaf exclude-prefix {
                                    mandatory true;
                                    type inet:ipv6-prefix;
                                }
                                list other-reserv-prefix {
                                    key reserv-id;
                                    leaf reserv-id {
                                        mandatory true;
                                        type uint8;
                                    }
                                    leaf prefix-len {
                                        mandatory true;
                                        type uint8;
                                    }
                                    leaf prefix {
                                        mandatory true;
                                        type inet:ipv6-prefix;
                                    }
                                }
                            }
                        }
                        list binding-info {
                            config "false";
                            description "A list records a binding information for each DHCPv6 client that has already been allocated IPv6 addresses.";
                            key cli-id;
                            leaf cli-id {
                                mandatory true;
                                type uint32;
                            }
                            uses duid-para;
                            list cli-iapd {
                                key iaid;
                                leaf iaid {
                                    mandatory true;
                                    type uint8;
                                }
                                leaf-list cli-prefix {
                                    type inet:ipv6-prefix;
                                }
                                leaf-list cli-prefix-len {
                                    type uint8;
                                }
                                leaf pool-id {
                                    mandatory true;
                                    type uint8;
                                }
                            }
                        }
                    }
                    container hosts {
                        list host {
                            key cli-id;
                            leaf cli-id {
                                mandatory true;
                                type uint32;
                            }
                            uses duid-para;
                            leaf inherit-option-set {
                                mandatory true;
                                type boolean;
                            }
                            leaf-list option-set {
                                type uint8;
                            }
                            leaf nis-domain-name {
                                type string;
                            }
                            leaf nis-plus-domain-name {
                                type string;
                            }
                        }
                    }
                }
            }
            container relay-opaque-paras {
                description "This container contains some opaque values in Relay Agent options that need to be configured on the server side only for value match.
                Such Relay Agent options include Interface-Id option, Remote-Id
                option and Subscriber-Id option.";
                list relays {
                    key relay-name;
                    leaf relay-name {
                        mandatory true;
                        type string;
                    }
                    list interface-info {
                        key if-name;
                        leaf if-name {
                            mandatory true;
                            type string;
                        }
                        leaf interface-id {
                            mandatory true;
                            type string;
                        }
                    }
                    list subscribers {
                        key subscriber;
                        leaf subscriber {
                            mandatory true;
                            type uint8;
                        }
                        leaf subscriber-id {
                            mandatory true;
                            type string;
                        }
                    }
                    list remote-host {
                        key ent-num;
                        leaf ent-num {
                            mandatory true;
                            type uint32;
                        }
                        leaf remote-id {
                            mandatory true;
                            type string;
                        }
                    }
                }
            }
            container rsoo-enabled-options {
                list rsoo-enable-option{
                    key option-code;
                    leaf option-code {
                        mandatory true;
                        type uint16;
                    }
                    leaf description {
                        mandatory true;
                        type string;
                    }
                }
            }
            container packet-stats {
                config "false";
                description "A container presents the packet statistics related to the DHCPv6 server.";
                leaf solicit-count {
                    mandatory true;
                    type uint32;
                }
                leaf request-count {
                    mandatory true;
                    type uint32;
                }
                leaf renew-count {
                    mandatory true;
                    type uint32;
                }
                leaf rebind-count {
                    mandatory true;
                    type uint32;
                }
                leaf decline-count {
                    mandatory true;
                    type uint32;
                }
                leaf release-count {
                    mandatory true;
                    type uint32;
                }
                leaf info-req-count {
                    mandatory true;
                    type uint32;
                }
                leaf advertise-count {
                    mandatory true;
                    type uint32;
                }
                leaf confirm-count {
                    mandatory true;
                    type uint32;
                }
                leaf reply-count {
                    mandatory true;
                    type uint32;
                }
                leaf reconfigure-count {
                    mandatory true;
                    type uint32;
                }
                leaf relay-forward-count {
                    mandatory true;
                    type uint32;
                }
                leaf relay-reply-count {
                    mandatory true;
                    type uint32;
                }
            }
        }
    }
    container relay {
        if-feature dhcpv6-relay;
        container relay-attributes {
            description "A container describes some basic attributes of the relay agent including some relay agent specific options data that need to be configured previously. Such options include Remote-Id option and Subscriber-Id option.";
            leaf name {
                mandatory true;
                type string;
            }
            leaf enable {
                mandatory true;
                type boolean;
            }
            leaf ipv6-address {
                mandatory true;
                type inet:ipv6-address;
            }
            leaf description {
                type string;
            }
            leaf-list dest-addrs {
                description "Each DHCPv6 relay agent may be configured with a list of destination addresses. This node defines such a list of IPv6 addresses that may include unicast addresses, multicast addresses or other addresses.";
                type inet:ipv6-address;
            }
            list subscribers {
                key subscriber;
                leaf subscriber {
                    mandatory true;
                    type uint8;
                }
                leaf subscriber-id {
                    mandatory true;
                    type string;
                }
            }
            list remote-host {
                key ent-num;
                leaf ent-num {
                    mandatory true;
                    type uint32;
                }
                leaf remote-id {
                    mandatory true;
                    type string;
                }
            }
            uses vendor-infor;
            container relay-supplied-options-option {
                list rsoo-set {
                    key rsoo-set-id;
                    leaf rsoo-set-id {
                        mandatory true;
                        type uint8;
                    }
                    container erp-local-domain-name-option {
                        leaf enable {
                            mandatory true;
                            type boolean;
                        }
                        list erp-for-client {
                            key cli-id;
                            leaf cli-id {
                                mandatory true;
                                type uint32;
                            }
                            uses duid-para;
                            leaf erp-name {
                                mandatory true;
                                type string;
                            }
                        }
                    }
                }
            }
            container relay-interfaces {
                description "It is a container that defines common configuration and state parameters in the interfaces of a DHCPv6 relay agent. In this YANG data model for DHCPv6 relay agent, the parameters are configured in a per-interface manner.";
                list relay-if {
                    description "A list describes a specific interface and its corresponding parameters. Here we use a string called 'ifName' as the key of list.";
                    key if-name;
                    leaf if-name {
                        mandatory true;
                        type string;
                    }
                    leaf enable {
                        mandatory true;
                        type boolean;
                    }
                    leaf interface-id {
                        type string;
                    }
                    leaf-list rsoo-set {
                        type uint8;
                    }
                    list pd-route {
                        key pd-route-id;
                        leaf pd-route-id {
                            mandatory true;
                            type uint8;
                        }
                        leaf requesting-router-id {
                            mandatory true;
                            type uint32;
                        }
                        leaf delegating-router-id {
                            mandatory true;
                            type uint32;
                        }
                        leaf next-router {
                            mandatory true;
                            type inet:ipv6-address;
                        }
                        leaf last-router {
                            mandatory true;
                            type inet:ipv6-address;
                        }
                    }
                    list next-entity {
                        description "This node defines a list that is used to describe the next hop entity of this relay distinguished by their addresses.";
                        key dest-addr;
                        leaf dest-addr {
                            mandatory true;
                            type inet:ipv6-address;
                        }
                        leaf available {
                            mandatory true;
                            type boolean;
                        }
                        leaf multicast {
                            mandatory true;
                            type boolean;
                        }
                        leaf server {
                            mandatory true;
                            type boolean;
                        }
                        container packet-stats {
                            config "false";
                            leaf cli-packet-rvd-count {
                                mandatory true;
                                type uint32;
                            }
                            leaf solicit-rvd-count {
                                mandatory true;
                                type uint32;
                            }
                            leaf request-rvd-count {
                                mandatory true;
                                type uint32;
                            }
                            leaf renew-rvd-count {
                                mandatory true;
                                type uint32;
                            }
                            leaf rebind-rvd-count {
                                mandatory true;
                                type uint32;
                            }
                            leaf decline-rvd-count {
                                mandatory true;
                                type uint32;
                            }
                            leaf release-rvd-count {
                                mandatory true;
                                type uint32;
                            }
                            leaf info-req-rvd-count {
                                mandatory true;
                                type uint32;
                            }
                            leaf relay-for-rvd-count {
                                mandatory true;
                                type uint32;
                            }
                            leaf relay-rep-rvd-count {
                                mandatory true;
                                type uint32;
                            }
                            leaf packet-to-cli-count {
                                mandatory true;
                                type uint32;
                            }
                            leaf adver-sent-count {
                                mandatory true;
                                type uint32;
                            }
                            leaf confirm-sent-count {
                                mandatory true;
                                type uint32;
                            }
                            leaf reply-sent-count {
                                mandatory true;
                                type uint32;
                            }
                            leaf reconfig-sent-count {
                                mandatory true;
                                type uint32;
                            }
                            leaf relay-for-sent-count {
                                mandatory true;
                                type uint32;
                            }
                            leaf relay-rep-sent-count {
                                mandatory true;
                                type uint32;
                            }
                        }
                    }
                }
            }
            container relay-stats {
                config "false";
                leaf cli-packet-rvd-count {
                    mandatory true;
                    type uint32;
                }
                leaf relay-for-rvd-count {
                    mandatory true;
                    type uint32;
                }
                leaf relay-rep-rvd-count {
                    mandatory true;
                    type uint32;
                }
                leaf packet-to-cli-count {
                    mandatory true;
                    type uint32;
                }
                leaf relay-for-sent-count {
                    mandatory true;
                    type uint32;
                }
                leaf relay-rep-sent-count {
                    mandatory true;
                    type uint32;
                }
                leaf discarded-packet-count {
                    mandatory true;
                    type uint32;
                }
            }
        }
    }
    container client {
        if-feature dhcpv6-client;
        container client-interfaces {
            description "A client may have several interfaces, it is more reasonable to configure and manage parameters on the interface-level. This container includes configuration and state data of a DHCPv6 client in a per-interface manner.";
            list client-if {
                description "The list defines a specific client interface and its data. Different interfaces are distinguished by the key which is a configurable string value.";
                key if-name;
                leaf if-name {
                    mandatory true;
                    type string;
                }
                leaf cli-id {
                    mandatory true;
                    type uint32;
                }
                uses duid-para;
                leaf enable {
                    mandatory true;
                    type boolean;
                }
                leaf description {
                    type string;
                }
                leaf pd-function {
                    description "Whether the client can act as a requesting router to request prefixes using prefix delegation ([RFC3633]).";
                    mandatory true;
                    type boolean;
                }
                leaf rapid-commit {
                    description "'1' indicates a client can initiate a Solicit-Reply message exchange by adding a Rapid Commit option in Solicit message. '0' means the client is not allowed to add a Rapid Commit option to request addresses in a two-message exchange pattern.";
                    mandatory true;
                    type boolean;
                }
                container mo-tab {
                    description "The management tab label indicates the operation mode of the DHCPv6 client. 'm'=1 and 'o'=1 indicate the client will use DHCPv6 to obtain all the configuration data. 'm'=1 and 'o'=0 are a meaningless combination. 'm'=0 and 'o'=1 indicate the client will use stateless DHCPv6 to obtain configuration data apart from addresses/prefixes data. 'm'=0 and 'o'=0 represent the client will not use DHCPv6 but use SLAAC to achieve configuration.";
                    leaf m-tab {
                        mandatory true;
                        type boolean;
                    }
                    leaf o-tab {
                        mandatory true;
                        type boolean;
                    }
                }
                container oro-options {
                    list oro-option {
                        key option-code;
                        leaf option-code {
                            mandatory true;
                            type uint16;
                        }
                        leaf description {
                            mandatory true;
                            type string;
                        }
                    }
                }
                container client-cofigured-options {
                    container user-class-option {
                        leaf enable {
                            mandatory true;
                            type boolean;
                        }
                        list user-class {
                            key user-class-id;
                            leaf user-class-id {
                                mandatory true;
                                type uint8;
                            }
                            leaf user-class-info {
                                mandatory true;
                                type string;
                            }
                        }
                    }
                    container vendor-class-option {
                        leaf enable {
                            mandatory true;
                            type boolean;
                        }
                        leaf ent-num {
                            mandatory true;
                            type uint32;
                        }
                        leaf-list data {
                            type string;
                        }
                    }
                    container client-fqdn-option {
                        leaf enable {
                            mandatory true;
                            type boolean;
                        }
                        leaf fqdn {
                            mandatory true;
                            type string;
                        }
                        leaf server-initiate-update {
                            mandatory true;
                            type boolean;
                        }
                        leaf client-initiate-update {
                            mandatory true;
                            type boolean;
                        }
                    }
                    container client-architecture-type-option {
                        leaf enable {
                            mandatory true;
                            type boolean;
                        }
                        list architecture-types {
                            key type-id;
                            leaf type-id {
                                mandatory true;
                                type uint16;
                            }
                            leaf most-preferred {
                                mandatory true;
                                type boolean;
                            }
                        }
                    }
                    container client-network-interface-option {
                        leaf enable {
                            mandatory true;
                            type boolean;
                        }
                        leaf type {
                            mandatory true;
                            type uint8;
                        }
                        leaf major {
                            mandatory true;
                            type uint8;
                        }
                        leaf minor {
                            mandatory true;
                            type uint8;
                        }
                    }
                    container kerberos-principal-name-option {
                        leaf enable {
                            mandatory true;
                            type boolean;
                        }
                        leaf principal-name {
                            mandatory true;
                            type string;
                        }
                    }
                    container client-link-layer-addr-option {
                        leaf enable {
                            mandatory true;
                            type boolean;
                        }
                        leaf link-layer-type {
                            mandatory true;
                            type uint16;
                        }
                        leaf link-layer-addr {
                            mandatory true;
                            type string;
                        }
                    }
                }
                container identity-associations {
                    config "false";
                    description "IA is a construct through which a server and a client can identify, group, and manage a set of related IPv6 addresses. The key of the list is a 4-byte number IAID defined in [RFC3315] .";
                    list identity-association {
                        key iaid;
                        leaf iaid {
                            mandatory true;
                            type uint32;
                        }
                        leaf ia-type {
                            mandatory true;
                            type string;
                        }
                        leaf-list ipv6-addr {
                            type inet:ipv6-address;
                        }
                        leaf-list ipv6-prefix {
                            type inet:ipv6-prefix;
                        }
                        leaf-list prefix-length {
                            type uint8;
                        }
                        leaf t1-time {
                            mandatory true;
                            type yang:date-and-time;
                        }
                        leaf t2-time {
                            mandatory true;
                            type yang:date-and-time;
                        }
                        leaf preferred-lifetime {
                            mandatory true;
                            type yang:timeticks;
                        }
                        leaf valid-lifetime {
                            mandatory true;
                            type yang:timeticks;
                        }
                    }
                }
                container if-other-paras {
                    config "false";
                    description "A client can obtain extra configuration data other than address and prefix information through DHCPv6. This container describes such data the client was configured. The potential configuration data may include DNS server addresses, SIP server domain names, etc.";
                    leaf-list uni-dhcpv6-serv-addr {
                        type inet:ipv6-address;
                    }
                    container dns-paras {
                        leaf domain-search-list {
                            mandatory true;
                            type string;
                        }
                        list dns-servers {
                            key dns-serv-id;
                            leaf dns-serv-id {
                                mandatory true;
                                type uint8;
                            }
                            leaf dns-serv-addr {
                                mandatory true;
                                type inet:ipv6-address;
                            }
                        }
                    }
                    container sip-paras {
                        list sip-servers {
                            key sip-serv-id;
                            leaf sip-serv-id {
                                mandatory true;
                                type uint8;
                            }
                            leaf sip-serv-addr {
                                mandatory true;
                                type inet:ipv6-address;
                            }
                            leaf sip-serv-domain-name {
                                mandatory true;
                                type string;
                            }
                        }
                    }
                    container nis-paras {
                        leaf nis-domain-name {
                            mandatory true;
                            type string;
                        }
                        list nis-server {
                            key nis-serv-id;
                            leaf nip-serv-id {
                                mandatory true;
                                type uint8;
                            }
                            leaf nip-serv-addr {
                                mandatory true;
                                type inet:ipv6-address;
                            }
                        }
                    }
                    container nis-plus-paras {
                        leaf nis-plus-domain-name {
                            mandatory true;
                            type string;
                        }
                        list nis-plus-server {
                            key nis-plus-serv-id;
                            leaf nip-plus-serv-id {
                                mandatory true;
                                type uint8;
                            }
                            leaf nip-plus-serv-addr {
                                mandatory true;
                                type inet:ipv6-address;
                            }
                        }
                    }
                    leaf info-refresh-time {
                        type yang:timeticks;
                    }
                    container time-zone-paras {
                        leaf tz-posix {
                            mandatory true;
                            type string;
                        }
                        leaf tz-database {
                            mandatory true;
                            type string;
                        }
                    }
                    leaf cli-fqdn {
                        type string;
                    }
                    container ntp-paras {
                        list ntp-server {
                            key ntp-serv-id;
                            leaf ntp-serv-id {
                                mandatory true;
                                type uint8;
                            }
                            leaf ntp-serv-addr {
                                mandatory true;
                                type inet:ipv6-address;
                            }
                            leaf ntp-serv-mul-addr {
                                mandatory true;
                                type inet:ipv6-address;
                            }
                            leaf ntp-serv-fqdn {
                                mandatory true;
                                type string;
                            }
                        }
                    }
                    container sntp-paras {
                        list sntp-server {
                            key sntp-serv-id;
                            leaf sntp-serv-id {
                                mandatory true;
                                type uint8;
                            }
                            leaf sntp-serv-addr {
                                mandatory true;
                                type inet:ipv6-address;
                            }
                        }
                    }
                    container network-boot-paras {
                        list boot-file {
                            key boot-file-id;
                            leaf boot-file-id {
                                mandatory true;
                                type uint8;
                            }
                            leaf-list suitable-arch-type {
                                type uint16;
                            }
                            leaf-list suitable-net-if {
                                type uint32;
                            }
                            leaf boot-file-url {
                                mandatory true;
                                type string;
                            }
                            list boot-file-paras {
                                key para-id;
                                leaf para-id {
                                    mandatory true;
                                    type uint8;
                                }
                                leaf parameter {
                                    mandatory true;
                                    type string;
                                }
                            }
                        }
                    }
                    container kerveros-paras {
                        leaf default-realm-name {
                            mandatory true;
                            type string;
                        }
                        list kdc-info {
                            key kdc-id;
                            leaf kdc-id {
                                mandatory true;
                                type uint8;
                            }
                            leaf priority {
                                mandatory true;
                                type uint16;
                            }
                            leaf weight {
                                mandatory true;
                                type uint16;
                            }
                            leaf transport-type {
                                mandatory true;
                                type uint8;
                            }
                            leaf port-number {
                                mandatory true;
                                type uint16;
                            }
                            leaf kdc-ipv6-addr {
                                mandatory true;
                                type inet:ipv6-address;
                            }
                            leaf realm-name {
                                mandatory true;
                                type string;
                            }
                        }
                    }
                    container addr-selection-paras {
                        leaf automatic-row-add {
                            mandatory true;
                            type boolean;
                        }
                        leaf prefer-temporary-addr {
                            mandatory true;
                            type boolean;
                        }
                        list policy-table {
                            key policy-id;
                            leaf policy-id {
                                mandatory true;
                                type uint8;
                            }
                            leaf label {
                                mandatory true;
                                type uint8;
                            }
                            leaf precedence {
                                mandatory true;
                                type uint8;
                            }
                            leaf prefix-len {
                                mandatory true;
                                type uint8;
                            }
                            leaf prefix {
                                mandatory true;
                                type inet:ipv6-prefix;
                            }
                        }
                    }
                    leaf sol-max-rt {
                        mandatory true;
                        type yang:timeticks;
                    }
                    leaf inf-max-rt {
                        mandatory true;
                        type yang:timeticks;
                    }
                    container pcp-server-paras {
                        list pcp-server {
                            key pcp-serv-id;
                            leaf pcp-serv-id {
                                mandatory true;
                                type uint8;
                            }
                            leaf pcp-serv-addr {
                                mandatory true;
                                type inet:ipv6-address;
                            }
                        }
                    }
                    container s46-rule-paras {
                        list s46-rule {
                            key rule-id;
                            leaf rule-id {
                                mandatory true;
                                type uint8;
                            }
                            leaf rule-type {
                                mandatory true;
                                type enumeration {
                                enum "BMR";
                                enum "FMR";
                                }
                            }
                            leaf ea-len {
                                mandatory true;
                                type uint8;
                            }
                            leaf prefix4-len {
                                mandatory true;
                                type uint8;
                            }
                            leaf ipv4-prefix {
                                mandatory true;
                                type inet:ipv4-prefix;
                            }
                            leaf prefix6-len {
                                mandatory true;
                                type uint8;
                            }
                            leaf ipv6-prefix {
                                mandatory true;
                                type inet:ipv6-prefix;
                            }
                            uses portset-para;
                        }
                    }
                    container s46-br-paras {
                        list br {
                            key br-id;
                            leaf br-id {
                                mandatory true;
                                type uint8;
                            }
                            leaf br-ipv6-addr {
                                mandatory true;
                                type inet:ipv6-address;
                            }
                        }
                    }
                    container s46-dmr-paras {
                        list dmr {
                            key dmr-id;
                            leaf dmr-id {
                                mandatory true;
                                type uint8;
                            }
                            leaf dmr-prefix-len {
                                mandatory true;
                                type uint8;
                            }
                            leaf dmr-ipv6-prefix {
                                mandatory true;
                                type inet:ipv6-prefix;
                            }
                        }
                    }
                    container s46-v4-v6-binding-paras {
                        leaf ipv4-addr {
                            mandatory true;
                            type inet:ipv4-address;
                        }
                        leaf bind-prefix6-len {
                            mandatory true;
                            type uint8;
                        }
                        uses portset-para;
                        leaf erp-local-domain-name {
                            mandatory true;
                            type string;
                        }
                    }
                    container supported-options {
                        list supported-option {
                            key option-code;
                            leaf option-code {
                                mandatory true;
                                type uint16;
                            }
                            leaf description {
                                mandatory true;
                                type string;
                            }
                        }
                    }
                }
                container packet-stats {
                    config "false";
                    description "A container records all the packet status information of a specific interface.";
                    leaf solicit-count {
                        mandatory true;
                        type uint32;
                    }
                    leaf request-count {
                        mandatory true;
                        type uint32;
                    }
                    leaf renew-count {
                        mandatory true;
                        type uint32;
                    }
                    leaf rebind-count {
                        mandatory true;
                        type uint32;
                    }
                    leaf decline-count {
                        mandatory true;
                        type uint32;
                    }
                    leaf release-count {
                        mandatory true;
                        type uint32;
                    }
                    leaf info-req-count {
                        mandatory true;
                        type uint32;
                    }
                    leaf advertise-count {
                        mandatory true;
                        type uint32;
                    }
                    leaf confirm-count {
                        mandatory true;
                        type uint32;
                    }
                    leaf reply-count {
                        mandatory true;
                        type uint32;
                    }
                    leaf reconfigure-count {
                        mandatory true;
                        type uint32;
                    }
                }
            }
        }
    }

/*
 * Notifications
 */

    notification notifications {
        container dhcpv6-server-event {
            if-feature dhcpv6-server;
            container pool-running-out {
                leaf utilization-ratio {
                    mandatory true;
                    type uint16;
                }
                uses duid-para;
                leaf serv-name {
                    type string;
                }
                leaf pool-name {
                    mandatory true;
                    type string;
                }
            }
            container invalid-client-detected {
                uses duid-para;
                leaf description {
                    type string;
                }
            }
        }
        container dhcpv6-relay-event {
            if-feature dhcpv6-relay;
            container topo-changed {
                leaf relay-if-name {
                    mandatory true;
                    type string;
                }
                leaf first-hop {
                    mandatory true;
                    type boolean;
                }
                leaf last-entity-addr {
                    mandatory true;
                    type inet:ipv6-address;
                }
            }
        }
        container dhcpv6-client-event {
            if-feature dhcpv6-client;
            container ia-lease-event {
                leaf event-type {
                    mandatory true;
                    type enumeration{
                    enum "allocation";
                    enum "rebind";
                    enum "renew";
                    enum "release";
                    }
                }
                uses duid-para;
                leaf iaid {
                    mandatory true;
                    type uint32;
                }
                leaf serv-name {
                    type string;
                }
                leaf description {
                    type string;
                }
            }
            container invalid-ia-detected {
                uses duid-para;
                leaf cli-duid {
                    mandatory true;
                    type uint32;
                }
                leaf iaid {
                    mandatory true;
                    type uint32;
                }
                leaf serv-name {
                    type string;
                }
                leaf description {
                    type string;
                }
            }
            container retransmission-failed {
                uses duid-para;
                leaf description {
                    mandatory true;
                    type enumeration {
                        enum "MRC failed";
                        enum "MRD failed";
                    }
                }
            }
            container failed-status-turn-up {
                uses duid-para;
                leaf status-code {
                    mandatory true;
                    type enumeration {
                        enum "1" {
                            description "UnspecFail";
                        }
                        enum "2" {
                            description "NoAddrAvail";
                        }
                        enum "3" {
                            description "NoBinding";
                        }
                        enum "4" {
                            description "NotOnLink";
                        }
                        enum "5" {
                            description "UseMulticast";
                        }
                    }
                }
            }
        }
    }
}
