module ietf-schc-mgmt-basic {
  yang-version 1.1;
  namespace "urn:ietf:params:xml:ns:yang:ietf-schc-mgmt-basic";
  prefix schc-bmgmt;

  import ietf-schc {
    prefix schc;
    reference
      "draft-toutain-schc-rfc9363bis A YANG Data Model for Static
       Context Header Compression (SCHC)";
  }

  organization
    "IETF Static Context Header Compression (schc) Working Group";
  contact
    "WG Web:   <https://datatracker.ietf.org/wg/schc/about/>
     WG List:  <mailto:schc@ietf.org>
     Editor:   Laurent Toutain
       <mailto:laurent.toutain@imt-atlantique.fr>";
  description
    "Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     This module defines the basic management operations of the
     SCHC Rules with CORECONF: the 'duplicate-rule' and
     'reset-context' RPCs.";

  revision 2026-10-29 {
    description
      "Initial version, with the 'duplicate-rule' RPC moved from the
       'ietf-schc' module, and the 'reset-context' RPC.";
    reference
      "draft-toutain-schc-coreconf-management CORECONF Rule
       management for SCHC";
  }

  rpc duplicate-rule {
    if-feature "schc:management";
    description
      "Duplicate an existing Rule, given by 'from', into a new Rule,
       given by 'to', which does not exist yet. The new Rule may be
       updated with the CORECONF iPATCH payload carried in
       'ipatch-sequence' before it is added to the Set of Rules.
       The 'from' Rule can be an origin Rule, except a management
       Rule. The new Rule is created as any Rule created by
       management, and is never an origin Rule.";
    input {
      container from {
        description
          "Rule ID of the existing Rule to duplicate.";
        uses schc:rule-id-type;
      }
      container to {
        description
          "Rule ID of the new Rule.";
        uses schc:rule-id-type;
      }
      leaf ipatch-sequence {
        type binary;
        description
          "CBOR sequence of a CORECONF iPATCH payload, applied to the
           new Rule before it is added. This parameter is optional;
           when it is absent, the new Rule is an exact copy.";
      }
    }
    output {
      leaf status {
        type enumeration {
          enum success-with-validation {
            value 0;
            description
              "The new Rule has been created and validated.";
          }
          enum success-not-validated {
            value 1;
            description
              "The new Rule has been created, but not validated
               yet.";
          }
          enum to-rule-already-exists {
            value -1;
            description
              "The Rule ID given by 'to' already exists.";
          }
          enum from-rule-not-found {
            value -2;
            description
              "The Rule ID given by 'from' does not exist.";
          }
          enum invalid-ipatch {
            value -3;
            description
              "The 'ipatch-sequence' cannot be applied to the new
               Rule.";
          }
        }
        description
          "Result of the duplication. A negative value indicates that
           the duplication did not take place.";
      }
    }
  }

  rpc reset-context {
    if-feature "schc:management";
    description
      "Reset the Set of Rules to its initial content: only the
       origin Rules are kept. Every other Rule, whatever its status,
       becomes invalid, and its RuleID becomes free when the guard
       period is over. The node that invokes the RPC applies the
       reset when it sends the request, the node that receives it
       applies the reset when it receives the request.";
    output {
      leaf status {
        type enumeration {
          enum success {
            value 0;
            description
              "The reset has been applied.";
          }
        }
        description
          "Result of the reset. A reset that cannot be applied is
           refused with a CoAP error code.";
      }
    }
  }
}
