module ietf-network-inventory-topology {
  yang-version 1.1;
  namespace
    "urn:ietf:params:xml:ns:yang:ietf-network-inventory-topology";
  prefix nwit;

  import ietf-network {
    prefix nw;
    reference
      "RFC 8345: A YANG Data Model for Network Topologies";
  }
  import ietf-network-topology {
    prefix nt;
    reference
      "RFC 8345: A YANG Data Model for Network Topologies";
  }
  import ietf-network-inventory {
    prefix nwi;
    reference
      "RFC AAAA: A YANG Data Model for Network Inventory";
  }

  organization
    "IETF Network Inventory YANG (ivy) Working Group";
  contact
    "WG Web:   <https://datatracker.ietf.org/wg/ivy>
     WG List:  <mailto:inventory-yang@ietf.org>

     Editor: Bo Wu
          <lana.wubo@huawei.com>
     Editor: Cheng Zhou
          <zhouchengyjy@chinamobile.com>
     Editor: Qin Wu
          <bill.wu@huawei.com>
     Editor: Mohamed Boucadair
          <mohamed.boucadair@orange.com>";
  description
    "This YANG module defines XXX.

     Copyright (c) 2024 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.";

  revision 2024-04-29 {
    description
      "Initial revision.";
    reference
      "RFC XXXX: A YANG Data Model for Network Inventory Mapping
                     Topology";
  }

  /* Identities */
  /* Typedef */

  typedef ne-ref {
    type leafref {
      path "/nwi:network-inventory/nwi:network-elements"
         + "/nwi:network-element/nwi:ne-id";
    }
    description
      "This type is used by data models that need to reference
       Network Element.";
  }

  /* Groupings */

  grouping inventory-mapping-network-type {
    description
      "Indicates the topology type to be Network Inventory mapping.";
    container network-inventory-mapping {
      presence "Indicates Network Inventory mapping topology.";
      description
        "The presence of the container node indicates
         Network Inventory mapping.";
    }
  }

  grouping system-mount-point {
    description
      "Indicates system configuration or state mount point.";
    container system-mount-point {
      description
        "Container for system configuration or state mount point.";
    }
  }

  grouping node-inventory-attributes {
    description
      "Network Inventory mapping node scope attributes";
    container inventory-mapping-attributes {
      description
        "The container node attributes of Network Inventory mapping.";
      leaf node-name {
        type string;
        description
          "The name of the node.";
      }
      leaf ne-ref {
        type ne-ref;
        config false;
        description
          "The reference of the Network Element (NE) from which this
           node is abstracted.";
      }
      uses system-mount-point;
    }
  }

  grouping termination-point-inventory-attributes {
    description
      "Network Inventory mapping termination point (TP) scope
       attributes";
    container inventory-mapping-attributes {
      description
        "The container TP attributes of Network Inventory mapping.";
      leaf tp-name {
        type string;
        config false;
        description
          "The name of the TP.";
      }
      leaf port-component-ref {
        type leafref {
          path
            "/nwi:network-inventory/nwi:network-elements"
          + "/nwi:network-element[nwi:ne-id=current()/../../../"
          + "inventory-mapping-attributes/ne-ref]/nwi:components"
          + "/nwi:component/nwi:component-id";
        }
        config false;
        description
          "The reference of the port component from which this
           termination point is abstracted.";
      }
      leaf-list interface-name {
        type string;
        description
          "Name of the interface.  The name can (but does not
           have to) correspond to an interface reference of a
           containing node's interface, i.e., the path name of a
           corresponding interface data node on the containing
           node is reminiscent of data type interface-ref defined
           in RFC 8343.  It should be noted that data type
           interface-ref of RFC 8343 cannot be used directly,
           as this data type is used to reference an interface
           in a datastore of a single node in the network, not
           to uniquely reference interfaces across a network.";
      }
      uses system-mount-point;
    }
  }

  grouping link-inventory-attributes {
    description
      "Network Inventory mapping link scope attributes";
    container inventory-mapping-attributes {
      description
        "The container link attributes of network inventory mapping.";
      leaf link-name {
        type string;
        description
          "The name of the link.";
      }
      leaf cable-name {
        type string;
        config false;
        description
          "The reference of the cable inventory from which
           this link is abstracted
           Note: this will be changed based on the future inventoy
           cable model.";
      }
      leaf link-type {
        type string;
        config false;
        description
          "The type of the link.
           Note: this will be changed based on the future inventoy
           cable model.";
      }
    }
  }

  /* Main blocks */

  augment "/nw:networks/nw:network/nw:network-types" {
    description
      "Introduces new network type for network inventory mapping.";
    uses inventory-mapping-network-type;
  }

  augment "/nw:networks/nw:network/nw:node" {
    when '/nw:networks/nw:network/nw:network-types/
   nwit:network-inventory-mapping' {
      description
        "Augmentation parameters apply only for network inventory
         mapping.";
    }
    description
      "Configuration parameters for inventory at the node
       level.";
    uses node-inventory-attributes;
  }

  augment "/nw:networks/nw:network/nt:link" {
    when '/nw:networks/nw:network/nw:network-types/
     nwit:network-inventory-mapping' {
      description
        "Augmentation parameters apply only for network
         inventory.";
    }
    description
      "Augments inventory topology link information.";
    uses link-inventory-attributes;
  }

  augment
    "/nw:networks/nw:network/nw:node/nt:termination-point" {
      when '/nw:networks/nw:network/nw:network-types/
     nwit:network-inventory-mapping' {
        description
          "Augmentation parameters apply only for network
           inventory.";
      }
      description
        "Augments inventory termination point information.";
      uses termination-point-inventory-attributes;
  }
}
