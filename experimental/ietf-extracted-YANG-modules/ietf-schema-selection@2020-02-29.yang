module ietf-schema-selection {
  yang-version 1.1;
  namespace
    "urn:ietf:params:xml:ns:yang:ietf-schema-selection";
  prefix "schema";

  import ietf-yang-revisions {
    prefix rev;
    reference "XXXX: Updated YANG Module Revision Handling";
  }

  import ietf-datastores {
    prefix ds;
    rev:revision-or-derived 2018-02-14;
    reference
      "RFC 8342: Network Management Datastore Architecture (NMDA)";
  }

  import ietf-yang-packages {
    prefix pkgs;
    rev:revision-or-derived 0.2.0;
    reference "RFC XXX: YANG Packages.";
  }

  organization
    "IETF NETMOD (Network Modeling) Working Group";

  contact
    "WG Web:   <http://tools.ietf.org/wg/netmod/>
     WG List:  <mailto:netmod@ietf.org>

     Author:   Reshad Rahman
               <mailto:rrahman@cisco.com>

     Author:   Rob Wilton
               <mailto:rwilton@cisco.com>

     Author:   Joe Clarke
               <mailto:jclarke@cisco.com>

     Author:   Jason Sterne
               <mailto:jason.sterne@nokia.com>

     Author:   Bo Wu
               <mailto:lana.wubo@huawei.com>";

  description
    "This module provide a data model to advertise and allow the
     selection of schema versions by clients.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: update the date below with the date of RFC publication
  // and remove this note.
  // RFC Ed.: replace XXXX with actual RFC number and remove this
  // note.
  revision 2020-02-29 {
    description
      "Initial revision";
    reference
      "RFC XXXX: YANG Schema Selection";
  }

  /*
   * Features
   */
  feature "custom-schema-set" {
    description
      "Feature to choose whether clients may configurable custom
       schema definitions.";
  }

  /*
   * Top level data nodes.
   */

  container schema-set-selection {
    presence "Enable schema selection";

    description
      "YANG schema-set selection.

       Contains configuration and state related to client selectable
       YANG schema-sets.";

    leaf-list selectable {
      type leafref {
        path "/schema-set-selection/schema-set/name";
        require-instance false;
      }
      min-elements 1;

      description
        "Specifies the selectable schema used by this server, that
         can be selected by clients (either through NETCONF
         capability negotiation or RESTCONF schema specific path).";
    }

    leaf default {
      type leafref {
        path "/schema-set-selection/selectable";
      }
      mandatory true;
      description
        "Defines the default schema-set used by this server.

         This is the schema-set that is chosen if a NETCONF client
         doesn't select a schema during capability negotiation, or if
         the standard RESTCONF (or NMDA datastore URLs) are used.";
    }

    list custom {
      if-feature "custom-schema-set";
      key "name";

      description
        "Defines a custom selectable schema constructed from
         compatible schema";

      leaf name {
        type "string";
        description
          "Name of custom schema.

           Format can either be the form of a YANG identifer, or
           '<name>@<rev-label>'.

           The selectable-schema name is used in NETCONF capabilties
           negotiation and also the RESTCONF path (XXX, is encoding
           required, e.g. for '@'?)";
      }

      leaf description {
        type string;
        description
          "The description associated with this custom package.";
      }

      leaf-list included-schema {
        type leafref {
          path "/schema-set-selection/schema-set/name";
          require-instance false;
        }
        description
          "Lists the schema that are combined together into a single
           selectable schema (i.e. via a union operation on each
           datastore schema package).";
      }
    }

    list schema-set {
      key "name";
      config false;

      description
        "Lists all available schema-set's that can be used in schema
         selection.";

      leaf name {
        type string;

        description
          "Name of the schema.

           Do we restrict what is allowed, specifically, do we allow
           '@'";
      }

      leaf partial {
        type empty;

        description
          "Indicates that this schema-set only represents a subset of
           the full configurable schema of the device.";
      }

      list datastore {
        key "name";

        description
          "The list of datastores supported for this pan-datastore
           selectable-package, along with the package schema
           associated with that datastore.";

        leaf name {
          type ds:datastore-ref;
          description
            "The datastore that this datastore schema is associated
             with.";
          reference
            "RFC 8342: Network Management Datastore Architecture
             (NMDA)";
        }

        leaf read-only {
          type empty;
          description
            "For datastores that are normally writable, the read-only
             flag indicates that the datastore cannot be written
             using this schema-set.  E.g., if <running> was a
             supported datastore then it could be read, but not
             written.

             This flag is not required for datastores, like
             operational, that are defined as being read-only.";
        }

        uses pkgs:yang-ds-pkg-ref;
      }

      leaf-list selectable-with {
        type leafref {
          path "/schema-set-selection/schema-set/name";
        }
        description
          "Lists other schema-sets that MAY be selected at the same
           time as this schema.";
      }

      container custom-selectable {
        if-feature "custom-schema-set";
        presence
          "This schema MAY be selected as part of a custom
           schema-set.";
        description
          "Indicates that this schema-set is selectable as part of a
           custom schema-set and also lists other schema-sets that
           may be combined together into a custom schema-set.";

        leaf-list combinable-with {
          type leafref {
            path "/schema-set-selection/schema-set/name";
          }
          description
            "Lists the schema-sets that MAY be combined with this
             schema into a single custom schema-set'.";
        }
      }
    }
  }
}
