module ietf-dc-fabric-topology {

yang-version 1.1;
namespace "urn:ietf:params:xml:ns:yang:ietf-dc-fabric-topology";
prefix fabric;

import ietf-network {
    prefix nw;

    reference
    "draft-ietf-i2rs-yang-network-topo-20
    NOTE TO RFC EDITOR:
    (1) Please replace above reference to
    draft-ietf-i2rs-yang-network-topo-20 with RFC
    number when published (i.e. RFC xxxx).
    (2) Please replace the date in the revision statement with the
     date of publication when published.";
}

import ietf-network-topology {
    prefix nt;

    reference
    "draft-ietf-i2rs-yang-network-topo-20
    NOTE TO RFC EDITOR:
    (1) Please replace above reference to
    draft-ietf-i2rs-yang-network-topo-20 with RFC
    number when published (i.e. RFC xxxx).
    (2) Please replace the date in the revision statement with the
     date of publication when published.";
}

import ietf-dc-fabric-types {
    prefix fabrictypes;

    reference
    "draft-ietf-i2rs-yang-dc-fabric-network-topology-03
    NOTE TO RFC EDITOR:
     (1) Please replace above reference to draft-ietf-i2rs-yang-dc
     -fabric-network-topology-03 with RFC number when publised
     (i.e. RFC xxxx).
     (2) Please replace the data in the revision statement with the
     data of publication when published.";
}

organization
"IETF I2RS (Interface to the Routing System) Working Group";

contact
"WG Web:    <http://tools.ietf.org/wg/i2rs/ >
 WG List:   <mailto:i2rs@ietf.org>

 Editor:    Yan Zhuang
            <mailto:zhuangyan.zhuang@huawei.com>

 Editor:    Danian Shi
            <mailto:shidanian@huawei.com>";

description
   "This module contains a collection of YANG definitions for Fabric.

    Copyright (c) 2016 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of
    draft-ietf-i2rs-yang-dc-fabric-network-topology;see the RFC
    itself for full legal notices.

    NOTE TO RFC EDITOR: Please replace above reference to
    draft-ietf-i2rs-yang-dc-fabric-network-topology-03 with RFC
    number when published (i.e. RFC xxxx).";

    revision "2017-12-21"{
    description
         "Initial revision.
          NOTE TO RFC EDITOR: Please replace the following reference
          to draft-ietf-i2rs-yang-dc-fabric-network-topology-03 with
          RFC number when published (i.e. RFC xxxx).";
    reference
        "draft-ietf-i2rs-yang-dc-fabric-network-topology-03";
}

identity fabric-context {
    description
       "Identity of fabric context";
}

typedef fabric-id {
    type nw:node-id;
    description
        "An identifier for a fabric in a topology.
        The identifier is generated by compose-fabric RPC.";
}

//grouping statements
grouping fabric-network-type {
    description "Identify the topology type to be fabric.";
    container fabric-network {
        presence "indicates fabric Network";
    description
      "The presence of the container node indicates fabric topology";
  }
}

grouping fabric-options {
    description "Options for a fabric";

    leaf gateway-mode {
        type enumeration {
            enum centralized {
                description "The Fabric uses centerilized gateway, in
                which gateway is deployed on SPINE node.";
            }
            enum distributed {
                description "The Fabric uses distributed gateway, in
                which gateway is deployed on LEAF node.";
            }
        }
        default "distributed";
        description "Gateway mode of the fabric";
    }

    leaf traffic-behavior {
        type enumeration {
            enum normal {
                description "Normal";
            }
            enum policy-driven {
                description "Policy driven";
            }
        }
        default "normal";
        description "Traffic behavior of the fabric";
    }

    leaf-list capability-supported {
        type fabrictypes:service-capabilities;
        description
           "Supported services of the fabric";
    }
}

grouping device-attributes {
    description "device attributes";
    leaf device-ref {
        type fabrictypes:node-ref;
        description
            "The device the fabric includes.";
    }
    leaf role {
        type fabrictypes:device-role;
        default fabrictypes:leaf;
        description
            "Role of the device node";
    }
}

grouping link-attributes {
            description "Link attributes";
    leaf link-ref {
        type fabrictypes:link-ref;
        description
            "The link it includes";
    }
}

grouping port-attributes {
    description "Port attributes";
    leaf port-ref {
        type fabrictypes:tp-ref;
        description
            "The port it refers to.";
    }
    leaf port-type {
        type fabrictypes:port-type;
        description
            "Port type: ethernet or serial or others.";
    }
    leaf bandwidth {
        type fabrictypes:bandwidth;
        description
            "Bandwidth of the port.";
    }
}

grouping fabric-attributes {
    description "Attributes of a fabric";

    leaf fabric-id {
        type fabric-id;
        description
            "Fabric id";
    }

    leaf name {
        type string;
        description
            "Name of the fabric";
    }

    leaf type {
        type fabrictypes:underlay-network-type;
        description
            "The type of physical network that implements this
             fabric.Examples are vlan, and trill.";
    }

    container vni-capacity {
        description "Number of vnis that the fabric has";
        leaf min {
            type int32;
            description
                "Vni min capacity";
        }

        leaf max {
            type int32;
            description
                "Vni max capacity";
        }
    }

    leaf description {
        type string;
        description
            "Description of the fabric";
    }

    container options {
        description "Options of the fabric";
        uses fabric-options;
    }

    list device-nodes {
        key device-ref;
        description "Device nodes that include in a fabric.";
        uses device-attributes;
    }

    list device-links {
        key link-ref;
        description "Links that include within a fabric.";
        uses link-attributes;
    }

    list device-ports {
        key port-ref;
        description "Ports that include in the fabric.";
        uses port-attributes;
    }

}

    // augment statements

augment "/nw:networks/nw:network/nw:network-types" {
description
    "Introduce new network type for Fabric-based logical topology";

    uses fabric-network-type;
    }

augment "/nw:networks/nw:network/nw:node" {
    when "/nw:networks/nw:network/nw:network-types/fabric:fabric-network" {
    description
      "Augmentation parameters apply only for networks
       with fabric topology";
  }
    description "Augmentation for fabric nodes created by faas.";

    container fabric-attributes {
                    description
                    "Attributes for a fabric network";

        uses fabric-attributes;
    }
}

augment "/nw:networks/nw:network/nw:node/nt:termination-point" {
    when "/nw:networks/nw:network/nw:network-types/fabric:fabric-network" {
    description
      "Augmentation parameters apply only for networks
       with fabric topology";
  }
    description "Augmentation for port on fabric.";

    container fport-attributes {
        config false;
        description
           "Attributes for fabric ports";
        uses fabrictypes:fabric-port;
    }
}
}
