module ietf-acldns {
  yang-version 1.1;
  namespace "urn:ietf:params:xml:ns:yang:ietf-acldns";
  prefix ietf-acldns;

  import ietf-access-control-list {
    prefix acl;
  }
  import ietf-inet-types {
    prefix inet;
  }

  organization
    "IETF OPSAWG (Ops Area) Working Group";
  contact
    "WG Web: http://tools.ietf.org/wg/opsawg/
     WG List: opsawg@ietf.org
     Author: Eliot Lear
     lear@cisco.com
     Author: Ralph Droms
     rdroms@gmail.com
     Author: Dan Romascanu
     dromasca@gmail.com
    ";
  description
    "This YANG module defines a component that augments the
     IETF description of an access list to allow DNS names
     as matching criteria.";

  revision 2018-06-15 {
    description
      "Base version of dnsname extension of ACL model";
    reference
      "RFC XXXX: Manufacturer Usage Description
       Specification";
  }

  grouping dns-matches {
    description
      "Domain names for matching.";
    leaf src-dnsname {
      type inet:host;
      description
        "domain name to be matched against";
    }
    leaf dst-dnsname {
      type inet:host;
      description
        "domain name to be matched against";
    }
  }

  augment "/acl:acls/acl:acl/acl:aces/acl:ace/acl:matches" +
   "/acl:l3/acl:ipv4/acl:ipv4" {
    description
      "Adding domain names to matching";
    uses dns-matches;
  }
  augment "/acl:acls/acl:acl/acl:aces/acl:ace/acl:matches" +
   "/acl:l3/acl:ipv6/acl:ipv6" {
    description
      "Adding domain names to matching";
    uses dns-matches;
  }
}
