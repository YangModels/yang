module ietf-twamp-light {
   namespace "urn:ietf:params:xml:ns:yang:ietf-twamp-light";
    //namespace need to be assigned by IANA
   prefix "ietf-twamp-light";

   import ietf-inet-types {
     prefix inet;
   }

   organization
     "IETF IPPM (IP Performance Metrics) Working Group";

   contact
     "draft-mirsky-ippm-twamp-light-yang@tools.ietf.org";

   description "TWAMP Light Data Model";

   revision "2016-03-05" {
     description "01 version. RFC5357 is covered,
 including Appendix I and the Errata.";
     reference "draft-mirsky-ippm-twamp-light-yang";
   }

   feature sessionSenderLight {
     description "This feature relates to the device functions as the
 TWAMP Light Session-Sender.";
   }

   feature sessionReflectorLight {
     description "This feature relates to the device functions as the
     TWAMP Light Session-Reflector.";
   }

   grouping maintenanceStatistics {
     description "Maintenance statistics grouping";
     leaf sentPackets {
       type uint32;
       default 0;
       config "false";
       description "Packets sent";
     }
     leaf rcvPackets {
       type uint32;
       default 0;
       config "false";
       description "Packets received";
     }
     leaf lastSentSeq {
       type uint32;
       default 0;
       config "false";
       description "Last sent sequence number";
     }
     leaf lastRcvSeq {
       type uint32;
       default 0;
       config "false";
      description "Last received sequence number";
     }
   }

   grouping sessionLightParameters {
     description "Parameters common among Session-Sender and
 Session-Reflector.";
     leaf senderIp {
       type inet:ip-address;
       description "Sender IP address";
     }
     leaf senderUdpPort {
       type inet:port-number {
           range "49152..65535";}
       description "Sender UDP port number";
     }
     leaf reflectorIp {
       type inet:ip-address;
       description "Reflector IP address";
     }
     leaf reflectorUdpPort {
       type inet:port-number{
           range "49152..65535";}
       description "Reflector UDP port number";
     }
     leaf dscp {
       type inet:dscp;
       description "The DSCP value to be placed in the header of TWAMP
           UDP
 test packets generated by the Session-Sender. Whether
           Session-Reflector uses this value depends upon its local
 configuration.";
     }
   }

    container twampLightSessionSender {
       if-feature sessionSenderLight;
       description "TWAMP-Light Session-Sender container";
       list testSession {
         key "senderIp senderUdpPort reflectorIp reflectorUdpPort dscp";
         ordered-by system;
         description "This structure is a container of test session
 managed objects.";

         leaf numberOfPackets {
           type uint32;
           description "The overall number of UDP test packets to be
             transmitted by the sender for this test session.";
         }

         leaf packetPaddingSize {
           type uint32;
           default 27;
           description "Size of the Packet Padding. Suggested to run
           Path MTU Discovery
 to avoid packet fragmentation in IPv4
           and packet backholing in IPv6.";
         }

          leaf sessionAuthenticationMode {
            type enumeration {
              enum unathenticated {
                   description "Unauthenticated TWAMP-Light
                   test session";
              }
              enum authenticated {
                   description "Authenticated TWAMP-Light test session";
              }
              enum encrypted {
                   description "Encrypted TWAMP-Light test session";
              }
            }
            default unathenticated;
            description "Authentication mode of the TWAMP-Light test
            session."
;
          }

         leaf interval  {
           type uint32;
          description "Time interval between transmission of two
          consecutive packets in the test session.";
         }

         leaf senderSessionState {
           type enumeration {
             enum active {
               description "Test session is active.";
             }
             enum ready {
               description "Test session is idle.";
             }
           }
           default ready;
           config "false";
           description "State of the particular TWAMP-Light test
           session at the sender.";
         }
         uses maintenanceStatistics;
         uses sessionLightParameters;
       }
     }

     container twampLightSessionReflector {
       if-feature sessionReflectorLight;
       description "TWAMP-Light Session-Reflector container";
         leaf reflectorLightState {
           type boolean;
           mandatory "true";
           description "Whether this network element is enabled to
           act as TWAMP-Light Reflector";
         }

         leaf refwait {
         type uint32 {
           range 1..604800;
         }
         units seconds;
         default 900;
         description "REFWAIT(TWAMP test session timeout in seconds),
 the default value is 900";
       }

       leaf reflectorLightMode {
         type enumeration {
           enum stateful {
             description "When the Session-Reflector Light is stateful,
               i.e. is aware of test session state.";
           }
           enum stateless {
             description "when the Session-Reflector is statelss.";
           }
         }
         default stateless;
         description "Whether Session-Sender copies sequence number
           of received TWAMP-Test packet, i.e. Stateless, or counts
           reflected TWAMP-Test packets and restarts counter based on
           external event.";
        }

        leaf dscpHandlingMode {
          type enumeration {
            enum copyReceivedValue {
              description "Use DSCP value copied from received TWAMP
 test packet of the test session.";
              }
              enum useConfiguredValue {
                description "Use DSCP value configured for this test
 session on the Session-Reflector.";
                }
             }
             default copyReceivedValue;
             description "Session-Reflector handling of DSCP:
                 - use value copied from received TWAMP-Test packet;
                 - use value explicitly configured.";
           }

       list testSession {
         key "senderIp senderUdpPort reflectorIp reflectorUdpPort dscp";
         ordered-by system;
         description "This structure is a container of test session
 managed objects.";
         uses maintenanceStatistics;
         uses sessionLightParameters;
       }
     }
   }
