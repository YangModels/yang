module ietf-data-node-tags {
 yang-version 1.1;
 namespace "urn:ietf:params:xml:ns:yang:ietf-self-explanation-node-tags";
 prefix ntags;
 import ietf-netconf-acm  { prefix nacm; }
 import ietf-module-tags  { prefix tags; }
 organization
   "IETF NetMod Working Group (NetMod)";
 contact
   "WG Web:  <https://tools.ietf.org/wg/netmod/>
    WG List: <mailto:netmod@ietf.org>
    Author:  Ran Tao
             <mailto:taoran20@huawei.com>
    Author:  Qin Wu
             <mailto:bill.wu@huawei.com>";

 // RFC Ed.: replace XXXX with actual RFC number and
 // remove this note.

 description
   "This module describes a mechanism associating self-explanation
    tags with YANG data node within YANG modules. Tags may be IANA
    assigned or privately defined.

    Copyright (c) 2018 IETF Trust and the persons identified as
    authors of the code. All rights reserved.

    Redistribution and use in source and binary forms, with or
    without modification, is permitted pursuant to, and subject to
    the license terms contained in, the Simplified BSD License set
    forth in Section 4.c of the IETF Trust's Legal Provisions
    Relating to IETF Documents
    (https://trustee.ietf.org/license-info).

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 [RFC2119] [RFC8174] when, and only when,
    they appear in all capitals, as shown here.

    This version of this YANG module is part of RFC XXXX
    (https://tools.ietf.org/html/rfcXXXX); see the RFC itself for
    full legal notices.";

 // RFC Ed.: update the date below with the date of RFC publication
 // and RFC number and remove this note.

 revision 2019-05-03 {
   description
     "Initial revision.";
   reference "RFC XXXX: YANG Data Node Tags";
 }
typedef tag {
  type string {
    length "1..max";
    pattern '[a-zA-Z_][a-zA-Z0-9\-_]*:[\S ]+';
  }
  description
    "A tag value is composed of a standard prefix followed by any type
     'string' value that does not include carriage return, newline or
     tab characters.";
}
  typedef measurement-precision {
    type int8 {
      range "-8 .. 9";
    }
    description
      "A node using this data type represents a sensor value
       precision range.

       A node of this type SHOULD be defined together with nodes of
       type measurement-units and type measurement-scale.  Together,
       associated nodes of these three types are used to identify the
       semantics of a node of type sensor-value.

       If a node of this type contains a value in the range 1 to 9,
       it represents the number of decimal places in the fractional
       part of an associated sensor-value fixed-point number.
       If a node of this type contains a value in the range -8 to -1,
       it represents the number of accurate digits in the associated
       sensor-value fixed-point number.

       The value zero indicates the associated sensor-value node is
       not a fixed-point number.

       Server implementers must choose a value for the associated
       sensor-value-precision node so that the precision and accuracy
       of the associated sensor-value node is correctly indicated.

       For example, a component representing a temperature sensor
       that can measure 0 to 100 degrees C in 0.1 degree
       increments, +/- 0.05 degrees, would have a
       sensor-value-precision value of '1', a sensor-value-scale
       value of 'units', and a sensor-value ranging from '0' to
       '1000'.  The sensor-value would be interpreted as
       'degrees C * 10'.";
    reference
      "RFC 3433: Entity Sensor Management Information Base -
                 EntitySensorPrecision";
  }

  typedef measurement-scale {
    type enumeration {
      enum yocto {
        value 1;
        description
          "Measurement scaling factor of 10^-24.";
      }
      enum zepto {
        value 2;
        description
          "Measurement scaling factor of 10^-21.";
      }
      enum atto {
        value 3;
        description
          "Measurement scaling factor of 10^-18.";
      }
      enum femto {
        value 4;
        description
          "Measurement scaling factor of 10^-15.";
      }
      enum pico {
        value 5;
        description
          "Measurement scaling factor of 10^-12.";
      }
      enum nano {
        value 6;
        description
          "Measurement scaling factor of 10^-9.";
      }
      enum micro {
        value 7;
        description
          "Measurement scaling factor of 10^-6.";
      }
      enum milli {
        value 8;
        description
          "Measurement scaling factor of 10^-3.";
      }
      enum units {
        value 9;
        description
          "Measurement scaling factor of 10^0.";
      }
      enum kilo {
        value 10;
        description
          "Measurement scaling factor of 10^3.";
      }
      enum mega {
        value 11;
        description
          "Measurement scaling factor of 10^6.";
      }
      enum giga {
        value 12;
        description
          "Measurement scaling factor of 10^9.";
      }
      enum tera {
        value 13;
        description
          "Measurement scaling factor of 10^12.";
      }
      enum peta {
        value 14;
        description
          "Measurement scaling factor of 10^15.";
      }
      enum exa {
        value 15;
        description
          "Measurement scaling factor of 10^18.";
      }
      enum zetta {
        value 16;
        description
          "Measurement scaling factor of 10^21.";
      }
      enum yotta {
        value 17;
        description
          "Measurement scaling factor of 10^24.";
      }
    }
    description
      "A node using this data type represents a data scaling factor,
       represented with an International System of Units (SI) prefix.
       The actual data units are determined by examining a node of
       this type together with the associated sensor-value-type.

       A node of this type SHOULD be defined together with nodes of
       type sensor-value-type and type sensor-value-precision.
       Together, associated nodes of these three types are used to
       identify the semantics of a node of type sensor-value.";
    reference
      "RFC 3433: Entity Sensor Management Information Base -
                 EntitySensorDataScale";
  }

 identity measurement-unit {
     description
      "Base identity for measurement unit.";
    }

   identity ac-volts {
    base measurement-unit;
     description
      "Identity for a measure of electric potential (alternating current).";
   }
   identity dc-volts {
    base measurement-unit;
     description
      "Identity for a measure of electric potential (direct current).";
   }
   identity amperes {
    base measurement-unit;
     description
      "Identity for a measure of electric current.";
   }
   identity power {
    base measurement-unit;
     description
      "Identity for a measure of power.";
   }
   identity hertz {
    base measurement-unit;
     description
      "Identity for a measure of frequency.";
   }
   identity celsius {
    base measurement-unit;
     description
      "Identity for a measure of temperature.";
   }
   identity rpm {
    base measurement-unit;
     description
      "Identity for a measure of shaft revolutions per minute.";
   }
extension metric-scale{
      argument tag;
      description
        "The argument 'tag' is of type 'tag'.The metric-scale can be
        used to provide an additional metric scale (e.g., Measurement
        scaling factor of 10^0, 10^-3,10^3) information associated with
        the performance metric data node tag.";
    }
extension metric-precision {
      argument tag;
      description
        "The argument 'tag' is of type 'tag'.The metric-precision can be
        used to provide an additional metric precision (e.g., the range -8 to -1,
        0, the range 1 to 9) information associated with the performance metric
        data node tag.";
    }

extension statistics-operation {
      argument tag;
      description
        "The argument 'tag' is of type 'tag'.The statistics-operation can be
        used to provide an additional statistics operation type(e.g., sum,
        min, max,last) information associated with the performance metric
        data node tag.";
    }
extension data-source-type{
      argument tag;
      description
        "The argument 'tag' is of type 'tag'.The data-source-type can be
        used to provide an additional data source type (e.g., connectivity,
        resource, hardware,qos,policy) information associated with
        the performance metric data node tag.";
    }
extension membership-tag {
      argument tag;
      description
        "The argument 'tag' is of type 'tag'.The membership-tag can be
        used to provide an additional multiple source aggregation
        information associated with the performance metric data node
        or interface related data node.";
    }
extension service-tag {
      argument tag;
      description
        "The argument 'tag' is of type 'tag'.The service-tag can be
        used to provide a service classification information (e.g., tunnel,
        l3vpn,l2vpn) information associated with YANG data node.";
    }

extension task-tag {
      argument tag;
      description
        "The argument 'tag' is of type 'tag'.The task-tag can be
        used to provide a task classification information (e.g., fault management,
        performance measurement) information associated with YANG data node.";
    }

extension opm-tag {
      argument tag;
      description
        "The argument 'tag' is of type 'tag'. This extension statement
         is used by module authors to indicate the opm tags that SHOULD be
         added automatically by the system. As such the origin of the
         value for the pre-defined tags should be set to 'system'
         [RFC8342].";
    }

 augment "/tags:module-tags/tags:module" {
   description
     "Augment the Tags module with data node tag attributes";
    container self-explanation-node-tags {
      description
        "Contains the list of data nodes and their associated tags";
      list self-explanation-node {
        key "node-name";
        description
          "A list of self-explanation nodes and their associated tags";
        leaf node-name {
          type nacm:node-instance-identifier;
          mandatory true;
          description
            "The YANG data node name.";
        }
        leaf metric-precision {
          type tags:tag;
          description
            "The numeric expression precision of performance
             metric related data node.";
        }
        leaf metric-unit {
           type tags:tag;
           description
            "The measurement unit of performance
             metric related data node.";
        }
       leaf metric-scale {
           type tags:tag;
           description
            "The measurement scale of performance
             metric related data node.";
        }
        leaf operation-type{
         type tags:tag;
         description
          "Statistics operation of performance metric related
          data node.";
        }
       leaf data-source-type {
           type tags:tag;
           description
            "The data source type with the data node within YANG module.";
        }
       leaf parent-grouping {
           type tags:tag;
           description
            "The parent-grouping tag can be used to identify multiple source
             (e.g., line card,member link in an aggregated Ethernet
            interface) related to performance metric related data node
             or interface related to data node.";
        }
        leaf  opm-tag {
          type tags:tag;
          description
            "Tags associated with the data node within YANG module. See
             the IANA 'YANG Data Node Tag Prefixes' registry for reserved
             prefixes and the IANA'IETF YANG Data Node Tags' registry for
             IETF tags.

             The 'operational' state [RFC8342] view of this list is
             constructed using the following steps:

             1) System tags (i.e., tags of 'system' origin) are added.
             2) User configured tags (i.e., tags of 'intended' origin)
             are added.
             3) Any tag that is equal to a masked-tag is removed.";
        }
        leaf service-tag {
         type tags:tag;
         description
          "The node-service-tag can be used to provide a service
          classification information (e.g., tunnel, l3vpn,l2vpn)
          information associated with YANG data node.";
        }
        leaf task-tag {
         type tags:tag;
         description
          "The node-task-tag can be used to provide a task
          classification information (e.g., fault management,
          performance measurement) information associated with
          YANG data node.";
        }
      leaf correlate-group-id {
        type string;
        description
         "This group ID is used to to correlate
         data nodes within the same YANG module or of different YANG modules.";
       }
      }
     }
    }
  }
