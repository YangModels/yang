module ietf-yang-mpl-domain {
  yang-version 1;

  namespace
      "urn:ietf:params:xml:ns:yang:ietf-yang-mpl-domain";

  prefix mpl;

import ietf-inet-types{
    prefix inet;
}

  organization
    "IETF ROLL (Routing Over Low power and lossy networks) Working Group";

  contact
     "WG Web:   http://tools.ietf.org/wg/roll/
     WG List:  mailto:roll@ietf.org

     WG Chair: Peter van der Stok
               mailto:consultancy@vanderstok.org

     WG Chair: Ines Robles
               mailto:maria.ines.robles@ericsson.com

     Editor:   Peter van der Stok
               mailto:consultancy@vanderstok.org";

  description
    "This module contains information about the state of the MPL domain.

     Copyright (c) 2016 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

revision "2016-05-18" {
      description "Initial revision.";
      reference
        "I-D:draft-vanderstok-roll-mpl-yang: A YANG model for Multicast Protocol for Low power and lossy Networks (MPL)";
    }
   choice single {
        description
        "A choice between single domain/interface and multiple
        domains and interfaces.";
     container mpl-domain {
        description
        "The entries describe the MPL domains, the associated
         Multicast addresses and interfaces.";

        list domains {
         key domainID;
         description
         "The entries describe a given domain identified with domainID and the associated Multicast addresses.";

        leaf domainID {
          type uint16;
          description
             "Entry uniquely identifies the domain in the
              forwarder.";
         }

         leaf-list MClist{
            type inet:ipv6-address;
            description
               "List of associated IPv6 Addresses.";
         }
       }   // domains list

       list addresses {
         key MCaddress;
         description
           "The entries describe the interfaces enabled with the specified MC address.";

         leaf MCaddress {
            type inet:ipv6-address;
            description
                "MC address belonging to a MPL domain.";
          }

         leaf-list interfaces {
             type string;
             description
             "List of names of interfaces enabled for this Multicast address. Interface name is defined in [RFC6206].";
         }
       }   // addresses list
     }   // container mpl-domain
     container mpl-single {
         description
         "For small devices list of MC addresses for single
          interface and domain.";
         leaf-list MCaddresses{
             type inet:ipv6-address;
             description
                "list of MC addresses belonging to one single domain and interface.";
         }
     }   // container mpl-simple
   }   // choice simple
}  //module ietf-yang-mpl-domain
