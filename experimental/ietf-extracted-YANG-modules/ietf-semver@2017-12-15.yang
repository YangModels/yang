module ietf-semver {
  yang-version 1.1;
  namespace "urn:ietf:params:xml:ns:yang:ietf-semver";
  prefix semver;

  organization
    "IETF NETMOD (Network Modeling) Working Group";
  contact
    "WG Web:   <https://datatracker.ietf.org/wg/netmod/>
     WG List:  <mailto:netmod@ietf.org>

     Author:   Benoit Claise
               <mailto:bclaise@cisco.com>

     Author:   Joe Clarke
               <mailto:jclarke@cisco.com>

     Author:   Kevin D'Souza
               <mailto:kd6913@att.com>

     Author:   Balazs Lengyel
               <mailto:balazs.lengyel@ericsson.com>";
  description
    "This module contains a definition for a YANG 1.1 extension to
     express the semantic version of YANG modules.";

  revision 2017-12-15 {
    description
      "Initial revision.";
    reference "draft-clacla-netmod-yang-model-update:
             New YANG Module Update Procedure";
    semver:module-semver 0.1.1;
  }

  extension module-version {
    argument semver;
    description
      "The version number for the module revision it is used in.
      This is expressed as a semantic version string in the form:
        x.y.z
       where:
        * x corresponds to the major version,
        * y corresponds to a minor version,
        * z corresponds to a patch version.

       A major version number of 0 indicates that this model is still
       in development, and is potentially subject to change.

       Following a release of major version 1, all modules will
       increment major revision number where backwards incompatible
       changes to the model are made.

       The minor version is changed when features are added to the
       model that do not impact current clients use of the model.
       When major version is stepped, the minor version is reset to 0.

       The patch-level version is incremented when non-feature changes
       (such as bugfixes or clarifications to human-readable
       descriptions that do not impact model functionality) are made
       that maintain backwards compatibility.
       When major or minor version is stepped, the patch-level is
       reset to 0.

       The version number is stored in the module meta-data.

       By comparing the module-version between two revisions of a
       given module, one can know if revision N+1 is backwards
       compatible or not relative to revision N, as well as
       whether or not new features have been added to revision N+1.

       If a module contains this extension it indicates that for this
       module the updated status and update rules as this described in
       RFC XXXX are used.

       The statement MUST only be a substatement of the revision,
       import or include statements.
       Zero or One module-version statement is allowed per parent
       statement. NO substatements are allowed.
       ";

    reference "http://semver.org/ : Semantic Versioning 2.0.0";
  }

  augment /yanglib:modules-state/yanglib:module {
      leaf module-version {
          type string {
              pattern "[0-9]+.[0-9]+.[0-9]+";
          }
      }
  }

  augment /yanglib:modules-state/yanglib:module/yanglib:submodule {
      leaf submodule-version {
          type string {
              pattern "[0-9]+.[0-9]+.[0-9]+";
          }
      }
  }

}
