module ietf-grp-ntw-elements {
  yang-version 1.1;
  namespace "urn:ietf:params:xml:ns:yang:ietf-grp-ntw-elements";
  prefix "grp";

  organization
    "IETF OPSA (Operations and Management Area) Working Group";
  contact
    "WG Web:  <https://datatracker.ietf.org/wg/opsawg/>
    WG List:  <mailto:opsawg@ietf.org>

    Editor:   Oscar Gonzalez de Dios
              <mailto:oscar.gonzalezdedios@telefonica.com>
    Editor:   Victor Lopez
              <mailto:victor.lopez@nokia.com>
    Editor:   Mohamed Boucadair
              <mailto:mohamed.boucadair@orange.com>";

  description
    "YANG model for group of network elements.

    Copyright (c) 2023 IETF Trust and the persons identified as
    authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC xxx; see the
    RFC itself for full legal notices.";

  revision "2023-10-23" {
    description "Initial revision.";
    reference "RFC XXXX: An Approach to Expose 'Device Models'
                         -as-'Network Models'";
  }

  list grp-ntw-element {
    key "grp-ne-id";
    description "List of groups of network elements.";
    leaf grp-ne-id {
      type string;
      description "Group of network element identifier.";
    }

    list ntw-element {
      key "ne-id";
      description "List of network elements.";

      leaf ne-id {
        type string;
        description "Network element identifier.";
      }
    }
  }
}
