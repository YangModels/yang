module ietf-ucl-acl {
  yang-version 1.1;
  namespace "urn:ietf:params:xml:ns:yang:ietf-ucl-acl";
  prefix uacl;

  import ietf-yang-types {
    prefix yang;
    reference
      "RFC 6991: Common YANG Data Types, Section 3";
  }
  import ietf-inet-types {
    prefix inet;
    reference
      "RFC 6991: Common YANG Data Types, Section 4";
  }
  import ietf-lmap-common {
    prefix lmap;
    reference
      "RFC 8194: A YANG Data Model for LMAP Measurement Agents";
  }
  import ietf-access-control-list {
    prefix acl;
    reference
      "RFC 8519: YANG Data Model for Network Access
                 Control Lists (ACLs)";
  }

  organization
    "IETF OPSWG Working Group";
  contact
    "WG Web: <https://datatracker.ietf.org/wg/opsawg/>
     WG List: <mailto:opsawg@ietf.org>";
  description
    "This YANG module defines XXX.

     Copyright (c) 2022 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.";

  revision 2022-10-14 {
    description
      "Initial revision.";
    reference
      "RFC XXXX: A Policy-based Network Access Control";
  }

  feature match-on-user-group {
    description
      "The device can support matching on user groups.";
  }

  grouping match-range-source-destination {
    description
      "A grouping used for source/desttination macthes.";
    choice match {
      description
        "Add a new match choice for the user group.";
      case user-group {
        leaf user-group-id {
          type uint32;
          description
            "The matched user group ID that uniquely identifies
             a user group.";
        }
      }
      case IP-address {
        leaf ipv4-network {
          type inet:ipv4-prefix;
          description
            "The matched IPv4 address prefix.";
        }
        leaf ipv6-network {
          type inet:ipv6-prefix;
          description
            "The matched IPv6 address prefix.";
        }
      }
    }
  }

  augment "/acl:acls/acl:acl/acl:aces/acl:ace/acl:matches" {
    if-feature "match-on-user-group";
    description
      "Add new match types.";
    choice user-control-groups {
      description
        "Add new source and destination matches based on the
         user group.";
      container source-match {
        description
          "The source matched information.";
        uses match-range-source-destination;
      }
      container destination-match {
        description
          "The destination matched information.";
        uses match-range-source-destination;
      }
    }
  }

  augment "/acl:acls/acl:acl/acl:aces/acl:ace" {
    if-feature "match-on-user-group";
    description
      "Add a new parameter to the Access Control Entry (ACE).";
    container time-range {
      description
        "This container defines when the access control
         entry rules are in effect.

         If it is not configured, the access control entry
         is immediately and always in effect.";
      choice time-range-type {
        description
          "Choice based on the type of the time range.";
        case periodic-range {
          leaf-list month {
            type lmap:month-or-all;
            description
              "A set of months at which ace will trigger.
               The wildcard means all months.";
          }
          leaf-list day-of-month {
            type lmap:day-of-months-or-all;
            description
              "A set of days of the month at which ace will
               trigger. The wildcard means all days of a month.";
          }
          leaf-list day-of-week {
            type lmap:weekday-or-all;
            description
              "A set of weekdays at which ace will trigger.
               The wildcard means all weekdays.";
          }
          leaf-list hour {
            type lmap:hour-or-all;
            description
              "A set of hours at which ace will trigger. The
               wildcard means all hours of a day.";
          }
        }
        case absolute-range {
          leaf start-time {
            type yang:date-and-time;
            description
              "The time when the ace starts to take effect.";
          }
          leaf end-time {
            type yang:date-and-time;
            description
              "The time when the ace ends to take effect.";
          }
        }
      }
    }
  }
}
