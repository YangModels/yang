module sfc-common {

  namespace "urn:cisco:params:xml:ns:yang:sfc-common";

  prefix sfc-common;

  organization "Cisco Systems, Inc.";
  contact "Keith Burns <krb@cisco.com>";

  description
    "Common typedefs and leafrefs for project";

  revision 2015-10-17 {
    description
      "Initial revision";
    reference "https://tools.ietf.org/html/draft-penno-sfc-yang";
  }

  // general typedefs
  typedef tenant-id {
      type string;
      description "Tenant ID";
  }
  // typedef for Service Node
  typedef sn-name {
      type string;
      description "Service Node Name Type";
  }

  // typedefs for Service Function Chain
  typedef sfc-name {
      type string;
      description "Service Function Chain Name";
  }

  // typedefs for Service Function Type
  typedef sft-type-name {
      type string;
      description "Service function type name";
  }

  // typedefs for Service Function
  typedef sf-name {
      type string;
      description "Service Function Name";
  }

  typedef sf-data-plane-locator-name {
      type string;
      description
        "A unique name for SF data-plane-locator";
  }

  // typedefs for Rendererd Service Paths
  typedef rsp-name {
      type string;
      description
        "Rendererd Service Path Name Type";
  }

  // typedefs for Service Function Path
  typedef sfp-name {
      type string;
      description "Service Function Path Name Type";
  }

  // typedefs for sff names
  typedef sff-data-plane-locator-name {
      type string;
      description
        "Service Function Forwarder data-plane-locator name type";
  }

  typedef sff-name {
      type string;
      description "Service Function Forwarder Name type";
  }

  // typedefs for renderer names
  typedef renderer-name {
      type string;
      description "Renderer Name type";
  }
}
