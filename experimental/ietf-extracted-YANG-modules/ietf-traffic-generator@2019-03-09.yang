module ietf-traffic-generator {
  yang-version 1.1;
  namespace "urn:ietf:params:xml:ns:yang:ietf-traffic-generator";
  prefix tg;

  import ietf-interfaces {
    prefix if;
  }
  import ietf-yang-types {
    prefix yang;
  }
  import iana-if-type {
    prefix ianaift;
  }

  organization
    "IETF Benchmarking Methodology Working Group";
  contact
    "WG Web:   <http://tools.ietf.org/wg/bmwg/>
     WG List:  <mailto:bmwg@ietf.org>

     Editor:   Vladimir Vassilev
               <mailto:vladimir@transpacket.com>";
  description
    "This module contains a collection of YANG definitions for
     description and management of network interconnect testers.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2019-03-09 {
    description
      "Initial revision.";
    reference "RFC XXXX: Network Interconnect Tester";
  }

  feature egress-direction {
    description
      "The device can generate traffic in the egress direction.";
  }

  feature ingress-direction {
    description
      "The device can generate traffic in the ingress direction.";
  }

  feature multi-stream {
    description
      "The device can generate multi-stream traffic.";
  }

  feature ethernet {
    description
      "The device can generate ethernet traffic.";
  }

  feature ethernet-vlan {
    if-feature "ethernet";
    description
      "The device can generate vlan tagged ethernet traffic.";
  }

  grouping traffic-generator-burst-data {
    leaf frame-size {
      type uint32;
      description
        "Size of the frames generated. For example for
         ethernet interfaces the following definition
         applies:

         Ethernet frame-size in octets includes:
         * Destination Address (6 octets),
         * Source Address (6 octets),
         * Frame Type (2 octets),
         * Data (min 46 octets or 42 octets + 4 octets 802.1Q tag),
         * CRC Checksum (4 octets).

         Ethernet frame-size does not include:
         * Preamble (dependent on MAC configuration
                    by default 7 octets),
         * Start of frame delimeter (1 octet)

         Minimum standard ethernet frame-size is 64 bytes but
         generators might support smaller sizes for validation.";
      mandatory true;
    }
    choice frame-data-type {
      case raw-frame-data {
        leaf frame-data {
          type string {
            pattern '([0-9A-F]{2})*';
          }
          must 'string-length(.)<=(../frame-size*2)';
          description
            "The raw frame data specified as hexadecimal string.
             The specified data can be shorter then the ../frame-size
             value specifying only the header or the header and the
             payload without for example the 4 byte CRC Checksum
             in the case of a Ethernet frame.";
        }
      }
    }
    leaf interframe-gap {
      type uint32;
      description
        "Length of the idle period between generated frames.
         For example for ethernet interfaces the following
         definition applies:

         Ethernet interframe-gap between transmission of frames
         known as the interframe gap (IFG). A brief recovery time
         between frames allows devices to prepare for
         reception of the next frame. The minimum
         interframe gap is 96 bit times (12 octet times) (the time it
         takes to transmit 96 bits (12 octets) of raw data on the
         medium). However the preamble (7 octets) and start of
         frame delimeter (1 octet) are considered a constant gap that
         should be included in the interframe-gap. Thus the minimum
         value for standard ethernet transmission should be considered
         20 octets.";
      mandatory true;
    }
    leaf interburst-gap {
      type uint32;
      description
        "Similar to the interframe-gap but takes place between
         any two bursts of the stream.";
    }
    leaf frames-per-burst {
      type uint32;
      description
        "Number of frames contained in a burst";
    }
  }

  grouping traffic-generator-multi-stream-data {
    container streams {
      list stream {
        key "id";
        leaf id {
          type uint32;
          description
            "Number specifying the order of the stream.";
        }
        uses traffic-generator-burst-data;
        leaf frames-per-stream {
          type uint32;
          description
            "The count of frames to be generated before
             generation of the next stream is started.";
          mandatory true;
        }
        leaf interstream-gap {
          type uint32;
          description
            "Idle period after the last frame of the last burst.";
          mandatory true;
        }
      }
    }
  }

  augment "/if:interfaces/if:interface" {
    container traffic-generator {
      if-feature "egress-direction";
      choice type {
        case single-stream {
          uses traffic-generator-burst-data;
        }
        case multi-stream {
          uses traffic-generator-multi-stream-data;
        }
      }
      leaf total-frames {
        type uint64;
        description
          "If this leaf is present the stream generation will stop
           after the specified number of frames are generated.";
      }
    }
    container traffic-generator-ingress {
      if-feature "ingress-direction";
      choice type {
        case single-stream {
          uses traffic-generator-burst-data;
        }
        case multi-stream {
          uses traffic-generator-multi-stream-data;
        }
      }
      leaf total-frames {
        type uint64;
        description
          "If this leaf is present the stream generation will stop
           after the specified number of frames are generated.";
      }
    }
  }
  augment "/if:interfaces-state/if:interface/if:statistics" {
    description
      "Counters of generated traffic octets and packets.";
    leaf generated-pkts {
      type yang:counter64;
      description
        "Traffic generator packets sent.";
    }
    leaf generated-octets {
      type yang:counter64;
      description
        "Traffic generator octets sent.";
    }
    leaf generated-ingress-pkts {
      if-feature "ingress-direction";
      type yang:counter64;
      description
        "Traffic generator packets generated in ingress mode.";
    }
    leaf generated-ingress-octets {
      if-feature "ingress-direction";
      type yang:counter64;
      description
        "Traffic generator octets generated in ingress mode.";
    }
  }

  grouping ethernet-data {
    leaf src-mac-address {
      type yang:mac-address;
    }
    leaf dst-mac-address {
      type yang:mac-address;
    }
    leaf ether-type {
      type uint16;
      description
        "The Ethernet Type (or Length) value
         defined by IEEE 802.";
      reference "IEEE 802-2014 Clause 9.2";
    }
    choice encapsulation {
      case vlan {
        container vlan {
          if-feature "ethernet-vlan";
          leaf id {
            type uint16 {
              range "0..4095";
            }
            mandatory true;
          }
          leaf tpid {
            type uint16;
            default "33024";
            description
              "Configures the Tag Protocol Identifier (TPID)
               of the 802.1q VLAN tag sent. This value is used
               together whith the vlan id for filtering incoming
               vlan tagged packets.";
          }
          leaf pcp {
            type uint8 {
              range "0..7";
            }
            default "0";
            description
              "Configures the IEEE 802.1p Priority Code Point (PCP) value
               of the transmitted 802.1q VLAN tag.";
          }
          leaf cfi {
            type uint8 {
              range "0..1";
            }
            default "0";
            description
              "Configures the Canonical Format Identifier (CFI) field
               (shall be 0 for Ethernet switches) of the transmitted
               802.1q VLAN tag.";
          }
        }
      }
    }
  }

  augment "/if:interfaces/if:interface/tg:traffic-generator/tg:type/"
        + "tg:single-stream" {
    if-feature "ethernet";
    when "derived-from-or-self(../if:type, 'ianaift:ethernetCsmacd')" {
      description
        "Ethernet interface type.";
    }
    uses ethernet-data;
  }
  augment "/if:interfaces/if:interface/tg:traffic-generator/tg:type/"
        + "tg:multi-stream/tg:streams/tg:stream" {
    if-feature "ethernet";
    when "derived-from-or-self(../../../if:type, 'ianaift:ethernetCsmacd')" {
      description
        "Ethernet interface type.";
    }
    uses ethernet-data;
  }
  augment "/if:interfaces/if:interface/tg:traffic-generator-ingress/tg:type/"
        + "tg:single-stream" {
    if-feature "ethernet";
    when "derived-from-or-self(../if:type, 'ianaift:ethernetCsmacd')" {
      description
        "Ethernet interface type.";
    }
    uses ethernet-data;
  }
  augment "/if:interfaces/if:interface/tg:traffic-generator-ingress/tg:type/"
        + "tg:multi-stream/tg:streams/tg:stream" {
    if-feature "ethernet";
    when "derived-from-or-self(../../../if:type, 'ianaift:ethernetCsmacd')" {
      description
        "Ethernet interface type.";
    }
    uses ethernet-data;
  }
}
