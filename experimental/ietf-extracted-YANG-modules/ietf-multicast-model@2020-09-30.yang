module ietf-multicast-model {

  yang-version 1.1;

  namespace "urn:ietf:params:xml:ns:yang:ietf-multicast-model";
  prefix multicast-model;

  import ietf-inet-types {
    prefix "inet";
    reference
      "RFC 6991: Common YANG Data Types";
  }
  import ietf-routing-types {
    prefix "rt-types";
    reference
      "RFC 8294: Common YANG Data Types for the Routing Area";
  }
  import ietf-routing {
    prefix "rt";
    reference
      "RFC 8349: A YANG Data Model for Routing Management
                 (NMDA Version)";
  }
  import ietf-ospf {
    prefix "ospf";
    reference
      "I-D.ietf-ospf-yang: YANG Data Model for OSPF Protocol";
  }

  organization " IETF MBONED (MBONE Deployment) Working Group";
  contact
    "WG List:  <mailto:mboned@ietf.org>

     Editor:   Zheng Zhang
               <mailto:zhang.zheng@zte.com.cn>
     Editor:   Cui Wang
               <mailto:lindawangjoy@gmail.com>
     Editor:   Ying Cheng
               <mailto:chengying10@chinaunicom.cn>
     Editor:   Xufeng Liu
               <mailto:xufeng.liu.ietf@gmail.com>
     Editor:   Mahesh Sivakumar
               <mailto:sivakumar.mahesh@gmail.com>
    ";

  // RFC Ed.: replace XXXX with actual RFC number and remove
  // this note

  description
    "The module defines the YANG definitions for multicast service
     management.

     Copyright (c) 2020 IETF Trust and the persons identified as
     authors of the code.  All rights reserved.

     Redistribution and use in source and binary forms, with or
     without modification, is permitted pursuant to, and subject
     to the license terms contained in, the Simplified BSD
     License set forth in Section 4.c of the IETF Trust's Legal
     Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2020-09-30 {
    description
      "Initial revision.";
    reference
      "RFC XXXX: A YANG Data Model for multicast YANG.";
  }

  /*
   *typedef
   */

  typedef ip-multicast-source-address {
    type union {
      type rt-types:ipv4-multicast-source-address;
      type rt-types:ipv6-multicast-source-address;
    }
    description
      "This type represents a version-neutral IP multicast
       source address.  The format of the textual
       representation implies the IP version.";
    reference
      "RFC8294: Common YANG Data Types for the Routing Area.";
  }

  typedef virtual-type {
    type enumeration {
      enum vxlan {
        description
          "The VXLAN encapsulation is used for flow encapsulation.";
        reference
          "RFC 7348: Virtual eXtensible Local Area Network (VXLAN):
           A Framework for Overlaying Virtualized Layer 2 Networks
           over Layer 3 Networks.";
      }
      enum nvgre {
        description
          "The NVGRE encapsulation is used for flow encapsulation.";
        reference
          "RFC 7637: NVGRE: Network Virtualization Using Generic
           Routing Encapsulation.";
      }
      enum geneve {
        description
          "The GENEVE encapsulation is used for flow encapsulation.";
        reference
          "I-D.ietf-nvo3-geneve: Geneve: Generic Network
           Virtualization Encapsulation.";
      }
    }
    description
      "The encapsulation type used for the flow. In case the virtual
       type is set, the associated vni-value should also be defined.";
  } // virtual-type

  /*
   * Identities
   */

  identity multicast-model {
    base rt:control-plane-protocol;
    description "Identity for the Multicast model.";
  }

  grouping general-multicast-key {
    description
      "The general multicast keys. They are used to distinguish
       different multicast service.";
    leaf vpn-rd {
      type rt-types:route-distinguisher;
      description
        "A Route Distinguisher used to distinguish
         routes from different MVPNs.";
      reference
        "RFC 8294: Common YANG Data Types for the Routing Area.
         RFC 6513: Multicast in MPLS/BGP IP VPNs.";
    }
    leaf source-address {
      type ip-multicast-source-address;
      description
        "The IPv4/IPv6 source address of the multicast flow. The
         value set to zero means that the receiver interests
         in all source that relevant to one given group.";
    }
    leaf group-address {
      type rt-types:ip-multicast-group-address;
      description
        "The IPv4/IPv6 group address of multicast flow. This
         type represents a version-neutral IP multicast group
         address. The format of the textual representation
         implies the IP version.";
      reference
        "RFC8294: Common YANG Data Types for the Routing Area.";
    }
    leaf vni-type {
      type virtual-type;
      description
        "The type of virtual network identifier. Includes the
         Vxlan, NVGRE and Geneve. This value and vni-value is
         used to indicate a specific virtual multicast service.";
    }
    leaf vni-value {
      type uint32;
      description
        "The value of Vxlan network identifier, virtual subnet ID
         or virtual net identifier. This value and vni-type is used
         to indicate a specific virtual multicast service.";
    }
  } // general-multicast-key

  grouping encap-type {
    description
      "The encapsulation type used for flow forwarding.";
    choice encap-type {
      case mpls {
        description "The BIER forwarding depends on mpls.";
        reference
          "RFC 8296: Encapsulation for Bit Index Explicit
           Replication (BIER) in MPLS and Non-MPLS Networks.";
      }
      case eth {
        description "The BIER forwarding depends on ethernet.";
        reference
          "RFC 8296: Encapsulation for Bit Index Explicit
           Replication (BIER) in MPLS and Non-MPLS Networks.";
      }
      case ipv6 {
        description "The BIER forwarding depends on IPv6.";
        reference
          "I-D.zhang-bier-bierin6: BIER in IPv6 (BIERin6)";
      }
      description "The encapsulation type in BIER.";
    }
  } // encap-type

  grouping bier-key {
    description
      "The key parameters set for BIER/BIER TE forwarding.";
    reference
      "RFC 8279: Multicast Using Bit Index Explicit Replication
       (BIER).";
    leaf sub-domain {
      type uint16;
      description
        "The subdomain id that the multicast flow belongs to.";
    }
    leaf bitstringlength {
      type uint16;
      description
        "The bitstringlength used by BIER forwarding.";
    }
    leaf set-identifier {
      type uint16;
      description
        "The set identifier used by the multicast flow.";
    }
    uses encap-type;
  }

  grouping lsp {
    description "The lsp information.";
    leaf root-address {
      type ip-multicast-source-address;
      description
        "Root address of the mldp fec.";
    }
    leaf lsp-id {
      type uint32;
      description
        "The lsp id that corresponding this flow.";
    }
    leaf backup-lsp-id {
      type uint32;
      description
        "The backup lsp id that corresponding this flow.
         In case the lsp fails, the backup lsp can be used.";
    }
  } // lsp

  grouping transport-tech {
    choice transport {
      description "The selected transport technology.";
      container bier {
        description
          "The transport technology is BIER. The BIER technology
           is introduced in RFC8279. The parameter is consistent
           with the definition in BIER YANG data model.";
        reference
          "RFC 8279: Multicast Using Bit Index Explicit
           Replication (BIER).
           I-D.ietf-bier-bier-yang: YANG Data Model for BIER
           Protocol.";

        uses bier-key;
      }

      container bier-te {
        description
          "The transport technology is BIER-TE.";
        reference
          "I-D.ietf-bier-te-arch: Traffic Engineering for Bit Index
           Explicit Replication (BIER-TE)";

        uses bier-key;

        leaf-list bier-te-adj {
          type uint16;
          description
            "The adjacencies ID used in BIER TE forwarding
             encapsulation.";
        }
      }

      container cisco-mode {
        description
          "The transport technology is cisco-mode: Cisco MDT.";
        reference
          "RFC 6037: Cisco Systems' Solution for Multicast in
           BGP/MPLS IP VPNs";

        leaf p-group {
          type rt-types:ip-multicast-group-address;
          description
            "The address of p-group. It is used to encapsulate
             and forward flow according to multicast tree from
             ingress node to egress nodes.";
        }
        uses transport-pim;
      }

      container mpls {
        description
          "The transport technology is mpls. Multicast overlay can use
           mpls technologies to build transport layer.";
        reference
          "RFC 6513: Multicast in MPLS/BGP IP VPNs.";

        choice mpls-lsp-type {
          case mldp {
            description
              "The mldp type of lsp is used as multicast
               transportation.
               The YANG data model defined in 'ietf-mpls-mldp-yang'
               can be invoked.";
            reference
              "RFC 6388: Label Distribution Protocol Extensions
               for Point-to-Multipoint and Multipoint-to-Multipoint
               Label Switched Paths.
               I-D.ietf-mpls-mldp-yang:
                     YANG Data Model for MPLS mLDP.";

            container mldp-lsp {
              description
                "The specific parameters can be set to use
                 the specific mldp fec.";
              uses lsp;
            }
          }
          case p2mp-te {
            description
              "The p2mp te type of lsp is used as multicast
               transportation.";
            reference
              "RFC 4875: Extensions to Resource Reservation Protocol
               - Traffic Engineering (RSVP-TE) for Point-to-Multipoint
               TE Label Switched Paths (LSPs).";

            container p2mp-te-lsp {
              description
                "The specific parameters can be set to use
                 the specific mldp fec.";
              uses lsp;
            }
          }
          description "The collection types of mpls tunnels";
        }
      } // mpls

      container pim {
        description
          "The transport technology is PIM. PIM is used
           commonly in traditional network.";
        reference
          "RFC 7761: Protocol Independent Multicast - Sparse Mode
               (PIM-SM): Protocol Specification (Revised).";
        uses transport-pim;
      }
    } // choice
  } // transport-tech

  grouping underlay-tech {
    choice underlay {
      case bgp {
        description
          "The underlay technology is BGP. BGP protocol
           should run if BGP is used as underlay protocol.";
        reference
          "RFC 4271: A Border Gateway Protocol 4 (BGP-4)";
      }
      container ospf {
        description
          "The underlay technology is OSPF. OSPF protocol
           should be triggered to run if OSPF is used as underlay
           protocol.";
        reference
          "RFC 2328: OSPF Version 2.
           RFC 5340: OSPF for IPv6.
           I-D.ietf-ospf-yang: YANG Data Model for OSPF Protocol.";

        leaf topology {
          type leafref {
            path "/rt:routing/rt:control-plane-protocols/"
               + "rt:control-plane-protocol/ospf:ospf/"
               + "ospf:topologies/ospf:topology/ospf:name";
          }
          description
            "The designed topology name of ospf protocol.";
        }
      }
      case isis {
        description
          "The underlay technology is ISIS. ISIS protocol should
           be triggered to run if ISIS is used as underlay protocol.
           And the associated extensions can be used.";
        reference
          "RFC 1195: Use of OSI IS-IS for Routing in TCP/IP and
           Dual Environments";
      }
      case babel {
        description
          "The underlay technology is Babel. Babel protocol
           should be triggered to run if Babel is used as
           underlay protocol.";
        reference
          "I-D.ietf-babel-rfc6126bis: The Babel Routing Protocol.";
      }
    } // choice
  } // underlay-tech

  /*overlay*/

  grouping overlay-tech {
    choice overlay-tech-type {
      case bgp {
        description
          "BGP technology is used for multicast overlay.";
        reference
          "RFC 7716: Global Table Multicast with BGP Multicast
                     VPN (BGP-MVPN) Procedures.";
      }
      case evpn {
        description
          "EVPN technology is used for multicast overlay.";
        reference
          "RFC 7432: BGP MPLS-Based Ethernet VPN.
           I-D.ietf-bess-evpn-bum-procedure-updates: Updates on
             EVPN BUM Procedures.
           I-D.ietf-bier-evpn: EVPN BUM Using BIER.";
      }
      case mld {
        description
          "MLD technology is used for multicast overlay.";
        reference
          "I-D.ietf-bier-mld: BIER Ingress Multicast Flow Overlay
             using Multicast Listener Discovery Protocols.";
        leaf mld-instance-group {
          type rt-types:ip-multicast-group-address;
          description
            "The multicast address used for multiple MLD instance
             support.";
        }
      }
      case mld-snooping {
        description
          "MLD snooping technology is used for multicast overlay.";
        reference
          "RFC 4541: Considerations for Internet Group Management
                     Protocol (IGMP) and Multicast Listener
                     Discovery (MLD) Snooping Switches.";
      }
      case mvpn {
        description
          "MVPN technology is used for multicast overlay.";
        reference
          "RFC 6513: Multicast in MPLS/BGP IP VPNs.";
      }
      case pim {
        description
          "PIM technology is used for multicast overlay.";
        reference
          "I-D.ietf-bier-pim-signaling: PIM Signaling
             Through BIER Core.";
      }
      description
        "The overlay technology used for multicast service.";
    }
    description "The overlay technology used for multicast service.";
  } // overlay-tech

  /*transport*/

  grouping transport-pim {
    description
      "The requirement information of pim transportion.";
    reference
      "RFC 7761: Protocol Independent Multicast - Sparse Mode
                 (PIM-SM): Protocol Specification (Revised).";
  } //transport-pim

  /*underlay*/

  container multicast-model {
    description
      "The model of multicast YANG data. Include keys, overlay,
       transport and underlay.";

    list multicast-keys{
      key "vpn-rd source-address group-address vni-type vni-value";
      uses general-multicast-key;

      container multicast-overlay {
        description
          "The overlay information of multicast service.
           Overlay technology is used to exchange multicast
           flows information. Overlay technology may not be
           used in SDN controlled completely situation, but
           it can be used in partial SDN controlled situation
           or non-SDN controlled situation. Different overlay
           technologies can be choosed according to different
           deploy consideration.";

        container ingress-egress {
          description
            "The ingress and egress nodes address collection.
             The ingress node may use the egress nodes set
             directly to encapsulate the multicast flow by
             transport technology.";

          leaf ingress-node {
            type inet:ip-address;
            description
              "The ip address of ingress node for one or more
               multicast flow. Or the ingress node of MVPN and
               BIER. In MVPN, this is the address of ingress
               PE; in BIER, this is the BFR-prefix of ingress
               nodes.";
          }
          list egress-nodes {
            key "egress-node";
            description
              "The egress multicast nodes of the multicast flow.
               Or the egress node of MVPN and BIER. In MVPN, this
               is the address of egress PE; in BIER, this is the
               BFR-prefix of ingress nodes.";

            leaf egress-node {
              type inet:ip-address;
              description
                "The ip-address set of egress multicast nodes.";
            }
          }
        }

        container bier-ids {
          description
            "The BFR-ids of ingress and egress BIER nodes for
             one or more multicast flows. This overlay is used
             with BIER transport technology. The egress nodes
             set can be used to encapsulate the multicast flow
             directly in the ingress node.";
          reference
            "RFC 8279: Multicast Using Bit Index Explicit
             Replication (BIER)";

          leaf sub-domain {
            type uint16;
            description
              "The sub-domain that this multicast flow belongs to.";
          }
          leaf ingress-node {
            type uint16;
            description
              "The ingress node of multicast flow. This is the
               BFR-id of ingress nodes.";
          }
          list egress-nodes {
            key "egress-node";
            description
              "The egress nodes of multicast flow.";

            leaf egress-node {
              type uint16;
              description
                "The BFR-ids of egress multicast BIER nodes.";
            }
          }
        }
        uses overlay-tech;
      }

      container multicast-transport {
        description
          "The transportion of multicast service. Transport
           protocol is responsible for delivering multicast
           flows from ingress nodes to egress nodes with or
           without specific encapsulation. Different transport
           technology can be choosed according to different
           deploy consideration. Once a transport technology
           is choosed, associated protocol should be triggered
           to run.";

        uses transport-tech;
      }
      container multicast-underlay {
        description
          "The underlay of multicast service. Underlay protocol
           is used to build transport layer. Underlay protocol
           need not be assigned in ordinary network since
           existed underlay protocol fits well, but it can be
           assigned in particular networks for better
           controll. Once a underlay technology is choosed,
           associated protocol should be triggered to run.";

        uses underlay-tech;
      }
      description
        "The model of multicast YANG data. Include keys,
         overlay, transport and underlay.";
    }
  }

  /*Notifications*/

  notification head-end-event {
    leaf event-type {
      type enumeration {
        enum down {
          description
            "There is something wrong with head end node,
             and head end node can't work properlay.";
        }
        enum module-loaded {
          description
            "The new modules that can be used by multicast
             flows have been loaded.";
        }
        enum module-unloaded {
          description
            "The new modules that can be used by multicast
             flows have been unloaded.";
        }
      }
      description "Event type.";
    }
    container multicast-key {
      uses general-multicast-key;
      description
        "The associated multicast keys that are influenced by
         head end node failer.";
    }
    uses overlay-tech;

    container transport-tech {
      description
        "The modules can be used to forward multicast flows.";
      uses transport-tech;
    }

    container underlay-tech {
      description
        "There is something wrong with the module which is
         used to build multicast transport layer.";
      uses underlay-tech;
    }
    description
      "Notification events for the head end nodes. Like head
       node failer, overlay/ transport/ underlay module
       loading/ unloading. And the potential failer about some
       multicast flows and associated
       overlay/ transport/ underlay technologies.";
  }
}
