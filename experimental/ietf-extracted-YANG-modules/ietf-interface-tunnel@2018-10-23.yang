module ietf-interface-tunnel {
  yang-version 1.1;

  namespace "urn:ietf:params:xml:ns:yang:ietf-interface-tunnel";
  prefix ietf-interface-tunnel;

  import ietf-interfaces {
    prefix if;
    reference
      "RFC 8343: A YANG Data Model for Interface Management";
  }

  import iana-if-type  {
    prefix ift;
    reference
      "RFC 7224: IANA Interface Type YANG Module";
  }

  organization "IETF xxx Working Group";

  contact

    "WG Web:   <https://datatracker.ietf.org/wg/softwires/>
     WG List:  <mailto:softwire@ietf.org>

     Editor:  Mohamed Boucadair
              <mailto:mohamed.boucadair@orange.com>";

   description
      "This module is a YANG module for associating a tunnel type with
      tunnel interfaces.

      Copyright (c) 2018 IETF Trust and the persons identified as
      authors of the code.  All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC XXXX; see
      the RFC itself for full legal notices.";

  revision 2018-10-23 {
    description
      "Initial revision.";
    reference
      "RFC XXXX: YANG Modules for IPv4-in-IPv6 Address plus Port
                 Softwires";
  }
  augment "/if:interfaces/if:interface" {
    when 'derived-from(if:type, "ift:tunnel")';
    description
      "Augments Interface module with tunnel-specific parameters.

       IANA interface types are maintained at this registry:
       https://www.iana.org/assignments/ianaiftype-mib/ianaiftype-mib.

       tunnel (131),       -- Encapsulation interface";

    leaf tunnel-type {
      type identityref {
        base ift:tunnel;
      }
      description
        "Indicates the type of the tunnel. It corresponds
         to the IANAtunnelType.

         IANA tunnel types are maintained at this registry:
         https://www.iana.org/assignments/ianaiftype-mib/
         ianaiftype-mib.";
    }
  }
}
