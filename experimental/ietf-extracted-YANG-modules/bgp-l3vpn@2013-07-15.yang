module bgp-l3vpn {
  namespace "urn:ietf:params:xml:ns:yang:ietf-l3vpn-yang";
  // replace with IANA namespace when assigned
  prefix l3vpn ;

  import ietf-inet-types {
    prefix inet;
  }

  import ietf-routing {
    prefix rt;
    revision-date 2015-05-25;
  }
  import bgp {
    prefix bgp;
  }

  organization
    "Cisco Systems
     170 West Tasman Drive
     San Jose, CA 95134-1706
     USA";

  description
    "This YANG module defines the configuration for the BGP Layer 3 VPNs.
     It augments the IETF bgp yang model and IETF routing model to add L3VPN specific
     configuration and operational knobs.

     Terms and Acronyms

     AS : Autonomous System

     ASBR : Autonomous Systems Border Router

     BGP (bgp): Border Gateway Protocol

     CE  : Customer Edge

     IP (ip): Internet Protocol

     IPv4 (ipv4):Internet Protocol Version 4

     IPv6 (ipv6): Internet Protocol Version 6
     PE : Provider Edge

     RT : Route Target

     RD : Route Distinguisher

     VPN : Virtual Private Network

    ";

  revision 2015-10-15 {
    description
      "Initial revision.";
    reference
      "RFC XXXX: A YANG Data Model for L3VPN config management";
  }

  typedef bgp-rd-type {
     type enumeration {
       enum  type-0 {
          description "AS format RD as type-0 in RFC4364";
       }
       enum type-1 {
          description "4-byte AS format RD as type-1 in RFC4364";
       }
       enum type-2 {
          description "IPv4 address format RD as type-2 in RFC4364";
       }
       enum auto {
          description "Automatic RD value assignment";
       }
    }
    description "BGP route distinguisher format as described in RFC4364";
  }

  grouping rd-value-type0 {
      leaf as {
         type uint16;
         description "AS number 2 bytes";
      }
      leaf as-index {
         type uint32;
         description "AS index 4 bytes";
      }
  }
  grouping rd-value-type1 {
      leaf as-4byte {
         type uint32;
         description "AS number 4 bytes";
      }
      leaf as-4byte-index {
         type uint16;
         description "AS index 2 bytes";
      }
  }

  grouping rd-value-type2 {
      leaf address {
         type inet:ipv4-address;
         description "IPv4 address";
      }
      leaf address-index {
         type uint16;
         description "AS index 2 bytes";
      }
  }

  grouping bgp-rd-spec {
      description "BGP route-distinguisher as per RFC4364";
      leaf rd-type {
          type bgp-rd-type;
          description "Route distinguisher format type as per RFC4364";
      }
      uses rd-value-type0 {
          when "rd-type = 'type-0'" ;
      }
      uses rd-value-type1 {
          when "rd-type = 'type-1'" ;
      }
      uses rd-value-type2 {
          when "rd-type = 'type-2'" ;
      }
  }
  grouping bgp-rd {
      container route-distinguisher {
         container config {
            uses bgp-rd-spec ;
         }
         container state {
            config "false" ;
            uses bgp-rd-spec ;
         }
      }
  }

  typedef bgp-label-mode {
      description "Label allocation mode for prefixes in a VRF";
      type enumeration {
        enum per-ce {
             description "Allocate labels per CE";
        }
        enum per-prefix {
             description "Allocate labels per prefix";
        }
        enum per-vrf {
             description "Allocate labels per VRF";
        }
     }
     description "BGP label allocation mode";
  }

  typedef fwd-mode-type {
      type enumeration {
        enum mpls {
             description "Forwarding mode mpls";
        }
      }
      description "Enable forwarding mode under ASBR facing interface";
  }

  grouping forwarding-mode {
      container forwarding-mode {
          container config {
              leaf forwarding-mode {
                 type  fwd-mode-type;
                 description "Forwarding mode for this interface";
              }
          }
          container state {
              leaf forwarding-mode {
                 type  fwd-mode-type;
                 description "Forwarding mode for this interface";
              }
          }
      }
  }
  grouping route-target-set {
       description
          "Extended community route-target set ";
       container route-targets {
          description
            "Route-target";
          list route-target-list {
              description
                 "List of route-targets" ;
              key "route-target";
              leaf route-target {
                 type string {
                    pattern '([0-9]+:[0-9]+)';
                 }
              }
          }
       }
       leaf route-target-policy {
            description
              "Reference to the policy containing set of routes.
              "TBD: leafref to policy entry in IETF policy model";
            type string;
       }
  }

  grouping route-import-set {
      container import-routes {
         description "Set of route-targets to match to import routes into VRF";
         container config {
           description
               "Import routes";
           uses route-target-set ;
         }
         container state {
           config "false" ;
           description
               "Import routes";
           uses route-target-set ;
         }
      }
  }
  grouping route-export-set {
      container export-routes {
        description "Set of route-targets to attach with exported routes from VRF";
        container config {
           description
              "Export routes";
           uses route-target-set ;
        }
        container state {
           config "false" ;
           description
              "Export routes";
           uses route-target-set ;
        }
      }
  }

  grouping route-import-export-set {
      container import-export-routes {
          container config {
              description "Both import/export routes";
              uses route-target-set;
          }
          container state {
           config "false" ;
              description "Both import/export routes";
              uses route-target-set;
          }
      }
  }

  grouping route-filter-set {
      uses route-import-set;
      uses route-export-set;
      uses route-import-export-set;
  }

  grouping bgp-label-mode {
       description "MPLS/VPN label allocation mode";
       container config {
         leaf label-mode {
           type bgp-label-mode;
           description "Label allocation mode";
         }
       }
       container state {
         config "false" ;
         leaf label-mode {
           type bgp-label-mode;
           description "Label allocation mode";
         }
       }
  }

  grouping retain-route-targets {
       description "Grouping for route target accept";
    container retain-rts {
      description "Control route target acceptance behavior for ASBRs";
      container config {
         leaf retain-all {
            type empty;
            description "Disable filtering of all route-targets";
         }
         leaf retain-policy-filter {
            type string;
            description "Filter routes as per filter policy name";
         }
      }
      container state {
         config "false" ;
         leaf retain-all {
            type empty;
            description "Disable filtering of all route-targets";
         }
         leaf retain-policy-filter {
            type string;
            description "Filter routes as per filter policy name";
         }
      }
    }
  }

  // Augmentations of base models.

  // Route-distinguisher is added in BGP global level. BGP is supposed to be
  // under scope of VRF as a routing instance, once BGP model is augmented.
  // Which means rd defined here will be per VPN per BGP instance.
  //
  augment "/bgp:bgp/bgp:global/" {
     uses bgp-rd ;
  }

  // route import/export rules in applicable address families.
  augment "/bgp:bgp/bgp:global/bgp:afi-safis/bgp:afi-safi/bgp:ipv4-unicast/" {
   uses route-filter-set;
  }

  augment "/bgp:bgp/bgp:global/bgp:afi-safis/bgp:afi-safi/bgp:ipv4-multicast/" {
   uses route-filter-set ;
  }

  augment "/bgp:bgp/bgp:global/bgp:afi-safis/bgp:afi-safi/bgp:ipv6-unicast/" {
   uses route-filter-set ;
  }

  augment "/bgp:bgp/bgp:global/bgp:afi-safis/bgp:afi-safi/bgp:ipv6-multicast/" {
   uses route-filter-set ;
  }

  // Retain route-target for inter-as option ASBR knob.
  // vpnv4/vpnv6/mvpn address-family only.
  augment "/bgp:bgp/bgp:global/bgp:afi-safis/bgp:afi-safi/bgp:l3vpn-ipv4-unicast/" {
    uses retain-route-targets;
  }

  augment "/bgp:bgp/bgp:global/bgp:afi-safis/bgp:afi-safi/bgp:l3vpn-ipv6-unicast/" {
    uses retain-route-targets;
  }

  augment "/bgp:bgp/bgp:global/bgp:afi-safis/bgp:afi-safi/bgp:l3vpn-ipv4-multicast/" {
    uses retain-route-targets;
  }

  /* MPVN address family is not in BASE BGP model yet.
  augment "/bgp:bgp/bgp:global/bgp:afi-safis/bgp:afi-safi/bgp:ipv4-mpvn/" {
    uses retain-route-targets;
  }

  augment "/bgp:bgp/bgp:global/bgp:afi-safis/bgp:afi-safi/bgp:ipv6-mpvn/" {
    uses retain-route-targets;
  }
  */

  // Label allocation mode configuration. Certain AFs only.
  augment "/bgp:bgp/bgp:global/bgp:afi-safis/bgp:afi-safi/bgp:ipv4-unicast/" {
   uses bgp-label-mode ;
  }

  augment "/bgp:bgp/bgp:global/bgp:afi-safis/bgp:afi-safi/bgp:ipv6-unicast/" {
   uses bgp-label-mode ;
  }

  // Add route import-export rules in  VRF-AF mode (routing instance default rib per address family).
  augment "/rt:routing/rt:routing-instance/rt:default-ribs/rt:default-rib/" {
     uses route-filter-set ;
  }

  // bgp mpls forwarding enable required for inter-as option AB.
  augment "/rt:routing/rt:routing-instance/rt:interfaces/rt:interface/" {
    uses forwarding-mode ;
  }
}
