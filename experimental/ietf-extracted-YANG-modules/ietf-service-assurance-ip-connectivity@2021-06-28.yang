module ietf-service-assurance-ip-connectivity {
  yang-version 1.1;
  namespace "urn:ietf:params:xml:ns:yang:ietf-service-assurance-ip-connectivity";
  prefix service-assurance-ip-connectivity;

  import ietf-inet-types {
    prefix inet;
  }
  import ietf-service-assurance {
    prefix service-assurance;
  }

  organization
    "IETF OPSAWG Working Group";
  contact
    "WG Web:   <https://datatracker.ietf.org/wg/opsawg/>
     WG List:  <mailto:opsawg@ietf.org>
     Author:   Benoit Claise  <mailto:benoit.claise@huawei.com>
     Author:   Jean Quilbeuf   <mailto:jean.quilbeuf@huawei.com>";
  description
    "This module extends the ietf-service-assurance module to add
     support for the subservice ip-connectivity.

     Checks whether the ip connectivity between two ip addresses
     belonging to two network devices is healthy.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2021 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (https://trustee.ietf.org/license-info).

     This version of this YANG module is part of RFC XXXX; see the
     RFC itself for full legal notices.  ";

  revision 2021-06-28 {
    description
      "Initial revision.";
    reference
      "RFC xxxx: Title to be completed";
  }

  identity ip-connectivity-idty {
    base service-assurance:subservice-idty;
    description
      "Checks connectivity between two IP addresses.";
  }

  augment "/service-assurance:subservices/service-assurance:subservice/service-assurance:parameter" {
    description
      "Specify the required parameters for the ip-connectivity-idty subservice type";
    container parameters {
      when "derived-from-or-self(../service-assurance:type, 'ip-connectivity-idty')";
      description
        "Required parameters for the ip-connectivity-idty subservice type";
      leaf device1 {
        type string;
        mandatory true;
        description
          "Device at the first end of the connection.";
      }
      leaf address1 {
        type inet:ip-address;
        mandatory true;
        description
          "Address at the first end of the connection.";
      }
      leaf device2 {
        type string;
        mandatory true;
        description
          "Device at the second end of the connection.";
      }
      leaf address2 {
        type inet:ip-address;
        mandatory true;
        description
          "Address at the second end of the connection.";
      }
    }
  }
}
