module openconfig-catalog-types {

  yang-version "1";
  // namespace
  namespace "http://openconfig.net/yang/catalog-types";

  prefix "cat-types";

  // import some basic types

  // meta
  organization "OpenConfig working group";

  contact
    "OpenConfig working group
    www.openconfig.net";

  description
    "This module defines types and identities used by the OpenConfig
    YANG module catalog model.";

  revision "2015-10-18" {
    description
      "Initial revision";
    reference "TBD";
  }

  // extension statements

  // feature statements

  // identity statements

  identity implementation-status-type {
    description
      "Indications of the status of a module's implementation on a
      device or server";
  }

  identity in-progress {
    base implementation-status-type;
    description
      "Implementation is in progress";
  }

  identity planned {
    base implementation-status-type;
    description
      "Implementation is planned";
  }
  identity complete {
    base implementation-status-type;
    description
      "Implementation is complete and fully supports the model";
  }

  identity partial {
    base implementation-status-type;
    description
      "Implementation is complete, but only supports the model
      partially";
  }

  identity module-status-type {
    description
      "Indicates the deployment status of the module";
  }

  identity experimental {
    base module-status-type;
    description
      "Module should be considered experimental, not deployed in
      production settings";
  }

  identity production {
    base module-status-type;
    description
      "Module is suitable for use in production, or has been
      deployed in production";
  }

  identity module-category-base {
    description
      "Base identity for the module category.  It is expected that
      publishing organizations will define additional derived
      identities to describe their categorization scheme.";
  }

  identity module-subcategory-base {
    description
      "Base identity for the module subcategory.  It is expected that
      publishing organizations will define additional derived
      identities to describe their categorization scheme.";
  }

  identity organization-type {
    description
      "Publishing organization type for the set of modules";
  }

  identity standards {
    base organization-type;
    description
      "Standards development organization (SDO) publisher type";
  }

  identity industry {
    base organization-type;
    description
      "Industry forum or other industry group";
  }

  identity commercial {
    base organization-type;
    description
      "Commercial entity, company, etc.";
  }

  identity individual {
    base organization-type;
    description
      "For modules published by an individual";
  }

  // typedef statements

  typedef yang-model-publisher
  {
    type enumeration {
       enum "standards";
       enum "commercial";
       enum "forum";
     }
  }

  // grouping statements

  // data definition statements

  // augment statements

  // rpc statements

  // notification statements
}
