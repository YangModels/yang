module ietf-segment-routing {
  namespace "urn:ietf:params:xml:ns:"
          + "yang:ietf-segment-routing";
  prefix sr;

  import ietf-inet-types {
    prefix "inet";
  }

  import ietf-yang-types {
    prefix "yang";
  }

  import ietf-routing {
    prefix "rt";
  }

  organization
   "IETF SPRING Working Group";

  contact
    "WG List:  <mailto:spring@ietf.org>

    Editor:    Stephane Litkowski
               <mailto:stephane.litkowski@orange.com>

    Author:    Acee Lindem
               <mailto:acee@cisco.com>
    Author:    Yingzhen Qu
               <mailto:yiqu@cisco.com>
    Author:    Pushpasis Sarkar
               <mailto:psarkar@juniper.net>
    Author:    Ing-Wher Chen
               <mailto:ing-wher.chen@ericsson.com>
    Author:    Jeff Tantsura
               <jeff.tantsura@ericsson.com>

    ";

  description
    "The YANG module defines a generic configuration model for
    Segment routing common across all of the vendor
    implementations.";

  revision 2016-07-07 {
    description "
      * Add support of prefix-sid algorithm configuration
      * change routing-protocols to control-plane-protocols
    ";
    reference
      "RFC XXXX: YANG Data Model for Segment Routing.";
  }

  revision 2016-03-17 {
    description "
      * Add notification segment-routing-global-srgb-collision
      * Add router-id to segment-routing-global-sid-collision
      * Remove routing-instance
      * Add typedef router-id
    ";
    reference
      "RFC XXXX: YANG Data Model for Segment Routing.";
  }
  revision 2015-10-17 {
    description "
      * Add per-protocol SRGB config feature
      * Move SRBG config to a grouping
    ";
    reference
      "RFC XXXX: YANG Data Model for Segment Routing.";
  }
  revision 2015-06-22 {
    description "
      * Prefix SID config moved to
        connected-prefix-sid-map in global SR cfg
        rather than IGP.
      ";
      reference "draft-litkowski-spring-sr-yang-01";
  }
  revision 2015-04-23 {
    description "
      * Node flag deprecated from prefixSID
      * SR interface cfg moved to protocol
      * Adding multiple binding policies for SRMS
      ";
      reference "";
  }
  revision 2015-02-27 {
    description "Initial";
    reference "draft-litkowski-spring-sr-yang-00";
  }

  /* Identities */
  identity segment-routing-transport {
    description
    "Base identity for segment routing transport.";
  }
  identity segment-routing-transport-mpls {
    base segment-routing-transport;
    description
    "This identity represents MPLS transport for segment
    routing.";
  }

  identity prefix-sid-algorithm {
    description
    "Base identity for prefix-sid algorithm.";
  }

  identity prefix-sid-algorithm-shortest-path {
    base prefix-sid-algorithm;
    description
    "The default behavior of prefix-sid algorithm.";
  }

  identity prefix-sid-algorithm-strict-spf {
    base prefix-sid-algorithm;
    description
    "This algorithm mandates that the packet is forwared
     according to ECMP-aware SPF algorithm.";
  }

  /* Features */

  feature mapping-server {
    description
     "Support of SRMS.";
  }

  feature sid-last-hop-behavior {
    description
      "Configurable last hop behavior.";
  }

  feature protocol-srgb {
    description
      "Support per-protocol srgb configuration.";
  }

  /* Type Definitions */

  typedef system-id {
    type string {
      pattern
       '[0-9A-Fa-f]{4}\.[0-9A-Fa-f]{4}\.[0-9A-Fa-f]{4}\.00';
    }
    description
     "This type defines ISIS system id using pattern,
      system id looks like : 0143.0438.AeF0.00";
  }

  typedef router-id {
    type union {
      type system-id;
      type yang:dotted-quad;
    }
    description
      "OSPF/BGP router id or ISIS system ID.";
  }

  /* Groupings */

  grouping srgb-cfg {
    list srgb {
      key "lower-bound upper-bound";
      ordered-by user;
      leaf lower-bound {
        type uint32;
        description
          "Lower value in the block.";
      }
      leaf upper-bound {
        type uint32;
        description
          "Upper value in the block.";
      }
      description
        "List of global blocks to be
         advertised.";
    }
    description
      "Grouping for SRGB configuration.";
  }

  grouping controlplane-cfg {
    container segment-routing {
      leaf enabled {
        type boolean;
        default false;
        description
         "Enables segment-routing
         protocol extensions.";
      }
      container bindings {
        container advertise {
          leaf-list policies {
                        type string;
                        description
                         "List of policies to be advertised.";
                  }
          description
                  "Authorize the advertise
          of local mappings in binding TLV.";
        }
        leaf receive {
          type boolean;
          default true;
          description
          "Authorize the reception and usage
          of binding TLV.";
        }
        description
         "Control of binding advertisement
         and reception.";
      }

      description
      "segment routing global config.";
    }
    description
     "Defines protocol configuration.";
  }

  grouping sid-value-type {
    leaf value-type {
      type enumeration {
        enum index {
          description
            "The value will be
             interpreted as an index.";
        }
        enum absolute {
          description
            "The value will become
             interpreted as an absolute
             value.";
        }
      }
      default index;
      description
        "This leaf defines how value
         must be interpreted.";
    }
        description
         "Defines how the SID value is expressed.";
  }

  grouping ipv4-sid-cfg {

      leaf prefix {
        type inet:ipv4-prefix;
        description
          "connected prefix sid.";
      }

    uses sid-value-type;

      leaf start-sid {
        type uint32;
        mandatory true;
        description
        "Value associated with
        prefix. The value must
        be interpreted in the
        context of value-type.";
      }

      leaf range {
        type uint32;
        description
          "Describes how many SIDs could be
           allocated.";
      }

      leaf algorithm {
        type identityref {
          base prefix-sid-algorithm;
        }
        description "Prefix-sid algorithm.";
      }
    description
     "This grouping defines cfg of prefix SID.";
  }

  grouping ipv6-sid-cfg {
      leaf prefix {
        type inet:ipv6-prefix;
        description
          "connected prefix sid.";
      }

    uses sid-value-type;

      leaf start-sid {
        type uint32;
        mandatory true;
        description
        "Value associated with
        prefix. The value must
        be interpreted in the
        context of value-type.";
      }

      leaf range {
        type uint32;
        description
          "Describes how many SIDs could be
           allocated.";
      }

      leaf algorithm {
        type identityref {
          base prefix-sid-algorithm;
        }
        description "Prefix-sid algorithm.";
      }

    description
     "This grouping defines cfg of prefix SID.";
  }

  grouping last-hop-behavior {
    leaf last-hop-behavior {
      if-feature sid-last-hop-behavior;
      type enumeration {
        enum explicit-null {
          description
            "Use explicit-null for the SID.";
        }
        enum no-php {
          description
            "Do no use PHP for the SID.";
        }
        enum php {
            description
             "Use PHP for the SID.";
        }
      }
      description
        "Configure last hop behavior.";
    }
        description
         "Defines last hop behavior";
  }

  grouping igp-interface-cfg {
        container segment-routing {

         container adjacency-sid {
                list advertise-adj-group-sid {
                  key group-id;

                  leaf group-id {
                        type uint32;
                        description
                         "The value is an internal value to identify
                         a group-ID. Interfaces with the same
                         group-ID will be bundled together.
                         ";
                  }
                  description
                   "Control advertisement of S flag.
                         Enable to advertise a common Adj-SID
                         for parallel links.";
                }
                leaf advertise-protection {
                  type enumeration {
                        enum "single" {
                          description
                           "A single Adj-SID is associated
                           with the adjacency and reflects
                           the protection configuration.";
                        }
                        enum "dual" {
                          description
                           "Two Adj-SIDs will be associated
                           with the adjacency if interface
                           is protected. In this case
                           one will be enforced with
                           backup flag set, the other
                           will be enforced to backup flag unset.
                           In case, protection is not configured,
                           a single Adj-SID will be advertised
                           with backup flag unset.";
                        }
                  }
                  description
                   "If set, the Adj-SID refers to an
                  adjacency being protected.";
                }
                description
                 "Defines the adjacency SID properties.";
          }
          description
           "container for SR interface cfg.";
        }
          description
           "Grouping for IGP interface cfg.";
  }

  /* Cfg */

  augment "/rt:routing" {
    description
     "This augments routing-instance
     configuration with segment-routing.";
    container segment-routing {
      leaf transport-type {
        type identityref {
          base segment-routing-transport;
        }
        default "segment-routing-transport-mpls";
        description "Dataplane to be used.";
      }
      container bindings {
          container mapping-server {
            if-feature mapping-server;
            list policy {
              key name;
              leaf name {
                type string;
                description
                  "Name of the mapping policy.";
              }
              container ipv4 {
                list mapping-entry {
                  key "prefix algorithm";
                  uses ipv4-sid-cfg;

                  description
                    "Mapping entries.";
                }
                description
                  "IPv4 mapping entries.";
              }
              container ipv6 {
                list mapping-entry {
                  key "prefix algorithm";
                  uses ipv6-sid-cfg;
                  description
                    "Mapping entries.";
                }
                description
                  "IPv6 mapping entries.";
              }
              description
                "Definition of mapping policy.";
            }
            description
              "Configuration of mapping-server
               local entries.";
          }
          container connected-prefix-sid-map {
            container ipv4 {
              list ipv4-prefix-sid {
                key "prefix algorithm";
                uses ipv4-sid-cfg;
                uses last-hop-behavior;
                description
                  "List of prefix SID
                   mapped to IPv4 local prefixes.";
              }
              description
                "Parameters associated with IPv4 prefix SID";
            }
            container ipv6 {
              list ipv6-prefix-sid {
                key "prefix algorithm";
                uses ipv6-sid-cfg;
                uses last-hop-behavior;
                description
                  "List of prefix SID
                   mapped to IPv6 local prefixes.";
              }
              description
                "Parameters associated with IPv6 prefix SID";
            }
            description
              "Prefix SID configuration.";
          }
        description
          "List of bindings.";
      }
      container global-srgb {
        uses srgb-cfg;
        description
          "Global SRGB configuration.";
      }
      description
        "segment routing global config.";
    }
  }

  /* Operational states */

  augment "/rt:routing-state" {
    description
     "This augments the operational states
      with segment-routing.";
    container segment-routing {
      container node-capabilities {
        list transport-planes {
          key transport-plane;
          leaf transport-plane {
            type identityref {
              base segment-routing-transport;
            }
            description
              "Transport plane supported";
          }
          description
            "List of supported transport planes.";
        }
        leaf segment-stack-push-limit {
          type uint8;
          description
            "Describes the number of segments
             that can be pushed by the node.";
        }
        leaf readable-label-stack-depth {
          type uint8;
          description
            "Number of MPLS labels that
             can be read in the stack.";
        }
        description
          "Shows the SR capability of the node.";
      }
      list label-blocks {
        leaf lower-bound {
          type uint32;
          description
           "Lower bound of the label block.";
        }
        leaf upper-bound {
          type uint32;
          description
           "Upper bound of the label block.";
        }
        leaf size {
          type uint32;
          description
           "Number of indexes in the block.";
        }
        leaf free {
          type uint32;
          description
           "Number of indexes free in the block.";
        }
        leaf used {
          type uint32;
          description
           "Number of indexes used in the block.";
        }
        description
         "List of labels blocks currently
         in use.";
      }

      container global-sid-list {
        list sid {
          key "target sid source source-protocol binding-type";
          ordered-by system;
          leaf target {
            type string;
            description
             "Defines the target of the binding.
             It can be a prefix or something else.";
          }
          leaf sid {
            type uint32;
            description
             "Index associated with the prefix.";
          }
          leaf algorithm {
            type uint8;
            description
             "Algorithm to be used for the prefix
             SID.";
          }
          leaf source {
            type inet:ip-address;
            description
             "IP address of the router than own
              the binding.";
          }
          leaf used {
            type boolean;
            description
             "Defines if the binding is used
              in forwarding plane.";
          }
          leaf source-protocol {
            type leafref {
              path "/rt:routing-state/rt:control-plane-protocols/"
                 + "rt:control-plane-protocol/rt:name";
            }
            description
             "Rtg protocol that owns the binding";
          }
          leaf binding-type {
            type enumeration {
              enum prefix-sid {
                description
                 "Binding is learned from
                 a prefix SID.";
              }
              enum binding-tlv {
                description
                 "Binding is learned from
                 a binding TLV.";
              }
            }
            description
             "Type of binding.";
          }
          description
            "Binding.";

        }
        description
         "List of prefix and SID associations.";
      }
      description
       "Segment routing operational states.";
    }
  }

  /* Notifications */

  notification segment-routing-global-srgb-collision {
    list srgb-collisions {
      leaf lower-bound {
        type uint32;
          description
            "Lower value in the block.";
      }
      leaf upper-bound {
        type uint32;
          description
            "Upper value in the block.";
      }
      leaf routing-protocol {
        type leafref {
          path "/rt:routing-state/rt:control-plane-protocols/"
             + "rt:control-plane-protocol/rt:name";
        }
        description
          "Routing protocol reference that received the event.";
      }
      leaf originating-rtr-id {
        type router-id;
        description
          "Originating router id of this SRGB block.";
      }
      description
        "List of SRGB blocks that conflict.";
    }
    description
      "This notification is sent when received SRGB blocks from
       a router conflict.";
  }
  notification segment-routing-global-sid-collision {
    leaf received-target {
      type string;
      description
      "Target received in the controlplane that
                         caused SID collision.";
    }
    leaf new-sid-rtr-id {
      type router-id;
      description
        "Router Id that advertising the conflicting SID.";
    }
    leaf original-target {
      type string;
      description
      "Target already available in database that have the same SID
      as the received target.";
    }
    leaf original-sid-rtr-id {
      type router-id;
      description
        "Original router ID that advertised the conflicting SID.";
    }
    leaf index {
      type uint32;
      description
      "Value of the index used by two different prefixes.";
    }
    leaf routing-protocol {
      type leafref {
        path "/rt:routing-state/rt:control-plane-protocols/"
           + "rt:control-plane-protocol/rt:name";
      }
      description
       "Routing protocol reference that received the event.";
    }
    description
      "This notification is sent when a new mapping is learned
      , containing mapping
      where the SID is already used.
      The notification generation must be throttled with at least
       a 5 second gap. ";
  }
  notification segment-routing-index-out-of-range {
    leaf received-target {
      type string;
      description
      "Target received in the controlplane
                        that caused SID collision.";
    }
    leaf received-index {
      type uint32;
      description
      "Value of the index received.";
    }
    leaf routing-protocol {
      type leafref {
        path "/rt:routing-state/rt:control-plane-protocols/" +
        "rt:control-plane-protocol/rt:name";
      }
      description
       "Routing protocol reference that received the event.";
    }
    description
      "This notification is sent when a binding
      is received, containing a segment index
      which is out of the local configured ranges.
      The notification generation must be throttled with at least
       a 5 second gap. ";
  }

}
