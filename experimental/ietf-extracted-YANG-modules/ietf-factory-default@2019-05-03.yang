module ietf-factory-default {
  yang-version 1.1;
  namespace "urn:ietf:params:xml:ns:yang:ietf-factory-default";
  prefix fd;

  import ietf-datastores {
    prefix ds;
  }
  import ietf-netconf-acm {
    prefix nacm;
  }

  organization
    "IETF NETMOD (Network Modeling) Working Group";
  contact
    "WG Web:   <https://tools.ietf.org/wg/netconf/>
     WG List:  <mailto:netconf@ietf.org>

     Editor:   Qin Wu
               <mailto:bill.wu@huawei.com>
     Editor:   Balazs Lengyel
               <mailto:balazs.lengyel@ericsson.com>
     Editor:   Ye Niu
               <mailto:niuye@huawei.com>";
  description
    "This module defines the
     - factory-reset RPC
     - factory-default datastore
     It provides functionality to reset a server to its
     factory-default content.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";

  revision 2019-05-03 {
    description
      "Initial revision.";
    reference
      "RFC XXXX: Factory default Setting";
  }

  feature factory-default-datastore {
    description
      "Indicates that the factory default configuration is
       available as a datastore.";
  }

  rpc factory-reset {
    nacm:default-deny-all;
    description
      "The server resets the content of all read-write
       configuration datastores (i.e.,<running> , <startup><candidate>) to
       their factory default content.";
  }

  identity factory-default {
    if-feature "factory-default-datastore";
    base ds:datastore;
    description
      "This read-only datastore contains the configuration data used to
       replace the contents ofthe read-write conventional configuration
       datastores during a factory-reset RPC operation.";
  }
}
