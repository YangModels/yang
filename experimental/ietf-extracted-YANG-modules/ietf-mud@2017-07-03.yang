module ietf-mud {
 yang-version 1.1;
 namespace "urn:ietf:params:xml:ns:yang:ietf-mud";
 prefix "ietf-mud";

 import ietf-access-control-list {
   prefix "acl";
 }

 import ietf-yang-types {
   prefix "yang";
 }

 import ietf-inet-types {
   prefix "inet";
 }

 organization
   "IETF OPSAWG (Ops Area) Working Group";

 contact
      "WG Web: http://tools.ietf.org/wg/opsawg/
      WG List: opsawg@ietf.org
      Author: Eliot Lear
      lear@cisco.com
      Author: Ralph Droms
      rdroms@gmail.com
      Author: Dan Romascanu
      dromasca@gmail.com

   ";

 description
   "This YANG module defines a component that augments the
    IETF description of an access list.  This specific module
    focuses on additional filters that include local, model,
    and same-manufacturer.

   Copyright (c) 2016,2017 IETF Trust and the persons
   identified as the document authors.  All rights reserved.
   Redistribution and use in source and binary forms, with or
   without modification, is permitted pursuant to, and subject
   to the license terms contained in, the Simplified BSD
   License set forth in Section 4.c of the IETF Trust's Legal
   Provisions Relating to IETF Documents
   (http://trustee.ietf.org/license-info).
   This version of this YANG module is part of RFC XXXX; see
   the RFC itself for full legal notices.";

 revision "2017-07-03"  {
   description
     "More work on ACL usage.";
   reference "RFC XXXX: Manufacturer Usage Description
              Specification";
 }

 revision "2017-06-29"  {
   description
     "Take packet directionality out of ACL. " +
     "Introduce device container.";
   reference "RFC XXXX: Manufacturer Usage Description
              Specification";
 }

 revision "2017-04-18"  {
   description "Base version of MUD extensions to ACL model";
   reference "RFC XXXX: Manufacturer Usage Description
              Specification";
 }

 typedef direction {
    type enumeration {
        enum to-device {
          description "packets or flows destined to the target
                       device";
        }
        enum from-device {
          description "packets or flows destined from
                       the target device";
          }
        }
    description "Which way are we talking about?";
 }

 identity mud-acl {
   base "acl:acl-base";
   description
     "ACL that contains MUD-specific access control list entries.";
 }

 feature mud-acl {
   description
     "MUD ACL augmentations supported.";
 }

 container metainfo  {

   description "Information about when support end(ed), and
                when to refresh";

   leaf last-update {
     type yang:date-and-time;
     description "This is intended to be when
                  the MUD file was generated.";
   }

   leaf cache-validity {
     type uint8 {
       range "1..168";
     }
     description "The information retrieved from the MUD server is
                valid for these many hours, after which it should
                be refreshed.";
   }

   leaf masa-server {
     type inet:uri;
     description "The URI of the MASA server that network
     elements should forward requests to for this device.";
   }

   leaf is-supported {
     type boolean;
     description "The element is currently supported
                  by the manufacturer.";
   }
   leaf systeminfo {
     type inet:uri;
     description "A reference to a description of this device";
   }

   leaf-list extensions {
     type string;
     description "A list of extension names that are used in this MUD
                  file.  Each name is registered with the IANA and
                  described in an RFC.";
  }
 }

 grouping ACCESS_LISTS {
   description "A grouping for access lists in the context of device
                policy.";
   container access-lists {
     description "The access lists that should be applied to traffic
                    to or from the device.";
     list access-list {
       key "acl-name acl-type";
       description "Each entry on this list refers to an ACL that
                      should be present in the overall access list
                      data model. Each ACL is identified by name and
                      type.";
       leaf acl-name {
         type leafref {
           path "/acl:access-lists/acl:acl/acl:acl-name";
         }
         description "The name of the ACL for this entry.";
       }
       leaf acl-type {
         type identityref {
           base acl:acl-base;
         }
         description "The type of the ACL for this entry.";
       }
     }
   }
 }

 container device {
   description "A container allowing us to associate data with the
                device type being described in the instance document";

   container from-device-policy {
     description "The policies that should be enforced on traffic
                  coming from the device. These policies are not
                  necessarily intended to be enforced at a single
                  point, but may be rendered by the controller to any
                  relevant enorcement points in the network or
                  elsewhere.";
     uses ACCESS_LISTS;
   }

   container to-device-policy {
     description "The policies that should be enforced on traffic
                  going to the device. These policies are not
                  necessarily intended to be enforced at a single
                  point, but may be rendered by the controller to any
                  relevant enorcement points in the network or
                  elsewhere.";
     uses ACCESS_LISTS;
   }

 }

 augment "/acl:access-lists/acl:acl/" +
    "acl:access-list-entries/acl:ace/" +
    "acl:matches" {
   description "adding abstractions to avoid need of IP addresses";

   container mud-acl {
     if-feature mud-acl;
     must "../../../../acl-type = 'ietf-mud:mud-acl'";

     description
       "TODO; improve. MUD-specific matches.";

     leaf manufacturer {
       type inet:host;
       description "authority component of the manufacturer URI";
     }

     leaf same-manufacturer {
       type empty;
       description "expand to ACEs for each device
                  with the same origin";
     }

     leaf model {
       type string;
       description "specific model (including version) for a
                    given manufacturer";
     }

     leaf local-networks {
       type empty;
       description "this string is used to indicate networks
                  considered local in a given environment.";
     }

     leaf controller {
       type inet:uri;
       description "expands to one or more controllers for a
                  given service that is codified by inet:uri.";
     }

     leaf my-controller {
       type empty;
       description "This element indicates that the network should manage
                  a class of devices related to this MUD-URL that are
                  intended to control this device.";
     }
   }

 }

 augment "/acl:access-lists/acl:acl/" +
   "acl:access-list-entries/acl:ace/" +
   "acl:matches/acl:tcp-acl" {
   description "Adding domain names to matching";
   leaf direction-initiated {
     type direction;
     description "which direction a flow was initiated";
   }
 }
}
