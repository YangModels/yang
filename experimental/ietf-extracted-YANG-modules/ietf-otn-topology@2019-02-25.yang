module ietf-otn-topology {
  yang-version 1.1;

  namespace "urn:ietf:params:xml:ns:yang:ietf-otn-topology";
  prefix "otntopo";

  import ietf-network {
    prefix "nw";
    reference "RFC 8345: A YANG Data Model for Network Topologies";
  }

  import ietf-network-topology {
    prefix "nt";
    reference "RFC 8345: A YANG Data Model for Network Topologies";
  }

  import ietf-te-topology {
    prefix "tet";
    reference
    "I-D.ietf-teas-yang-te-topo: YANG Data Model for
    Traffic Engineering (TE) Topologies";
  }
  import ietf-otn-types {
    prefix "otn-types";
    reference
         "I-D.ietf-ccamp-otn-tunnel-model: OTN Tunnel YANG Model";
         }

  organization
    "IETF CCAMP Working Group";
  contact
    "WG Web: <http://tools.ietf.org/wg/ccamp/>
     WG List: <mailto:ccamp@ietf.org>

     Editor: Haomian Zheng
             <mailto:zhenghaomian@huawei.com>

     Editor: Aihua Guo
             <mailto:aihuaguo@huawei.com>

     Editor: Italo Busi
             <mailto:italo.busi@huawei.com>

     Editor: Anurag Sharma
             <mailto:ansha@google.com>

     Editor: Xufeng Liu
             <mailto:xufeng.liu.ietf@gmail.com>

     Editor: Sergio Belotti
             <mailto:sergio.belotti@nokia.com>

     Editor: Yunbin Xu
             <mailto:xuyunbin@ritt.cn>

     Editor: Lei Wang
             <mailto:wangleiyj@chinamobile.com>

     Editor: Oscar Gonzalez de Dios
             <mailto:oscar.gonzalezdedios@telefonica.com>";

  description
    "This module defines a protocol independent Layer 1/ODU topology
     data model.

    Copyright (c) 2019 IETF Trust and the persons
          identified as authors of the code.  All rights reserved.

        Redistribution and use in source and binary forms, with or
        without modification, is permitted pursuant to, and subject
        to the license terms contained in, the Simplified BSD License
        set forth in Section 4.c of the IETF Trust's Legal Provisions
        Relating to IETF Documents
        (https://trustee.ietf.org/license-info).";

  revision 2019-02-25 {
    description
      "draft-ietf-ccamp-otn-topo-yang-06";
    reference
      "RFC XXXX: A YANG Data Model for Optical Transport Network Topology";
    // RFC Ed.: replace XXXX with actual RFC number, update date
    // information and remove this note
  }

 /*
  * Groupings
  */

  grouping otn-link-attributes {
    description "link attributes for OTN";

    leaf tsg {
      type identityref {
        base otn-types:tributary-slot-granularity;
      }
      description "Tributary slot granularity.";
      reference
        "G.709/Y.1331, February 2016: Interfaces for the
         Optical Transport Network (OTN)";
    }
    leaf distance {
      type uint32;
      description "distance in the unit of kilometers";
    }
  }

  grouping otn-tp-attributes {
    description "tp attributes for OTN";
    list supported-payload-types {
      key "index";
      description
        "Supported payload types of a TP. The payload type is defined
         as the generalized PIDs in GMPLS.";
      leaf index {
        type uint16;
        description "payload type index";
      }
      leaf payload-type {
        type string;
        description "the payload type supported by this client tp";
        reference
          "http://www.iana.org/assignments/gmpls-sig-parameters
           /gmpls-sig-parameters.xhtml";
      }
    }
    leaf client-facing {
      type boolean;
      default 'false';
      description
        "Indicating if it is a client-facing TP.";
    }
  }

 /*
  * Data nodes
  */
  augment "/nw:networks/nw:network/nw:network-types/"
        + "tet:te-topology" {
    container otn-topology {
      presence "indicates a topology type of Optical Transport
                Network (OTN)-electrical layer.";
      description "otn topology type";
    }
    description "augment network types to include otn newtork";
  }

  augment "/nw:networks/nw:network/nt:link/tet:te/"
        + "tet:te-link-attributes" {
    when "../../../nw:network-types/tet:te-topology/"
       + "otntopo:otn-topology" {
      description "Augment only for otn network.";
    }
    description "Augment link configuration";
    uses otn-link-attributes;
  }

  augment "/nw:networks/nw:network/nw:node/nt:termination-point/"
        + "tet:te" {
    when "../../../nw:network-types/tet:te-topology/"
       + "otntopo:otn-topology" {
      description "Augment only for otn network";
    }
    description "OTN TP attributes config in ODU topology.";
    uses otn-tp-attributes;
  }

  /*
   * Augment TE bandwidth
   */

  /* Augment maximum LSP bandwidth of link terminationpoint (LTP) */
  augment "/nw:networks/nw:network/nw:node/nt:termination-point/"
        + "tet:te/"
        + "tet:interface-switching-capability/tet:max-lsp-bandwidth/"
        + "tet:te-bandwidth/tet:technology" {
    when "../../../../../../nw:network-types/tet:te-topology/"
       + "otntopo:otn-topology" {
      description "Augment OTN TE bandwidth";
    }
    description "OTN bandwidth.";
    case otn {
      uses otn-types:otn-path-bandwidth;
    }
  }
  /* Augment bandwidth path constraints of connectivity-matrices */
  augment "/nw:networks/nw:network/nw:node/tet:te/"
        + "tet:te-node-attributes/tet:connectivity-matrices/"
        + "tet:path-constraints/tet:te-bandwidth/tet:technology" {
    when "../../../../../../nw:network-types/tet:te-topology/"
       + "otntopo:otn-topology" {
      description "Augment OTN TE bandwidth";
    }
    description "OTN bandwidth.";
    case otn {
      uses otn-types:otn-link-bandwidth;
    }
  }

  /* Augment bandwidth path constraints of connectivity-matrix */
  augment "/nw:networks/nw:network/nw:node/tet:te/"
        + "tet:te-node-attributes/tet:connectivity-matrices/"
        + "tet:connectivity-matrix/"
        + "tet:path-constraints/tet:te-bandwidth/tet:technology" {
    when "../../../../../../../nw:network-types/tet:te-topology/"
       + "otntopo:otn-topology" {
      description "Augment OTN TE bandwidth";
    }
    description "OTN bandwidth.";
    case otn {
      uses otn-types:otn-link-bandwidth;
    }
  }

  /* Augment bandwidth path constraints of connectivity-matrices information-source */
  augment "/nw:networks/nw:network/nw:node/tet:te/"
        + "tet:information-source-entry/tet:connectivity-matrices/"
        + "tet:path-constraints/tet:te-bandwidth/tet:technology" {
    when "../../../../../../nw:network-types/tet:te-topology/"
       + "otntopo:otn-topology" {
      description "Augment OTN TE bandwidth";
    }
    description "OTN bandwidth.";
    case otn {
      uses otn-types:otn-link-bandwidth;
    }
  }

  /* Augment bandwidth path constraints of connectivity-matrix information-source */
  augment "/nw:networks/nw:network/nw:node/tet:te/"
        + "tet:information-source-entry/tet:connectivity-matrices/"
        + "tet:connectivity-matrix/"
        + "tet:path-constraints/tet:te-bandwidth/tet:technology" {
    when "../../../../../../../nw:network-types/tet:te-topology/"
       + "otntopo:otn-topology" {
      description "Augment OTN TE bandwidth";
    }
    description "OTN bandwidth.";
    case otn {
      uses otn-types:otn-link-bandwidth;
    }
  }

  /* Augment client bandwidth of tunnel termination point (TTP) */
  augment "/nw:networks/nw:network/nw:node/tet:te/"
        + "tet:tunnel-termination-point/"
        + "tet:client-layer-adaptation/tet:switching-capability/"
        + "tet:te-bandwidth/tet:technology" {
    when "../../../../../../nw:network-types/tet:te-topology/"
       + "otntopo:otn-topology" {
      description "Augment OTN TE bandwidth";
    }
    description "OTN bandwidth.";
    case otn {
      uses otn-types:otn-link-bandwidth;
    }
  }

  /* Augment bandwidth path constraints of local-link-connectivities */
  augment "/nw:networks/nw:network/nw:node/tet:te/"
        + "tet:tunnel-termination-point/"
        + "tet:local-link-connectivities/tet:path-constraints/"
        + "tet:te-bandwidth/tet:technology" {
    when "../../../../../../nw:network-types/tet:te-topology/"
       + "otntopo:otn-topology" {
      description "Augment OTN TE bandwidth";
    }
    description "OTN bandwidth.";
    case otn {
      uses otn-types:otn-link-bandwidth;
    }
  }

  /* Augment bandwidth path constraints of local-link-connectivity (LLC) */
  augment "/nw:networks/nw:network/nw:node/tet:te/"
        + "tet:tunnel-termination-point/"
        + "tet:local-link-connectivities/"
        + "tet:local-link-connectivity/tet:path-constraints/"
        + "tet:te-bandwidth/tet:technology" {
    when "../../../../../../../nw:network-types/tet:te-topology/"
       + "otntopo:otn-topology" {
      description "Augment OTN TE bandwidth";
    }
    description "OTN bandwidth.";
    case otn {
      uses otn-types:otn-link-bandwidth;
    }
  }

  /* Augment maximum LSP bandwidth of TE link */
  augment "/nw:networks/nw:network/nt:link/tet:te/"
        + "tet:te-link-attributes/"
        + "tet:interface-switching-capability/tet:max-lsp-bandwidth/"
        + "tet:te-bandwidth/tet:technology" {
    when "../../../../../../nw:network-types/tet:te-topology/"
       + "otntopo:otn-topology" {
      description "OTN TE bandwidth.";
    }
    description "OTN bandwidth.";
    case otn {
      uses otn-types:otn-path-bandwidth;
    }
  }

  /* Augment maximum bandwidth of TE link */
  augment "/nw:networks/nw:network/nt:link/tet:te/"
        + "tet:te-link-attributes/"
        + "tet:max-link-bandwidth/"
        + "tet:te-bandwidth/tet:technology" {
    when "../../../../../nw:network-types/tet:te-topology/"
       + "otntopo:otn-topology" {
      description "OTN TE bandwidth.";
    }
    description "OTN bandwidth.";
    case otn {
      uses otn-types:otn-link-bandwidth;
    }
  }

  /* Augment maximum reservable bandwidth of TE link */
  augment "/nw:networks/nw:network/nt:link/tet:te/"
        + "tet:te-link-attributes/"
        + "tet:max-resv-link-bandwidth/"
        + "tet:te-bandwidth/tet:technology" {
    when "../../../../../nw:network-types/tet:te-topology/"
       + "otntopo:otn-topology" {
      description "OTN TE bandwidth.";
    }
    description "OTN bandwidth.";
    case otn {
      uses otn-types:otn-link-bandwidth;
    }
  }

  /* Augment unreserved bandwidth of TE Link */
  augment "/nw:networks/nw:network/nt:link/tet:te/"
        + "tet:te-link-attributes/"
        + "tet:unreserved-bandwidth/"
        + "tet:te-bandwidth/tet:technology" {
    when "../../../../../nw:network-types/tet:te-topology/"
       + "otntopo:otn-topology" {
      description "OTN TE bandwidth.";
    }
    description "OTN bandwidth.";
    case otn {
      uses otn-types:otn-link-bandwidth;
    }
  }
  /* Augment maximum LSP bandwidth of TE link information-source */
  augment "/nw:networks/nw:network/nt:link/tet:te/"
        + "tet:information-source-entry/"
        + "tet:interface-switching-capability/"
        + "tet:max-lsp-bandwidth/"
        + "tet:te-bandwidth/tet:technology" {
    when "../../../../../../nw:network-types/tet:te-topology/"
       + "otntopo:otn-topology" {
      description "OTN TE bandwidth.";
    }
    description "OTN bandwidth.";
    case otn {
      uses otn-types:otn-path-bandwidth;
    }
  }

  /* Augment maximum bandwidth of TE link information-source */
  augment "/nw:networks/nw:network/nt:link/tet:te/"
        + "tet:information-source-entry/"
        + "tet:max-link-bandwidth/"
        + "tet:te-bandwidth/tet:technology" {
    when "../../../../../nw:network-types/tet:te-topology/"
       + "otntopo:otn-topology" {
      description "OTN TE bandwidth.";
    }
    description "OTN bandwidth.";
    case otn {
      uses otn-types:otn-link-bandwidth;
    }
  }

  /* Augment maximum reservable bandwidth of TE link information-source */
  augment "/nw:networks/nw:network/nt:link/tet:te/"
        + "tet:information-source-entry/"
        + "tet:max-resv-link-bandwidth/"
        + "tet:te-bandwidth/tet:technology" {
    when "../../../../../nw:network-types/tet:te-topology/"
       + "otntopo:otn-topology" {
      description "OTN TE bandwidth.";
    }
    description "OTN bandwidth.";
    case otn {
      uses otn-types:otn-link-bandwidth;
    }
  }

  /* Augment unreserved bandwidth of TE link information-source */
  augment "/nw:networks/nw:network/nt:link/tet:te/"
        + "tet:information-source-entry/"
        + "tet:unreserved-bandwidth/"
        + "tet:te-bandwidth/tet:technology" {
    when "../../../../../nw:network-types/tet:te-topology/"
       + "otntopo:otn-topology" {
      description "OTN TE bandwidth.";
    }
    description "OTN bandwidth.";
    case otn {
      uses otn-types:otn-link-bandwidth;
    }
  }

  /* Augment maximum LSP bandwidth of TE link template */
  augment "/nw:networks/tet:te/tet:templates/"
        + "tet:link-template/tet:te-link-attributes/"
        + "tet:interface-switching-capability/"
        + "tet:max-lsp-bandwidth/"
        + "tet:te-bandwidth/tet:technology" {
/*
    when "../../../../../../nw:network-types/tet:te-topology/"
       + "otntopo:otn-topology" {
      description "OTN TE bandwidth.";
    }
*/
    description "OTN bandwidth.";
    case otn {
      uses otn-types:otn-path-bandwidth;
    }
  }

  /* Augment maximum bandwidth of TE link template */
  augment "/nw:networks/tet:te/tet:templates/"
        + "tet:link-template/tet:te-link-attributes/"
        + "tet:max-link-bandwidth/"
        + "tet:te-bandwidth/tet:technology" {
/*
    when "../../../../../nw:network-types/tet:te-topology/"
        + "otntopo:otn-topology" {
      description "OTN TE bandwidth.";
    }
*/
    description "OTN bandwidth.";
    case otn {
      uses otn-types:otn-link-bandwidth;
    }
  }

  /* Augment maximum reservable bandwidth of TE link template */
  augment "/nw:networks/tet:te/tet:templates/"
        + "tet:link-template/tet:te-link-attributes/"
        + "tet:max-resv-link-bandwidth/"
        + "tet:te-bandwidth/tet:technology" {
/*
    when "../../../../../nw:network-types/tet:te-topology/"
        + "otntopo:otn-topology" {
      description "OTN TE bandwidth.";
    }
*/
    description "OTN bandwidth.";
    case otn {
      uses otn-types:otn-link-bandwidth;
    }
  }

  /* Augment unreserved bandwidth of TE link template */
  augment "/nw:networks/tet:te/tet:templates/"
        + "tet:link-template/tet:te-link-attributes/"
        + "tet:unreserved-bandwidth/"
        + "tet:te-bandwidth/tet:technology" {
/*
    when "../../../../../../nw:network-types/tet:te-topology/"
        + "otntopo:otn-topology" {
      description "OTN TE bandwidth.";
    }
*/
    description "OTN bandwidth.";
    case otn {
      uses otn-types:otn-link-bandwidth;
    }
  }

  /*
   * Augment TE label.
   */

  /* Augment label restrictions of connectivity-matrices */
  augment "/nw:networks/nw:network/nw:node/tet:te/"
        + "tet:te-node-attributes/tet:connectivity-matrices/"
        + "tet:label-restrictions/tet:label-restriction" {
    when "../../../../../../nw:network-types/tet:te-topology/"
       + "otntopo:otn-topology" {
      description "Augment OTN TE label";
    }
    description "OTN label restriction.";
    uses otn-types:otn-label-restriction;
  }

  /* Augment label restrictions start of connectivity-matrices */
  augment "/nw:networks/nw:network/nw:node/tet:te/"
        + "tet:te-node-attributes/tet:connectivity-matrices/"
        + "tet:label-restrictions/tet:label-restriction/tet:label-start/"
        + "tet:te-label/tet:technology" {
    when "../../../../../../../../nw:network-types/tet:te-topology/"
       + "otntopo:otn-topology" {
      description "Augment OTN TE label";
    }
    description "OTN label.";
    case otn {
      uses otn-types:otn-link-label;
    }
  }

  /* Augment label restrictions end of connectivity-matrices */
  augment "/nw:networks/nw:network/nw:node/tet:te/"
        + "tet:te-node-attributes/tet:connectivity-matrices/"
        + "tet:label-restrictions/tet:label-restriction/tet:label-end/"
        + "tet:te-label/tet:technology" {
    when "../../../../../../../../nw:network-types/tet:te-topology/"
       + "otntopo:otn-topology" {
      description "Augment OTN TE label";
    }
    description "OTN label.";
    case otn {
      uses otn-types:otn-link-label;
    }
  }

  /* Augment label restrictions step of connectivity-matrices */
  augment "/nw:networks/nw:network/nw:node/tet:te/"
        + "tet:te-node-attributes/tet:connectivity-matrices/"
        + "tet:label-restrictions/tet:label-restriction/tet:label-step/"
        + "tet:technology" {
    when "../../../../../../../nw:network-types/tet:te-topology/"
       + "otntopo:otn-topology" {
      description "Augment OTN TE label";
    }
    description "OTN label.";
    case otn {
      uses otn-types:otn-label-step;
    }
  }

  /* Augment label hop of underlay primary path of connectivity-matrices */
  augment "/nw:networks/nw:network/nw:node/tet:te/"
        + "tet:te-node-attributes/tet:connectivity-matrices/"
        + "tet:underlay/tet:primary-path/tet:path-element/"
        + "tet:type/tet:label/tet:label-hop/"
        + "tet:te-label/tet:technology" {
    when "../../../../../../../../../"
       + "nw:network-types/tet:te-topology/"
       + "otntopo:otn-topology" {
      description "Augment OTN TE label";
    }
    description "OTN label.";
    case otn {
      uses otn-types:otn-path-label;
    }
  }
  /* Augment label hop of underlay backup path of connectivity-matrices */
  augment "/nw:networks/nw:network/nw:node/tet:te/"
        + "tet:te-node-attributes/tet:connectivity-matrices/"
        + "tet:underlay/tet:backup-path/tet:path-element/"
        + "tet:type/tet:label/tet:label-hop/"
        + "tet:te-label/tet:technology" {
    when "../../../../../../../../../"
       + "nw:network-types/tet:te-topology/"
       + "otntopo:otn-topology" {
      description "Augment OTN TE label";
    }
    description "OTN label.";
    case otn {
      uses otn-types:otn-path-label;
    }
  }

  /* Augment label hop of route-exclude of connectivity-matrices */
  augment "/nw:networks/nw:network/nw:node/tet:te/"
        + "tet:te-node-attributes/tet:connectivity-matrices/"
        + "tet:optimizations/tet:algorithm/tet:metric/"
        + "tet:optimization-metric/"
        + "tet:explicit-route-exclude-objects/"
        + "tet:route-object-exclude-object/"
        + "tet:type/tet:label/tet:label-hop/"
        + "tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of route-include of connectivity-matrices (added) */
  augment "/nw:networks/nw:network/nw:node/tet:te/"
        + "tet:te-node-attributes/tet:connectivity-matrices/"
        + "tet:optimizations/tet:algorithm/tet:metric/"
        + "tet:optimization-metric/"
        + "tet:explicit-route-include-objects/"
        + "tet:route-object-include-object/"
        + "tet:type/tet:label/tet:label-hop/"
        + "tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of path-route of connectivity-matrices */
  augment "/nw:networks/nw:network/nw:node/tet:te/"
        + "tet:te-node-attributes/tet:connectivity-matrices/"
        + "tet:path-properties/tet:path-route-objects/"
        + "tet:path-route-object/tet:type/tet:label/tet:label-hop/"
        + "tet:te-label/tet:technology"{
    when "../../../../../../../../../"
       + "nw:network-types/tet:te-topology/"
       + "otntopo:otn-topology" {
      description "Augment OTN TE label";
    }
    description "OTN label.";
    case otn {
      uses otn-types:otn-path-label;
    }
  }

  /* Augment ingress label restrictions of connectivity-matrix */
  augment "/nw:networks/nw:network/nw:node/tet:te/"
        + "tet:te-node-attributes/tet:connectivity-matrices/"
        + "tet:connectivity-matrix/tet:from/"
        + "tet:label-restrictions/tet:label-restriction" {
    when "../../../../../../../../nw:network-types/tet:te-topology/"
       + "otntopo:otn-topology" {
      description "Augment OTN TE label";
    }
    description "OTN label.";
    uses otn-types:otn-label-restriction;
  }

  /* Augment ingress label restrictions start of connectivity-matrix */
  augment "/nw:networks/nw:network/nw:node/tet:te/"
        + "tet:te-node-attributes/tet:connectivity-matrices/"
        + "tet:connectivity-matrix/tet:from/"
        + "tet:label-restrictions/tet:label-restriction/tet:label-start/"
        + "tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment ingress label restrictions end of connectivity-matrix */
  augment "/nw:networks/nw:network/nw:node/tet:te/"
        + "tet:te-node-attributes/tet:connectivity-matrices/"
        + "tet:connectivity-matrix/tet:from/"
        + "tet:label-restrictions/tet:label-restriction/tet:label-end/"
        + "tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment ingress label restrictions step of connectivity-matrix */
  augment "/nw:networks/nw:network/nw:node/tet:te/"
        + "tet:te-node-attributes/tet:connectivity-matrices/"
        + "tet:connectivity-matrix/tet:from/"
        + "tet:label-restrictions/tet:label-restriction/tet:label-step/"
        + "tet:technology" {
    when "../../../../../../../../../"
       + "nw:network-types/tet:te-topology/"
       + "otntopo:otn-topology" {
      description "Augment OTN TE label";
    }
    description "OTN label.";
    case otn {
      uses otn-types:otn-label-step;
    }
  }

  /* Augment egress label restrictions of connectivity-matrix */
  augment "/nw:networks/nw:network/nw:node/tet:te/"
        + "tet:te-node-attributes/tet:connectivity-matrices/"
        + "tet:connectivity-matrix/tet:to/"
        + "tet:label-restrictions/tet:label-restriction" {
    when "../../../../../../../../nw:network-types/tet:te-topology/"
       + "otntopo:otn-topology" {
      description "Augment OTN TE label";
    }
    description "OTN label.";
    uses otn-types:otn-label-restriction;
  }

  /* Augment egress label restrictions start of connectivity-matrix */
  augment "/nw:networks/nw:network/nw:node/tet:te/"
        + "tet:te-node-attributes/tet:connectivity-matrices/"
        + "tet:connectivity-matrix/tet:to/"
        + "tet:label-restrictions/tet:label-restriction/tet:label-start/"
        + "tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment egress label restrictions end of connectivity-matrix */
  augment "/nw:networks/nw:network/nw:node/tet:te/"
        + "tet:te-node-attributes/tet:connectivity-matrices/"
        + "tet:connectivity-matrix/tet:to/"
        + "tet:label-restrictions/tet:label-restriction/tet:label-end/"
        + "tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment egress label restrictions step of connectivity-matrix */
  augment "/nw:networks/nw:network/nw:node/tet:te/"
        + "tet:te-node-attributes/tet:connectivity-matrices/"
        + "tet:connectivity-matrix/tet:to/"
        + "tet:label-restrictions/tet:label-restriction/tet:label-step/"
        + "tet:technology" {
    when "../../../../../../../../../"
       + "nw:network-types/tet:te-topology/"
       + "otntopo:otn-topology" {
      description "Augment OTN TE label";
    }
    description "OTN label.";
    case otn {
      uses otn-types:otn-label-step;
    }
  }

  /* Augment label hop of underlay primary path of connectivity-matrix */
  augment "/nw:networks/nw:network/nw:node/tet:te/"
        + "tet:te-node-attributes/tet:connectivity-matrices/"
        + "tet:connectivity-matrix/"
        + "tet:underlay/tet:primary-path/tet:path-element/"
        + "tet:type/tet:label/tet:label-hop/"
        + "tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of underlay backup path of connectivity-matrix */
  augment "/nw:networks/nw:network/nw:node/tet:te/"
        + "tet:te-node-attributes/tet:connectivity-matrices/"
        + "tet:connectivity-matrix/"
        + "tet:underlay/tet:backup-path/tet:path-element/"
        + "tet:type/tet:label/tet:label-hop/"
        + "tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of route-exclude of connectivity-matrix */
  augment "/nw:networks/nw:network/nw:node/tet:te/"
        + "tet:te-node-attributes/tet:connectivity-matrices/"
        + "tet:connectivity-matrix/tet:optimizations/"
        + "tet:algorithm/tet:metric/tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "otntopo:otn-topology" {
      description "Augment OTN TE label";
    }
    description "OTN label.";
    case otn {
      uses otn-types:otn-path-label;
    }
  }

  /* Augment label hop of route-include of connectivity-matrix */
  augment "/nw:networks/nw:network/nw:node/tet:te/"
        + "tet:te-node-attributes/tet:connectivity-matrices/"
        + "tet:connectivity-matrix/tet:optimizations/"
        + "tet:algorithm/tet:metric/tet:optimization-metric/"
        + "tet:explicit-route-include-objects/"
        + "tet:route-object-include-object/tet:type/"
        + "tet:label/tet:label-hop/tet:te-label/tet:technology" {
    when "../../../../../../../../../../../"
       + "nw:network-types/tet:te-topology/"
       + "otntopo:otn-topology" {
      description "Augment OTN TE label";
    }
    description "OTN label.";
    case otn {
      uses otn-types:otn-path-label;
    }
  }

  /* Augment label hop of path-route of connectivity-matrix */
  augment "/nw:networks/nw:network/nw:node/tet:te/"
        + "tet:te-node-attributes/tet:connectivity-matrices/"
        + "tet:connectivity-matrix/"
        + "tet:path-properties/tet:path-route-objects/"
        + "tet:path-route-object/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label restrictions of connectivity-matrices information-source */
  augment "/nw:networks/nw:network/nw:node/tet:te/"
        + "tet:information-source-entry/"
        + "tet:connectivity-matrices/tet:label-restrictions/tet:label-restriction" {
    when "../../../../../../nw:network-types/tet:te-topology/"
       + "otntopo:otn-topology" {
      description "Augment OTN TE label";
    }
    description "OTN label.";
    uses otn-types:otn-label-restriction;
  }
  /* Augment label restrictions start of connectivity-matrices information-source */
  augment "/nw:networks/nw:network/nw:node/tet:te/"
        + "tet:information-source-entry/"
        + "tet:connectivity-matrices/tet:label-restrictions/tet:label-restriction/"
        + "tet:label-start/tet:te-label/tet:technology" {
    when "../../../../../../../../"
       + "nw:network-types/tet:te-topology/"
       + "otntopo:otn-topology" {
      description "Augment OTN TE label";
    }
    description "OTN label.";
    case otn {
      uses otn-types:otn-link-label;
    }
  }

  /* Augment label restrictions end of connectivity-matrices information-source */
  augment "/nw:networks/nw:network/nw:node/tet:te/"
        + "tet:information-source-entry/"
        + "tet:connectivity-matrices/tet:label-restrictions/tet:label-restriction/"
        + "tet:label-end/tet:te-label/tet:technology" {
    when "../../../../../../../../"
       + "nw:network-types/tet:te-topology/"
       + "otntopo:otn-topology" {
      description "Augment OTN TE label";
    }
    description "OTN label.";
    case otn {
      uses otn-types:otn-link-label;
    }
  }

  /* Augment label restrictions step of connectivity-matrices information-source */
  augment "/nw:networks/nw:network/nw:node/tet:te/"
        + "tet:information-source-entry/"
        + "tet:connectivity-matrices/tet:label-restrictions/tet:label-restriction/"
        + "tet:label-step/tet:technology" {
    when "../../../../../../../"
       + "nw:network-types/tet:te-topology/"
       + "otntopo:otn-topology" {
      description "Augment OTN TE label";
    }
    description "OTN label.";
    case otn {
      uses otn-types:otn-label-step;
    }
  }

  /* Augment label hop of underlay primary path of connectivity-matrices information-source */
  augment "/nw:networks/nw:network/nw:node/tet:te/"
        + "tet:information-source-entry/tet:connectivity-matrices/"
        + "tet:underlay/tet:primary-path/tet:path-element/tet:type/"
        + "tet:label/tet:label-hop/tet:te-label/tet:technology" {
    when "../../../../../../../../../"
       + "nw:network-types/tet:te-topology/"
       + "otntopo:otn-topology" {
      description "Augment OTN TE label";
    }
    description "OTN label.";
    case otn {
      uses otn-types:otn-path-label;
    }
  }

  /* Augment label hop of underlay backup path of connectivity-matrices information-source */
  augment "/nw:networks/nw:network/nw:node/tet:te/"
        + "tet:information-source-entry/tet:connectivity-matrices/"
        + "tet:underlay/tet:backup-path/tet:path-element/tet:type/"
        + "tet:label/tet:label-hop/tet:te-label/tet:technology" {
    when "../../../../../../../../../"
       + "nw:network-types/tet:te-topology/"
       + "otntopo:otn-topology" {
      description "Augment OTN TE label";
    }
    description "OTN label.";
    case otn {
      uses otn-types:otn-path-label;
    }
  }

  /* Augment label hop of route-exclude of connectivity-matrices information-source */
  augment "/nw:networks/nw:network/nw:node/tet:te/"
        + "tet:information-source-entry/tet:connectivity-matrices/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of route-include of connectivity-matrices information-source */
  augment "/nw:networks/nw:network/nw:node/tet:te/"
        + "tet:information-source-entry/tet:connectivity-matrices/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of path-route of connectivity-matrices information-source */
  augment "/nw:networks/nw:network/nw:node/tet:te/"
        + "tet:information-source-entry/tet:connectivity-matrices/"
        + "tet:path-properties/tet:path-route-objects/"
        + "tet:path-route-object/tet:type/"
        + "tet:label/tet:label-hop/tet:te-label/tet:technology" {
    when "../../../../../../../../../"
       + "nw:network-types/tet:te-topology/"
       + "otntopo:otn-topology" {
      description "Augment OTN TE label";
    }
    description "OTN label.";
    case otn {
      uses otn-types:otn-path-label;
    }
  }

  /* Augment ingress label restrictions of connectivity-matrix information-source */
  augment "/nw:networks/nw:network/nw:node/tet:te/"
        + "tet:information-source-entry/tet:connectivity-matrices/"
        + "tet:connectivity-matrix/"
        + "tet:from/tet:label-restrictions/tet:label-restriction" {
    when "../../../../../../../../nw:network-types/tet:te-topology/"
       + "otntopo:otn-topology" {
      description "Augment OTN TE label";
    }
    description "OTN label.";
    uses otn-types:otn-label-restriction;
  }

  /* Augment ingress label restrictions start of connectivity-matrix information-source */
  augment "/nw:networks/nw:network/nw:node/tet:te/"
        + "tet:information-source-entry/tet:connectivity-matrices/"
        + "tet:connectivity-matrix/"
        + "tet:from/tet:label-restrictions/tet:label-restriction/"
        + "tet:label-start/tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment ingress label restrictions end of connectivity-matrix information-source */
  augment "/nw:networks/nw:network/nw:node/tet:te/"
        + "tet:information-source-entry/tet:connectivity-matrices/"
        + "tet:connectivity-matrix/"
        + "tet:from/tet:label-restrictions/tet:label-restriction/"
        + "tet:label-end/tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment ingress label restrictions step of connectivity-matrix information-source */
  augment "/nw:networks/nw:network/nw:node/tet:te/"
        + "tet:information-source-entry/tet:connectivity-matrices/"
        + "tet:connectivity-matrix/"
        + "tet:from/tet:label-restrictions/tet:label-restriction/"
        + "tet:label-step/tet:technology" {
    when "../../../../../../../../../"
       + "nw:network-types/tet:te-topology/"
       + "otntopo:otn-topology" {
      description "Augment OTN TE label";
    }
    description "OTN label.";
    case otn {
      uses otn-types:otn-label-step;
    }
  }

  /* Augment egress label restrictions of connectivity-matrix information-source */
  augment "/nw:networks/nw:network/nw:node/tet:te/"
        + "tet:information-source-entry/tet:connectivity-matrices/"
        + "tet:connectivity-matrix/"
        + "tet:to/tet:label-restrictions/tet:label-restriction" {
    when "../../../../../../../../nw:network-types/tet:te-topology/"
       + "otntopo:otn-topology" {
      description "Augment OTN TE label";
    }
    description "OTN label.";
    uses otn-types:otn-label-restriction;
  }

  /* Augment egress label restrictions start of connectivity-matrix information-source */
  augment "/nw:networks/nw:network/nw:node/tet:te/"
        + "tet:information-source-entry/tet:connectivity-matrices/"
        + "tet:connectivity-matrix/"
        + "tet:to/tet:label-restrictions/tet:label-restriction/"
        + "tet:label-start/tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment egress label restrictions end of connectivity-matrix information-source */
  augment "/nw:networks/nw:network/nw:node/tet:te/"
        + "tet:information-source-entry/tet:connectivity-matrices/"
        + "tet:connectivity-matrix/"
        + "tet:to/tet:label-restrictions/tet:label-restriction/"
        + "tet:label-end/tet:te-label/tet:technology" {
    when "../../../../../../../../../../"
       + "nw:network-types/tet:te-topology/"
       + "otntopo:otn-topology" {
      description "Augment OTN TE label";
    }
    description "OTN label.";
    case otn {
      uses otn-types:otn-link-label;
    }
  }

  /* Augment egress label restrictions step of connectivity-matrix information-source */
  augment "/nw:networks/nw:network/nw:node/tet:te/"
        + "tet:information-source-entry/tet:connectivity-matrices/"
        + "tet:connectivity-matrix/"
        + "tet:to/tet:label-restrictions/tet:label-restriction/"
        + "tet:label-step/tet:technology" {
    when "../../../../../../../../../"
       + "nw:network-types/tet:te-topology/"
       + "otntopo:otn-topology" {
      description "Augment OTN TE label";
    }
    description "OTN label.";
    case otn {
      uses otn-types:otn-label-step;
    }
  }

  /* Augment label hop of underlay primary path of connectivity-matrix information-source */
  augment "/nw:networks/nw:network/nw:node/tet:te/"
        + "tet:information-source-entry/tet:connectivity-matrices/"
        + "tet:connectivity-matrix/"
        + "tet:underlay/tet:primary-path/tet:path-element/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of underlay backup path of connectivity-matrix information-source */
  augment "/nw:networks/nw:network/nw:node/tet:te/"
        + "tet:information-source-entry/tet:connectivity-matrices/"
        + "tet:connectivity-matrix/"
        + "tet:underlay/tet:backup-path/tet:path-element/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of route-exclude of connectivity-matrix information-source */
  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "otntopo:otn-topology" {
      description "Augment OTN TE label";
    }
    description "OTN label.";
    case otn {
      uses otn-types:otn-path-label;
    }
  }

  /* Augment label hop of route-include of connectivity-matrix information-source */
  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../../"
       + "nw:network-types/tet:te-topology/"
       + "otntopo:otn-topology" {
      description "Augment OTN TE label";
    }
    description "OTN label.";
    case otn {
      uses otn-types:otn-path-label;
    }
  }
  /* Augment label hop of path-route of connectivity-matrix information-source */
  augment "/nw:networks/nw:network/nw:node/tet:te/"
        + "tet:information-source-entry/tet:connectivity-matrices/"
        + "tet:connectivity-matrix/"
        + "tet:path-properties/tet:path-route-objects/"
        + "tet:path-route-object/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }
  /* Augment label restrictions of local-link-connectivities */
  augment "/nw:networks/nw:network/nw:node/tet:te/"
        + "tet:tunnel-termination-point/"
        + "tet:local-link-connectivities/"
        + "tet:label-restrictions/tet:label-restriction" {
    when "../../../../../../nw:network-types/tet:te-topology/"
       + "otntopo:otn-topology" {
      description "Augment OTN TE label";
    }
    description "OTN label.";
    uses otn-types:otn-label-restriction;
  }

  /* Augment label restrictions start of local-link-connectivities */
  augment "/nw:networks/nw:network/nw:node/tet:te/"
        + "tet:tunnel-termination-point/"
        + "tet:local-link-connectivities/"
        + "tet:label-restrictions/tet:label-restriction/tet:label-start/"
        + "tet:te-label/tet:technology" {
    when "../../../../../../../../nw:network-types/tet:te-topology/"
       + "otntopo:otn-topology" {
      description "Augment OTN TE label";
    }
    description "OTN label.";
    case otn {
      uses otn-types:otn-link-label;
    }
  }

  /* Augment label restrictions end of local-link-connectivities */
  augment "/nw:networks/nw:network/nw:node/tet:te/"
        + "tet:tunnel-termination-point/"
        + "tet:local-link-connectivities/"
        + "tet:label-restrictions/tet:label-restriction/tet:label-end/"
        + "tet:te-label/tet:technology"{
    when "../../../../../../../../nw:network-types/tet:te-topology/"
       + "otntopo:otn-topology" {
      description "Augment OTN TE label";
    }
    description "OTN label.";
    case otn {
      uses otn-types:otn-link-label;
    }
  }

  /* Augment label restrictions step of local-link-connectivities */
  augment "/nw:networks/nw:network/nw:node/tet:te/"
        + "tet:tunnel-termination-point/"
        + "tet:local-link-connectivities/"
        + "tet:label-restrictions/tet:label-restriction/tet:label-step/"
        + "tet:technology"{
    when "../../../../../../../nw:network-types/tet:te-topology/"
       + "otntopo:otn-topology" {
      description "Augment OTN TE label";
    }
    description "OTN label.";
    case otn {
      uses otn-types:otn-label-step;
    }
  }

  /* Augment label hop of underlay primary path of local-link-connectivities */
  augment "/nw:networks/nw:network/nw:node/tet:te/"
        + "tet:tunnel-termination-point/"
        + "tet:local-link-connectivities/"
        + "tet:underlay/tet:primary-path/tet:path-element/tet:type/"
        + "tet:label/tet:label-hop/tet:te-label/tet:technology" {
    when "../../../../../../../../../"
       + "nw:network-types/tet:te-topology/"
       + "otntopo:otn-topology" {
      description "Augment OTN TE label";
    }
    description "OTN label.";
    case otn {
      uses otn-types:otn-path-label;
    }
  }

  /* Augment label hop of underlay backup path of local-link-connectivities */
  augment "/nw:networks/nw:network/nw:node/tet:te/"
        + "tet:tunnel-termination-point/"
        + "tet:local-link-connectivities/"
        + "tet:underlay/tet:backup-path/tet:path-element/tet:type/"
        + "tet:label/tet:label-hop/tet:te-label/tet:technology" {
    when "../../../../../../../../../"
       + "nw:network-types/tet:te-topology/"
       + "otntopo:otn-topology" {
      description "Augment OTN TE label";
    }
    description "OTN label.";
    case otn {
      uses otn-types:otn-path-label;
    }
  }

  /* Augment label hop of route-exclude of local-link-connectivities */
  augment "/nw:networks/nw:network/nw:node/tet:te/"
        + "tet:tunnel-termination-point/"
        + "tet:local-link-connectivities/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of route-include of local-link-connectivities */
  augment "/nw:networks/nw:network/nw:node/tet:te/"
        + "tet:tunnel-termination-point/"
        + "tet:local-link-connectivities/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of path-route of local-link-connectivities */
  augment "/nw:networks/nw:network/nw:node/tet:te/"
        + "tet:tunnel-termination-point/"
        + "tet:local-link-connectivities/"
        + "tet:path-properties/tet:path-route-objects/"
        + "tet:path-route-object/tet:type/"
        + "tet:label/tet:label-hop/tet:te-label/tet:technology" {
    when "../../../../../../../../../"
       + "nw:network-types/tet:te-topology/"
       + "otntopo:otn-topology" {
      description "Augment OTN TE label";
    }
    description "OTN label.";
    case otn {
      uses otn-types:otn-path-label;
    }
  }

  /* Augment label restrictions of local-link-connectivity (LLC) */
  augment "/nw:networks/nw:network/nw:node/tet:te/"
        + "tet:tunnel-termination-point/"
        + "tet:local-link-connectivities/"
        + "tet:local-link-connectivity/"
        + "tet:label-restrictions/tet:label-restriction" {
    when "../../../../../../../nw:network-types/tet:te-topology/"
       + "otntopo:otn-topology" {
      description "Augment OTN TE label";
    }
    description "OTN label.";
    uses otn-types:otn-label-restriction;
  }

  /* Augment label restrictions start of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-start/tet:te-label/tet:technology" {
    when "../../../../../../../../../"
       + "nw:network-types/tet:te-topology/"
       + "otntopo:otn-topology" {
      description "Augment OTN TE label";
    }
    description "OTN label.";
    case otn {
      uses otn-types:otn-link-label;
    }
  }

  /* Augment label restrictions end of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-end/tet:te-label/tet:technology" {
    when "../../../../../../../../../"
       + "nw:network-types/tet:te-topology/"
       + "otntopo:otn-topology" {
      description "Augment OTN TE label";
    }
    description "OTN label.";
    case otn {
      uses otn-types:otn-link-label;
    }
  }

  /* Augment label restrictions step of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-step/tet:technology" {
    when "../../../../../../../../"
       + "nw:network-types/tet:te-topology/"
       + "otntopo:otn-topology" {
      description "Augment OTN TE label";
    }
    description "OTN label.";
    case otn {
      uses otn-types:otn-label-step;
    }
  }

  /* Augment label hop of underlay primary path of local-link-connectivity (LLC) */
  augment "/nw:networks/nw:network/nw:node/tet:te/"
        + "tet:tunnel-termination-point/"
        + "tet:local-link-connectivities/"
        + "tet:local-link-connectivity/"
        + "tet:underlay/tet:primary-path/tet:path-element/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of underlay backup path of local-link-connectivity (LLC) */
  augment "/nw:networks/nw:network/nw:node/tet:te/"
        + "tet:tunnel-termination-point/"
        + "tet:local-link-connectivities/"
        + "tet:local-link-connectivity/"
        + "tet:underlay/tet:backup-path/tet:path-element/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of route-exclude of local-link-connectivity (LLC) */
  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "otntopo:otn-topology" {
      description "Augment OTN TE label";
    }
    description "OTN label.";
    case otn {
      uses otn-types:otn-path-label;
    }
  }

  /* Augment label hop of route-include of local-link-connectivity (LLC) */
  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../../"
       + "nw:network-types/tet:te-topology/"
       + "otntopo:otn-topology" {
      description "Augment OTN TE label";
    }
    description "OTN label.";
    case otn {
      uses otn-types:otn-path-label;
    }
  }

  /* Augment label hop of path-route of local-link-connectivity (LLC) */
  augment "/nw:networks/nw:network/nw:node/tet:te/"
        + "tet:tunnel-termination-point/"
        + "tet:local-link-connectivities/"
        + "tet:local-link-connectivity/"
        + "tet:path-properties/tet:path-route-objects/"
        + "tet:path-route-object/tet:type/"
        + "tet:label/tet:label-hop/tet:te-label/tet:technology" {
    when "../../../../../../../../../../"
       + "nw:network-types/tet:te-topology/"
       + "otntopo:otn-topology" {
      description "Augment OTN TE label";
    }
    description "OTN label.";
    case otn {
      uses otn-types:otn-path-label;
    }
  }

  /* Augment label hop of underlay primary path of TE link */
  augment "/nw:networks/nw:network/nt:link/tet:te/"
        + "tet:te-link-attributes/"
        + "tet:underlay/tet:primary-path/tet:path-element/tet:type/"
        + "tet:label/tet:label-hop/tet:te-label/tet:technology" {
    when "../../../../../../../../"
       + "nw:network-types/tet:te-topology/"
       + "otntopo:otn-topology" {
      description "Augment OTN TE label";
    }
    description "OTN label.";
    case otn {
      uses otn-types:otn-path-label;
    }
  }

  /* Augment label hop of underlay backup path of TE link */
  augment "/nw:networks/nw:network/nt:link/tet:te/"
        + "tet:te-link-attributes/"
        + "tet:underlay/tet:backup-path/tet:path-element/tet:type/"
        + "tet:label/tet:label-hop/tet:te-label/tet:technology" {
    when "../../../../../../../../"
       + "nw:network-types/tet:te-topology/"
       + "otntopo:otn-topology" {
      description "Augment OTN TE label";
    }
    description "OTN label.";
    case otn {
      uses otn-types:otn-path-label;
    }
  }

  /* Augment label restrictions of TE link */
  augment "/nw:networks/nw:network/nt:link/tet:te/"
        + "tet:te-link-attributes/"
        + "tet:label-restrictions/tet:label-restriction" {
    when "../../../../../nw:network-types/tet:te-topology/"
       + "otntopo:otn-topology" {
      description "Augment OTN TE label";
    }
    description "OTN label.";
    uses otn-types:otn-label-restriction;
  }

  /* Augment label restrictions start of TE link */
  augment "/nw:networks/nw:network/nt:link/tet:te/"
        + "tet:te-link-attributes/"
        + "tet:label-restrictions/tet:label-restriction/"
        + "tet:label-start/tet:te-label/tet:technology" {
    when "../../../../../../../nw:network-types/tet:te-topology/"
       + "otntopo:otn-topology" {
      description "Augment OTN TE label";
    }
    description "OTN label.";
    case otn {
      uses otn-types:otn-link-label;
    }
  }

  /* Augment label restrictions end of TE link */
  augment "/nw:networks/nw:network/nt:link/tet:te/"
        + "tet:te-link-attributes/"
        + "tet:label-restrictions/tet:label-restriction/"
        + "tet:label-end/tet:te-label/tet:technology" {
    when "../../../../../../../nw:network-types/tet:te-topology/"
       + "otntopo:otn-topology" {
      description "Augment OTN TE label";
    }
    description "OTN label.";
    case otn {
      uses otn-types:otn-link-label;
    }
  }

  /* Augment label restrictions step of TE link */
  augment "/nw:networks/nw:network/nt:link/tet:te/"
        + "tet:te-link-attributes/"
        + "tet:label-restrictions/tet:label-restriction/"
        + "tet:label-step/tet:technology" {
    when "../../../../../../nw:network-types/tet:te-topology/"
       + "otntopo:otn-topology" {
      description "Augment OTN TE label";
    }
    description "OTN label.";
    case otn {
      uses otn-types:otn-label-step;
    }
  }

  /* Augment label restrictions of TE link information-source */
  augment "/nw:networks/nw:network/nt:link/tet:te/"
        + "tet:information-source-entry/"
        + "tet:label-restrictions/tet:label-restriction" {
    when "../../../../../nw:network-types/tet:te-topology/"
       + "otntopo:otn-topology" {
      description "Augment OTN TE label";
    }
    description "OTN label.";
    uses otn-types:otn-label-restriction;
  }

  /* Augment label restrictions start of TE link information-source */
  augment "/nw:networks/nw:network/nt:link/tet:te/"
        + "tet:information-source-entry/"
        + "tet:label-restrictions/tet:label-restriction/"
        + "tet:label-start/tet:te-label/tet:technology" {
    when "../../../../../../../nw:network-types/tet:te-topology/"
       + "otntopo:otn-topology" {
      description "Augment OTN TE label";
    }
    description "OTN label.";
    case otn {
      uses otn-types:otn-link-label;
    }
  }
  /* Augment label restrictions end of TE link information-source */
  augment "/nw:networks/nw:network/nt:link/tet:te/"
        + "tet:information-source-entry/"
        + "tet:label-restrictions/tet:label-restriction/"
        + "tet:label-end/tet:te-label/tet:technology" {
    when "../../../../../../../nw:network-types/tet:te-topology/"
       + "otntopo:otn-topology" {
      description "Augment OTN TE label";
    }
    description "OTN label.";
    case otn {
      uses otn-types:otn-link-label;
    }
  }

  /* Augment label restrictions step of TE link information-source */
  augment "/nw:networks/nw:network/nt:link/tet:te/"
        + "tet:information-source-entry/"
        + "tet:label-restrictions/tet:label-restriction/"
        + "tet:label-step/tet:technology" {
    when "../../../../../../nw:network-types/tet:te-topology/"
       + "otntopo:otn-topology" {
      description "Augment OTN TE label";
    }
    description "OTN label.";
    case otn {
      uses otn-types:otn-label-step;
    }
  }

  /* Augment label hop of underlay primary path of TE link template */
  augment "/nw:networks/tet:te/tet:templates/"
        + "tet:link-template/tet:te-link-attributes/"
        + "tet:underlay/tet:primary-path/tet:path-element/tet:type/"
        + "tet:label/tet:label-hop/tet:te-label/tet:technology" {
/*
    when "../../../../../../../../../../"
       + "nw:network-types/tet:te-topology/"
       + "otntopo:otn-topology" {
                         description "Augment OTN TE label";
    }
*/
    description "OTN label.";
    case otn {
      uses otn-types:otn-path-label;
    }
  }

  /* Augment label hop of underlay backup path of TE link template */
  augment "/nw:networks/tet:te/tet:templates/"
        + "tet:link-template/tet:te-link-attributes/"
        + "tet:underlay/tet:backup-path/tet:path-element/tet:type/"
        + "tet:label/tet:label-hop/tet:te-label/tet:technology" {
/*
    when "../../../../../../../../../../nw:network-types/tet:te-topology/"
        + "otntopo:otn-topology" {
      description "Augment OTN TE label";
    }
*/
    description "OTN label.";
    case otn {
      uses otn-types:otn-path-label;
    }
  }

  /* Augment label restrictions of TE link template */
  augment "/nw:networks/tet:te/tet:templates/"
        + "tet:link-template/tet:te-link-attributes/"
        + "tet:label-restrictions/tet:label-restriction" {
/*
    when "../../../../../nw:network-types/tet:te-topology/"
        + "otntopo:otn-topology" {
      description "Augment OTN TE label";
    }
*/
    description "OTN label.";
    uses otn-types:otn-label-restriction;
  }
  /* Augment label restrictions start of TE link template */
  augment "/nw:networks/tet:te/tet:templates/"
        + "tet:link-template/tet:te-link-attributes/"
        + "tet:label-restrictions/tet:label-restriction/"
        + "tet:label-start/tet:te-label/tet:technology" {
/*
    when "../../../../../../../nw:network-types/tet:te-topology/"
        + "otntopo:otn-topology" {
      description "Augment OTN TE label";
    }
*/
    description "OTN label.";
    case otn {
      uses otn-types:otn-link-label;
    }
  }

  /* Augment label restrictions end of TE link template */
  augment "/nw:networks/tet:te/tet:templates/"
        + "tet:link-template/tet:te-link-attributes/"
        + "tet:label-restrictions/tet:label-restriction/"
        + "tet:label-end/tet:te-label/tet:technology" {
/*
    when "../../../../../../../nw:network-types/tet:te-topology/"
        + "otntopo:otn-topology" {
      description "Augment OTN TE label";
    }
*/
    description "OTN label.";
    case otn {
      uses otn-types:otn-link-label;
    }
  }

  /* Augment label restrictions step of TE link template */
  augment "/nw:networks/tet:te/tet:templates/"
        + "tet:link-template/tet:te-link-attributes/"
        + "tet:label-restrictions/tet:label-restriction/"
        + "tet:label-step/tet:technology" {
/*
    when "../../../../../../nw:network-types/tet:te-topology/"
        + "otntopo:otn-topology" {
      description "Augment OTN TE label";
    }
*/
    description "OTN label.";
    case otn {
      uses otn-types:otn-label-step;
    }
  }

}
