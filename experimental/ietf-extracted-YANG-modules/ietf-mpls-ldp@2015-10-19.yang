module ietf-mpls-ldp {
  namespace "urn:ietf:params:xml:ns:yang:ietf-mpls-ldp";
  // replace with IANA namespace when assigned
  prefix ldp;

  import ietf-inet-types {
    prefix "inet";
  }

  import ietf-yang-types {
    prefix "yang";
  }

  import ietf-interfaces {
    prefix "if";
  }

  import ietf-ip {
    prefix "ip";
  }

  import ietf-routing {
    prefix "rt";
  }

  import ietf-mpls {
    prefix "mpls";
  }

  import routing-policy {
    prefix "rpl";
  }

  organization "TBD";
  contact "TBD";
  description
    "";

  revision 2015-10-19 {
    description
      "Initial revision.";
    reference
      "";
  }

  /*
   * Features
   */
  feature admin-down-config {
    description
      "This feature indicates that the system allows to configure
       administrative down on a VRF instance and a neighbor.";
  }

  feature capability-end-of-lib {
    description
      "This feature indicates that the system allows to configure
       LDP end-of-lib capability.";
  }

  feature capability-mldp-hsmp {
    description
      "This feature indicates that the system allows to configure
       mLDP hub-and-spoke-multipoint capability.";
  }

  feature capability-mldp-node-protection {
    description
      "This feature indicates that the system allows to configure
       mLDP node-protection capability.";
  }

  feature capability-typed-wildcard-fec {
    description
      "This feature indicates that the system allows to configure
       LDP typed-wildcard-fec capability.";
  }

  feature capability-upstream-label-assignment {
    description
      "This feature indicates that the system allows to configure
       LDP upstream label assignment capability.";
  }

  feature forwarding-nexthop-config {
    description
      "This feature indicates that the system allows to configure
       forwarding nexthop on interfaces.";
  }

  feature global-session-authentication {
    description
      "This feature indicates that the system allows to configure
       authentication at global level.";
  }

  feature graceful-restart-helper-mode {
    description
      "This feature indicates that the system supports graceful
       restart helper mode.";
  }

  feature mldp {
    description
      "This feature indicates that the system supports Multicast
       LDP (mLDP).";
  }

  feature mldp-mofrr {
    description
      "This feature indicates that the system supports mLDP
       Multicast only FRR (MoFRR).";
  }

  feature per-interface-timer-config {
    description
      "This feature indicates that the system allows to configure
       interface hello timers at the per-interface level.";
  }

  feature per-neighbor-graceful-restart-config {
    description
      "This feature indicates that the system allows to configure
       graceful restart at the per-neighbor level.";
  }

  feature per-neighbor-session-attributes-config {
    description
      "This feature indicates that the system allows to configure
       session attributes at the per-neighbor level.";
  }

  feature policy-extended-discovery-config {
    description
      "This feature indicates that the system allows to configure
       policies to control the acceptance of extended neighbor
       discovery hello messages.";
  }

  feature policy-label-assignment-config {
    description
      "This feature indicates that the system allows to configure
       policies to assign labels according to certain prefixes.";
  }
  feature policy-ordered-label-config {
    description
      "This feature indicates that the system allows to configure
       ordered label policies.";
  }

  feature session-downstream-on-demand-config {
    description
      "This feature indicates that the system allows to configure
       session downstream-on-demand";
  }

  feature session-protection {
    description
      "This feature indicates that the system supports session
       protection";
  }

  /*
   * Typedefs
   */
  typedef address-family-type {
    type enumeration {
      enum ipv4 {
        description "IPv4";
      }
      enum ipv6 {
        description "IPv6";
      }
    }
    description
      "Address family type.";
  }

  typedef multipoint-type {
    type enumeration {
      enum p2mp {
        description "Point to multipoint.";
      }
      enum mp2mp {
        description "Multipoint to multipoint.";
      }
    }
    description
      "p2mp or mp2mp.";
  }

  typedef peer-list-ref {
    type leafref {
      path "/rpl:routing-policy/rpl:defined-sets/rpl:neighbor-sets/"
        + "rpl:neighbor-set/rpl:neighbor-set-name";
    }
    description
      "A type for a reference to a peer list.";
  }

  typedef prefix-list-ref {
    type leafref {
      path "/rpl:routing-policy/rpl:defined-sets/rpl:prefix-sets/"
        + "rpl:prefix-set/rpl:prefix-set-name";
    }
    description
      "A type for a reference to a prefix list.";
  }

  typedef oper-status-event-type {
    type enumeration {
      enum up {
        value 1;
        description
          "Operational status changed to up.";
      }
      enum down {
        value 2;
        description
          "Operational status changed to down.";
      }
    }
    description "Operational status event type for notifications.";
  }

  /*
   * Identities
   */

  /*
   * Groupings
   */
  grouping ldp-instance-ref {
    description
      "An absolute reference to an LDP instance.";
    leaf routing-instance-ref {
      type rt:routing-instance-ref;
      description
        "Reference to the routing instance.";
    }
  } // ldp-instance-ref

  grouping ldp-neighbor-ref {
    description
      "An absolute reference to an LDP neighbor.";
    uses ldp-instance-ref;
    leaf neighbor-ref {
      type leafref {
        path "/rt:routing/rt:routing-instance"
          + "[rt:name = current()/../routing-instance-ref]/"
          + "mpls:mpls/mpls-ldp/"
          + "neighbors/neighbor/lsr-id";
      }
      description
        "Reference to an LDP neighbor.";
    }
  } // ldp-neighbor-ref

  grouping ldp-adjacency-ref {
    description
      "An absolute reference to an LDP adjacency.";
    uses ldp-instance-ref;
    choice adjacency-type {
      description
        "Interface or targeted adjacency.";
      case targeted {
        container targeted {
          description "Targeted adjacency.";
          leaf target-address {
            type inet:ip-address;
            description
              "The target address.";
          }
        } // targeted
      }
      case link {
        container link {
          description "Link adjacency.";
          leaf next-hop-interface {
            type if:interface-ref;
            description
              "Interface connecting to next-hop.";
          }
          leaf next-hop-address {
            type inet:ip-address;
            must "../next-hop-interface" {
              description
                "Applicable when interface is specified.";
            }
            description
              "IP address of next-hop.";
          }
        } // link
      }
    }
  } // ldp-adjacency-ref

  grouping ldp-fec-event {
    description
      "A LDP FEC event.";
    uses ldp-instance-ref;
    leaf prefix {
      type inet:ip-prefix;
      description
        "FEC.";
    }
  } // ldp-fec-event

  grouping mldp-fec-event {
    description
      "A mLDP FEC event.";
    uses ldp-instance-ref;
    leaf tree-type {
      type multipoint-type;
      description
        "p2mp or mp2mp.";
    }
    leaf root {
      type inet:ip-address;
      description
        "Root address.";
    }
    choice lsp-key-type {
      description
        "LSP ID based or source-group based .";
      case lsp-id-based {
        leaf lsp-id {
          type uint16;
          description
            "ID to identify the LSP.";
        }
      }
      case source-group-based {
        leaf source-addr {
          type inet:ip-address;
          description
            "LSP source address.";
        }
        leaf group-addr {
          type inet:ip-address;
          description
            "Multicast group address.";
        }
      } // case source-group-based
    }
  } // mldp-fec-event

  grouping basic-discovery-timers {
    description
      "Basic discovery timer attributes.";
    leaf hello-holdtime {
      type uint16 {
        range 15..3600;
      }
      units seconds;
      default 15;
      description
        "The time interval for which a LDP link Hello adjacency
         is maintained in the absence of link Hello messages from
         the LDP neighbor";
    }
    leaf hello-interval {
      type uint16 {
        range 5..1200;
      }
      units seconds;
      default 5;
      description
        "The interval between consecutive LDP link Hello messages
         used in basic LDP discovery";
    }
  } // basic-discovery-timers

  grouping extended-discovery-timers {
    description
      "Extended discovery timer attributes.";
    leaf hello-holdtime {
      type uint16 {
        range 15..3600;
      }
      units seconds;
      default 45;
      description
        "The time interval for which LDP targeted Hello adjacency
         is maintained in the absence of targeted Hello messages
         from an LDP neighbor.";
    }
    leaf hello-interval {
      type uint16 {
        range 5..3600;
      }
      units seconds;
      default 15;
      description
        "The interval between consecutive LDP targeted Hello
         messages used in extended LDP discovery.";
    }
  } // extended-discovery-timers

  grouping graceful-restart-attributes {
    description
      "Graceful restart configuration attributes.";
    container graceful-restart {
      description
        "Attributes for graceful restart.";
      leaf enable {
        type boolean;
        description
          "Enable or disable graceful restart.";
      }
      leaf helper-enable {
        if-feature graceful-restart-helper-mode;
        type boolean;
        description
          "Enable or disable graceful restart helper mode.";
      }
      leaf reconnect-time {
        type uint16 {
          range 10..1800;
        }
        units seconds;
        description
          "Specifies the time interval that the remote LDP peer
           must wait for the local LDP peer to reconnect after the
           remote peer detects the LDP communication failure.";
      }
      leaf recovery-time {
        type uint16 {
          range 30..3600;
        }
        units seconds;
        description
          "";
      }
      leaf forwarding-holdtime {
        type uint16 {
          range 30..3600;
        }
        units seconds;
        description
          "";
      }
    } // graceful-restart
  } // graceful-restart-attributes

  grouping graceful-restart-attributes-per-neighbor {
    description
      "Per neighbor graceful restart configuration attributes.";
    container graceful-restart {
      description
        "Attributes for graceful restart.";
      leaf enable {
        type boolean;
        description
          "Enable or disable graceful restart.";
      }
      leaf reconnect-time {
        type uint16 {
          range 10..1800;
        }
        units seconds;
        description
          "Specifies the time interval that the remote LDP peer
           must wait for the local LDP peer to reconnect after the
           remote peer detects the LDP communication failure.";
      }
      leaf recovery-time {
        type uint16 {
          range 30..3600;
        }
        units seconds;
        description
          "";
      }
    } // graceful-restart
  } // graceful-restart-attributes-per-neighbor

  grouping neighbor-attributes {
    description "Neighbor configuration attributes.";

    leaf session-ka-holdtime {
      type uint16 {
        range 45..3600;
      }
      units seconds;
      description
        "The time interval after which an inactive LDP session
         terminates and the corresponding TCP session closes.
         Inactivity is defined as not receiving LDP packets from the
         neighbor.";
    }
    leaf session-ka-interval {
      type uint16 {
        range 15..1200;
      }
      units seconds;
      description
        "The interval between successive transmissions of keepalive
         packets. Keepalive packets are only sent in the absence of
         other LDP packets transmitted over the LDP session.";
    }
  } // neighbor-attributes

  grouping session-protection-per-vrf {
    description "Session protection attributes.";
    container session-protection {
      if-feature session-protection;
      description
        "Session protection attributes.";
      leaf enable {
        type boolean;
        description
          "'true' if session protection is enabled.";
      }
      leaf duration {
        type union {
          type uint32;
          type enumeration {
            enum "infinite" {
              description "The duration is infinite.";
            }
          }
        }
        units seconds;
        description
          "Session protection duration.";
      }
      leaf peer-list {
        type peer-list-ref;
        description
          "The name of a peer ACL.";
      }
    } // session-protection
  } // session-protection-per-vrf

  grouping session-protection-per-neighbor {
    description "Session protection attributes.";
    container session-protection {
      if-feature session-protection;
      description
        "Session protection attributes.";
      leaf enable {
        type boolean;
        description
          "'true' if session protection is enabled.";
      }
      leaf duration {
        type union {
          type uint32;
          type enumeration {
            enum "infinite" {
              description "The duration is infinite.";
            }
          }
        }
        units seconds;
        description
          "Session protection duration.";
      }
    } // session-protection
  } // session-protection-per-neighbor

  grouping neighbor-authentication {
    description
      "Neighbor authentication attributes.";
    leaf md5-password {
      type string {
        length "1..80";
      }
      description
        "Assigns an encrypted MD5 password to an LDP
         neighbor";
    } // md5-password
  } // neighbor-authentication

  grouping neighbor-attributes-container {
    description "Container of neighbor configuration attributes.";
    container neighbors {
      description
        "Container of neighbor configuration attributes.";
      uses neighbor-authentication {
        if-feature global-session-authentication;
      }
      uses neighbor-attributes;
    }
  } // neighbor-attributes-container

  grouping instance-attributes {
    description "Configuration attributes at instance level.";

    container capability {
      description "Configure capability.";
      container end-of-lib {
        if-feature capability-end-of-lib;
        description
          "Configure upstream label assignment capability.";
        leaf enable {
          type boolean;
          description
            "Enable end-of-lib capability.";
        }
      }
      container typed-wildcard-fec {
        if-feature capability-typed-wildcard-fec;
        description
          "Configure typed-wildcard-fec capability.";
        leaf enable {
          type boolean;
          description
            "Enable typed-wildcard-fec capability.";
        }
      }
      container upstream-label-assignment {
        if-feature capability-upstream-label-assignment;
        description
          "Configure upstream label assignment capability.";
        leaf enable {
          type boolean;
          description
            "Enable upstream label assignment.";
        }
      }
      container mldp {
        if-feature mldp;
        description
          "Multipoint capabilities.";
        uses mldp-capabilities;
      }
    } // capability

    uses graceful-restart-attributes;

    leaf igp-synchronization-delay {
      type uint16 {
        range 3..60;
      }
      units seconds;
      description
        "Sets the interval that the LDP waits before notifying the
         Interior Gateway Protocol (IGP) that label exchange is
         completed so that IGP can start advertising the normal
         metric for the link.";
    }
    leaf lsr-id {
      type yang:dotted-quad;
      description "Router ID.";
    }
  } // instance-attributes

  grouping global-attributes {
    description "Configuration attributes at global level.";

    uses instance-attributes;

    leaf nonstop-routing {
      type boolean;
      default false;
      description
        "Enables Nonstop Routing (NSR)";
    }
  } // global-attributes

  grouping policy-attributes {
    description
      "LDP policy attributes.";
    container label-policy {
      description
        "Label policy attributes.";
      container independent-mode {
        description
          "Independent label policy attributes.";
        container assign {
          if-feature policy-label-assignment-config;
          description
            "Label assignment policies";
          choice prefix-option {
            description
              "Use either prefix-list or host-routes-only.";
            case prefix-list {
              leaf prefix-list {
                type prefix-list-ref;
                description
                  "Assign labels according to certain prefixes.";
              }
            }
            case host-routes-only {
              leaf host-routes-only {
                type boolean;
                description
                  "'true' to apply host routes only.";
              }
            }
          } // prefix-option
        }
        container advertise {
          description
            "Label advertising policies.";
          container explicit-null {
            presence "Present to enable explicit null.";
            description
              "Enables an egress router to advertise an
               explicit null label (value 0) in place of an
               implicit null label (value 3) to the
               penultimate hop router.";
            leaf prefix-list {
              type prefix-list-ref;
              description
                "Prefix list name. Applies the filters in the
                 specified prefix list to label
                 advertisements.
                 If the prefix list is not specified, explicit
                 null label advertisement is enabled for all
                 directly connected prefixes.";
            }
          }
          leaf prefix-list {
            type prefix-list-ref;
            description
              "Applies the prefix list to outgoing label
               advertisements.";
          }
        }
        container accept {
          description
            "Label advertisement acceptance policies.";
          leaf prefix-list {
            type prefix-list-ref;
            description
              "Applies the prefix list to incoming label
               advertisements.";
          }
        }
      } // independent-mode
      container ordered-mode {
        if-feature policy-ordered-label-config;
        description
          "Ordered label policy attributes.";
        container egress-lsr {
          description
            "Egress LSR label assignment policies";
          leaf prefix-list {
            type prefix-list-ref;
            description
              "Assign labels according to certain prefixes.";
          }
        }
        container advertise {
          description
            "Label advertising policies.";
          leaf prefix-list {
            type prefix-list-ref;
            description
              "Applies the prefix list to outgoing label
               advertisements.";
          }
        }
        container accept {
          description
            "Label advertisement acceptance policies.";
          leaf prefix-list {
            type prefix-list-ref;
            description
              "Applies the prefix list to incoming label
               advertisements.";
          }
        }
      } // ordered-mode
    } // label-policy
  } // policy-attributes

  grouping neighbor-af-policy-attributes {
    description
      "LDP policy attributes under neighbor address-family.";
    container label-policy {
      description
        "Label policy attributes.";
      container advertise {
        description
          "Label advertising policies.";
        leaf prefix-list {
          type prefix-list-ref;
            description
              "Applies the prefix list to outgoing label
               advertisements.";
        }
      }
      container accept {
        description
          "Label advertisement acceptance policies.";
        leaf prefix-list {
          type prefix-list-ref;
          description
            "Applies the prefix list to incoming label
             advertisements.";
        }
      } // accept
    } // label-policy
  } // neighbor-af-policy-attributes

  grouping extended-discovery-policy-attributes {
    description
      "LDP policy to control the acceptance of extended neighbor
       discovery hello messages.";
    container hello-accept {
      if-feature policy-extended-discovery-config;
      description
        "Extended discovery acceptance policies.";

      leaf enable {
        type boolean;
        description
          "'true' to accept; 'false' to deny.";
      }
      leaf peer-list {
        type peer-list-ref;
        description
          "The name of a peer ACL.";
      }
    } // hello-accept
  } // extended-discovery-policy-attributes

  grouping mldp-capabilities {
    description
      "mLDP capabilities.";
    container p2mp {
      description
        "Configure point-to-multipoint capability.";
      leaf enable {
        type boolean;
        description
          "Enable point-to-multipoint.";
      }
    }
    container mp2mp {
      description
        "Configure multipoint-to-multipoint capability.";
      leaf enable {
        type boolean;
        description
          "Enable multipoint-to-multipoint.";
      }
    }
    container make-before-break {
      description
        "Configure make-before-break capability.";
      leaf enable {
        type boolean;
        description
          "Enable make-before-break.";
      }
      leaf switchover-delay {
        type uint16;
        units seconds;
        description
          "Switchover delay in seconds.";
      }
      leaf timeout {
        type uint16;
        units seconds;
        description
          "Timeout in seconds.";
      }
    }
    container hub-and-spoke {
      if-feature capability-mldp-hsmp;
      description
        "Configure hub-and-spoke-multipoint capability.";
      reference
        "RFC7140: LDP Extensions for Hub and Spoke Multipoint
         Label Switched Path";
      leaf enable {
        type boolean;
        description
          "Enable hub-and-spoke-multipoint.";
      }
    }
    container node-protection {
      if-feature capability-mldp-node-protection;
      description
        "Configure node-protection capability.";
      reference
        "draft-ietf-mpls-mldp-node-protection: mLDP Node
         Protection.";
      leaf plr {
        type boolean;
        description
          "Point of Local Repair capable for MP LSP node
           protection.";
      }
      container merge-point {
        description
          "Merge Point capable for MP LSP node protection.";
        leaf enable {
          type boolean;
          description
            "Enable merge point capability.";
        }
        leaf targeted-session-teardown-delay {
          type uint16;
          units seconds;
          description
            "Targeted session teardown delay.";
        }
      } // merge-point
    }
  } // mldp-capabilities

  grouping  mldp-configured-lsp-roots {
    description
      "mLDP roots containers.";

    container roots-ipv4 {
      when "../../../af = 'ipv4'" {
        description
          "Only for IPv4.";
      }
      description
        "Configured IPv4 multicast LSPs.";
      list root {
        key "root-addr";
        description
          "List of roots for configured multicast LSPs.";

        leaf root-addr {
          type inet:ipv4-address;
          description
            "Root address.";
        }

        list lsp {
          must "(lsp-id = 0 and source-addr != '0.0.0.0' and "
            + "group-addr != '0.0.0.0') or "
            + "(lsp-id != 0 and source-addr = '0.0.0.0' and "
            + "group-addr = '0.0.0.0')" {
            description
              "A LSP can be identified by either <lsp-id> or
               <source-addr, group-addr>.";
          }
          key "lsp-id source-addr group-addr";
          description
            "List of LSPs.";
          leaf lsp-id {
            type uint16;
            description "ID to identify the LSP.";
          }
          leaf source-addr {
            type inet:ipv4-address-no-zone;
            description
              "Source address.";
          }
          leaf group-addr {
            type inet:ipv4-address-no-zone;
            description
              "Group address.";
          }
        } // list lsp
      } // list root
    } // roots-ipv4

    container roots-ipv6 {
      when "../../../af = 'ipv6'" {
        description
          "Only for IPv6.";
      }
      description
        "Configured IPv6 multicast LSPs.";

      list root {
        key "root-addr";
        description
          "List of roots for configured multicast LSPs.";

        leaf root-addr {
          type inet:ipv6-address;
          description
            "Root address.";
        }

        list lsp {
          must "(lsp-id = 0 and source-addr != '::' and "
            + "group-addr != '::') or "
            + "(lsp-id != 0 and source-addr = '::' and "
            + "group-addr = '::')" {
            description
              "A LSP can be identified by either <lsp-id> or
               <source-addr, group-addr>.";
          }
          key "lsp-id source-addr group-addr";
          description
            "List of LSPs.";
          leaf lsp-id {
            type uint16;
            description "ID to identify the LSP.";
          }
          leaf source-addr {
            type inet:ipv6-address-no-zone;
            description
              "Source address.";
          }
          leaf group-addr {
            type inet:ipv6-address-no-zone;
            description
              "Group address.";
          }
        } // list lsp
      } // list root
    } // roots-ipv6
  } // mldp-configured-lsp-roots
  /*
   * Configuration data nodes
   */

  augment "/rt:routing/rt:routing-instance/mpls:mpls" {
    description "LDP augmentation.";

    container mpls-ldp {
      presence "Container for LDP protocol.";
      description
        "Container for LDP protocol.";

      container global {
        description
          "Global attributes for LDP.";
        container config {
          description
            "Configuration data.";
          uses global-attributes;
        }
        container state {
          config false;
          description
            "Operational state data.";
          uses global-attributes;
        }
      }

      container mldp {
        if-feature mldp;
        description
          "mLDP attributes at per instance level. Defining attributes
           here does not enable any MP capabilities. MP capabilities
           need to be explicitly enabled under container
           capability.";

        container config {
          description
            "Configuration data.";
          leaf enable {
            type boolean;
            description
              "Enable mLDP.";
          }
        }
        container state {
          config false;
          description
            "Operational state data.";
          leaf enable {
            type boolean;
            description
              "Enable mLDP.";
          }
        }

        list address-family {
          key "af";
          description
            "Per-af params.";
          leaf af {
            type address-family-type;
            description
              "Address family type value.";
          }

          container config {
            description
              "Configuration data.";
            container multicast-only-frr {
              if-feature mldp-mofrr;
              description
                "Multicast only FRR (MoFRR) policy.";
              leaf prefix-list {
                type prefix-list-ref;
                description
                  "Enables MoFRR for the specified access list.";
              }
            } // multicast-only-frr
            container recursive-fec {
              description
                "Recursive FEC policy.";
              leaf prefix-list {
                type prefix-list-ref;
                description
                  "Enables recursive FEC for the specified access
                   list.";
              }
            } // recursive-for
          }
          container state {
            config false;
            description
              "Operational state data.";
            container multicast-only-frr {
              if-feature mldp-mofrr;
              description
                "Multicast only FRR (MoFRR) policy.";
              leaf prefix-list {
                type prefix-list-ref;
                description
                  "Enables MoFRR for the specified access list.";
              }
            } // multicast-only-frr
            container recursive-fec {
              description
                "Recursive FEC policy.";
              leaf prefix-list {
                type prefix-list-ref;
                description
                  "Enables recursive FEC for the specified access
                   list.";
              }
            } // recursive-for
          }

          container configured-leaf-lsps {
            description
              "Configured multicast LSPs.";

            container p2mp {
              description
                "Configured point-to-multipoint LSPs.";
              uses mldp-configured-lsp-roots;
            }
            container mp2mp {
              description
                "Configured multipoint-to-multipoint LSPs.";
              uses mldp-configured-lsp-roots;
            }
          } // configured-leaf-lsps
        } // list address-family
      } // mldp

      list address-family {
        key "af";
        description
          "Per-vrf per-af params.";
        leaf af {
          type address-family-type;
          description
            "Address family type value.";
        }

        container config {
          description
            "Configuration data.";
          leaf enable {
            type boolean;
            description
              "'true' to enable the address family.";
          }
          uses policy-attributes;

          container ipv4 {
            when "../../af = 'ipv4'" {
              description
                "Only for IPv4.";
            }
            description
              "IPv4 address family.";
            leaf transport-address {
              type inet:ipv4-address;
              description
                "The transport address advertised in LDP Hello
                 messages.";
            }
          } // ipv4
          container ipv6 {
            when "../../af = 'ipv6'" {
              description
                "Only for IPv6.";
            }
            description
              "IPv6 address family.";
            leaf transport-address {
              type inet:ipv6-address;
              description
                "The transport address advertised in LDP Hello
                 messages.";
            }
          } // ipv6
        }
        container state {
          config false;
          description
            "Operational state data.";
          leaf enable {
            type boolean;
            description
              "'true' to enable the address family.";
          }
          uses policy-attributes;

          container ipv4 {
            when "../../af = 'ipv4'" {
              description
                "Only for IPv4.";
            }
            description
              "IPv4 address family.";
            leaf transport-address {
              type inet:ipv4-address;
              description
                "The transport address advertised in LDP Hello
                 messages.";
            }
          } // ipv4
          container ipv6 {
            when "../../af = 'ipv6'" {
              description
                "Only for IPv6.";
            }
            description
              "IPv6 address family.";
            leaf transport-address {
              type inet:ipv6-address;
              description
                "The transport address advertised in LDP Hello
                 messages.";
            }
          } // ipv6
        }
      }

      container discovery {
        description
          "Neibgbor discovery configuration.";

        container interfaces {
          description
            "A list of interfaces for basic descovery.";
          container config {
            description
              "Configuration data.";
            uses basic-discovery-timers;
          }
          container state {
            config false;
            description
              "Operational state data.";
            uses basic-discovery-timers;
          }

          list interface {
            key "interface";
            description
              "List of LDP interfaces.";
            leaf interface {
              type if:interface-ref;
              description
                "Interface.";
            }
            container config {
              description
                "Configuration data.";
              uses basic-discovery-timers {
                if-feature per-interface-timer-config;
              }
              leaf igp-synchronization-delay {
                if-feature per-interface-timer-config;
                type uint16 {
                  range 3..60;
                }
                units seconds;
                description
                  "Sets the interval that the LDP waits before
                   notifying the Interior Gateway Protocol (IGP) that
                   label exchange is completed so that IGP can start
                   advertising the normal metric for the link.";
              }
            }
            container state {
              config false;
              description
                "Operational state data.";
              uses basic-discovery-timers {
                if-feature per-interface-timer-config;
              }
              leaf igp-synchronization-delay {
                if-feature per-interface-timer-config;
                type uint16 {
                  range 3..60;
                }
                units seconds;
                description
                  "Sets the interval that the LDP waits before
                   notifying the Interior Gateway Protocol (IGP) that
                   label exchange is completed so that IGP can start
                   advertising the normal metric for the link.";
              }
            }

            list address-family {
              key "af";
              description
                "Per-vrf per-af params.";
              leaf af {
                type address-family-type;
                description
                  "Address family type value.";
              }
              container config {
                description
                  "Configuration data.";
                leaf enable {
                  type boolean;
                  description
                    "Enable the address family on the interface.";
                }

                container ipv4 {
                  must "/if:interfaces/if:interface"
                    + "[name = current()/../../../interface]/"
                    + "ip:ipv4" {
                    description
                      "Only if IPv4 is enabled on the interface.";
                  }
                  description
                    "IPv4 address family.";
                  leaf transport-address {
                    type union {
                      type enumeration {
                        enum "use-interface-address" {
                          description
                          "Use interface address as the transport
                           address.";
                        }
                      }
                      type inet:ipv4-address;
                    }
                    description
                      "IP address to be advertised as the LDP
                        transport address.";
                  }
                }
                container ipv6 {
                  must "/if:interfaces/if:interface"
                    + "[name = current()/../../../interface]/"
                    + "ip:ipv6" {
                    description
                      "Only if IPv6 is enabled on the interface.";
                  }
                  description
                    "IPv6 address family.";
                  leaf transport-address {
                    type union {
                      type enumeration {
                        enum "use-interface-address" {
                          description
                          "Use interface address as the transport
                           address.";
                        }
                      }
                      type inet:ipv4-address;
                    }
                    description
                      "IP address to be advertised as the LDP
                       transport address.";
                  }
                } // ipv6
              }
              container state {
                config false;
                description
                  "Operational state data.";
                leaf enable {
                  type boolean;
                  description
                    "Enable the address family on the interface.";
                }

                container ipv4 {
                  must "/if:interfaces/if:interface"
                    + "[name = current()/../../../interface]/"
                    + "ip:ipv4" {
                    description
                      "Only if IPv4 is enabled on the interface.";
                  }
                  description
                    "IPv4 address family.";
                  leaf transport-address {
                    type union {
                      type enumeration {
                        enum "use-interface-address" {
                          description
                          "Use interface address as the transport
                           address.";
                        }
                      }
                      type inet:ipv4-address;
                    }
                    description
                      "IP address to be advertised as the LDP
                       transport address.";
                  }
                }
                container ipv6 {
                  must "/if:interfaces/if:interface"
                    + "[name = current()/../../../interface]/"
                    + "ip:ipv6" {
                    description
                      "Only if IPv6 is enabled on the interface.";
                  }
                  description
                    "IPv6 address family.";
                  leaf transport-address {
                    type union {
                      type enumeration {
                        enum "use-interface-address" {
                          description
                          "Use interface address as the transport
                           address.";
                        }
                      }
                      type inet:ipv4-address;
                    }
                    description
                      "IP address to be advertised as the LDP
                       transport address.";
                  }
                } // ipv6
              }
            } // address-family
          } // list interface
        } // interfaces

        container targeted
        {
          description
            "A list of targeted neighbors for extended discovery.";
          container config {
            description
              "Configuration data.";
            uses extended-discovery-timers;
            uses extended-discovery-policy-attributes;
          }
          container state {
            config false;
            description
              "Operational state data.";
            uses extended-discovery-timers;
            uses extended-discovery-policy-attributes;
          }

          container address-family {
            description
              "Per-vrf per-af params.";
            container ipv4 {
              description
                "IPv4 address family.";
              list target {
                key "address";
                description
                  "Targeted discovery params.";

                leaf address {
                  type inet:ipv4-address;
                  description
                    "Configures a remote LDP neighbor and enables
                     extended LDP discovery of the specified
                     neighbor.";
                }
                container config {
                  description
                    "Configuration data.";
                  leaf enable {
                    type boolean;
                    description
                      "Enable the target.";
                  }
                }
                container state {
                  config false;
                  description
                    "Operational state data.";
                  leaf enable {
                    type boolean;
                    description
                      "Enable the target.";
                  }
                }
              }
            } // ipv4
            container ipv6 {
              description
                "IPv6 address family.";
              list target {
                key "address";
                description
                  "Targeted discovery params.";

                leaf address {
                  type inet:ipv6-address;
                  description
                    "Configures a remote LDP neighbor and enables
                     extended LDP discovery of the specified
                     neighbor.";
                }
                container config {
                  description
                    "Configuration data.";
                  leaf enable {
                    type boolean;
                    description
                      "Enable the target.";
                  }
                }
                container state {
                  config false;
                  description
                    "Operational state data.";
                  leaf enable {
                    type boolean;
                    description
                      "Enable the target.";
                  }
                }
              }
            } // ipv6
          } // address-family
        } // targeted
      } // discovery

      container forwarding-nexthop {
        if-feature forwarding-nexthop-config;
        description
          "Configuration for forwarding nexthop.";
        container interfaces {
          description
            "A list of interfaces on which forwarding is disabled.";

          list interface {
            key "interface";
            description
              "List of LDP interfaces.";
            leaf interface {
              type if:interface-ref;
              description
                "Interface.";
            }
            list address-family {
              key "af";
              description
                "Per-vrf per-af params.";
              leaf af {
                type address-family-type;
                description
                  "Address family type value.";
              }
              container config {
                description
                  "Configuration data.";
                leaf ldp-disable {
                  type boolean;
                  description
                    "Disable LDP forwarding on the interface.";
                }
                leaf mldp-disable {
                  if-feature mldp;
                  type boolean;
                  description
                    "Disable mLDP forwarding on the interface.";
                }
              }
              container state {
                config false;
                description
                  "Operational state data.";
                leaf ldp-disable {
                  type boolean;
                  description
                    "Disable LDP forwarding on the interface.";
                }
                leaf mldp-disable {
                  if-feature mldp;
                  type boolean;
                  description
                    "Disable mLDP forwarding on the interface.";
                }
              }
            } // address-family
          } // list interface
        } // interfaces
      } // forwarding-nexthop

      container neighbors {
        description
          "Neighbors configuration attributes.";

        container config {
          description
            "Configuration data.";
          uses neighbor-authentication {
            if-feature global-session-authentication;
          }
          uses neighbor-attributes;

          container session-downstream-on-demand {
            if-feature session-downstream-on-demand-config;
            description
              "Session downstream-on-demand attributes.";
            leaf enable {
              type boolean;
              description
                "'true' if session downstream-on-demand is enabled.";
            }
            leaf peer-list {
              type peer-list-ref;
              description
                "The name of a peer ACL.";
            }
          }

          uses session-protection-per-vrf;
        }
        container state {
          config false;
          description
            "Operational state data.";
          uses neighbor-authentication {
            if-feature global-session-authentication;
          }
          uses neighbor-attributes;
          container session-downstream-on-demand {
            if-feature session-downstream-on-demand-config;
            description
              "Session downstream-on-demand attributes.";
            leaf enable {
              type boolean;
              description
                "'true' if session downstream-on-demand is enabled.";
            }
            leaf peer-list {
              type peer-list-ref;
              description
                "The name of a peer ACL.";
            }
          }

          uses session-protection-per-vrf;
        }

        list neighbor {
          key "lsr-id";
          description
            "List of neighbors.";

          leaf lsr-id {
            type union {
              type yang:dotted-quad;
              type uint32;
            }
            description "LSR ID.";
          }

          container config {
            description
              "Configuration data.";
            leaf admin-down {
              type boolean;
              default false;
              description
                "'true' to disable the neighbor.";
            }

            container capability {
              description
                "Per neighbor capability";
              container mldp {
                if-feature mldp;
                description
                  "mLDP capabilities.";
                uses mldp-capabilities;
              }
            }

            uses neighbor-authentication;

            uses graceful-restart-attributes-per-neighbor {
              if-feature per-neighbor-graceful-restart-config;
            }

            uses neighbor-attributes {
              if-feature per-neighbor-session-attributes-config;
            }
            uses session-protection-per-neighbor;

            container address-family {
              description
                "Per-vrf per-af params.";
              container ipv4 {
                description
                  "IPv4 address family.";
                uses neighbor-af-policy-attributes;
              }
              container ipv6 {
                description
                  "IPv6 address family.";
                uses neighbor-af-policy-attributes;
              } // ipv6
            } // address-family
          }
          container state {
            config false;
            description
              "Operational state data.";
            leaf admin-down {
              type boolean;
              default false;
              description
                "'true' to disable the neighbor.";
            }

            container capability {
              description
                "Per neighbor capability";
              container mldp {
                if-feature mldp;
                description
                  "mLDP capabilities.";
                uses mldp-capabilities;
              }
            }

            uses neighbor-authentication;

            uses graceful-restart-attributes-per-neighbor {
              if-feature per-neighbor-graceful-restart-config;
            }

            uses neighbor-attributes {
              if-feature per-neighbor-session-attributes-config;
            }
            uses session-protection-per-neighbor;

            container address-family {
              description
                "Per-vrf per-af params.";
              container ipv4 {
                description
                  "IPv4 address family.";
                uses neighbor-af-policy-attributes;
              }
              container ipv6 {
                description
                  "IPv6 address family.";
                uses neighbor-af-policy-attributes;
              } // ipv6
            } // address-family
          }
        } // list neighbor
      } // neighbors
    } // container mpls-ldp
  }

  /*
   * RPCs
   */
  rpc mpls-ldp-clear-neighbor {
    description
      "Clears the session to the neighbor.";
    input {
      uses ldp-instance-ref {
        description
          "VRF instance name. If this is not provided
           then all instances are cleared.";
      }
      leaf lsr-id {
        type union {
          type yang:dotted-quad;
          type uint32;
        }
        description
          "LSR ID of neighbor to be cleared. If this is not provided
           then all neighbors are cleared";
      }
    }
  }

  rpc mpls-ldp-clear-adjacency {
    description
      "Clears the hello adjacency";
    input {
      uses ldp-instance-ref {
        description
          "VRF instance name. If this is not provided
           then all instances are cleared.";
      }
      container adjacency {
        description
          "Link adjacency or targettted adjacency. If this is not
           provided then all hello adjacencies are cleared";
        choice adjacency-type {
          description "Adjacency type.";
          case targeted {
            container targeted {
              presence "Present to clear targeted adjacencies.";
              description
                "Clear targeted adjacencies.";
              leaf target-address {
                type inet:ip-address;
                description
                  "The target address. If this is not provided then
                   all targeted adjacencies are cleared";
              }
            } // targeted
          }
          case link {
            container link {
              presence "Present to clear link adjacencies.";
              description
                "Clear link adjacencies.";
              leaf next-hop-interface {
                type if:interface-ref;
                description
                  "Interface connecting to next-hop. If this is not
                   provided then all link adjacencies are cleared.";
              }
              leaf next-hop-address {
                type inet:ip-address;
                must "../next-hop-interface" {
                  description
                    "Applicable when interface is specified.";
                }
                description
                  "IP address of next-hop. If this is not provided
                   then adjacencies to all next-hops on the given
                   interface are cleared.";
              } // next-hop-address
            } // link
          }
        }
      }
    }
  }

  rpc mpls-ldp-clear-neighbor-statistics {
    description
      "Clears protocol statistics (e.g. sent and received
       counters).";
    input {
      uses ldp-instance-ref {
        description
          "VRF instance name. If this is not provided
          then all instances are cleared.";
      }
      leaf lsr-id {
        type union {
          type yang:dotted-quad;
          type uint32;
        }
        description
          "LSR ID of neighbor whose statistic are to be cleared.
           If this is not provided then all neighbors statistics are
           cleared";
      }
    }
  }

  /*
   * Notifications
   */
  notification mpls-ldp-neighbor-event {
    description
      "Notification event for a change of LDP neighbor operational
       status.";
    leaf event-type {
      type oper-status-event-type;
      description "Event type.";
    }
    uses ldp-neighbor-ref;
  }

  notification mpls-ldp-adjacency-event {
    description
      "Notification event for a change of LDP adjacency operational
       status.";
    leaf event-type {
      type oper-status-event-type;
      description "Event type.";
    }
    uses ldp-adjacency-ref;
  }

  notification mpls-ldp-fec-event {
    description
      "Notification event for a change of FEC status.";
    leaf event-type {
      type oper-status-event-type;
      description "Event type.";
    }
    uses ldp-fec-event;
  }

  notification mpls-mldp-fec-event {
    description
      "Notification event for a change of FEC status.";
    leaf event-type {
      type oper-status-event-type;
      description "Event type.";
    }
    uses mldp-fec-event;
  }
}
