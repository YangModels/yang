module ietf-supa-policy { 
  namespace "urn:ietf:params:xml:ns:yang:ietf-supa-policy"; 
  // replace with IANA namespace when assigned 
  prefix policy; 

  import ietf-inet-types { 
    prefix inet; 
  } 

  organization "IETF"; 
  contact 
    "Editor: Jun Bi 
     junbi@tsinghua.edu.cn"; 

  description 
    "This YANG module defines a component that describing 
     the ddc policy model for monitoring and optimizing 
     tenant's DC (data center) services that are deployed 
     in multiple data centers. 
     Terms and Acronyms 
       DDC: Distributed Data Center 
       L2VPN: Layer 2 Virtual Private Network 
       L3VPN: Layer 3 Virtual Private Network"; 

  revision 2015-03-05 { 
    description 
      "Initial revision."; 
      reference 
        " Network Policy YANG Data Model "; 
  } 

container ddc-policy{ 
  description 
    "Distributed Data Center Service Operation Data"; 

  container adjust-flow-paths { 
    description 
      "To improve the bandwidth utilization (or reduce the cost, 
       or other reason) and mitigate traffic congestion,management 
       system/ application requires controller to adjust certain 
       flows to pass/bypass certain nodes(or links), when, e.g., 
       bandwidth utilization exceed certain threshold. Vpn name, 
       vpn type, adjusted flow and specified nodes (that the flow 
       should pass) should be told to controller. so that the 
       controller can configure the network elements to change the 
       VRF table and routing table"; 

    list adjust-flow-path { 
      key "vpn-name"; 
      description 
        "The list of VPN and flow that need to be adjusted in  
         specific paths. So as to optimizing traffic in the links  
         that are between data centers."; 
      leaf vpn-name { 
        type string; 
        mandatory true; 
        description 
          "Indicates the name of VPN that the adjusted flow 
belongs  
           to. A VPN instance is identified by vpn-name. It should 
           be one of the created VPN instance names"; 
      } 
      leaf vpn-type { 
        type enumeration { 
          enum L2VPN { 
            description "L2VPN";        
          } 
          enum L3VPN { 
            description "L3VPN";        
          } 
        } 
        description 
             "Indicates the type of VPN instance that the adjusted 
flow belongs to. L2VPN or L3VPN"; 
      } 
      leaf flow-name { 
        type string; 
        description 
          "The name of the adjusted flow. So as to tell the  
           Controller which flow should be adjusted"; 
    } 

    container traffic-steering-policy{ 

      list bandwidth { 
        key "type"; 
        leaf type { 
          type enumeration { 
                 enum utilization { 
              description "the link utilization ratio, 0-
100%"; 
          } 
              enum BW { 
              description "the bandwidth value, 2G,10G 
e.g."; 
              } 
            } 
          } 
        leaf value { 
          type uint32; 
          } 
        } 

      list threshold { 
        key "match"; 
        leaf match {   
          type enumeration { 
                 enum above { 
              description "if the value is above the 
threshold"; 
              } 
              enum below { 
                description "if the value is below the 
threshold"; 
              } 
            } 
          } 
        } 
      container adjust-path { 

        container constraint-nodes { 
            list constraint-node { 

          max-elements unbounded; 
          min-elements 0; 
          description "."; 
          key nodeId; 
        description " List of nodes that the adjusted flow 
needs to pass or bypass So as to adjust the flow path between data 
centers."; 

          leaf nodeId { 
              description "constraint node"; 
              config true; 
              type string { 
              length "0..64"; 
              pattern "([^?]*)"; 
              } 
          } 
          leaf constraint-type { 

            description "The constraint type of the node"; 
            config false; 

            type enumeration { 
              enum bypass { 
                value 0; 
                description "The node will be bypassed"; 
              } 
              enum pass { 
                value 1; 
                description "The node will be passed"; 
              } 
            } 
          } 
          leaf sequence { 
                description "constraint node sequence"; 
                config true; 
                default 1; 
                type uint32 { 
                  range "0..128"; 
                } 
              } 
            } 
          } 
        container constraint-sites { 
          list constraint-site { 

          max-elements unbounded; 
          min-elements 0; 
          description "."; 
          key siteId; 
        description " List of nodes that the adjusted flow 
needs to pass or bypass So as to adjust the flow path between data 
centers."; 

          description 
          " List of sites that the adjusted flow needs to pass or 
bypass So as to adjust the flow path between data centers."; 

          leaf siteId { 
              description "constraint site"; 
              config true; 
              type string { 
              length "0..64"; 
              pattern "([^?]*)"; 
              } 
          } 
          leaf constraint-type { 

            description "The constraint type of the site"; 
            config false; 

            type enumeration { 
              enum bypass { 
                value 0; 
                description "The site will be bypassed"; 
              } 
              enum pass { 
                value 1; 
                description "The site will be passed"; 
              } 
            } 
          } 
          leaf sequence { 
                description "constraint site sequence"; 
                config true; 
                default 1; 
                type uint32 { 
                  range "0..128"; 
                } 
              } 
            } 
          } 
        }  
      } 
    } 
  } 
} 
}
