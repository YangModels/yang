module ietf-isis-remaining-lifetime {
  yang-version 1.1;
  namespace
    "urn:ietf:params:xml:ns:yang:ietf-isis-remaining-lifetime";

  prefix isis-remaining-lifetime;

  import ietf-isis {
    prefix "isis";
    reference
      "RFC 9130: YANG Data Model for the IS-IS Protocol";
  }
  organization
    "IETF LSR - Link State Routing Working Group";

  contact
     "WG Web:   <https://datatracker.ietf.org/wg/lsr>
      WG List:  <mailto:lsr@ietf.org>

      Author:   Yingzhen Qu
                <mailto:yingzhen.ietf@gmail.com>
      Author:   Acee Lindem
                <mailto:acee.ietf@gmail.com>
      Author:   Stephane Litkowski
                <mailto:slitkows.ietf@gmail.com>";

  description
    "This YANG module defines a notification which is sent when the
     IS-IS system detects corrupted lifetime of an LSP. This is for
     IS-IS Minimum Remaining Lifetime feature as defined in RFC 7987.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (http://trustee.ietf.org/license-info).

     This version of this YANG module is part of RFC XXXX;
     see the RFC itself for full legal notices.";

  reference "RFC XXXX";

  revision 2024-09-02 {
    description
      "Initial version";
    reference
      "RFC XXXX: A YANG Data Model for IS-IS Minimum Remaining
      Lifetime.";
  }

  notification corrupt-remaining-lifetime {
    uses isis:notification-instance-hdr;
    leaf lsp-id {
      type isis:lsp-id;
      description "LSP ID";
    }
    description
      "This notification is sent when the system
       detects corrupted lifetime of an LSP.";
    reference "RFC 7987: IS-IS Minimum Remaining Lifetime";
  }
}
