module ietf-http-server {
  yang-version 1.1;
  namespace "urn:ietf:params:xml:ns:yang:ietf-http-server";
  prefix https;

  organization
    "IETF NETCONF (Network Configuration) Working Group";
  contact
    "WG Web:   <http://datatracker.ietf.org/wg/netconf/>
     WG List:  <mailto:netconf@ietf.org>
     Author:   Kent Watsen <mailto:kent+ietf@watsen.net>";
  description
    "This module defines reusable groupings for HTTP servers that
     can be used as a basis for specific HTTP server instances.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 [RFC2119]
     [RFC8174] when, and only when, they appear in all
     capitals, as shown here.

     Copyright (c) 2019 IETF Trust and the persons identified as
     authors of the code. All rights reserved.

     Redistribution and use in source and binary forms, with or
     without modification, is permitted pursuant to, and subject
     to the license terms contained in, the Simplified BSD
     License set forth in Section 4.c of the IETF Trust's
     Legal Provisions Relating to IETF Documents
     (http://trustee.ietf.org/license-info).

     This version of this YANG module is part of RFC XXXX; see
     the RFC itself for full legal notices.";

  revision 2019-03-09 {
    description
      "Initial version";
    reference
      "RFC XXXX: YANG Groupings for HTTP Clients and HTTP Servers";
  }

  // Features

  feature http-server-keepalives {
    description
      "Per socket HTTP keepalive parameters are configurable for
       HTTP servers on the server implementing this feature.";
  }

  // Groupings

  grouping http-server-grouping {
    description
      "A reusable grouping for configuring a HTTP server,
       including the IP address and port number it listens
       for connections on.";
    uses keepalives-grouping;
  }

  grouping keepalives-grouping {
    description
      "A reusable grouping for configuring HTTP server keepalive
       parameters.";
    container http-keepalives {
      if-feature "http-server-keepalives";
      description
        "Configures the keep-alive policy, to proactively test
         the aliveness of the HTTP client.  An unresponsive
         HTTP client is dropped after approximately max-wait
         * max-attempts seconds.";
      leaf max-wait {
        type uint16 {
          range "1..max";
        }
        units "seconds";
        default "30";
        description
          "Sets the amount of time in seconds after which if no
           data has been received from the HTTP client, a HTTP
           level message will be sent to test the aliveness of
           the HTTP client.";
      }
      leaf max-attempts {
        type uint8;
        default "3";
        description
          "Sets the maximum number of sequential keep-alive messages
           that can fail to obtain a response from the HTTP client
           before assuming the HTTP client is no longer alive.";
      }
    }
  }
}
