module ietf-yang-notifications2 {
  yang-version 1.1;
  namespace "urn:ietf:params:xml:ns:yang:ietf-yang-notifications2";
  prefix yn2;

  import ietf-yang-types {
    prefix yang;
  }
  import ietf-subscribed-notifications {
    prefix sn;
  }

  organization "IETF";
  contact
    "WG Web:   <http://tools.ietf.org/wg/netconf/>
     WG List:  <mailto:netconf@ietf.org>

     WG Chair: Lou Berger
               <mailto:lberger@labn.net>

     WG Chair: Kent Watsen
               <mailto:kwatsen@juniper.net>

     Editor:   Eric Voit
               <mailto:evoit@cisco.com>

     Editor:   Alexander Clemm
               <mailto:ludwig@clemm.org>

     Editor:   Tim Jenkins
               <mailto:timjenki@cisco.com>

     Editor:   Andy Bierman
               <mailto:andy@yumaworks.com>";

  description
    "This module contains conceptual YANG specifications for NETCONF
    Event Notifications.";

  revision 2017-02-23 {
    description
      "This module includes several definitions for two new yang
      notification message formats:
      (a) a message format including the definitions for common header
          information prior to notification payload.
      (b) a message format allowing the bundling of multiple
          notifications within it

      It also includes data nodes for querying related information such
      as:
         - ability to see contents of notifications both before and
           after any NACM filtering has been applied.
         - ability to see which message numbers have been sent to which
         receivers.";

    reference
      "draft-voit-netmod-yang-notifications2-00";
  }

  /*
   * IDENTITIES
   */

   /* Identities for notification record types */

   identity notification-record-format {
    description
      "Base identity to represent a different formats for notification
      records.";
  }

  identity system-event {
    base notification-record-format;
    description
      "System XML event";
  }

  identity yang-datastore {
    base notification-record-format;
    description
      "yang tree info";
  }

  identity yang-patch {
    base notification-record-format;
    description
      "yang patch record";
  }

  identity syslog-entry {
    base notification-record-format;
    description
      "Entry into syslog (figure linkage to existing draft.";
  }

  identity alarm {
    base notification-record-format;
    description
      "Alarm (perhaps link draft-sharma-netmod-fault-model-01 for more
      info)";
  }

  /*
   * TYPEDEFs
   */

  typedef notification-record-ref {
    type leafref {
      path "/notification-records/notification-record/record-id";
    }
    description
      "This type is used to reference a notification record (a.k.a.,
      event).";
  }

  typedef receiver-ref {
    type leafref {
      path "/sn:subscriptions/sn:subscription/sn:receivers/"+
      "sn:receiver/sn:address";
    }
    description
      "This type is used to reference a receiver.";
  }

  typedef subscription-ref {
    type leafref {
      path "/sn:subscriptions/sn:subscription/sn:identifier";
    }
    description
      "This type is used to reference a receiver.";
  }

  typedef notification-record-format-type {
    type identityref {
      base notification-record-format;
    }
    description
      "Type of notification record";
  }

  /*
   * GROUPINGS
   */

  grouping notification-message-header {
    description
      "Header information included with a notification.";
    leaf notification-id {
      type uint32;
      description
        "unique id for a notification which may go to one or many
        receivers.";
    }
    leaf signature {
      type string;
      description
        "Any originator signing of the contents of a notification
        message.  This can be useful for originating applications to
        verify record contents even when shipping over unsecure
        transport.";
    }
    leaf message-generator-id {
      type string;
      description
        "Software entity which created the notification message (e.g.,
        linecard 1).";
    }
  }

  grouping notification-message-receiver-header {
    description
      "Header information included with a notification which is
      specific to a receiver.";
    leaf notification-time {
      type yang:date-and-time;
      description
        "time the notification was generated prior to being sent to
        transport.";
    }
    leaf previous-notification-id {
      type uint32;
      description
        "Notification id previously sent by publisher to a specific
        receiver (allows detection of loss/duplication).";
    }
  }

  grouping notification-record-header {
    description
      "Common informational objects which might help a receiver
      interpret the meaning, details, and importance of an event
      notification.";
    leaf record-time {
      type yang:date-and-time;
      mandatory true;
      description
        "Time the system recognized the occurence of an event.";
    }
    leaf record-type {
      type notification-record-format-type;
      description
        "Describes the type of payload included.  This is turn allow
        the interpretation of the record contents.";
    }
    leaf record-id {
      type uint32;
      description
        "Identifier for the notification record.";
    }
    leaf record-severity {
      type string;
      description
        "System assigned severity.  (Likely we need to build/find an
        enumeration of common ones.)";
    }
    leaf observation-domain-id {
      type string;
      description
        "Software entity which created the notification record (e.g.,
        process id).";
    }
  }

  grouping subscribed-notification-record-header {
    description
      "Header information included with a notification.";
    uses notification-record-header;
    leaf subscription-id {
      type uint32;
      description
        "Id of the subscription which led to the notification being
        generated.";
    }
  }

  /*
   * NOTIFICATIONS
   */

  notification notification-message {
    description
      "Notification message to a receiver containing only one event.";
    container notification-message-header {
      description
        "delineates header info from notification messages for easy
        parsing.";
        uses subscribed-notification-record-header;
        uses notification-message-header;
        uses notification-message-receiver-header;
    }
    anydata receiver-record-contents {
      description
        "Non-header info of what actually got sent to receiver after
        security filter.  (Note: Possible to have extra process
        encryption.)";
    }
  }

  notification bundled-notification-message {
    description
      "Notification message to a receiver containing many events,
      possibly relating to independent subscriptions.";
    container bundled-notification-message-header {
        description
            "Delineates header info from notification messages for easy
            parsing.";
        uses notification-message-header;
        uses notification-message-receiver-header {
          refine notification-time {
            mandatory true;
          }
        }
        leaf record-count {
            type uint16;
            description
                "Quantity of events in a bundled-notification-message
                for a specific receiver.  This value is per receiver in
                case an entire notification record is filtered out.";
        }
    }

    list notification-records {
      description
        "Set of messages within a notification to a receiver.";
      container notification-record-header {
        description
          "delineates header info from notification messages for easy
          parsing.";
        uses subscribed-notification-record-header;
      }
      anydata receiver-record-contents {
        description
          "Non-header info of what actually got sent to receiver after
          security filter.  (Note: Possible to have extra process
          encryption.)";

      }
    }
  }

  /*
   * DATA NODES
   */

  container notification-records {
    config false;
    description
      "Maintains instances of event notifications recorded by the
      system.";
    list notification-record {
      key "record-id";
      description
        "Specific instances of event notifications recorded by the
        system.";
      uses notification-record-header {
        refine record-id {
          mandatory true;
        }
        refine record-type {
          mandatory true;
        }
      }
      anydata notification-record-contents {
        mandatory true;
        description
          "Notification event contents independent of any receiver
          security filtering.";
      }
      leaf-list subscription-id {
        type subscription-ref;
        description
          "Instances of subscriptions which should receive or have
          received this event notification record.";
      }
    }
  }
  container notification-messages {
    config false;
    description
      "Contains a history of the notification messages which have been
      generated.";
    list notification-message {
      key "notification-id";
      description
        "Instances of notification messages generated with the intent
        of sending them to one or more receivers.";
      uses notification-message-header {
        refine notification-id {
          mandatory true;
        }
      }
      leaf notification-record {
        type notification-record-ref;
        mandatory true;
        description
          "Included notification. The record itself, or elements of
          this record might not be sent to any included receiver based
          on security permissions for that receiver.";
      }
      container receiver-notification-messages {
        description
          "Contains a history of messages targeted for a receiver.";
         list receiver-notification-message {
          description
            "Maintains instances of messages targeted for a receiver.";
          leaf receiver {
            type receiver-ref;
            description
              "Reference to the recipient targeted for this
              notification message.  (This also allows the unique
              identification of the subscription.)";
          }
          uses notification-message-receiver-header {
            refine notification-time {
              mandatory true;
            }
          }
          anydata receiver-record-contents {
            mandatory true;
            description
              "The specific security filtered contents of one record
              going to a receiver.";
          }
        }
      }
    }
  }
  container bundled-notification-messages {
    config false;
    description
      "Contains a history of bundled notification messages which have
      been generated.";
    list bundled-notification-message {
      key "notification-id";
      min-elements 1;
      description
        "Maintains instances of a bundled notification messages
        generated with the intent of sending them to one or more
        receivers.";
      uses notification-message-header{
        refine notification-id {
          mandatory true;
        }
      }
      container included-notification-records {
          description
          "Contains specific records included in the bundle.";
        list included-notification-record {
          description
            "A specific instance of record included in a bundle.";
          leaf notification-record {
            type notification-record-ref;
            description
              "Included notification within the bundle.  Full records
              or elements of this record might not be sent to any
              included receiver based on security permissions for that
              receiver.";
          }
        }
      }
      container receiver-notification-messages {
          description
          "Contains instances of messages generated for a specific
          receiver.";
         list receiver-notification-message {
          description
            "Maintains instances of bundled messages targeted for a
            receiver.";
           leaf receiver {
            type receiver-ref;
            description
              "Reference to the recipient targeted for this bundled
              notification message.  (As a receiver is unique to a
              subscription, this also identifies the subscription
              explicitly.  If something other than receiver is used, a
              method to identify the subscription is also needed as it
              can't automatically be derived from the notification
              record.";
          }
          uses notification-message-receiver-header {
            refine notification-time {
              mandatory true;
            }
          }
          leaf record-count {
            type uint16;
              description
              "Number of records actually sent to a receiver after
              considering the application of NACM policies on the
              notification records.";
          }
          container included-notification-records {
            description
              "Contains the records sent to a receiver within a
              specific notification message.";
            list notification-record {
              description
                "Maintains instances of records sent to a receiver.";
              anydata receiver-record-contents {
                mandatory true;
                  description
                  "The specific security filtered contents of one
                  record going to a receiver.";
              }
            }
          }
        }
      }
    }
  }
}
