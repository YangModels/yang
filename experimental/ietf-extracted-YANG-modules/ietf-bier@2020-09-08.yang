module ietf-bier {
     yang-version 1.1;
     namespace "urn:ietf:params:xml:ns:yang:ietf-bier";
     prefix "bier";

    import ietf-routing {
       prefix "rt";
     }
    import ietf-interfaces {
      prefix "if";
      reference "RFC7223";
    }
    import ietf-inet-types {
       prefix "inet";
     }

        import ietf-isis{
       prefix "isis";
     }

    import ietf-ospf  {
       prefix "ospf";
     }

     organization
       "IETF BIER(Bit Indexed Explicit Replication ) Working Group";

     contact
        "WG List:  <mailto:bier@ietf.org>

        WG Chair: Tony Przygienda
                  <mailto:tonysietf@gmail.com>

        WG Chair: Greg Shepherd
                  <mailto:gjshep@gmail.com>

        Editor:   Ran Chen
                   <mailto:chen.ran@zte.com.cn>
        Editor:   Fangwei Hu
                   <mailto:hu.fangwei@zte.com.cn>
        Editor:   Zheng Zhang
                   <mailto:zhang.zheng@zte.com.cn>
        Editor:   Xianxian Dai
                   <mailto:dai.xianxian@zte.com.cn>
        Editor:    Mahesh Sivakumar
                   <mailto:masivaku@cisco.com>
        ";
       description
         "The YANG module defines a generic configuration
          model for BIER.";

                revision 2020-09-08{
         description
           "latest revision";
         reference "RFC XXXX: YANG Data Model for BIER Protocol.";
       }

                revision 2019-05-14{
         description
           "latest revision";
         reference "RFC XXXX: YANG Data Model for BIER Protocol.";
       }

                revision 2018-09-29{
         description
           "04 revision";
         reference "RFC XXXX: YANG Data Model for BIER Protocol.";
       }

                revision 2018-02-07{
         description
           "03 revision";
         reference "RFC XXXX: YANG Data Model for BIER Protocol.";
       }

                revision 2017-08-10{
         description
           "02 revision";
         reference "RFC XXXX: YANG Data Model for BIER Protocol.";

       }

        revision 2017-01-20{
         description
           "01 revision";
         reference "RFC XXXX: YANG Data Model for BIER Protocol.";
       }

                revision 2016-07-23{
         description
           "00 revision";
         reference "RFC XXXX: YANG Data Model for BIER Protocol.";
       }

           revision 2016-05-12{
         description
           "04 revision";
         reference "RFC XXXX: YANG Data Model for BIER Protocol.";
       }

       revision 2016-03-16 {
         description
           "03 revision";
         reference "RFC XXXX: YANG Data Model for BIER Protocol.";
       }

       revision 2015-12-03 {
         description
           "02 revision";
         reference "RFC XXXX: YANG Data Model for BIER Protocol.";
       }

       revision 2015-10-16 {
         description
           "01 revision.";
         reference "RFC XXXX: YANG Data Model for BIER Protocol.";
       }

       revision 2015-06-22 {
         description
           "Initial revision.";
         reference "RFC XXXX: YANG Data Model for BIER Protocol.";
     }

     /* Identities */
     identity bier-encapsulation{
       description
         "Base identity for BIER encapsulation.";
     }
     identity bier-encapsulation-mpls {
       base bier-encapsulation;
       description
         "This identity represents MPLS encapsulation for bier.";
     }
         identity bier-encapsulation-ipv6 {
       base bier-encapsulation;
       description
         "This identity represents ipv6 encapsulation for bier.";
     }
     identity bier-encapsulation-ethernet {
       base bier-encapsulation;
       description
         "This identity represents ethernet encapsulation for bier.";
     }
     identity address-family {
       description
         "Base identity from which identities describing address
          families are derived.";
     }
     identity ipv4 {
       base address-family;
       description
         "This identity represents an IPv4 address family.";
     }

     identity ipv6 {
       base address-family;
       description
         "This identity represents an IPv6 address family.";
     }

        /*grouping*/
          grouping bier-protocol-extensions{
             description
                   "Defines protocol extensions.";
                leaf mt-id{
                  type uint16 ;
                  description
                        "Multi-topology associated with bier sub-domain.";
                 }
            container bier {
                  leaf enable {
                    type boolean;
                        default false;
                        description
                          "Enables bier protocol extensions.";
                  }
                  leaf advertise {
                        type boolean;
                        default true;
                        description
                          "Enable to advertise the parameters associated with bier.";
                        }
                  leaf receive {
                        type boolean;
                        default true;
                        description
                          "Enable to receive the parameters associated with bier.";
                        }
                  description
                        "BIER global config.";
                }
           }

         grouping bsl {
        description
                  "The bitstringlength type.";
                leaf bsl {
                  type enumeration{
                     enum "64-bit"{
                   description
                     "bitstringlength is 64";
                        }
                 enum "128-bit"{
                   description
                         "bitstringlength is 128";
                        }
                 enum "256-bit"{
                   description
                     "bitstringlength is 256";
                        }
                 enum "512-bit"{
                         description
                           "bitstringlength is 512";
                        }
                 enum "1024-bit"{
                   description
                     "bitstringlength is 1024";
                        }
                 enum "2048-bit"{
                   description
                     "bitstringlength is 2048";
                        }
                 enum "4096-bit"{
                   description
                     "bitstringlength is 4096";
                        }
                }
                default "256-bit";
                 description
                   "list of the bitstringlength type to be supported.";
       }
          }
        grouping underlay-protocol-type {
         description
           "The underlay protocol type.";
     leaf underlay-protocol-type {
            type enumeration{
        enum "isis" {
                   description
                     "isis protocol";
                        }
                 enum "ospf" {
                   description
                     "ospf protocol";
                        }
                  enum "bgp" {
                   description
                     "bgp protocol";
                        }
                   }
                  description
                   "list of the underlay protocol to be supported.";
                 }
    }

         grouping encapsulation {
           description
             "The Bit Index Forwarding T6able.When MPLS is used as the transport, the Bit Indexed Forwarding Table (BIFT) is identified by a MPLS Label.  When non-MPLS transport is used, the BIFT is identified by a 20bit value.";
            list encapsulation {
                  key "bsl encapsulation-type";
           leaf bsl{
                     type uint16;
                description
                 "The value of the bitstringlength.";
              }

                  leaf encapsulation-type {
                     type identityref {
               base bier-encapsulation;
                          }
                          description
                 "Dataplane to be used.";
                                 }
                  leaf max-si {
                    type uint16;
                description
                      "Maximum Set Identifier .";
                  }
                  leaf bift-id-base {
                   type uint32;
                   description
                     "The value of the bift id.";
                   }
                 description
                   "Different dataplane, different value of the bift-id.";
                 }
        }
        grouping sub-domain {
          description
        "The parameters of the sub domain.";
           list sub-domain {
            key "sub-domain-id address-family";
                leaf sub-domain-id {
               type uint16;
               description
                 "The type for sub-domain-id";
           }
           leaf address-family {
             type identityref {
           base address-family;
         }
         mandatory true;
         description
           "Address family.";
       }

           leaf bfr-prefix {
             type inet:ip-prefix;
             description
           "the bfr prefix.";
       }
        uses underlay-protocol-type;
                leaf mt-id {
                  type uint16;
              description
                "The type for multi-topology identifier";
            }
                leaf bfr-id {
                  type uint16;
              description
                "The type for bfr identifier";
            }
        uses bsl;
                leaf igp-algorithm {
          type uint8;
                  description
                "The type for igp algorithm";
            }
                leaf bier-algorithm {
          type uint8;
                  description
                "The type for bier algorithm";
            }
        leaf load-balance-num {
                  type uint8;
                  description
                "The multicast load balance num.";
            }
        uses encapsulation;
                 description
                "list the parameters of the sub domain.";
                }
                }

        grouping bfr-nbr{
          description "The bfr nbr information, including bfr-nbr, encapsulation type and out-bift-id.";
          leaf bfr-nbr {
             type inet:ip-prefix;
             description
           "the bfr nbr.";
           }
          leaf encapsulation-type {
            type identityref {
              base bier-encapsulation;
                          }
               description
                 "Dataplane to be used.";
                                 }
            leaf out-bift-id{
                  type uint32;
                    description
                      "BIER out-bift-id.";
                    }
                   }

      augment "/rt:routing" {
            description
                  "This augments routing-instance configuration with bier.";
            container bier{
          description
            "bier global configuration.";
                        leaf encapsulation-type {
                     type identityref {
               base bier-encapsulation;
                          }
                          description
                 "Dataplane to be used.";
                                 }
                        uses bsl;
                        leaf bfr-id {
                      type uint16;
                  description
                    "The type for bfr identifier";
                }
                        leaf bfr-prefix {
                type inet:ip-prefix;
                  description
                "the bfr prefix.";
            }
                        uses sub-domain;
                        list birt{
              key "sub-domain-id";
              leaf sub-domain-id{
                type uint16;
                  description
                    "BIER sub domain ID";
                }
               list birt-bitstringlength {
                 key "bitstringlength";
                 leaf bitstringlength{
                   type uint16;
                   description
                     "BIER bitstringlength.";
                }
                list birt-si {
                  key "si";
                  leaf si{
                    type uint16;
                    description
                      "BIER set identifier.";
                   }
                leaf in-bift-id{
                  type uint32;
                    description
                      "BIER in-bift-id.";
                    }
                                uses bfr-nbr;
                description
                   "The BIRT based on the key set identifier";
                                   }
                description
                   "The BIRT based on the key set identifier & bitstringlength";
                    }
                description
                    "The information of the BIRT.";
              }

                        }
                }

     augment "/rt:routing/rt:control-plane-protocols/"
           + "rt:control-plane-protocol/ospf:ospf" {
       when "../rt:type = 'ospf:ospfv2' or
             ../rt:type = 'ospf:ospfv3'" {
         description
           "This augments the ospf routing protocol when used";
         }
       description
         "This augments ospf protocol configuration with bier.";
                container bier-ospf-cfg{
                  uses bier-protocol-extensions;
          description
                        "Control of bier advertisement and reception.";
                }
      }

     augment "/rt:routing/rt:control-plane-protocols/"
             +"rt:control-plane-protocol/isis:isis"{
       when "/rt:routing/rt:control-plane-protocols/"+
           "rt:control-plane-protocol/rt:type = 'isis:isis'" {
         description
         "This augment ISIS routing protocol when used";
       }
       description
         "This augments ISIS protocol configuration with bier.";
                  container bier-isis-cfg{
            uses bier-protocol-extensions;
                        description
                          "Control of bier advertisement and reception.";

                }
      }

          /* Notifications */
      notification bfr-id-collision{
                leaf bfr-id{
                  type uint16;
              description
                "The type for bfr identifier";
           }

           description
                 "BFR ID received in the controlplane that caused BFR ID collision.";
       }

      notification bfr-zero{
                leaf ipv4-bfr-prefix{
                  type inet:ipv4-prefix;
                  description
                        "BIER ipv4 bfr prefix";
         }
                leaf ipv6-bfr-prefix{
                  type inet:ipv6-prefix;
                  description
                        "BIER ipv6 bfr prefix";
        }
                description
                        "Invalid value associated with prefix";
       }

      notification sub-domain-id-collision{
                leaf sub-domain-id {
               type uint16;
               description
                 "The type for sub-domain-id";
           }
                leaf mt-id{
                  type uint16;
                  description
                        "Multi-topology ID";
        }
           description
                 "Sub domain ID received in the controlplane that caused Sub domain ID collision";
       }
     }
