module ietf-data-export-capabilities {
  yang-version 1.1;
  namespace urn:ietf:params:xml:ns:yang:ietf-notification-data-export-capabilities;
  prefix dec;
  import ietf-system-capabilities  { prefix sysc ; }
  import ietf-notification-capabilities { prefix inc; }
  organization
    "IETF NETCONF (Network Configuration) Working Group";
  contact
    "WG Web:   <https://tools.ietf.org/wg/netconf/>
     WG List:  <mailto:netconf@ietf.org>
     Editor:   Ran Tao
               <mailto:taoran20@huawei.com>
               Qin Wu
               <mailto:bill.wu@huawei.com";
  description
    "This module defines an extension to System Capability and YANG Push
     Notification Capabilities model and provides additional data export
    attributes for transport dependent capability negotiation.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";
     /* Identities */
      identity transport-protocol {
       description
        "Base identity for transport protocol type.";
      }

     identity tcp {
      base transport-protocol;
       description
        "Identity for tcp transport protocol.";
     }

     identity udp {
       base transport-protocol;
       description
        "Identity for udp transport protocol.";
     }

     identity grpc {
       base transport-protocol;
       description
        "Identity for grpc transport protocol.";
     }

      identity security-protocol {
       description
        "Base identity for security protocol type.";
      }

     identity tls {
      base security-protocol;
       description
        "Identity for tls security protocol.";
     }

     identity ssh {
       base security-protocol;
       description
        "Identity for ssh transport protocol.";
     }

      identity encoding-format {
       description
        "Base identity for encoding format type.";
      }

     identity xml {
      base encoding-format;
       description
        "Identity for xml encoding format.";
     }

     identity json {
       base encoding-format;
       description
        "Identity for json encoding format.";
     }

     identity gpb {
       base encoding-format;
       description
        "Identity for gpb encoding format.";
     }
     identity cbor {
       base encoding-format;
       description
        "Identity for cbor encoding format.";
     }
      identity compression-mode {
       description
        "Base identity for compression mode.";
      }

     identity gzip {
      base security-protocol;
       description
        "Identity for gzip compression mode.";
     }

     identity deflate {
       base security-protocol;
       description
        "Identity for deflate compression mode.";
     }

      identity subscription-mode {
       description
        "Base identity for subscription mode.";
      }

     identity periodic {
      base subscription-mode;
       description
        "Identity for periodic subscription mode.";
     }

     identity on-change {
       base subscription-mode;
       description
        "Identity for on change subscription mode.";
     }
    identity event {
       base subscription-mode;
       description
        "Identity for event based subscription mode.";
     }
    augment /sysc:system-capabilities {
     description "Add system level capability.";
        container data-export-capabilities {
      description "Capabilities related to transport dependent capability negotiation.";
        leaf transport-protocol {
              type identityref {
               base transport-protocol;
            }
           description
            "Type of transport protocol.";
         }
         leaf encoding-format {
           type identityref {
              base encoding-format;
           }
           description
             "Type of encoding format.";
         }
         leaf security-protocol {
          type identityref {
             base security-protocol;
          }
          description
           "Type of secure transport.";
         }
       leaf compression-mode{
         type identityref {
            base compression-mode;
         }
         description
          "Type of compression mode.";
      }
      leaf max-nodes-per-sensor-group {
        type uint32 {
              range "1..max";
        }
        description
          "Maximum number of selected data nodes that can be sent
           per sensor group.";
      }
      leaf max-sensor-group-per-update {
        type uint32 {
              range "1..max";
        }
        description
          "Maximum number of sensor groups that can be sent
           in an update.";
      }
    }
  }
    augment /sysc:system-capabilities/inc:subscription-capabilities {
     description "Add subscription level capability.";
         leaf message-bundling-support {
           type boolean;
            default false;
            description
             "Enables message bundling support.";
          }
         leaf subscription-mode {
              type identityref {
               base subscription-mode;
            }
           description
            "Type of subscription mode.";
         }
  }
    augment /sysc:system-capabilities/sysc:datastore-capabilities/sysc:per-node-capabilities {
     description "Add datastore and node level capability.";
        leaf-list sampling-interval {
          type uint32;
          units "centiseconds";
          description "Time-based start and stop triggers
          are used to define the Sampling intervals.  All packets
          are selected that arrive at the Observation Point within
          the time intervals defined by the start and stop triggers
          (i.e., arrival time of the packet is larger than the start
          time and smaller than the stop time).";
           reference
         "RFC 5475: Sampling and Filtering Techniques for IP Packet
         Selection";
        }
      leaf threshold-support {
         type boolean;
         default false;
         description
         "Set to true if the subscription mode is event based
         subscription mode.  Set to false
         if event based subscription mode is not supported.";
      }
  }
}
