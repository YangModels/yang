module ietf-actn-vn {
 namespace "urn:ietf:params:xml:ns:yang:ietf-actn-vn";
 prefix "vn";

 /* Import network */
 import ietf-network {
     prefix "nw";
 }

 /* Import TE generic types */
 import ietf-te-types {
     prefix "te-types";
 }

 /* Import Abstract TE Topology */
 import ietf-te-topology {
     prefix "tet";
 }

 organization
     "IETF Traffic Engineering Architecture and Signaling (TEAS)
     Working Group";
 contact
     "Editor: Young Lee <leeyoung@huawei.com>
            : Dhruv Dhody <dhruv.ietf@gmail.com>";
 description
     "This module contains a YANG module for the ACTN VN. It
     describes a VN operation module that takes place in the
     context of the CNC-MDSC Interface (CMI) of the ACTN
     architecture where the CNC is the actor of a VN
     Instantiation/modification /deletion.";
 revision 2018-02-24 {
     description
         "initial version.";
     reference
         "TBD";
 }
 /*
  * Features
  */
 feature multi-src-dest {
     description
       "Support for selection of one src or destination
       among multiple.";
 }

 /*identity path-metric-delay {
    base te-types:path-metric-type;
    description
      "delay  path metric";
  }
  identity path-metric-delay-variation {
    base te-types:path-metric-type;
    description
      "delay-variation path metric";
  }
  identity path-metric-loss {
    base te-types:path-metric-type;
    description
      "loss path metric";
  }*/

  identity vn-state-type {
    description
      "Base identity for VN state";
  }
  identity vn-state-up {
      base vn-state-type;
      description "VN state up";
  }
  identity vn-state-down {
      base vn-state-type;
      description "VN state down";
  }
  identity vn-admin-state-type {
      description
        "Base identity for VN admin states";
  }
  identity vn-admin-state-up {
      base vn-admin-state-type;
      description "VN administratively state up";
  }
  identity vn-admin-state-down {
      base vn-admin-state-type;
      description "VN administratively state down";
  }
  identity vn-compute-state-type {
      description
        "Base identity for compute states";
  }
  identity vn-compute-state-computing {
      base vn-compute-state-type;
      description
        "State path compute in progress";
  }
  identity vn-compute-state-computation-ok {
      base vn-compute-state-type;
      description
        "State path compute successful";
  }
  identity vn-compute-state-computatione-failed {
      base vn-compute-state-type;
      description
        "State path compute failed";
  }
 /*
  * Groupings
  */
 grouping vn-ap {
     description
         "VNAP related information";
     leaf vn-ap-id {
         type uint32;
         description
             "unique identifier for the referred
             VNAP";
     }
     leaf vn {
         type leafref {
            path "/actn/vn/vn-list/vn-id";
         }
         description
              "reference to the VN";
     }
       leaf abstract-node {
            type leafref {
                 path "/nw:networks/nw:network/nw:node/"
                 + "tet:te-node-id";
                 }
            description
                 "a reference to the abstract node in TE
                 Topology";
       }
     leaf ltp {
         type te-types:te-tp-id;
         description
             "Reference LTP in the TE-topology";
     }
 }
 grouping access-point{
     description
         "AP related information";
     leaf access-point-id {
         type uint32;
         description
             "unique identifier for the referred
             access point";
     }
     leaf access-point-name {
         type string;
         description
             "ap name";
     }

     leaf max-bandwidth {
         type te-types:te-bandwidth;
         description
             "max bandwidth of the AP";
     }
     leaf avl-bandwidth {
         type te-types:te-bandwidth;
         description
             "available bandwidth of the AP";
     }
     /*add details and any other properties of AP,
     not associated by a VN
     CE port, PE port etc.
     */
     list vn-ap {
          key vn-ap-id;
          uses vn-ap;
          description
              "list of VNAP in this AP";
     }
 }//access-point
 grouping vn-member {
     description
         "vn-member is described by this container";
     leaf vn-member-id {
         type uint32;
         description
             "vn-member identifier";
     }
     container src
     {
         description
             "the source of VN Member";
         leaf src {
             type leafref {
                 path "/actn/ap/access-point-list/access-point-id";
             }
             description
                 "reference to source AP";
         }
         leaf src-vn-ap-id{
             type leafref {
                 path "/actn/ap/access-point-list/vn-ap/vn-ap-id";
             }
             description
                 "reference to source VNAP";
         }
         leaf multi-src {
             if-feature multi-src-dest;
             type boolean;
             description
                 "Is source part of multi-source, where
                 only one of the source is enabled";
         }
     }
     container dest
     {
         description
             "the destination of VN Member";
         leaf dest {
             type leafref {
                 path "/actn/ap/access-point-list/access-point-id";
             }
             description
                 "reference to destination AP";
         }
         leaf dest-vn-ap-id{
             type leafref {
                 path "/actn/ap/access-point-list/vn-ap/vn-ap-id";
             }
             description
                 "reference to dest VNAP";
         }
         leaf multi-dest {
             if-feature multi-src-dest;
             type boolean;
             description
                 "Is destination part of multi-destination, where
                 only one of the destination is enabled";
         }
     }
     leaf connetivity-matrix-id{
         type leafref {
             path "/nw:networks/nw:network/nw:node/tet:te/"
             + "tet:te-node-attributes/"
             + "tet:connectivity-matrices/"
             + "tet:connectivity-matrix/tet:id";
         }
         description
             "reference to connetivity-matrix";
     }
 }//vn-member
 /*
 grouping policy {
     description
         "policy related to vn-member-id";
     leaf local-reroute {
         type boolean;
         description
             "Policy to state if reroute
             can be done locally";
     }
     leaf push-allowed {
         type boolean;
         description
             "Policy to state if changes
             can be pushed to the customer";
     }
     leaf incremental-update {
         type boolean;
         description
             "Policy to allow only the
             changes to be reported";
     }
 }//policy
 */
 /*
 grouping metrics-op {
     description
         "metric related information";
     list metric{
         key "metric-type";
         config false;
         description
             "The list of metrics for VN";
         leaf metric-type {
             type identityref {
                 base te-types:path-metric-type;
             }
             description
                 "The VN metric type.";
         }
         leaf value{
             type uint32;
             description
                 "The limit value";
         }
     }
 }
 */
 /*
 grouping metrics {
     description
         "metric related information";
     list metric{
         key "metric-type";
         description
             "The list of metrics for VN";
         uses te:path-metrics-bounds_config;
         container optimize{
             description
                 "optimizing constraints";
             leaf enabled{
                 type boolean;
                 description
                     "Metric to optimize";
              }
              leaf value{
                  type uint32;
                  description
                     "The computed value";
             }
         }
     }
 }
 */
 /*
 grouping service-metric {
     description
         "service-metric";
     uses te:path-objective-function_config;
     uses metrics;
     uses te-types:common-constraints_config;
     uses te:protection-restoration-params_config;
     uses policy;
 }//service-metric
 */
 /*
  * Configuration data nodes
  */
 container actn {
     description
         "actn is described by this container";
     container ap {
         description
             "AP configurations";
      list access-point-list {
             key "access-point-id";
             description
                 "access-point identifier";
             uses access-point{
                 description
                     "access-point information";
             }
      }
     }
     container vn {
         description
             "VN configurations";
         list vn-list {
             key "vn-id";
             description
                 "a virtual network is identified by a vn-id";
             leaf vn-id {
                 type uint32;
                 description
                     "a unique vn identifier";
             }
             leaf vn-name {
                 type string;
                 description "vn name";
             }
             leaf vn-topology-id{
                 type te-types:te-topology-id;
                 description
                     "An optional identifier to the TE Topology
                      Model where the abstract nodes and links
                      of the Topology can be found for Type 2
                      VNS";
             }
             leaf abstract-node {
                  type leafref {
                    path "/nw:networks/nw:network/nw:node/"
                         + "tet:te-node-id";
                  }
                  description
                    "a reference to the abstract node in TE
                     Topology";
             }
             list vn-member-list{
                 key "vn-member-id";
                 description
                     "List of VN-members in a VN";
                 uses vn-member;
                 /*uses metrics-op;*/
                 leaf oper-status {
                     type identityref {
                         base vn-state-type;
                     }
                     config false;
                     description
                         "VN-member operational state.";
                 }

             }
               leaf if-selected{
                 if-feature multi-src-dest;
                   type boolean;
                   default false;
                 config false;
                   description
                       "Is the vn-member is selected among the
                        multi-src/dest options";
               }
             /*
             container multi-src-dest{
                 if-feature multi-src-dest;
                 config false;
                 description
                     "The selected VN Member when multi-src
                     and/or mult-destination is enabled.";
                 leaf selected-vn-member{
                     type leafref {
                         path "/actn/vn/vn-list/vn-member-list"
                              + "/vn-member-id";
                     }
                     description
                         "The selected VN Member along the set
                         of source and destination configured
                         with multi-source and/or multi-destination";
                 }
             }
             */
             /*uses service-metric;*/
             leaf admin-status {
                 type identityref {
                     base vn-admin-state-type;
                 }
                 default vn-admin-state-up;
                 description "VN administrative state.";
             }
             leaf oper-status {
                 type identityref {
                     base vn-state-type;
                 }
                 config false;
                 description "VN operational state.";
             }
         }//vn-list
     }//vn
 }//actn
 /*
 * Notifications - TBD
 */
 /*
 * RPC
 */
 rpc  vn-compute{
     description
         "The VN computation without actual
         instantiation";
     input {
       leaf abstract-node {
             type leafref {
               path "/nw:networks/nw:network/nw:node/"
                    + "tet:te-node-id";
               }
               description
                    "a reference to the abstract node in TE
                     Topology";
         }
         list vn-member-list{
             key "vn-member-id";
             description
                 "List of VN-members in a VN";
             uses vn-member;
         }
         /*uses service-metric;*/
     }
     output {
         list vn-member-list{
             key "vn-member-id";
             description
                 "List of VN-members in a VN";
             uses vn-member;
               leaf if-selected{
                 if-feature multi-src-dest;
                   type boolean;
                   default false;
                   description
                       "Is the vn-member is selected among
                        the multi-src/dest options";
               }
             /*uses metrics-op;*/
             leaf compute-status {
                 type identityref {
                     base vn-compute-state-type;
                 }
                 description
                     "VN-member compute state.";
             }
         }
         /*
         container multi-src-dest{
             if-feature multi-src-dest;
             description
                 "The selected VN Member when multi-src
                 and/or mult-destination is enabled.";
             leaf selected-vn-member-id{
                 type uint32;
                 description
                     "The selected VN Member-id from the
                     input";
             }
         }*/
     }
 }
}
