module abstract-topology {
  yang-version 1;
  namespace "urn:ietf:params:xml:ns:yang:abstract-topology";
  // replace with IANA namespace when assigned

  prefix "abst";

  import ietf-yang-types {
    prefix "yang";
  }

  import network-topology {
    prefix "nt";
  }

  import l3-unicast-igp-topology {
    prefix "l3t";
  }

  import ted {
    prefix "ted";
  }

  organization "TBD";
  contact "TBD";
  description "Abstract topology model";

  revision "2014-07-01" {
    description "Initial revision";
    reference "TBD";
  }

  grouping abstract-topology-type {
    description
      "Identifies the abstract topology type.";
    container abstract {
      presence "indicates abstract topology";
      description
        "Its presence identifies the abstract topology type.";
    }
  }

  augment "/nt:network-topology/nt:topology/nt:topology-types/"
          + "l3t:l3-unicast-igp-topology" {
    description
      "Defines the abstract topology type.";
    uses abstract-topology-type;
  }

  grouping te-path-element {
    description
      "A group of attributes defining an element in a TE path";
    leaf loose {
      type boolean;
      description "true if the element is loose.";
    }
    choice element-type {
      description "Attributes for various element types.";
      case numbered-link {
        leaf link-ipv4 {
          type uint32;
          description "IPv4 address in 4 byte integer format.";
        }
      }
      case unnumbered-link {
        leaf link-node-id {
          type uint32;
          description
            "Node ID of the node where the link end point resides.";
        }
        leaf link-id {
          type uint32;
          description "Identifies the link end point";
        }
      }
      case node {
        leaf node-id {
          type uint32;
          description "Identifies the node.";
        }
      }
      case label {
        leaf label {
          type uint32;
          description "Identifies the label";
        }
      }
    }
  } // te-path-element

  grouping config-schedule-attributes {
    description
      "A list of schedules defining when a particullar
       configuration takes effect.";
    list schedules {
      key "schedule-id";
      description "A list of schedule elements.";
      leaf schedule-id {
        type uint32;
        description "Identifies the schedule element.";
      }
      leaf start {
        type yang:date-and-time;
        description "Start time.";
      }
      leaf schedule-duration {
        type string {
          pattern
            'P(\d+Y)?(\d+M)?(\d+W)?(\d+D)?T(\d+H)?(\d+M)?(\d+S)?';
        }
        description "Schedule duration in ISO 8601 format.";
      }
      leaf repeat-interval {
        type string {
          pattern
            'R\d*/P(\d+Y)?(\d+M)?(\d+W)?(\d+D)?T(\d+H)?(\d+M)?'
            + '(\d+S)?';
        }
        description "Repeat interval in ISO 8601 format.";
     }
    }
  }

  grouping abstract-node-attributes {
    description "Node attributes in an abstract topology.";
    container abstract-node-attributes {
      description "Node attributes in an abstract topology.";
      uses config-schedule-attributes;
      leaf is-virtual {
        type boolean;
        description "true if the node is virtual.";
      }
      leaf underlay-topology {
        type nt:topology-ref;
        description
          "When a node contains a topology, such as a virtual node,
           this reference points to the topology that defines the
           topology inside this node.";
      }
      list connectivity-matrix {
        key "from-tp to-tp";
        description
          "Representation of the limit to the connectivity within
           the node";
        leaf from-tp {
          type nt:tp-ref;
          description
            "Reference to source connectivity point.";
        }
        leaf to-tp {
          type nt:tp-ref;
          description
            "Reference to destination connectivity point.";
        }
      }
      container ted {
        description "Includes TE node attributes.";
        uses ted:ted-node-attributes;
      }
    }
  } // abstract-node-attributes

  grouping abstract-tp-attributes {
    description
      "Termination point attributes in an abstract topology.";
    container abstract-tp-attributes {
      description
        "Termination point attributes in an abstract topology.";
      leaf node-ref {
        type nt:node-ref;
        description "Node where this termination point resides.";
      }
    }
  } // abstract-tp-attributes

  grouping abstract-link-attributes {
    description "Link attributes in an abstract topology.";
    container abstract-link-attributes {
      description "Link attributes in an abstract topology.";
      uses config-schedule-attributes;
      leaf advertising-node-src {
        type nt:node-id;
        description
          "The node that advertises the source link end point";
      }
      leaf advertising-node-des {
        type nt:node-id;
        description
          "The node that advertises the destination link end point";
      }
      leaf is-virtual {
        type boolean;
        description "truel if the link is virtual.";
      }
      leaf-list melg {
        type uint32;
        config false;
        description "A list of MELG values of the link.";
      }
      leaf-list srclg {
        type uint32;
        config false;
        description "A list of SRcLG values of the link.";
      }
      container server-path {
        description
          "The service path on the server layer that supports this
           link.";
        list path-element {
          key "path-element-id";
          description
            "A list of path elements describing the service path";
          leaf path-element-id {
            type uint32;
            description "To identify the element in a path.";
          }
          uses te-path-element;
        }
      } // server-path
      container server-backup-path {
        description
          "The backup service path on the server layer that
           supports this link.";
        list path-element {
          key "path-element-id";
          description
            "A list of path elements describing the backup service
             path";
          leaf path-element-id {
            type uint32;
            description "To identify the element in a path.";
          }
          uses te-path-element;
        }
      } // server-backup-path
      leaf server-protection-type {
        type uint16;
        description
          "Server layer protection type desired for this link";
      }
      leaf server-trail-src {
        type nt:tp-ref;
        description
          "Source termination point of the server layer trail.";
      }
      leaf server-trail-des {
        type nt:tp-ref;
        description
          "Destination termination point of the server layer
           trail.";
      }
      container ted {
        description "Includes TE link attributes.";
        uses ted:ted-link-attributes;
      }
    }
  } // abstract-link-attributes

  augment "/nt:network-topology/nt:topology/nt:node/"
          + "nt:termination-point/"
          + "l3t:igp-termination-point-attributes" {
    when "../../../topology-types/abstract-topology" {
      description
        "The augment is valid only for abstract topology.";
    }
    description "Augments attributes on a termination point.";
    uses abstract-tp-attributes;
  }

  augment "/nt:network-topology/nt:topology/nt:node/"
          + "l3t:igp-node-attributes" {
    when "../../topology-types/abstract-topology" {
      description
        "The augment is valid only for abstract topology.";
    }
    description "Augments attributes on a node.";
    uses abstract-node-attributes;
  }

  augment "/nt:network-topology/nt:topology/nt:link/"
          + "l3t:igp-link-attributes" {
    when "../../topology-types/abstract-topology" {
      description
        "The augment is valid only for abstract topology.";
    }
    description "Augments attributes on a link.";
    uses abstract-link-attributes;
  }

  augment "/l3t:igp-node-event" {
    description "Augments node event.";
    uses abstract-topology-type;
    uses abst:abstract-node-attributes;
  }

  augment "/l3t:igp-link-event" {
    description "Augments link event.";
    uses abstract-topology-type;
    uses abst:abstract-link-attributes;
  }
}
