module ietf-mpls-l2vpn {
  namespace "urn:ietf:params:xml:ns:yang:ietf-mpls-l2vpn";
  prefix "mpls-l2vpn";

  import ietf-inet-types {
    prefix "inet";
  }

  organization  "ietf";
  contact       "ietf";
  description   "mpls-l2vpn";
  revision "2015-06-30" {
    description "Initial revision";
    reference   "";
  }

  /* identities */

  identity link-discovery-protocol {
    description "Base identiy from which identities describing " +
                "link discovery protocols are derived.";
  }

  identity lacp {
    base "link-discovery-protocol";
    description "This identity represents LACP";
  }

  identity lldp {
    base "link-discovery-protocol";
    description "This identity represents LLDP";
  }

  identity bpdu {
    base "link-discovery-protocol";
    description "This identity represens BPDU";
  }

  identity cpd {
    base "link-discovery-protocol";
    description "This identity represents CPD";
  }

  identity udld {
    base "link-discovery-protocol";
    description "This identity represens UDLD";
  }
  /* typedefs */

  typedef l2vpn-service-type {
    type enumeration {
      enum ethernet {
        description "Ethernet service";
      }
      enum ATM {
        description "Asynchronous Transfer Mode";
      }
      enum FR {
        description "Frame-Relay";
      }
      enum TDM {
        description "Time Division Multiplexing";
      }
    }
    description "L2VPN service type";
  }

  typedef l2vpn-discovery-type {
    type enumeration {
      enum manual {
        description "Manual configuration";
      }
      enum bgp-ad {
        description "Border Gateway Protocol (BGP) auto-discovery";
      }
    }
    description "L2VPN discovery type";
  }

  typedef l2vpn-signaling-type {
    type enumeration {
      enum static {
        description "Static configuration of labels (no signaling)";
      }
      enum ldp {
        description "Label Distribution Protocol (LDP) signaling";
      }
      enum bgp {
        description "Border Gateway Protocol (BGP) signaling";
      }
    }
    description "L2VPN signaling type";
  }

  typedef bgp-rt-type {
    type enumeration {
      enum import {
        description "For import";
      }
      enum export {
        description "For export";
      }
      enum both {
        description "For both import and export";
      }
    }
    description "BGP route-target type. Import from BGP YANG";
  }

  typedef cw-negotiation-type {
    type enumeration {
      enum "non-preferred" {
        description "No preference for control-word";
      }
      enum "preferred" {
        description "Prefer to have control-word negotiation";
      }
    }
    description "control-word negotiation preference type";
  }

  typedef link-discovery-protocol-type {
    type identityref {
      base "link-discovery-protocol";
    }
    description "This type is used to identify " +
                "link discovery protocol";
  }

  typedef pw-template-ref {
    type leafref {
      path "/l2vpn/common/pw-templates/pw-template/name";
    }
    description "pw-template-ref";
  }

  typedef ac-template-ref {
    type leafref {
      path "/l2vpn/common/ac-templates/ac-template/name";
    }
    description "ac-tempalte-ref";
  }

  /* groupings */

  grouping vpws-endpoint {
    description
      "A vpws-endpoing could either be an ac or a pw";
    choice ac-or-pw-or-redundancy-grp {
      description "A choice ofattachment circuit or " +
                  "pseudowire or redundancy group";
      case ac {
        leaf ac {
          type leafref {
            path "../../ac/name";
          }
          description "reference to an attachment circuit";
        }
      }
      case pw {
        leaf pw {
          type leafref {
            path "../../pw/name";
          }
          description "reference to a pseudowire";
        }
      }
      case redundancy-grp {
        choice primary {
          mandatory true;
          description "primary options";
          case primary-pw  {
            leaf primary-pw {
              type leafref {
                path "../../pw/name";
              }
              description "primary pseudowire";
            }
          }
          case primary-ac {
            leaf primary-ac {
              type leafref {
                path "../../ac/name";
              }
              description "primary attachment circuit";
            }
          }
        }
        choice backup {
          mandatory true;
          description "backup options";
          case backup-pw {
            leaf backup-pw {
              type leafref {
                path "../../pw/name";
              }
              description "backup pseudowire";
            }
          }
          case backup-ac {
            leaf backup-ac {
              type leafref {
                path "../../ac/name";
              }
              description "backup attachment circuit";
            }
          }
        }
        leaf protection-mode {
          type enumeration {
            enum "frr" {
              value 0;
              description "fast reroute";
            }
            enum "master-slave" {
              value 1;
              description "master-slave";
            }
            enum "independent" {
              value 2;
              description "independent";
            }
          }
          description "protection-mode";
        }
      }
      leaf reroute-mode {
        type enumeration {
          enum "immediate" {
            value 0;
            description "immediate reroute";
          }
          enum "delayed" {
            value 1;
            description "delayed reroute";
          }
          enum "never" {
            value 2;
            description "never reroute";
          }
        }
        description "reroute-mode";
      }
      leaf reroute-delay {
        when "../reroute-mode = 'delayed'" {
          description
            "Specify amount of time to delay reroute " +
            "only when delayed route is configured";
        }
        type uint16;
        description
          "amount of time to delay reroute";
      }
      leaf dual-receive {
        type boolean;
        description
          "allow extra traffic to be carried by backup";
      }
      leaf revert {
        type boolean;
        description
          "allow forwarding to revert to primary " +
          "after restoring primary";
        /* This is called "revertive" during the discussion. */
      }
      leaf revert-delay {
        when "../revert = 'true'" {
          description
            "Specify the amount of time to wait to revert " +
            "to primary only if reversion is configured";
        }
        type uint16;
        description
          "amount ot time to wait to revert to primary";
        /* This is called "wtr" during discussion. */
      }
    }
  }

  /* We can define vpls-endpoing-grp that has the same structure as
   * vpws-endpoing-grp, but has more endpoint options.
   */

  /* L2VPN YANG Model */

  container l2vpn {
    description "l2vpn";
    container common {
      description "common l2pn attributes";
      container pw-templates {
        description "pw-templates";
        list pw-template {
          key "name";
          description "pw-template";
          leaf name {
            type string;
            description "name";
          }
          leaf mtu {
            type uint32;
            description "pseudowire mtu";
          }
          leaf cw-negotiation {
            type cw-negotiation-type;
            default "preferred";
            description
              "control-word negotiation preference";
          }
          leaf tunnel-policy {
            type string;
            description "tunnel policy name";
          }
        }
      }
      container ac-templates {
        description "attachment circuit templates";
        /* To be fleshed out in future revisions */
        list ac-template {
          key "name";
          description "ac-template";
          leaf name {
            type string;
            description "name";
          }
        }
      }
    }
    container vpws-instances {
      description "vpws-instances";
      list vpws-instance {
        key "instance-name";
        description "A VPWS instance";
        leaf instance-name {
          type string;
          description "Name of VPWS instance";
        }
        leaf description {
          type string;
          description "Description of the VPWS instance";
        }
        leaf service-type {
          type l2vpn-service-type;
          default ethernet;
          description "VPWS service type";
        }
        leaf discovery-type {
          type l2vpn-discovery-type;
          default manual;
          description "VPWS discovery type";
        }
        leaf signaling-type {
          type l2vpn-signaling-type;
          mandatory true;
          description "VPWS signaling type";
        }
        container bgp-parameters {
          description "Parameters for BGP";
          container common {
            when "../../discovery-type = 'bgp-ad'" {
              description "Check discovery type: " +
                          "Can only configure BGP discovery if " +
                          "discovery type is BGP-AD";
            }
            description "Common BGP parameters";
            leaf route-distinguisher {
              type string;
              description "BGP RD";
            }
            list vpn-targets {
              key rt-value;
              description "Route Targets";
              leaf rt-value {
                type string;
                description "Route-Target value";
              }
              leaf rt-type {
                type bgp-rt-type;
                mandatory true;
                description "Type of RT";
              }
            }
          }
          container discovery {
            when "../../discovery-type = 'bgp-ad'" {
              description "BGP parameters for discovery: " +
                          "Can only configure BGP discovery if " +
                          "discovery type is BGP-AD";
            }
            description "BGP parameters for discovery";
            leaf vpn-id {
              type string;
              description "VPN ID";
            }
          }
          container signaling {
            when "../../signaling-type = 'bgp'" {
              description "Check signaling type: " +
                          "Can only configure BGP signaling if " +
                          "signaling type is BGP";
            }
            description "BGP parameters for signaling";
            leaf site-id {
              type uint16;
              description "Site ID";
            }
            leaf site-range {
              type uint16;
              description "Site Range";
            }
          }
        }
        list pw {
          key "name";
          description "pseudowire";
          leaf name {
            type string;
            description "pseudowire name";
          }
          leaf cw-negotiation {
            type cw-negotiation-type;
            default "preferred";
            description "Override the control-word negotiation " +
                        "preference specified in the " +
                        "pseudowire template.";
          }
          leaf template {
            type pw-template-ref;
            description "pseudowire template";
          }
          leaf vccv-ability {
            type boolean;
            description "vccvability";
          }
          leaf tunnel-policy {
            type string;
            description "Used to override the tunnel policy name " +
                        "specified in the pseduowire template";
          }
          leaf request-vlanid {
            type uint16;
            description "request vlanid";
          }
          leaf vlan-tpid {
            type string;
            description "vlan tpid";
          }
          leaf ttl {
            type uint8;
            description "time-to-live";
          }
          choice pw-type {
            description "A choice of pseudowire type";
            case ldp-pw {
              leaf peer-ip {
                type inet:ip-address;
                description "peer IP address";
              }
              leaf pw-id {
                type uint32;
                description "pseudowire id";
              }
              leaf transmit-label {
                type uint32;
                description "transmit lable";
              }
              leaf receive-label {
                type uint32;
                description "receive label";
              }
              leaf icb {
                type boolean;
                description "inter-chassis backup";
              }
            }
            case bgp-pw {
              leaf remote-pe-id {
                type inet:ip-address;
                description "remote pe id";
              }
            }
            case bgp-ad-pw {
              leaf remote-ve-id {
                type uint16;
                description "remote ve id";
              }
            }
          }
        }
        list ac {
          key "name";
          description "attachment circuit";
          leaf name {
            type string;
            description "name";
          }
          leaf template {
            type ac-template-ref;
            description "attachment circuit template";
          }
          leaf pipe-mode {
            type enumeration {
              enum "pipe" {
                value 0;
                description "regular pipe mode";
              }
              enum "short-pipe" {
                value 1;
                description "short pipe mode";
              }
              enum "uniform" {
                value 2;
                description "uniform pipe mode";
              }
            }
            description "pipe mode";
          }
          leaf link-discovery-protocol {
            type link-discovery-protocol-type;
            description "link discovery protocol";
          }
        }
        container endpoint-a {
          description "endpoint-a";
          uses vpws-endpoint;
        }
        container endpoint-z {
          description "endpoint-z";
          uses vpws-endpoint;
        }
      }
    }
    container vpls-instances {
      /* To be fleshed out in future revisions */
      description "vpls-instances";
    }
  }
}
