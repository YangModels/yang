module ietf-l2svc {

   namespace "urn:ietf:params:xml:ns:yang:ietf-l2svc";
   prefix "l2svc";

   import ietf-inet-types {
     prefix inet;
   }
   import ietf-yang-types {
        prefix yang;
   }
   organization
     "IETF L2SM Working Group.";

   contact
     "WG List:
      Editor: ";

   description
     "The YANG module defines a generic service configuration
     model for Layer 2 VPN common across all of the vendor
     implementations.";

   revision 2016-08-30{
     description
       "Initial revision.";
     reference
       "draft-XXXX
        A YANG Data Model for layer 2 VPN.";
   }

   /* Feature*/

   feature carrierscarrier {
     description
     "Enables support of carrier&apos;s carrier";
   }

   feature site-diversity {
     description
       "Enables support of site diversity constraints";
   }

     feature encryption {
       description
         "Enables support of encryption";
     }

   /* Typedefs*/

   typedef control-mode {
     type enumeration{
       enum peer{
         description
           "peer mode";
     }
     enum tunnel {
       description
         "tunnel mode";
     }
     enum discard {
       description
         "discard mode";
     }
    }

    description
      "defining a type of the control mode";
   }

   /* identity */
   identity vpn-signaling-type {
     description
       "identity of vpn signaling types";
   }

   identity vrf {
     base vpn-signaling-type;
     description
       "Virtual routing and forwarding (VRF).";
   }

   identity vfi {
     base vpn-signaling-type;
     description
       "Virtual forwarder interface";
   }

   identity evi {
     base vpn-signaling-type;
     description
       "ehternet virtual interconnect.";
   }

   identity l2vpn-type {
     description
       "layer 2 vpn types";
   }

   identity vpws {
     base l2vpn-type;
     description
       "Virtual Private Wire Service";
   }

   identity vpls {
     base l2vpn-type;
     description
       "Virtual Private LAN Service";
   }

   identity evpn {
     base l2vpn-type;
     description
       "Ethernet VPN";
   }

   identity management {
     description
       "Base identity for site management scheme.";
   }
   identity co-managed {
     base management;
     description
       "Base identity for comanaged site.";
   }

   identity customer-managed {
     base management;
     description
       "Base identity for customer managed site.";
   }

   identity provider-managed {
     base management;
     description
       "Base identity for provider managed site.";
   }

   identity address-family {
     description
       "Base identity for an address family.";
   }

   identity ipv4 {
     base address-family;
     description
       "Identity for IPv4 address family.";
   }

   identity ipv6 {
     base address-family;
     description
       "Identity for IPv6 address family.";
   }

   identity vpn-topology {
     description
       "Base identity for VPN topology.";
   }

   identity any-to-any {
     base vpn-topology;
     description
       "Identity for any to any VPN topology.";
   }

   identity hub-spoke {
     base vpn-topology;
     description
       "Identity for Hub&apos;n&apos;Spoke VPN topology.";
   }

   identity hub-spoke-disjoint {
     base vpn-topology;
     description
       "Identity for Hub&apos;n&apos;Spoke VPN topology
        where Hubs cannot talk between each other.";
   }

   identity site-role {
     description
       "Base identity for site type.";
   }

   identity any-to-any-role {
     base site-role;

     description
       "Site in a any to any IPVPN.";
   }

   identity spoke-role {
     base site-role;
     description
       "Spoke Site in a Hub &amp; Spoke IPVPN.";
   }

   identity hub-role {
     base site-role;
     description
       "Hub Site in a Hub &amp; Spoke IPVPN.";
   }

   identity pm-type{
    description
        "performance monitor type";
   }

   identity loss {
    base pm-type;
        description
        "loss measurement";
   }

   identity delay {
    base pm-type;
        description
        "delay measurement";
   }

    identity fault-alarm-defect-type {
     description
         "indicating the alarm priority defect";
    }
      identity remote-rdi {
          base fault-alarm-defect-type;
      description
          "Indicates the aggregate health of the remote MEPs.";
      }
      identity remote-mac-error {
      base fault-alarm-defect-type;
          description
          "Indicates that one or more of the remote MEPs is
      reporting a failure in its Port Status TLV or
      Interface Status TLV.";
      }
      identity remote-invalid-ccm {
      base fault-alarm-defect-type;
          description
          "Indicates that at least one of the Remote MEP
      state machines is not receiving valid CCMs
      from its remote MEP.";
      }
      identity invalid-ccm {
      base fault-alarm-defect-type;
          description
          "Indicates that one or more invalid CCMs has been
      received and that 3.5 times that CCMs transmission
      interval has not yet expired.";
      }
      identity cross-connect-ccm {
      base fault-alarm-defect-type;
          description
          "Indicates that one or more cross connect CCMs has been
       received and that 3.5 times of at least one of those
       CCMs transmission interval has not yet expired.";
      }

   /*groupings*/

   grouping customer-info-grouping {
     list customer-info {
       key "customer-account-number customer-name";
       leaf customer-account-number {
         type string;
         description
           "customer account number";
       }
       leaf customer-name {
         type string;
         description
           "customer name";
       }
       container customer-operation-center {
         leaf customer-noc-street-address {
           type string;
           description
             "customer NOC street Address.";
         }
         container customer-noc-phone-number {
           leaf main-phone-num {
             type uint32;
             description
               "main phone number.";
           }
           leaf extension-options {
             type uint32;
             description
               "extension or options";
           }

           description
             "configuration of customer noc phone number";
         }
         description
           "configuration of customer operation center";
       }
       description
         "list of customer information";
     }
     description
       "grouping for customer information";
   }

   grouping topology-grouping{
     leaf topology {
        type identityref {
          base vpn-topology;
        }
        default "any-to-any";
        description
          "VPN topology.";
     }
     description
       "grouping for topology parameters";
   }

   grouping vpn-service-mpls {
     leaf carrierscarrier {
       if-feature carrierscarrier;
       type boolean;
       default false;
       description
         "The VPN is using Carrier&apos;s Carrier,
          and so MPLS is required.";
     }
     description
       "grouping for mpls CsC definition";
   }

   grouping site-management {
     container management {
       leaf site-name {
         type string;
         description
           "site name";
       }
       leaf address {
         type inet:ip-address;

         description
         "address";
       }
       leaf ce-device-info {
         type string;
         description
           "CE device info";
       }
       leaf type {
         type identityref {
           base management;
         }
         description
           "Management type of the connection.";
       }
       leaf management-transport {
         type identityref {
           base address-family;
         }
         description
           "Transport protocol used for management.";
       }
       description
         "Management configuration";
     }
     description
       "Management parameters for the site.";
   }

   grouping customer-location-info {
     container location {
       leaf address {
         type string;
         description
           "Address (number and street) of the site.";
       }
       leaf zip-code {
         type string;
         description
           "ZIP code of the site.";
       }
       leaf state {
         type string;
         description
           "State of the site. This leaf can also be used
            to describe a region for country who does not have
            states.";
         }
       leaf city {

         type string;
         description
           "City of the site.";
       }
       leaf country-code {
         type string;
         description
           "Country of the site.";
       }
       description
         "Location of the site.";
     }
     description
       "This grouping defines customer location
        parameters";
    }

    grouping site-diversity {
      container site-diversity {
        if-feature site-diversity;
        container groups {
          list group {
            key group-id;
            leaf group-id {
              type string;
              description
                "Group-id the site is belonging to";
              }
            description
              "List of group-id";
          }
          description
            "Groups the site is belonging to.
             All site network accesses will
             inherit those group values.";
        }
        description
          "Diversity constraint type.";
      }
      description
        "This grouping defines site diversity
         parameters";
    }

    grouping site-service{

        leaf svlan-id-ethernet-tag {
                  type string;
          description
            "SVLAN-ID/Ethernet Tag configurations";
        }
        list cvlan-id-to-evc-map {
                  key map-id;
            leaf map-id {
              type string;
              description
                "Group-id the site is belonging to";
              }
          description
            "List of CVLAN-ID to EVC Map configurations";
        }
        leaf service-level-mac-limit {
                type string;
          description
            "Service-level MAC-limit (E-LAN only)";
        }
       /* container service-level {
          leaf cos-identifier {
            type string;
            description
              "COS Identifier [ EVC | EVC + PCP ]";
          }
          leaf color-identifier {
            type string;
            description
              "Color Identifier [ EVC | EVC + CVLAN ]";
          }
          leaf ingress-bw-profile-per-evc {
            type string;
            description
              "Ingress Bandwidth Profile per EVC";
          }
          leaf ingress-bw-profile-per-cos-id {
            type string;
            description
              "Ingress Bandwidth Profile per COS Identifier";
          }
          leaf egress-bw-profile-per-evc {
            type string;
            description
              "Egress Bandwidth Profile per EVC";
          }
          leaf egress-bw-profile-per-cos-id {
            type string;
            description
              "Egress Bandwidth Profile per COS Identifier";
          }
                  leaf byte-offset{
                    type uint16;
                        description
                        "For not including extra VLAN tags in
                         the QoS calculation";
                  }
          leaf COS{
            type uint32;
            description
              "Class of Service";
          }
          description
            "Container of service level configurations.";

        } */

      description
        "This grouping defines site service parameters";
    }

    grouping service-protection{
      container service-protection {
        container protection-model {
          description
            "Container of protection model configurations";
        }
        container peer-evc-id {
          description
            "Container of peer evc id configurations";
        }
        description
          "Container of End-to-end Service Protection
          configurations";
      }
      description
        "Grouping for service protection";
    }

    grouping ethernet-service-type {
      choice ethernet-svc-type {
        case e-line {
          leaf epl {
            type boolean;
            description
              "Ethernet private line";
          }
          leaf evpl {
            type boolean;
            description
              "Ethernet virtual private line";
          }
          description
            "Case of e-line";
        }
        case e-lan {
          leaf ep-lan {
            type boolean;
            description
              "Ethernet private LAN";
          }
          leaf evp-lan {

            type boolean;
            description
              "Ethernet virtual private lan";
          }
          description
            "Case of e-lan";
        }
        case e-access {
          leaf access-epl {
            type boolean;
            description
              "Access ethernet virtual private line";
          }
          leaf access-evpl {
            type boolean;
            description
              "Access ethernet virtual private line";
          }
          description
            "Case of e-access.";
        }
        description
          "Choice of ethernet service type";
      }
      description
        "Grouping for ethernet service type.";
    }

    grouping signaling-option-grouping {
      list signaling-option {
        key "name type";
        leaf name {
          type string;
          description
            "VRF/VFI/EVI Name";
        }
        leaf type {
          type identityref {
            base vpn-signaling-type;
          }
          description
            "VPN signaling types";
        }
        container mp-bgp-l2vpn {
            leaf vpn-id {
              type string;
              description
                "Identifies the target VPN";
            }
            leaf type {
              type identityref {
                base l2vpn-type;
              }
              description
                "L2VPN types";
            }
          description
          "Container for mp bgp l2vpn";
        }

        container mp-bgp-evpn {
            leaf vpn-id {
              type string;
              description
                "Identifies the target VPN";
            }
            leaf type {
              type identityref {
                base l2vpn-type;
              }
              description
                "L2VPN types";
            }
          description
          "Container for mp bgp l2vpn";
        }

        container t-ldp-pwe {
          list PE-EG-list {
            key "service-ip-lo-addr vc-id";
            leaf service-ip-lo-addr {
              type inet:ip-address;
              description
                "Service ip lo address";
            }
            leaf vc-id {
              type string;
              description
              "VC id";
            }
            description
              "List of PE/EG";
          }
          description
            "Container of T-LDP PWE configurations";

        }
                container pwe-encapsulation-type {
            leaf ethernet {
              type boolean;
              description
                "Ethernet";
            }
            leaf vlan {
              type boolean;
              description
                "VLAN";
            }
            description
            "Container of PWE Encapsulation Type configurations";
          }
         container pwe-mtu {
            leaf allow-mtu-mismatch {
              type boolean;
              description
                "Allow MTU mismatch";
            }
            description
            "Container of PWE MTU configurations";
          }
                container control-word {
            description
              "Container of control word configurations";
          }
        description
          "List of VPN Signaling Option.";
      }
      description
        "Grouping for signaling option";
    }

            grouping load-balance-grouping{
          container load-balance-option {
            leaf fat-pw {
              type boolean;
              description
                "Fat label is applied to Pseudowires
                 across MPLS network";
            }
            leaf entropy-label {
              type boolean;
              description
                "Entropy label is applied to IP forwarding,
                 L2VPN or L3VPN across MPLS network";
            }
            description
              "Container of load balance option";
          }
                  description
                  "grouping for load balance ";
        }

   grouping intra-mkt-grouping {
     list intra-mkt {
       key "metro-mkt-id mkt-name";
       leaf metro-mkt-id {
         type uint32;
         description
           "Metro MKT ID";
       }
       leaf mkt-name {
         type string;
         description
           "MKT Name";
       }
       description
         "List of intra-MKT";
     }
     description
       "Grouping for intra-MKT";
   }

   grouping oam-service{
          container Ethernet-Service-OAM {
         list uni-n2-uni-n {
           key "MD-name MD-level";
           leaf MD-name{
                    type string;
                        description
                        "Maintenance domain name";
                   }
                   leaf MD-level {
                    type uint8;
                        description
                        "Maintenance domain level";
                   }

                    leaf alarm-priority-defect {
             type identityref{
                         base fault-alarm-defect-type;
                         }
             description
             "The lowest priority defect that is
                         allowed to generate a Fault Alarm.
                         The non-existence of this leaf means
                         that no defects are to be reported";
                        }

           description
            "List of UNI-N to UNI-N";
         }
       description
         "Container for ehternet service oam";
     }
         description
         "grouping for oam service.";
   }
   grouping inter-mkt-service {
     leaf inter-mkt-service{
          type boolean;
          description
          "indicate whether service is inter market service.";
         }
     description
       "Grouping for inter-MKT service";
   }

   grouping evc-id-grouping {
     leaf evc-id {
       type boolean;
       description
         "Ethernet Virtual Connection identifier";
     }
     description
       "Grouping for EVC-ID";
   }

   grouping svc-type-grouping {
     container svc-type {
       container evc {
         leaf evc-id {
           type boolean;
           description
             "Indicate whether the Ethernet virtual connection
              id support.";
         }
         description
           "container for ethernet virtual connection";
       }
       container ovc {
             leaf on-net-ovc-id {
               type boolean;
               description
                 "Indicate whether the on net ovc id support.";
             }

             leaf off-net-ov-id {
               type boolean;
               description
                 "Indicate whether the off net ovc id support.";
             }
                         description
                         "container for ovc";
           }
           description
       "Container for servic types";
       }
     description
       "Grouping of service types.";
     }

   grouping cfm-802-grouping {
     leaf MAID {
       type string;
       description
         "MA ID";
     }
     leaf mep-level {
       type uint32;
       description
         "MEP level";
     }
     leaf mep-up-down {
       type enumeration {
         enum up {
           description
             "MEP up";
         }
         enum down {
           description
             "MEP down";
         }
       }
       description
         "MEP up/down";
     }
     leaf remote-mep-id {
       type uint32;
       description
         "Remote mep id";
     }
     leaf cos-for-cfm-pdus {
       type uint32;
       description
         "COS for CFM PDUs";
     }
     leaf ccm-interval {
       type uint32;
       description
         "CCM interval";
     }
     leaf ccm-holdtime {
       type uint32;
       description
         "CCM hold time";
     }
         leaf alarm-priority-defect {
       type identityref{
            base fault-alarm-defect-type;
           }
       description
       "The lowest priority defect that is
        allowed to generate a Fault Alarm.
            The non-existence of this leaf means
            that no defects are to be reported";
         }
     description
       "Grouping for 802.1ag CFM attribute";
   }

   grouping enni-site-info-grouping {
     container site-info {
       leaf site-name {
         type string;
         description
           "Site name";
       }
       leaf address {
         type inet:ip-address;
         description
           "Address";
       }
       leaf Edge-Gateway-Device-Info {
         type string;
         description
           "Edge Gateway Device Info ";
       }
       description
         "Container of site info configurations";
     }
     description
       "Grouping for site information";
   }

   grouping site-security-authentication {
     container authentication {
       description
         "Authentication parameters";
     }
     description
       "This grouping defines authentication parameters
        for a site";
   }

   grouping site-security-encryption {
     container encryption {
       if-feature encryption;
       leaf enabled {
         type boolean;
         description
           "If true, access encryption is required.";
       }
       leaf layer {
         type enumeration {

           enum layer2 {
             description
               "Encryption will occur at layer2.";
           }
           enum layer3 {
             description
               "IPSec is requested.";
           }
         }
         description
           "Layer on which encryption is applied.";
       }
       container encryption-profile {
         choice profile {
           case provider-profile {
             leaf profile-name {
               type string;
               description
                 "Name of the SP profile to be applied.";
             }
           }
           case customer-profile {
             leaf algorithm {
               type string;
               description
                 "Encryption algorithm to be used.";
             }
             choice key-type {
               case psk {
                 leaf preshared-key {
                   type string;
                   description
                     "Key coming from customer.";
                 }
               }
               case pki {
               }
               description
                 "Type of keys to be used.";
             }
           }
           description
             "Choice of profile.";
         }
         description
           "Profile of encryption to be applied.";
       }
       description

         "Encryption parameters.";
     }
     description
       "This grouping defines encryption parameters
        for a site";
   }

   grouping site-security {
     container security {
       uses site-security-authentication;
       uses site-security-encryption;
       description
         "Site specific security parameters.";
     }
     description
       "Grouping for security parameters.";
   }

   grouping port-info-grouping {
     container bearer {
       container phy-interface {
         leaf port-number {
           type uint32;
           description
             "Port number";
         }
         leaf port-speed {
           type uint32;
           description
             "Port speed";
         }
         leaf auto-neg {
           type string;
           description
             "Auto neg";
         }
         leaf phy-mtu {
           type uint32;
           description
            "PHY MTU";
         }
         leaf flow-control {
           type string;
           description
             "Flow control";
         }
         leaf encapsulation-type {
           type enumeration {
             enum VLAN {
               description
                 "VLAN";
             }
             enum Ethernet {
               description
                 "Ethernet";
             }
           }
           description
             "Encapsulation-type";
         }
         leaf ethertype {
           type string;
           description
             "Ethertype";
         }
         leaf lldp {
           type string;
           description
             "LLDP";
         }
         leaf oam-802.3AH-link {
           type string;
           description
             "802.3AH-link-OAM";
         }
                 leaf uni-loop-prevention{
                   type boolean;
                   description
                   "if this leaf set to truth that
                   the port automatically goes down when
                   a physical loopback is detect.";
                 }
         description
           "Container of PHY Interface Attributes configurations";
       }
       container LAG-interface {
         list LAG-interface {
           key "LAG-interface-number";
           leaf LAG-interface-number {
             type uint32;
             description
               "LAG interface number";
           }
           container LACP {
             leaf LACP-on-off {
               type enumeration {
                 enum on{
                   description
                    "LACP ON";
                 }
                 enum off{
                   description
                    "LACP OFF";
                 }
               }
               description
                 "LACP on/off";
             }
             leaf LACP-mode {
               type enumeration {
                 enum active {
                 description
                   "Active mode";
               }
               enum passive {
                 description
                   "Passive mode";
               }
             }
             description
               "LACP mode";
           }
           leaf LACP-speed {
             type enumeration {
               enum fast {
                 description
                   "Fast";
               }
               enum slow {
                 description
                   "Slow";
               }
             }
             description
               "LACP speed";
           }
           leaf mini-link {
             type uint32;
             description
               "Mini link";
           }
                   leaf system-priority{
                    type uint32;
                        description
                        "indicates the LACP priority for the system.
                        The range is from 0 to 65535.
                        The default is 32768.";
                   }
           container Micro-BFD {
             leaf Micro-BFD-on-off {
               type enumeration {
                 enum on {
                   description
                     "Micro-bfd on";
                 }
                 enum off {
                   description
                     "Micro-bfd off";
                 }
               }
               description
                 "Micro BFD ON/OFF";
             }
             leaf bfd-interval {
               type uint32;
               description
                 "BFD interval";
             }
             leaf bfd-hold-timer {
               type uint32;
               description
               "BFD hold timer";
             }
             description
             "Container of Micro-BFD configurations";
           }
           container Member-link-list {
             list member-link {
               key "name";
               leaf name {
                 type string;
                 description
                   "Member link name";
               }
               leaf port-speed {
                 type uint32;
                 description
                   "Port speed";
               }
               leaf auto-neg {
                 type string;
                 description
                   "Auto neg";
               }
               leaf mtu {
                 type uint32;
                 description
                   "MTU";
               }
               leaf oam-802.3AH-link {
                 type string;
                 description
                   "802.3AH-link-OAM";
               }
               description
                 "Member link";
             }
             description
               "Container of Member link list";
           }
           leaf flow-control {
             type string;
             description
               "Flow control";
           }
           leaf encapsulation-type {
             type enumeration {
               enum VLAN {
                 description
                   "VLAN";
               }
               enum ether {
                 description
                   "Ether";
               }
             }
             description
               "Encapsulation type";
           }
           leaf ethertype {
             type string;
             description
               "Ether type";
           }
           leaf lldp {
             type string;
             description
               "LLDP";
           }
           description
             "LACP";
         }
         description
           "List of LAG interfaces";
       }
       description
         "Container of LAG interface attributes configuration";
     }
     leaf interface-description {
       type string;
       description
         "Interface description";
     }
     leaf sub-if-id {
       type uint32;
       description
         "Sub-if id";
     }

     description
       "Container for bearer";
   }
   container ethernet-connection {
       container vlan {
             leaf svlan-id-ethernet-tag {
                  type string;
          description
            "SVLAN-ID/Ethernet Tag configurations";
        }
        list cvlan-id-to-evc-map {
                  key map-id;
            leaf map-id {
              type string;
              description
                "Group-id the site is belonging to";
              }
          description
            "List of CVLAN-ID to EVC Map configurations";
        }
         description
           "Abstract container for vlan";
       }
       container oam {
               leaf MD-name{
                    type string;
                        description
                        "Maintenance domain name";
                   }
                   leaf MD-level {
                    type uint8;
                        description
                        "Maintenance domain level";
                   }
         description
           "Abstract container for oam";
       }
       description
         "Container for ethernet connection";
   }
   leaf evc-mtu {
     type uint32;
     description
       "EVC MTU";
   }
   container mac-addr-limit {
     leaf exceeding-option {
       type uint32;
       description
         "Exceeding option";
     }
     description
       "Container of MAC-Addr limit configurations";
   }
   container S-vlan {
     leaf c-vlan2evc-mapping {
       type string;
       description
         "C-VLAN to EVC mapping";
     }
     description
       "Container of S-VLAN configurations";
   }
   container multihoming {
     list multihoming {
       key "ESI";
       leaf ESI{
         type string;
         description
           "Ethernet segment id";
       }
       choice redundancy-mode {
         case single-active {
           leaf single-active {
             type boolean;
             description
               "Single active";
           }
           description
             "Single active case";
         }
         case all-active {
           leaf all-active {
             type boolean;
             description
               "All active";
           }
           description
             "All active case";
         }
         description
           "Redundancy mode";
       }
       description
         "List of multihomings";
     }
     description
       "Container of multihoming optional configurations";
   }
   container L2CP-control {
     leaf stp-rstp-mstp {
       type control-mode;
       description
         "STP/RSTP/MSTP";
     }
     leaf pause {
       type control-mode;
       description
         "Pause";
     }
     leaf lacp-lamp {
       type control-mode;
       description
         "LACP/LAMP";
     }
     leaf link-oam {
       type control-mode;
       description
         "Link OAM";
     }
     leaf esmc {
       type control-mode;
       description
         "ESMC";
     }
     leaf l2cp-802.1x {
       type control-mode;
       description
         "802.x";
     }
     leaf e-lmi {
       type control-mode;
       description
         "E-LMI";
     }
     leaf lldp {
       type control-mode;
       description
         "LLDP";
     }
     leaf ptp-peer-delay {
       type control-mode;
       description
         "PTP peer delay";
     }
     leaf garp-mrp {
       type control-mode;
       description
         "GARP/MARP";
     }
         leaf provider-bridge-group{
           type yang:mac-address;
           description
           "provider bridge group reserved MAC address
           01-80-C2-00-00-08";
         }
         leaf provider-bridge-mvrp{
           type yang:mac-address;
           description
           "provider bridge mvrp reserved MAC address
           01-80-C2-00-00-0D";
         }
     description
       "Container of L2CP control configurations";
   }
   container service{
   uses site-service;
   description
   "container for site service.";
                  container service-level {
          leaf cos-identifier {
            type string;
            description
              "COS Identifier [ EVC | EVC + PCP ]";
          }
          leaf color-identifier {
            type string;
            description
              "Color Identifier [ EVC | EVC + CVLAN ]";
          }
          leaf ingress-bw-profile-per-evc {
            type string;
            description
              "Ingress Bandwidth Profile per EVC";
          }
          leaf ingress-bw-profile-per-cos-id {
            type string;
            description
              "Ingress Bandwidth Profile per COS Identifier";
          }
          leaf egress-bw-profile-per-evc {
            type string;
            description
              "Egress Bandwidth Profile per EVC";
          }
          leaf egress-bw-profile-per-cos-id {
            type string;
            description
              "Egress Bandwidth Profile per COS Identifier";
          }
                  leaf byte-offset{
                    type uint16;
                        description
                        "For not including extra VLAN tags in
                         the QoS calculation";
                  }

          leaf COS{
            type uint32;
            description
              "Class of Service";
          }
          description
            "Container of service level configurations.";
        }
   }
   container B-U-M-strom-control {
     description
       "Container of B-U-M-strom-control configurations";
   }
   container mac-loop-prevention{
    description
        "container of mac loop prevention.";
   }
     container Ethernet-Service-OAM {
       container cfm-802.1-ag {
         list uni-n2uni-c {
           key "MAID";
           uses cfm-802-grouping;
           description
             "List of NUI-N to NUI-C";
         }
         list uni-n2-uni-n {

           key "MAID";
           uses cfm-802-grouping;
           description
            "List of UNI-N to UNI-N";
         }
         description
           "Container of 802.1ag CFM configurations";
       }
       list y-1731 {
         key MAID;
         leaf MAID {
           type string;
           description
             "MA ID ";
         }
                 leaf type {
                  type identityref{
                   base pm-type;
                  }
                  description
                  "performance monitor types";
                 }
                 leaf remote-mep-id {
                  type uint32;
                  description
                  "remote mep identifier";
                 }
                 leaf measurement-interval{
                  type uint32;
                  description
                  "measurement interval";
                 }
                 leaf cos {
                  type uint32;
                  description
                  "class of service";
                 }
                 leaf frame-size{
                  type uint32;
                  description
                  "frame size";
                 }
         description
           "List for y-1731.";
       }
       description
         "Container for ehternet service oam";
     }
     container security {
       uses site-security;
       description
         "Container of security configurations";
     }
     //uses site-attachment-availability;
     description
       "Grouping for port info";
   }

 /*  grouping site-attachment-availability {
     container availability {
       leaf access-priority {
         type uint32;
         default 1;
         description
           "Defines the priority for the access. The highest the
            priority value is, the highest the preference of the
            access is.";
       }
       description
         "Availability parameters (used for multihoming)";
     }
     description
       "Defines site availability parameters.";
   }*/

   /* MAIN L2VPN SERVICE */
   container l2vpn-svc {

     /* CUSTOMER */
     container customer-info {
       uses customer-info-grouping;
       description
         "Container of customer information configurations";
     }

     /* SERVICE */
     container vpn-services {
       list vpn-svc {
         key "svc-id";
         leaf svc-id {
           type string;
           description
             "Defining a service id.";
         }
         uses svc-type-grouping;
            /* list uni{
             key uni-id;
             leaf uni-id{
              type leafref{
               path "/l2vpn-svc/site/uni-sites/uni-site/site-id";
              }
              description
              "uni id";
             }
             description
             "list of uni";
            } */

         container ethernet-svc-type {
           uses ethernet-service-type;
           description
             "Container of ethernet service type";
         }
         container metro-network-id {
                   uses inter-mkt-service;
           uses intra-mkt-grouping;
           description
             "Container of Metro-Network ID configurations";
         }
                 container signaling-option {
           uses signaling-option-grouping;
           description
           "Container for signaling option";
         }
                 uses load-balance-grouping;
                 uses site-service;
         /* container Ethernet-Service-OAM {
         list uni-n2-uni-n {
           key "MD-name MD-level";
           leaf MD-name{
                    type string;
                        description
                        "Maintenance domain name";
                   }
                   leaf MD-level {
                    type uint8;
                        description
                        "Maintenance domain level";
                   }
           description
            "List of UNI-N to UNI-N";
         }
       description
         "Container for ehternet service oam";
     } */
             uses service-protection;
         //uses topology-grouping;
         //uses vpn-service-mpls;
         description
           "List of vpn-svc";
       }
       description
         "Container of vpn-services configurations";
     }

     /* SITE */
     container site {
       container uni-sites {
         list uni-site {
           key "site-id";
           leaf site-id {
             type string;
             description
               "Container of site id";
           }
           uses site-management;
           uses customer-location-info;
           uses site-diversity;

           uses site-security;

                   /*container service{
           uses site-service;

                    description
                        "container for site service.";
                        uses oam-service;
                   } */
           //uses service-protection;
           container signaling-option {
             uses signaling-option-grouping;
             description
               "Container for signaling option";
           }
                   uses load-balance-grouping;
           container uni-ports {
             list uni-port {
               key "uni-id";
               leaf uni-id {
                 type string;
                 description
                   "UNI id";
               }
               uses port-info-grouping;
               description
                 "List of uni ports";
             }
             description
               "Container of uni port configurations";
           }
           description
             "List of uni sites";
         }
         description
           "Container of uni site configurations";
       }
       container enni-sites {
         list enni-site {
           key "site-id";
           leaf site-id {
             type string;
             description
               "Container of site id";
           }
           uses customer-location-info;
           uses site-diversity;
           container management {
             leaf site-name {
               type string;
               description
                 "Site name";
             }
             leaf address {
               type inet:ip-address;
               description
                 "Address";
             }
             leaf Edge-Gateway-Device-Info {
               type string;
               description
                 "Edge Gateway Device Information";
             }
             leaf type {
               type identityref {
                 base management;
               }
               description
                 "Management type of the connection.";
             }
             leaf management-transport {
               type identityref {
                 base address-family;
               }
               description
                 "Transport protocol used for management.";
             }
             description
               "Management configuration";
           }

             uses site-security;
           uses service-protection;
           container signaling-option {
             uses signaling-option-grouping;
             description
               "Container for signaling option";
           }
                   uses load-balance-grouping;
           container enni-ports {
             list enni-port {
               key "enni-id";
               leaf enni-id {
                 type string;
                 description
                 "ENNI id";
               }
                           leaf remote-carrier-name{
                            type string;
                                description
                                "remote carrier name";
                           }
               uses port-info-grouping;
               description
                 "List of enni ports";
             }
             description
               "Container of ENNI port configurations";
           }
           description
             "List of ENNI sites";
         }
         description
           "Container of ENNI site configurations";
       }
       description
        "Container for site configurations";
     }
     description
       "Container of l2vpn-svc configurations";
   }
   }
