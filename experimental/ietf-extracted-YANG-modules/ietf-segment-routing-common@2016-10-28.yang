module ietf-segment-routing-common {
  namespace "urn:ietf:params:xml:ns:"
          + "yang:ietf-segment-routing-common";
  prefix sr-cmn;

  import ietf-inet-types {
    prefix "inet";
  }

  organization
   "IETF SPRING Working Group";
  contact
    "WG List:  <mailto:spring@ietf.org>

    Editor:    Stephane Litkowski
               <mailto:stephane.litkowski@orange.com>

    Author:    Acee Lindem
               <mailto:acee@cisco.com>
    Author:    Yingzhen Qu
               <mailto:yiqu@cisco.com>
    Author:    Pushpasis Sarkar
               <mailto:pushpasis.ietf@gmail.com>
    Author:    Jeff Tantsura
               <jefftant.ietf@gmail.com>

    ";

  description
    "The YANG module defines a collection of types and groupings for
    Segment routing.";

  revision 2016-10-28 {
    description "
      * Add support of MSD (Maximum SID Depth)
      * Update contact info
    ";
    reference
      "RFC XXXX: YANG Data Model for Segment Routing.";
  }

  revision 2016-10-24 {
    description "Initial";
    reference
      "RFC XXXX: YANG Data Model for Segment Routing.";
  }

  /* Identities */
  identity segment-routing-transport {
    description
    "Base identity for segment routing transport.";
  }
  identity segment-routing-transport-mpls {
    base segment-routing-transport;
    description
    "This identity represents MPLS transport for segment
    routing.";
  }

  identity prefix-sid-algorithm {
    description
    "Base identity for prefix-sid algorithm.";
  }

  identity prefix-sid-algorithm-shortest-path {
    base prefix-sid-algorithm;
    description
    "The default behavior of prefix-sid algorithm.";
  }

  identity prefix-sid-algorithm-strict-spf {
    base prefix-sid-algorithm;
    description
    "This algorithm mandates that the packet is forwared
     according to ECMP-aware SPF algorithm.";
  }

  /* Features */

  feature sid-last-hop-behavior {
    description
      "Configurable last hop behavior.";
  }

  /* Groupings */

  grouping srgb-cfg {
    list srgb {
      key "lower-bound upper-bound";
      ordered-by user;
      leaf lower-bound {
        type uint32;
        description
          "Lower value in the block.";
      }
      leaf upper-bound {
        type uint32;
        description
          "Upper value in the block.";
      }
      description
        "List of global blocks to be
         advertised.";
    }
    description
      "Grouping for SRGB configuration.";
  }
  grouping sid-value-type {
    leaf value-type {
      type enumeration {
        enum index {
          description
            "The value will be
             interpreted as an index.";
        }
        enum absolute {
          description
            "The value will become
             interpreted as an absolute
             value.";
        }
      }
      default index;
      description
        "This leaf defines how value
         must be interpreted.";
    }
        description
         "Defines how the SID value is expressed.";
  }

  grouping ipv4-sid-cfg {

    leaf prefix {
      type inet:ipv4-prefix;
      description
        "connected prefix sid.";
    }

    uses prefix-sid-attributes;

    description
     "This grouping defines cfg of prefix SID.";
  }

  grouping ipv6-sid-cfg {
    leaf prefix {
      type inet:ipv6-prefix;
      description
        "connected prefix sid.";
    }

    uses prefix-sid-attributes;

    description
     "This grouping defines cfg of prefix SID.";
  }

  grouping last-hop-behavior {
    leaf last-hop-behavior {
      if-feature sid-last-hop-behavior;
      type enumeration {
        enum explicit-null {
          description
            "Use explicit-null for the SID.";
        }
        enum no-php {
          description
            "Do no use PHP for the SID.";
        }
        enum php {
            description
             "Use PHP for the SID.";
        }
      }
      description
        "Configure last hop behavior.";
    }
        description
         "Defines last hop behavior";
  }

  grouping node-capabilities {
    description "Containing SR node capabilities.";
    container node-capabilities {
      list transport-planes {
        key transport-plane;
        leaf transport-plane {
          type identityref {
            base segment-routing-transport;
          }
          description
            "Transport plane supported";
        }
        description
          "List of supported transport planes.";
      }
      leaf readable-label-stack-depth {
        type uint8;
        description
          "Number of MPLS labels that
           can be read in the stack.";
      }
      description
        "Shows the SR capability of the node.";
    } // node-capabilities
  } // sr-node-capabilities

  grouping prefix-sid-attributes {
    description "Containing SR attributes for a prefix.";

    uses sid-value-type;
    leaf start-sid {
      type uint32;
      mandatory true;
      description
        "Value associated with
         prefix. The value must
         be interpreted in the
         context of value-type.";
    }

    leaf range {
      type uint32;
      description
        "Describes how many SIDs could be
         allocated.";
    }

    leaf algorithm {
      type identityref {
        base prefix-sid-algorithm;
      }
      description "Prefix-sid algorithm.";
    }
  } //prefix-sid-attributes
}
