module ietf-nvo3-base {
  namespace "urn:ietf:params:xml:ns:yang:ietf-nvo3-base";
  //namespace need to be assigned by IANA
  prefix "nvo3";
  import ietf-inet-types {
    prefix "inet";
  }
  organization "IETF NVO3 Working Group";
  contact "vero.zheng@huawei.com
    zhangmingui@huawei.com
    habby.zheng@huawei.com";
  description "nvo3 yang module";
  revision "2015-12-16" {
    description
      "Initial version";
    reference "RFC 7364";
  }

  typedef flags-vxlan {
    type bits {
      bit validVni {
        position 4;	    
        description
          "Valid VNI.";
      }
    }
    description
      "VXLAN flags";
  }

  typedef  flags-nvgre {
    type bits {
      bit zero{
        position 0;
        description
          "Zero.";
      }
      bit KeyPresent{
        position 2;
        description
          "Key present.";	  
      }
      bit three{
        position 3;
        description
          "Three.";	  
      }
    }
    description
      "NVGRE flags";	
  }

  container nvo3Nves {
    list nvo3Nve {
      key "ifName";
      leaf ifName {
        type string;
        mandatory "true";
        description
          "Interface name.";		
      }
      leaf srcAddr {
        type inet:ip-address;
        description
          "Local NVE address.";    		
      }
      choice encapType{
        case vxlan{
          leaf srcUdpPortGenRule {
            type uint8;
            description
              "The rule of generating source udp port.";			
          }
          leaf destUdpPort {
            type uint16{
              range "0 .. 65535";
            }
            default "4789";
            description
              "Destination udp port.";			
          }
        }
        description
          "If the encapsulation type is VxLAN.";
      }
      container members {
        list member {
          key "VNI";
          leaf VNI {
            type uint32 {
              range "1 .. 16777215";
            }
            mandatory "true";
            description 
              "Virutal Network Instance (VNI). For VxLAN, it is 
              VXLAN Network Identifier; For NVGRE, it is Virtual 
              Subnet Identifier.";			
          }
          leaf bdId {
            type uint32 {
              range "1 .. 32768";
            }
            mandatory "true";			
            description
              "Bridge Domain ID";
          }
          choice encapType{
            case vxlan{
              leaf vxlanFlag {
                type flags-vxlan;
                description
                  "The 8 bits flags of VXLAN. The I flag MUST
                  be set to 1 for a valid VNI.
                  Others are reserved.";
              }
            }
            case nvgre{
              leaf nvgreFlag {
                  type flags-nvgre;
                  description
                    "The 13 bits flags of NVGRE. Bit 0 and 3 are set 
                    to 0 while bit 2 is set to 1. 
                    Others are reserved";				  
              }
              leaf flowId {
                type uint8;
                description
                  "This is an 8-bit value that is used to provide 
                  per-flow entropy for flows in the same VSID. 
                  If a FlowID is not generated, it MUST be set to 
                  all zero.";				
              }
            }
            description
              "The encapsulation type that the overlay is using.";
          }
          choice bumMode{
            case headEnd{
              leaf-list peerAddr {
                type inet:ip-address;
                description
                  "Remote NVE address.";				
              }
            }
            case multiGroup{
              leaf multiAddr {
                type inet:ip-address;
                description
                  "The multicast group address.";				
              }
            }
            description
              "The replication method.";
          }
          description
            "The list of the VNIs.";	  
        }
        description
          "The container of the VNI list.";	
      }//container members
      description
        "The list of the nvo3Nves.";	
    }
    description
      "The container of the nvo3Nves list.";		
  }//container nvo3Nves

  container nvo3Infos {
    list nvo3Info {
      key "VNI";
      leaf VNI {
        type uint32 {
          range "1 .. 16777215";
        }
        mandatory "true";		
        description
          "Virutal Network Instance (VNI). For VxLAN, it is 
          VXLAN Network Identifier; For NVGRE, it is Virtual 
          Subnet Identifier.";		
      }
      leaf statisticsEnable {
        type enumeration {
          enum enable {
            value "0";
            description
              "Enable";
          }
          enum disable {
            value "1";
            description
              "Disable";
          }
        }
        description
          "Collecting of statistics is enabled.";
      }
      leaf status {
        type enumeration {
          enum up {
            value "0";
            description
              "Up";
          }
          enum down {
            value "1";
            description
              "Down";
          }
        }
        config "false";
        description
          "The status can be up or down.";
      }
      description
        "The information per VNI.";
    }
    description
      "The container of the VNI info list.";	
  }//container nvo3Infos

  container nvo3Statistics {
    list localNVE {
      leaf count {
        type uint64;
        config "false";		
        description
          "The value of count.";		
      }  
      leaf-list ipAddr {
        type inet:ip-address;
        config "false";		
        description
          "List of local NVE address.";		
      }
      config "false";
      description
        "The number of local NVEs.";	
    }  
    list remoteNVE {
      config "false";
      leaf count {
        type uint64;
        config "false";		
        description
          "The value of count.";	
      }  
      leaf-list ipAddr {
        type inet:ip-address;
        config "false";
        description
          "List of remote NVE address.";	
      }
      description
        "The number of remote NVEs.";
    }  
    container flowStatistics {
      grouping inputStatistics {
        leaf inPacketsCount {
          type uint64;
          config "false";
          description
            "The number of incoming packets.";
        }  
        leaf inBytesCount {
          type uint64;
          config "false";
          description
            "The number of bytes.";
        }  
        leaf inUnicasts {
          type uint64;
          config "false";
          description
            "The number of incoming unicast packets.";		  
        }  
        leaf inMulticasts {
          type uint64;
          config "false";
          description
            "The number of incoming multicast packets.";		  
        }  
        leaf inBroadcasts {
          type uint64;
          config "false";
          description
            "The number of incoming broadcast packets.";		  
        }  
        leaf inUnknownUnicastDrops {
          type uint64;
          config "false";
          description
            "The number of incoming unknown unicast packets 
            that are dropped.";  	  
        }
        leaf inUnknownMulticastDrops {
          type uint64;
          config "false";
          description
            "The number of incoming unknown multicast packets 
            that are dropped.";  
        }  
        leaf inBroadcastsDrops {
          type uint64;
          config "false";
          description
            "The number of incoming broadcast packets 
            that are dropped";				  
        }
        description
          "The collection of information about incoming flows.";
      }
      grouping outputStatistics {
        leaf outPacketsCount {
          type uint64;          
          config "false";
          description
            "The number of outgoing packets.";		  
        }  
        leaf outBytesCount {
          type uint64;          
          config "false";
          description
            "The number of bytes.";		  
        }  
        leaf outUnicasts {
          type uint64;
          config "false";
          description
            "The number of outgoing unicast packets.";		  
        }  
        leaf outMulticasts {
          type uint64;
          config "false";
          description
            "The number of outgoing multicast packets.";		  
        }  
        leaf outBroadcasts {
          type uint64;
          config "false";		  
          description
            "The number of outgoing broadcast packets.";		  
        }
        description
          "The collection of information about outgoing flows.";
      }
      leaf instanceCount {
        type uint64;
        config "false";		
        description
          "The number of instances.";		
      }  
      list flowStatistic{
        leaf VNI {
          type uint32;
          config "false";		  
          description
            "Virutal Network Instance (VNI). For VxLAN, it is 
            VXLAN Network Identifier; For NVGRE, it is Virtual 
            Subnet Identifier.";		  
        }
        config "false";		
        uses inputStatistics;
        uses outputStatistics;
        description
          "The statistics per VNI.";
      }
      description
        "The statistics of the flows.";
    }//container flowStatistics
    container MacStatistics {
      list MacStatistic{
        leaf VNI {
          type uint32;
          config "false";		  
          description
            "Virutal Network Instance (VNI). For VxLAN, it is 
            VXLAN Network Identifier; For NVGRE, it is Virtual 
            Subnet Identifier.";		  
        }
        leaf vmMacCount {
          type uint64;          
          config "false";		  
          description
            "Count of learning Mac addresses for the VNI.";
        }
        config "false";	
        description
          "The statistics of the MAC addresses.";
      }
      description
        "The container of the MacStatistics list.";
    }//container MacStatistics
    description
      "The container of the nvo3Statistics list.";
  }//container nvo3Statistics
}
