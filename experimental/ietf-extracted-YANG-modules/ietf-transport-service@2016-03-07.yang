module ietf-transport-service { 
  yang-version 1;  
  namespace "urn:ietf:params:xml:ns:yang:ietf_transport_service"; 
  prefix tser; 
  import ietf-inet-types { 
    prefix inet; 
  } 

  import ietf-schedule {  
    prefix "sch";  
  } 

  organization "TBD"; 
  contact 
    "WILL-BE-DEFINED-LATER"; 
  description 
    "this module describes a service module that is essential  
    API for a client to ask for a provider network for a path  
    without the need to care about underlying technologies. 
    Capability to specify constraints/policies are provided as 
    optional features."; 

  revision 2016-03-07 { 
    description 
      "Initial revision."; 
      reference "to add the draft name"; 
  } 

  typedef tp-id {  //client termination port 
    type union { 
      type uint32;           
      type inet:ip-address; // IPv4 or IPv6 address 
    } 
    description 
      "the client termination port of a transport device"; 
  } 

  typedef node-id {  //client termination port 
    type union { 
      type uint32;           
      type inet:ip-address; // IPv4 or IPv6 address 
    } 
    description 
      "the node id of a transport device"; 
  } 

  typedef service-types { 
    type enumeration { 
      enum "EPL" { 
        value 0; 
        description  
        "EPL service"; 
      } 
      enum "EVPL" { 
        value 1; 
        description  
        "EVPL"; 
      } 
      enum "EPLAN" { 
        value 2; 
        description  
        "EPLAN"; 
      } 
      enum "EVPLAN" { 
        value 3; 
        description  
        "EVPLAN"; 
      } 
    } 
    description "the type of a service request"; 
  } 

  typedef state-types{ 
    type enumeration { 
      enum "NORMAL" { 
        value 0; 
        description  
        "service is normal/up and running"; 
      } 
      enum "DOWN" { 
        value 1; 
        description  
        "service is down."; 
      } 
      enum "DEGRADED"{ 
        value 2; 
        description 
        "service is in degraded state."; 
      } 
    } 
    description "the state of a service.";  
  } 

  typedef SLAtypes{ 
    type enumeration{ 
      enum "1+1+R"{ 
        value 0; 
        description  
        "A reroute will be provided after both the working and  
        protection path fails."; 
      } 
      enum "1+1"{ 
        value 1; 
        description 
        "a protection path is provided."; 
      } 
      enum "Rerouting"{ 
        value 2; 
        description 
        "rerouting after the working path fails"; 
      } 
      enum "unprotected"{ 
        value 3; 
        description 
        "no protection provided"; 
      } 
    } 
  } 

  grouping service-basics { 
    //later put all service under so that it can reused  
    // in states. 
    leaf service-id { 
      type uint32; 
      description "an unique identificaiton of a service."; 
    } 

    leaf service-name{ 
      type string; 
      description "name for a service"; 
    } 

    container source{ 
      leaf node-id { 
        type node-id; 
        description "node id"; 
      } 
      leaf tp-id { 
        type tp-id;                  
        description "TBD"; 
      } 
      description "Service source information"; 
    } 
    container destination{ 
      leaf node-id { 
        type node-id; 
        description "node id"; 
      } 
      leaf tp-id { 
        type tp-id;                  
        description "TBD"; 
      } 
      description "Service destination information"; 
    } 

    leaf service-type { 
      type service-types; 
      description "the type of a service request"; 
    } 

    list supporting-tunnel{ 
      key "name"; 
      leaf name{ 
        type string; 
        description "the name of a tunnel"; 
      } 

      description "the list of tunnesl to support the list"; 
    } 

    leaf bandwidth { 
      type decimal64 { 
        fraction-digits 2; 
      } 
      mandatory true; 
      description "the bandwidth requested by a service."; 
    } 

    leaf SLA{ 
      type SLAtypes; 
      description "the type of protection expected for this  
      service"; 
    } 
  } 

  container transport_service { 
    description 
      "serves as a top-level container for a list of services"; 
    list service { 
      key "service-id"; 
      description 
        "an unique identifier of a service"; 

      uses service-basics; 

      container intended-policies { 
        container schedule { 
          uses sch:schedules;  
          description "to specify bandwidth scheduling 
          information of this service."; 
        }  
        description "specify the policy associated with a  
        service"; 
      }//end of policy 
    }//end of service list    
  }//service top container 

  container service-state 
  { 
    list service { 
      config false; 
      key "service-id"; 
      description "operational state of a service"; 

      uses service-basics; 

      container applied-policies{ 
        container schedule { 
          uses sch:schedules;  
          description "to specify bandwidth scheduling 
          information of this service."; 
        } 
      } 

      leaf status { 
        type state-types; 
        description "TBD"; 
      } 
    }//end of a service state 
  }//end of state 
}
