module ietf-multiple-stream-originators {
  yang-version 1.1;
  namespace
    "urn:ietf:params:xml:ns:yang:ietf-multiple-stream-originators";
  prefix mso;
  import ietf-subscribed-notifications {
    prefix sn;
  }

  import ietf-inet-types {
    prefix inet;
  }

  organization "IETF NETCONF (Network Configuration) Working Group";
  contact
    "WG Web:   <http:/tools.ietf.org/wg/netconf/>
     WG List:  <mailto:netconf@ietf.org>

     Editor:   Tianran Zhou
               <mailto:zhoutianran@huawei.com>

     Editor:   Guangying Zheng
               <mailto:zhengguangying@huawei.com>";

  description
    "Defines augmentation for ietf-subscribed-notifications to enable
     the distributed publication with single subscription.

    Copyright (c) 2018 IETF Trust and the persons identified as authors
    of the code.  All rights reserved.

    Redistribution and use in source and binary forms, with or without
    modification, is permitted pursuant to, and subject to the license
    terms contained in, the Simplified BSD License set forth in Section
    4.c of the IETF Trust's Legal Provisions Relating to IETF Documents
    (https://trustee.ietf.org/license-info).

    This version of this YANG module is part of RFC XXXX; see the RFC

    itself for full legal notices.";

  revision 2019-07-07 {
    description
      "Initial version";
    reference
      "RFC XXXX: Subscription to Multiple Stream Originators";
  }

  grouping message-generator-ids {
    description
      "Provides a reusable list of message-generator-ids.";

    leaf-list message-generator-id {
      type string;
      config false;
      ordered-by user;
      description
        "Software entity which created the message (e.g.,
         linecard 1). This field is used to notify the
         collector the working originator.";
    }
  }

  grouping resource-access-list {
    description
      "Provides a reusable list of resource access information.";

    choice transport-access {
      description
        "identify the transport used.";

      case restconf-access {
        description
          "When the transport is RESTCONF";
        leaf-list uri {
          type inet:uri;
          config false;
          ordered-by user;
          description
            "Location of a subscription specific URI on the
             publisher.";
        }
      }
    }
  }

  augment "/sn:subscriptions/sn:subscription" {
    description
      "This augmentation allows the message generators to be exposed
       for a subscription.";

    uses resource-access-list;
    uses message-generator-ids;
  }

  augment "/sn:subscription-started" {
    description
      "This augmentation allows MSO specific parameters to be
       exposed for a subscription.";

    uses message-generator-ids;
  }

  augment "/sn:subscription-modified" {
    description
      "This augmentation allows MSO specific parameters to be
       exposed for a subscription.";

    uses message-generator-ids;
  }

  augment "/sn:establish-subscription/sn:output" {
    description
      "This augmentation allows MSO specific parameters to be
       exposed for a subscription.";

    uses resource-access-list;
    uses message-generator-ids;
  }

  augment "/sn:modify-subscription/sn:output" {
    description
      "This augmentation allows MSO specific parameters to be
       exposed for a subscription.";

    uses resource-access-list;
    uses message-generator-ids;
  }
}
