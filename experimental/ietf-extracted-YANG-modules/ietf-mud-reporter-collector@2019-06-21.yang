module ietf-mud-reporter-collector {
   yang-version 1.1;
   namespace "urn:ietf:params:xml:ns:yang:ietf-mud-reporter-collector";
   prefix "mud-collector";

   import ietf-mud-reporter {
        prefix "reporter";
    }
  organization
    "IETF OPSAWG (Ops Area) Working Group";
  contact
    "WG Web: http://tools.ietf.org/wg/opsawg/
     WG List: opsawg@ietf.org
     Author: Eliot Lear
     lear@cisco.com
     Author: Mudumbai Ranganathan
     mranga@nist.gov
    ";
  description
    "This YANG module specifies the reporting format for MUD managers
     to use when they are reporting to manufacturers.

     Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
       (https://trustee.ietf.org/license-info).
     This version of this YANG module is part of RFC XXXX
     (https://www.rfc-editor.org/info/rfcXXXX); see the RFC itself
      for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
    ";
  revision 2019-06-21 {
    description
      "Initial proposed standard.";
    reference
      "RFC XXXX: Extension for MUD Reporting";
  }
    rpc post-mud-report {
      description
         "Rpc interface that must be supported by collection point.";
      input {
        container mud-report {
          uses  reporter:mud-reporter-grouping;
          description "MUD report";
        }
      }
    }
}
