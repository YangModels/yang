module ietf-system {
  namespace "urn:ietf:params:xml:ns:yang:ietf-system";
  prefix "sys";

  import ietf-yang-types {
    prefix yang;
  }

  import ietf-inet-types {
    prefix inet;
  }

  import ietf-netconf-acm {
    prefix nacm;
  }

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Andy Bierman
               <mailto:andy@netconfcentral.org>

     Editor:   Martin Bjorklund
               <mailto:mbj@tail-f.com>";

  description
    "This module contains a collection of YANG definitions for the
     configuration and identification of the management system of a
     device.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: remove this note
  // Note: extracted from draft-ietf-netmod-system-mgmt-00.txt

  // RFC Ed.: update the date below with the date of RFC publication
  // and remove this note.
  revision 2012-01-31 {
    description
      "Initial revision.";
    reference
      "RFC XXXX: A YANG Data Model for System Management";
  }

  /*
   * Typedefs
   */

  typedef timezone-name {
    description
      "List of available timezone enumerations.
       Based on the referenced list, but non-unique names
       have been changed so they are unique enumeration
       identifiers.";
    reference
      "Wikipedia: http://en.wikipedia.org/wiki/"
       + "List_of_time_zone_abbreviations";
    type enumeration {
      enum ACDT {
        description
          "Australian Central Daylight Time UTC+10:30";
      }
      enum ACST {
        description
          "Australian Central Standard Time UTC+09:30";
      }
      enum ACT {
        description
          "ASEAN Common Time UTC+08";
      }
      enum ADT {
        description
          "Atlantic Daylight Time UTC-03";
      }
      enum AEDT {
        description
          "Australian Eastern Daylight Time UTC+11";
      }
      enum AEST {
        description
          "Australian Eastern Standard Time UTC+10";
      }
      enum AFT {
        description
          "Afghanistan Time UTC+04:30";
      }
      enum AKDT {
        description
          "Alaska Daylight Time UTC-08";
      }
      enum AKST {
        description
          "Alaska Standard Time UTC-09";
      }
      enum AMST {
        description
          "Armenia Summer Time UTC+05";
      }
      enum AMT {
        description
          "Armenia Time UTC+04";
      }
      enum ART {
        description
          "Argentina Time UTC-03";
      }
      enum AST {
        description
          "Arab Standard Time (Kuwait, Riyadh) UTC+03";
      }
      enum AST-2 {
        description
          "Arabian Standard Time (Abu Dhabi, Muscat) UTC+04";
      }
      enum AST-3 {
        description
          "Arabic Standard Time (Baghdad) UTC+03";
      }
      enum AST-4 {
        description
          "Atlantic Standard Time UTC-04";
      }
      enum AWDT {
        description
          "Australian Western Daylight Time UTC+09";
      }
      enum AWST {
        description
          "Australian Western Standard Time UTC+08";
      }
      enum AZOST {
        description
          "Azores Standard Time UTC-01";
      }
      enum AZT {
        description
          "Azerbaijan Time UTC+04";
      }
      enum BDT {
        description
          "Brunei Time UTC+08";
      }
      enum BIOT {
        description
          "British Indian Ocean Time UTC+06";
      }
      enum BIT {
        description
          "Baker Island Time UTC-12";
      }
      enum BOT {
        description
          "Bolivia Time UTC-04";
      }
      enum BRT {
        description
          "Brasilia Time UTC-03";
      }
      enum BST {
        description
          "Bangladesh Standard Time UTC+06";
      }
      enum BST-2 {
        description
          "British Summer Time (British Standard Time
           from Feb 1968 to Oct 1971) UTC+01";
      }
      enum BTT {
        description
          "Bhutan Time UTC+06";
      }
      enum CAT {
        description
          "Central Africa Time UTC+02";
      }
      enum CCT {
        description
          "Cocos Islands Time UTC+06:30";
      }
      enum CDT {
        description
          "Central Daylight Time (North America) UTC-05";
      }
      enum CEDT {
        description
          "Central European Daylight Time UTC+02";
      }
      enum CEST {
        description
          "Central European Summer Time (Cf. HAEC) UTC+02";
      }
      enum CET {
        description
          "Central European Time UTC+01";
      }
      enum CHADT {
        description
          "Chatham Daylight Time UTC+13:45";
      }
      enum CHAST {
        description
          "Chatham Standard Time UTC+12:45";
      }
      enum CIST {
        description
          "Clipperton Island Standard Time UTC-08";
      }
      enum CKT {
        description
          "Cook Island Time UTC-10";
      }
      enum CLST {
        description
          "Chile Summer Time UTC-03";
      }
      enum CLT {
        description
          "Chile Standard Time UTC-04";
      }
      enum COST {
        description
          "Colombia Summer Time UTC-04";
      }
      enum COT {
        description
          "Colombia Time UTC-05";
      }
      enum CST {
        description
          "Central Standard Time (North America) UTC-06";
      }
      enum CST-2 {
        description
          "China Standard Time UTC+08";
      }
      enum CST-3 {
        description
          "Central Standard Time (Australia) UTC+09:30";
      }
      enum CT {
        description
          "China Time UTC+08";
      }
      enum CVT {
        description
          "Cape Verde Time UTC-01";
      }
      enum CXT {
        description
          "Christmas Island Time UTC+07";
      }
      enum CHST {
        description
          "Chamorro Standard Time UTC+10";
      }
      enum DFT {
        description
          "AIX specific equivalent of Central European Time UTC+01";
      }
      enum EAST {
        description
          "Easter Island Standard Time UTC-06";
      }
      enum EAT {
        description
          "East Africa Time UTC+03";
      }
      enum ECT {
        description
          "Eastern Caribbean Time (does not recognise DST) UTC-04";
      }
      enum ECT-2 {
        description
          "Ecuador Time UTC-05";
      }
      enum EDT {
        description
          "Eastern Daylight Time (North America) UTC-04";
      }
      enum EEDT {
        description
          "Eastern European Daylight Time UTC+03";
      }
      enum EEST {
        description
          "Eastern European Summer Time UTC+03";
      }
      enum EET {
        description
          "Eastern European Time UTC+02";
      }
      enum EST {
        description
          "Eastern Standard Time (North America) UTC-05";
      }
      enum FJT {
        description
          "Fiji Time UTC+12";
      }
      enum FKST {
        description
          "Falkland Islands Summer Time UTC-03";
      }
      enum FKT {
        description
          "Falkland Islands Time UTC-04";
      }
      enum GALT {
        description
          "Galapagos Time UTC-06";
      }
      enum GET {
        description
          "Georgia Standard Time UTC+04";
      }
      enum GFT {
        description
          "French Guiana Time UTC-03";
      }
      enum GILT {
        description
          "Gilbert Island Time UTC+12";
      }
      enum GIT {
        description
          "Gambier Island Time UTC-09";
      }
      enum GMT {
        description
          "Greenwich Mean Time UTC";
      }
      enum GST {
        description
          "South Georgia and the South Sandwich Islands UTC-02";
      }
      enum GST-2 {
        description
          "Gulf Standard Time UTC+04";
      }
      enum GYT {
        description
          "Guyana Time UTC-04";
      }
      enum HADT {
        description
          "Hawaii-Aleutian Daylight Time UTC-09";
      }
      enum HAEC {
        description
          "Heure Avancee d'Europe Centrale francised name for
           CEST UTC+02";
      }
      enum HAST {
        description
          "Hawaii-Aleutian Standard Time UTC-10";
      }
      enum HKT {
        description
          "Hong Kong Time UTC+08";
      }
      enum HMT {
        description
          "Heard and McDonald Islands Time UTC+05";
      }
      enum HST {
        description
          "Hawaii Standard Time UTC-10";
      }
      enum ICT {
        description
          "Indochina Time UTC+07";
      }
      enum IDT {
        description
          "Israeli Daylight Time UTC+03";
      }
      enum IRKT {
        description
          "Irkutsk Time UTC+08";
      }
      enum IRST {
        description
          "Iran Standard Time UTC+03:30";
      }
      enum IST {
        description
          "Indian Standard Time UTC+05:30";
      }
      enum IST-2 {
        description
          "Irish Summer Time UTC+01";
      }
      enum IST-3 {
        description
          "Israel Standard Time UTC+02";
      }
      enum JST {
        description
          "Japan Standard Time UTC+09";
      }
      enum KRAT {
        description
          "Krasnoyarsk Time UTC+07";
      }
      enum KST {
        description
          "Korea Standard Time UTC+09";
      }
      enum LHST {
        description
          "Lord Howe Standard Time UTC+10:30";
      }
      enum LINT {
        description
          "Line Islands Time UTC+14";
      }
      enum MAGT {
        description
          "Magadan Time UTC+11";
      }
      enum MDT {
        description
          "Mountain Daylight Time (North America) UTC-06";
      }
      enum MET {
        description
          "Middle European Time Same zone as CET UTC+02";
      }
      enum MEST {
        description
          "Middle European Saving Time Same zone as CEST UTC+02";
      }
      enum MIT {
        description
          "Marquesas Islands Time UTC-09:30";
      }
      enum MSD {
        description
          "Moscow Summer Time UTC+04";
      }
      enum MSK {
        description
          "Moscow Standard Time UTC+03";
      }
      enum MST {
        description
          "Malaysian Standard Time UTC+08";
      }
      enum MST-2 {
        description
          "Mountain Standard Time (North America) UTC-07";
      }
      enum MST-3 {
        description
          "Myanmar Standard Time UTC+06:30";
      }
      enum MUT {
        description
          "Mauritius Time UTC+04";
      }
      enum MYT {
        description
          "Malaysia Time UTC+08";
      }
      enum NDT {
        description
          "Newfoundland Daylight Time UTC-02:30";
      }
      enum NFT {
        description
          "Norfolk Time[1] UTC+11:30";
      }
      enum NPT {
        description
          "Nepal Time UTC+05:45";
      }
      enum NST {
        description
          "Newfoundland Standard Time UTC-03:30";
      }
      enum NT {
        description
          "Newfoundland Time UTC-03:30";
      }
      enum NZDT {
        description
          "New Zealand Daylight Time UTC+13";
      }
      enum NZST {
        description
          "New Zealand Standard Time UTC+12";
      }
      enum OMST {
        description
          "Omsk Time UTC+06";
      }
      enum PDT {
        description
          "Pacific Daylight Time (North America) UTC-07";
      }
      enum PETT {
        description
          "Kamchatka Time UTC+12";
      }
      enum PHOT {
        description
          "Phoenix Island Time UTC+13";
      }
      enum PKT {
        description
          "Pakistan Standard Time UTC+05";
      }
      enum PST {
        description
          "Pacific Standard Time (North America) UTC-08";
      }
      enum PST-2 {
        description
          "Philippine Standard Time UTC+08";
      }
      enum RET {
        description
          "Reunion Time UTC+04";
      }
      enum SAMT {
        description
          "Samara Time UTC+04";
      }
      enum SAST {
        description
          "South African Standard Time UTC+02";
      }
      enum SBT {
        description
          "Solomon Islands Time UTC+11";
      }
      enum SCT {
        description
          "Seychelles Time UTC+04";
      }
      enum SGT {
        description
          "Singapore Time UTC+08";
      }
      enum SLT {
        description
          "Sri Lanka Time UTC+05:30";
      }
      enum SST {
        description
          "Samoa Standard Time UTC-11";
      }
      enum SST-2 {
        description
          "Singapore Standard Time UTC+08";
      }
      enum TAHT {
        description
          "Tahiti Time UTC-10";
      }
      enum THA {
        description
          "Thailand Standard Time UTC+07";
      }
      enum UTC {
        description
          "Coordinated Universal Time UTC";
      }
      enum UYST {
        description
          "Uruguay Summer Time UTC-02";
      }
      enum UYT {
        description
          "Uruguay Standard Time UTC-03";
      }
      enum VET {
        description
          "Venezuelan Standard Time UTC-04:30";
      }
      enum VLAT {
        description
          "Vladivostok Time UTC+10";
      }
      enum WAT {
        description
          "West Africa Time UTC+01";
      }
      enum WEDT {
        description
          "Western European Daylight Time UTC+01";
      }
      enum WEST {
        description
          "Western European Summer Time UTC+01";
      }
      enum WET {
        description
          "Western European Time UTC";
      }
      enum WST {
        description
          "Western Standard Time UTC+08";
      }
      enum YAKT {
        description
          "Yakutsk Time UTC+09";
      }
      enum YEKT {
        description
          "Yekaterinburg Time UTC+05";
      }
    }
  }

  typedef crypt-hash {
    type string {
      pattern "$0$.* | $1|5|6$[a-zA-Z0-9./]{2,16}$.*";
    }
    description
      "The crypt-hash type is used to store passwords using
       a hash function.  This type is implemented in various UNIX
       systems as the function crypt(3).

       When a clear text value is set to a leaf of this type, the
       server calculates a password hash, and stores the result
       in the datastore.  Thus, the password is never stored in
       clear text.

       When a leaf of this type is read, the stored password hash is
       returned.

       A value of this type matches one of the forms:

         $0$<clear text password>
         $<id>$<salt>$<password hash>
      The '$0$' prefix signals that the value is clear text.  When
      such a value is received by the server, a hash value is
      calculated, and the string '$<id>$<salt>$' is prepended to the
      result, where <salt> is a random 2-16 characters long salt
      used to generate the digest.  This value is stored in the
      configuration data store.

      If a value starting with '$<id>$<salt>$' is received, the
      server knows that the value already represents a hashed value,
      and stores it as is in the data store.

      When a server needs to verify a password given by a user, it
      finds the stored password hash string for that user, extracts
      the salt, and calculates the hash with the salt and given
      password as input.  If the calculated hash value is the same
      as the stored value, the password given by the client is
      correct.

      This type defines the following hash functions:

        id | hash function | feature
        ---+---------------+-------------------
         1 | MD5           | crypt-hash-md5
         5 | SHA-256       | crypt-hash-sha-256
         6 | SHA-512       | crypt-hash-sha-512

      The server indicates support for the different hash functions
      by advertising the corresponding feature.";
    reference
      "IEEE Std 1003.1-2008 - crypt() function
       Wikipedia: http://en.wikipedia.org/wiki/Crypt_(Unix)
       RFC 1321: The MD5 Message-Digest Algorithm
       FIPS.180-3.2008: Secure Hash Standard";
  }

  /*
   * Features
   */

  feature radius {
    description
      "Indicates that the device can be configured as a RADIUS
       client.";
    reference
      "RFC 2865: Remote Authentication Dial In User Service "
    + "(RADIUS)";
  }

  feature authentication {
    description
      "Indicates that the device can be configured
       to do authentication of users.";
  }

  feature local-users {
    if-feature authentication;
    description
      "Indicates that the device supports
       local user authentication.";
  }

  feature radius-authentication {
    if-feature radius;
    if-feature authentication;
    description
      "Indicates that the device supports user authentication over
       RADIUS.";
    reference
      "RFC 2865: Remote Authentication Dial In User Service (RADIUS)
       RFC 5607: Remote Authentication Dial-In User Service (RADIUS)
                 Authorization for Network Access Server (NAS)
                 Management";
  }

  feature crypt-hash-md5 {
    description
      "Indicates that the device supports the MD5
       hash function in 'crypt-hash' values";
    reference "RFC 1321: The MD5 Message-Digest Algorithm";
  }

  feature crypt-hash-sha-256 {
    description
      "Indicates that the device supports the SHA-256
       hash function in 'crypt-hash' values";
    reference "FIPS.180-3.2008: Secure Hash Standard";
  }

  feature crypt-hash-sha-512 {
    description
      "Indicates that the device supports the SHA-512
       hash function in 'crypt-hash' values";
    reference "FIPS.180-3.2008: Secure Hash Standard";
  }

  feature ntp {
    description
      "Indicates that the device can be configured
       to use one or more NTP servers to set the
       system date and time.";
  }

  feature timezone-location {
    description
      "Indicates that the local timezone on the device
       can be configured to use the TZ database
       to set the timezone and manage daylight savings time.";
    reference
      "TZ Database  http://www.twinsun.com/tz/tz-link.htm
       Maintaining the Timezone Database
         draft-lear-iana-timezone-database-04.txt";
  }

  feature timezone-name {
    description
      "Indicates that the local timezone on the device
       can be configured using the timezone enumeration
       strings as an alias for an UTC offset.";
    reference
      "Wikipedia: http://en.wikipedia.org/wiki/"
    + "List_of_time_zone_abbreviations";
  }

  /*
   * Identities
   */

  identity authentication-method {
    description
      "Base identity for user authentication methods.";
  }

  identity radius {
    base authentication-method;
    description
      "Indicates user authentication using RADIUS.";
    reference
      "RFC 2865: Remote Authentication Dial In User Service (RADIUS)
       RFC 5607: Remote Authentication Dial-In User Service (RADIUS)
                 Authorization for Network Access Server (NAS)
                 Management";
  }

  identity local-users {
    base authentication-method;
    description
      "Indicates password-based authentication of locally
       configured users.";
  }

  /*
   * Top-level container
   */

  container system {
    description
      "System group configuration.";

    leaf contact {
      type string {
        length "0..255";
      }
      default "";
      description
        "The administrator contact information for the system.";
      reference
        "RFC 3418 - Management Information Base (MIB) for the
                    Simple Network Management Protocol (SNMP)
                    SNMPv2-MIB.sysContact";
    }

    leaf name {
      type string {
        length "0..255";
      }
      default "";
      description
        "The administratively assigned system name.";
      reference
        "RFC 3418 - Management Information Base (MIB) for the
                    Simple Network Management Protocol (SNMP)
                    SNMPv2-MIB.sysName";
    }

    leaf location {
      type string {
        length "0..255";
      }
      default "";
      description
        "The system location";
      reference
        "RFC 3418 - Management Information Base (MIB) for the
                    Simple Network Management Protocol (SNMP)
                    SNMPv2-MIB.sysLocation";
    }

    container platform {
      config false;
      description
        "Contains vendor-specific information for
         identifying the system platform and operating system.";
      reference
        "IEEE Std 1003.1-2008 - sys/utsname.h";

      leaf os-name {
        type string;
        description
          "The name of the operating system in use,
           for example 'Linux'";
        reference
          "IEEE Std 1003.1-2008 - utsname.sysname";
      }

      leaf os-release {
        type string;
        description
          "The current release level of the operating
           system in use.  This string MAY indicate
           the OS source code revision.";
        reference
          "IEEE Std 1003.1-2008 - utsname.release";
      }

      leaf os-version {
        type string;
        description
          "The current version level of the operating
           system in use.  This string MAY indicate
           the specific OS build date and target variant
           information.";
        reference
          "IEEE Std 1003.1-2008 - utsname.version";
      }

      leaf machine {
        type string;
        description
          "A vendor-specific identifier string representing
           the hardware in use.";
        reference
          "IEEE Std 1003.1-2008 - utsname.machine";
      }

      leaf nodename {
        type string;
        description
          "The host name of this system.";
        reference
          "IEEE Std 1003.1-2008 - utsname.nodename";
      }
    }

    container clock {
      description
        "Configuration and monitoring of the system
         date and time properties.";

      leaf current-datetime {
        type yang:date-and-time;
        config false;
        description
          "The current system date and time.";
      }

      leaf boot-datetime {
        type yang:date-and-time;
        config false;
        description
          "The system date and time when the NETCONF
           server last restarted.";
      }

      choice timezone {
        description
          "Configure the system timezone information.";

        leaf timezone-location {
          if-feature timezone-location;
          type string;
          description
            "The TZ database location identifier string
             to use for the system, such as 'Europe/Stockholm'.";
        }

        leaf timezone-name {
          if-feature timezone-name;
          type timezone-name;
          description
            "The timezone enumeration string to use
             for the system, such as 'CET'.";
        }

        leaf timezone-utc-offset {
          type int16 {
            range "-1439 .. 1439";
          }
          description
            "The number of minutes to add to UTC time to
             identify the timezone for this system.
             For example, 'UTC - 8:00 hours' would be
             represented as '-480'.";
        }
      }
    }

    container ntp {
      if-feature ntp;

      description
        "Configuration of the NTP client.";

      leaf use-ntp {
        type boolean;
        default true;
        description
          "Indicates that the system should attempt
           to synchronize the system clock with an
           NTP server from the 'ntp-server' list.";
      }

      list ntp-server {
        key address;
        ordered-by user;
        description
          "List of NTP servers to use for
           system clock synchronization.  If 'use-ntp'
           is 'true', then the system will attempt to
           contact and utilize the specified NTP servers.
           The user specified order indicates the server priority.";

        leaf address {
          type inet:host;
          description
            "The IP address or domain name of the NTP server.";
        }
        leaf enabled {
          type boolean;
          default true;
          description
            "Indicates whether this server is enabled for use or
             not.";
        }
      }
    }

    container dns {
      description
        "Configuration of the DNS resolver.";

      leaf-list search {
        type inet:host;
        ordered-by user;
        description
          "An ordered list of domains to search when resolving
           a host name.";
      }
      leaf-list server {
        type inet:ip-address;
        ordered-by user;
        description
          "Addresses of the name servers that the resolver should
           query.

           Implementations MAY limit the number of entries in this
           leaf list.";
      }
      container options {
        description
          "Resolver options.  The set of available options has been
           limited to those that are generally available across
           different resolver implementations, and generally
           useful.";
        leaf ndots {
          type uint8;
          default "1";
          description
            "This parameter sets a threshold for the number of dots
             which must appear in a query request before an initial
             absolute query will be made.";
        }
        leaf timeout {
          type uint8;
          units "seconds";
          default "5";
          description
            "The amount of time the resolver will wait for a
             response from a remote name server before
             retrying the query via a different name server.";
        }
        leaf attempts {
          type uint8;
          default "2";
          description
            "The number of times the resolver will send a query to
             its name servers before giving up and returning an
             error to the calling application.";
        }
      }
    }

    container radius {
      if-feature radius;

      description
        "Configuration of the RADIUS client.";

      list server {
        key address;
        ordered-by user;
        description
          "List of RADIUS servers used by the device.";

        leaf address {
          type inet:host;
          description
            "The address of the RADIUS server.";
        }
        leaf authentication-port {
          type inet:port-number;
          default "1812";
          description
            "The port number of the RADIUS server.";
        }
        leaf shared-secret {
          type string;
          nacm:default-deny-all;
          description
            "The shared secret which is known to both the RADIUS
             client and server.";
          reference
            "RFC 2865: Remote Authentication Dial In User Service";
        }
      }
      container options {
        description
          "RADIUS client options.";

        leaf timeout {
          type uint8;
          units "seconds";
          default "5";
          description
            "The number of seconds the device will wait for a
             response from a RADIUS server before trying with a
             different server.";
        }
        leaf attempts {
          type uint8;
          default "2";
          description
            "The number of times the device will send a query to
             the RADIUS servers before giving up.";
        }
      }
    }

    container authentication {
      nacm:default-deny-write;
      if-feature authentication;

       description
         "The authentication configuration subtree.";

       leaf-list user-authentication-order {
         type identityref {
           base authentication-method;
         }
         must '(. = "sys:radius" and ../../radius/server) or'
            + '(. != "sys:radius")' {
           error-message
             "When 'radius' is used, a radius server"
           + " must be configured.";
         }
         ordered-by user;

         description
           "When the device authenticates a user with
            a password, it tries the authentication methods in this
            leaf-list in order.  If authentication with one method
            fails, the next method is used.  If no method succeeds,
            the user is denied access.

            If the 'radius-authentication' feature is advertised by
            the NETCONF server, the 'radius' identity can be added to
            this list.

            If the 'local-users' feature is advertised by the
            NETCONF server, the 'local-users' identity can be
            added to this list.";
       }

       list user {
         if-feature local-users;
         key name;
         description
           "The list of local users configured on this device.";

         leaf name {
           type string;
           description
            "The user name string identifying this entry.";
         }
         leaf password {
           type crypt-hash;
           description
             "The password for this entry.";
         }
         leaf ssh-dsa {
           type binary;
           description
             "The public DSA key for this entry.";
         }
         leaf ssh-rsa {
           type binary;
           description
             "The public RSA key for this entry.";
         }
       }
     }
  }

  rpc set-current-datetime {
    nacm:default-deny-all;
    description
      "Manually set the /system/clock/current-datetime leaf
       to the specified value.

       If the /system/ntp/ntp-in-use leaf exists and
       is set to 'true', then this operation will
       fail with error-tag 'operation-failed',
       and error-app-tag value of 'ntp-active'";
    input {
      leaf current-datetime {
        type yang:date-and-time;
        mandatory true;
        description
          "The current system date and time.";
      }
    }
  }

  rpc system-restart {
    nacm:default-deny-all;
    description
      "Request that the entire system be restarted immediately.
       A server SHOULD send an rpc reply to the client before
       restarting the system.";
  }

  rpc system-shutdown {
    nacm:default-deny-all;
    description
      "Request that the entire system be shut down immediately.
       A server SHOULD send an rpc reply to the client before
       shutting down the system.";
  }

}
