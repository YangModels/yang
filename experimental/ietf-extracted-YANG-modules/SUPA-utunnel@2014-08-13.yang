module SUPA-utunnel {
  namespace "TBD";
  prefix "nc";
  organization "TBD";
  contact "TBD";
  description "TBD";
  revision "2014-08-13";

  container tunnels {

    list tunnel {

      key "tunnelName";
      max-elements "unbounded";
      min-elements "0";
      description "tunnel";

      leaf tunnelName {
        description "Tunnel Name";
        config "true";
        type string {
          length "1..31";
        }
      }
      leaf tunnelID {
        description "tunnel ID";
        config "false";
        type string {
          length "1..31";
        }
      }
      leaf direction {
        description "tunnel direction";
        config "true";
        type enumeration {
          enum single {
            value "0";
            description "single direction:";
          }
          enum double {
            value "1";
            description "double direction:";
          }
        }
      }
      leaf tunnelType {
        description "tunnel type";
        config "true";
        type enumeration {
          enum ldp {
            value "0";
            description "ldp:";
          }
          enum bgp {
            value "1";
            description "bgp:";
          }
          enum te {
            value "2";
            description "te:";
          }
          enum static-lsp {
            value "3";
            description "static-lsp:";
          }
          enum gre {
            value "4";
            description "gre:";
          }
        }
      }
      leaf sourceNodeKeyType {
        description "Source Node Key Type";
        config "true";
        default "lsr-id";
        type enumeration {
          enum name {
            value "0";
            description "name:";
          }
          enum invalid {
            value "1";
            description "invalid:";
          }
          enum system-id {
            value "2";
            description "system-id:";
          }
          enum router-id {
            value "3";
            description "router-id:";
          }
          enum lsr-id {
            value "4";
            description "lsr-id:";
          }
          enum fp-id {
            value "5";
            description "fp-id:";
          }
          enum mac {
            value "6";
            description "mac:";
          }
        }
      }
      leaf sourceNodeId {
        description "Source Node Id";
        config "true";
        default "_sourceNode_";
        type string {
          length "1..31";
        }
      }
      leaf sourceTpType {
        description "Source Terminal Point Key";
        config "true";
        default "ip";
        type enumeration {
          enum ip {
            value "0";
            description "ip:";
          }
          enum invalid {
            value "1";
            description "invalid:";
          }
          enum interface {
            value "2";
            description "interface:";
          }
        }
      }
      leaf sourceTpId {
        description "Source Terminal Point Id";
        config "true";
        default "_sourceTp_";
        type string {
          length "1..31";
        }
      }
      leaf destinationNodeKeyType {
        description "Destination Node Key Type";
        config "true";
        default "lsr-id";
        type enumeration {
          enum name {
            value "0";
            description "name:";
          }
          enum invalid {
            value "1";
            description "invalid:";
          }
          enum system-id {
            value "2";
            description "system-id:";
          }
          enum router-id {
            value "3";
            description "router-id:";
          }
          enum lsr-id {
            value "4";
            description "lsr-id:";
          }
          enum fp-id {
            value "5";
            description "fp-id:";
          }
          enum mac {
            value "6";
            description "mac:";
          }
        }
      }
      leaf destinationNodeId {
        description "Destination Node Id";
        config "true";
        default "_destinationNode_";
        type string {
          length "1..31";
        }
      }
      leaf destinationTpType {
        description "Destination Terminal Point Key Type";
        config "true";
        default "ip";
        type enumeration {
          enum ip {
            value "0";
            description "ip:";
          }
          enum invalid {
            value "1";
            description "invalid:";
          }
          enum interface {
            value "2";
            description "interface:";
          }
        }
      }
      leaf destinationTpId {
        description "Destination Terminal Point Id";
        config "true";
        default "_destinationTp_";
        type string {
          length "1..31";
        }
      }
      leaf adminStatus {
        description "AdminState";
        config "true";
        default "up";
        type enumeration {
          enum down {
            value "0";
            description "down:";
          }
          enum up {
            value "1";
            description "up:";
          }
        }
      }
      leaf operStatus {
        description "operStatus";
        config "false";
        type enumeration {
          enum down {
            value "0";
            description "down:";
          }
          enum up {
            value "1";
            description "up:";
          }
        }
      }
    }

  }
}
