module service-function-forwarder {

  namespace "urn:cisco:params:xml:ns:yang:sfc-sff";

  prefix sfc-sff;

  import ietf-inet-types        { prefix inet;}
  import ietf-yang-types {
    prefix "yang";
    revision-date 2013-07-15;
  }
  import service-locator        { prefix sfc-sl; }

  organization "Cisco Systems, Inc.";
  contact "Reinaldo Penno <repenno@cisco.com>";

  description
    "This module contains a collection of YANG definitions for
     managing service function forwarders.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
      description
      "Revision based on Opendaylight project feedback";
  }

  // Failmode type definitions

  identity failmode-type-identity {
    description
      "Base identity from which specific failmode
       types are derived. Fail mode specifies the behavior
       when the interface does not have connectivity to the
       service node.";
  }
  typedef failmode-type {
    type identityref {
        base "failmode-type-identity";
    }
    description "This type is used to reference all
      registered failmode types";
  }

  identity close {
    base "failmode-type-identity";
    description "When service-function can not reach service
       function, packets will be dropped";
  }

  identity open {
    base "failmode-type-identity";
    description "When service-function can not reach service
       function, packets will be forwarded";
  }

  container service-function-forwarders {
    description
      "A service function forwarder is
       responsible for delivering traffic received from the SFC
       network forwarder to one or more connected service
       functions via information carried in the SFC encapsulation.
      ";
    list service-function-forwarder {
      description
        "A list that holds configuration of all SFFs in the domain";
      key "name";
      leaf name {
        type string;
        description
          "The unique name of this service function forwarder, such
           as ovs-1-bridge-2.";
      }

      leaf service-node {
        type string;
        description "The service node that hosts this SFF";
      }

      leaf classifier {
        type string;
        description "the access-list responsible for directing
          packets to a specific service path";
      }

      list sff-data-plane-locator {
        description
          "A list of all data-plane-locators of this SFF.";
        key "name";
        leaf name {
          type string;
          description
            "A unique string that represents this
             data-plane-locator";
        }

        container data-plane-locator {
          description
            "A network data-plane locator";
          uses sfc-sl:data-plane-locator;
        }
      }

      list service-function-dictionary {
        key "name";
        leaf name {
          type string;
          description
              "The name of the service function.";
        }
        leaf type {
          type string;
          description
            "Service Function Type from service-function-type yang
             model";
        }
        container sff-sf-data-plane-locator {
          description
            "A network data-plane locator";
          uses sfc-sl:data-plane-locator;
        }
        list sff-interfaces {
          key "sff-interface";
          leaf sff-interface {
            type string;
            description
              "An individual interface on the SFF connected to the
               SF";
          }
          description
            "A list of interfaces on the SFF which are connected
             to this SF, will usually be 1 or 2 elements";
        }
        leaf failmode {
          type failmode-type;
          description
            "This leaf defines what should the SFF do if it can not
             send packets to the SF";

        }
        description
          "A list of all Service Functions attached to this SFF.";
      }
    }
  }
}
