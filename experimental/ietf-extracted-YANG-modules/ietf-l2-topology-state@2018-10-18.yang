module ietf-l2-topology-state {
    yang-version 1.1;
    namespace "urn:ietf:params:xml:ns:yang:ietf-l2-topology-state";
    prefix "l2t-s";

    import ietf-network-state {
      prefix "nw-s";
    }

    import ietf-network-topology-state {
      prefix "nt-s";
    }

    import ietf-l2-topology {
      prefix "l2t";
    }

    organization
      "IETF I2RS (Interface to the Routing System) Working Group";
    contact
      "WG Web:   <http://tools.ietf.org/wg/i2rs/>
       WG List:  <mailto:i2rs@ietf.org>
       Editor:    Jie Dong
                 <mailto:jie.dong@huawei.com>
       Editor:    Xiugang Wei
                 <mailto:weixiugang@huawei.com>";

    description
      "This module defines a basic model for
       the layer-2 topology of a network.

       Copyright (c) 2018 IETF Trust and the persons identified as
       authors of the code.  All rights reserved.
       Redistribution and use in source and binary forms, with or
       without modification, is permitted pursuant to, and subject
       to the license terms contained in, the Simplified BSD License
       set forth in Section 4.c of the IETF Trust's Legal Provisions
       Relating to IETF Documents
       (http://trustee.ietf.org/license-info).

       This version of this YANG module is part of
       draft-ietf-i2rs-yang-l2-network-topo-05;
       see the RFC itself for full legal notices.";

    revision "2018-10-18" {
      description "Initial revision";
      reference "draft-ietf-i2rs-l2-network-topology-06";
    }

   /*
    * Data nodes
    */

    augment "/nw-s:networks/nw-s:network/nw-s:network-types" {
      description
        "Introduce new network type for L2 topology";
      uses l2t:l2-network-type;
    }

    augment "/nw-s:networks/nw-s:network" {
      when "/nw-s:networks/nw-s:network/nw-s:network-types/"+
        "l2t-s:l2-network" {
        description
          "Augmentation parameters apply only for networks
           with L2 topology";
      }
      description
        "Configuration parameters for the L2 network
         as a whole";
      uses l2t:l2-network-attributes;
    }

    augment "/nw-s:networks/nw-s:network/nw-s:node" {
      when "/nw-s:networks/nw-s:network/nw-s:network-types/"+
        "l2t-s:l2-network" {
        description
          "Augmentation parameters apply only for networks
           with L2 topology";
      }
      description
        "Configuration parameters for L2 at the node
         level";
      uses l2t:l2-node-attributes;
    }

    augment "/nw-s:networks/nw-s:network/nt-s:link" {
      when "/nw-s:networks/nw-s:network/nw-s:network-types/"+
        "l2t-s:l2-network" {
        description
          "Augmentation parameters apply only for networks
           with L2 topology";
      }
      description "Augment L2 topology link information";
      uses l2t:l2-link-attributes;
    }

    augment "/nw-s:networks/nw-s:network/nw-s:node/"+
      "nt-s:termination-point" {
      when "/nw-s:networks/nw-s:network/nw-s:network-types/"+
        "l2t-s:l2-network" {
        description
          "Augmentation parameters apply only for networks
           with L2 topology";
      }
      description
        "Augment L2 topology termination point information";
      uses l2t:l2-termination-point-attributes;
    }

   /*
    * Notifications
    */

    notification l2-node-event {
      description "Notification event for L2 node";
      leaf event-type {
        type l2t:l2-network-event-type;
        description "Event type";
      }
      uses nw-s:node-ref;
      uses l2t:l2-network-type;
      uses l2t:l2-node-attributes;
    }

    notification l2-link-event {
      description "Notification event for L2 link";
      leaf event-type {
        type l2t:l2-network-event-type;
        description "Event type";
      }
      uses nt-s:link-ref;
      uses l2t:l2-network-type;
      uses l2t:l2-link-attributes;
    }

    notification l2-termination-point-event {
      description "Notification event for L2 termination point";
      leaf event-type {
        type l2t:l2-network-event-type;
        description "Event type";
      }
      uses nt-s:tp-ref;
      uses l2t:l2-network-type;
      uses l2t:l2-termination-point-attributes;
    }

}  // module l2-topology-state
