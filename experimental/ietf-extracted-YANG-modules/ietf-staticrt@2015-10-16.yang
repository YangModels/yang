module ietf-staticrt{
  namespace "urn:ietf:params:xml:ns:yang:ietf-staticrt";
  prefix staticrt;

  import ietf-inet-types {
    prefix inet;
  }

  organization "TBD";
  contact "TBD";

  description
    "This module contains a collection of YANG definitions for
     configuring static routes.";

  revision 2015-10-16 {
    description
      "Initial revision.";
    reference
      " [draft-ietf-netmod-routing-cfg-16]
       A YANG Data Model for Routing Management.
      ";
  }

  identity address-family {
    description
      "Base identity from which identities describing address
       families are derived.";
  }

  identity ipv4 {
    base address-family;
    description
      "This identity represents IPv4 address family.";
  }

  identity ipv6 {
    base address-family;
    description
      "This identity represents IPv6 address family.";
  }
  grouping staticrt-entry {
    description
      "This group defines the static route.";

    leaf ip-prefix {
      type inet:ip-address;
      mandatory "true";
      description
        "The destination ip prefix of the static route.";
    }

    leaf ip-prefix-mask {
      type inet:ip-address;
      mandatory "true";
      description
        "The destination ip prefix mask of the
         static route.";
    }

    leaf output-interface {
      type string;
      description
        " The name of the output interface.";
    }

    leaf target-VRF-name {
      type string;
      description
        "The VRF name of the target nexthop.";
    }

    leaf target-nexthop {
      type inet:ip-address;
      description
        " The configured target nexthop.";
    }

    leaf description {
      type string;
      description
        " The description of the static route.";
    }

    leaf preference {
      type uint32;
      description "Specifies route preference.";
    }

    leaf cost {
      type uint32;
      description "Specifies route cost.";
    }

    leaf tag {
      type uint32;
      description "Specifies route tag.";
    }

    leaf enable-inherit-cost {
      type boolean;
      default false;
      description
        "The flag indicates whether the static route should
         inherit the cost of the iterated route.";
    }

    leaf is-permanent {
      type boolean;
      default false;
      description
        "The flag indicates whether the static route should
         be released permanently.";
    }

    leaf not-advertise {
      type boolean;
      default false;
      description
        "The flag indicates whether the router should not
         advertise the static route.";
    }

    leaf is-iterated-to-host-route {
      type boolean;
      default false;
      description
        "The flag indicates whether the static route should be
         iterated to a host route.";
    }
  }

  grouping staticrt-BFD-paras {
    description
      "This group defines the corresponding BFD session
       information for detecting the configured nexthop
       reachability of the static route.";
    leaf BFD-enable {
      type boolean;
      description
        " The flag indicates whether the router enable
         the corresponding BFD session for this static route.";
    }

    leaf BFD-session-name {
      type string;
      description "The BFD session name.";
    }

    leaf adminstated-down-not-selected {
      type boolean;
      description
        "If this flag is true,it indicates that the corresponding
         static route should not be selected when the BFD session
         associated with it is in the AdminDown State.";
    }
  }

  grouping staticrt-reachability-paras {
    description
      "This group defines the reachability detecting session
       information for detecting the configured nexthop
       reachability of the static route.";

    uses staticrt-BFD-paras;
  }

  grouping staticrt-BFD-state {
    description
      "This group defines the corresponding BFD session state
       as a detecting result of the configured nexthop
       reachability.";

    leaf BFD-state {
      type string;
      config false;
      description "The BFD session state.";
    }

    leaf local-address {
      type inet:ip-address;
      config false;
      description
        "the local IP address of the corresponding BFD session.";
    }
    leaf remote-address {
      type inet:ip-address;
      config false;
      description
        "the remote IP address of the corresponding BFD session.";
    }
  }

  grouping staticrt-reachability-state {
    description
      "This group defines the reachability detecting session
       state as a detecting result of the configured nexthop
       reachability.";

    uses staticrt-BFD-state;
  }

  container staticrt {
    description
      "Container for static route configuration and state";
    container staticrt-cfg {
      description
        "Configuration for static route.";
      list staticrt-topo {
        key "VRF-name address-family topo-name";
        description
          "Configuration of a static route list.";

        leaf topo-name {
          type string;
          description
            "The topology name of the destination ip prefix
             belonging to.";
        }
        leaf VRF-name {
          type string;
          description
            "The VRF-name of the staticrt-entry";
        }
        leaf address-family {
          type identityref {
            base address-family;
          }
          description
            "address-family of the staticrt-entry";
        }

        leaf enable-FRR {
          type boolean;
          description
            "Enable FRR.FRR is implemented only on static routes
             that are manually configured. That is, FRR is not
             implemented on iterated next hops.";
        }

        list staticrt-entries {
          key "ip-prefix ip-prefix-mask output-interface "
             +"target-VRF-name target-nexthop";
          ordered-by system;

          uses staticrt-entry;
          uses staticrt-reachability-paras;

          description
            "Define static routes.";
        }
      }
    }
    container staticrt-state {
      config false;
      description
         "Operational state of static routes.";

      container staticrt-rib{
        description
          "Define the operational state data for static routes.";

        list staticrt-route {
          description
            "Static routes are organized into list of routes.";

          leaf index {
            type uint32;
            description
              "Static route entry index.";
          }

          leaf topo-name {
            type string;
            description
              "The topology name of the destination ip prefix
               belonging to.";
          }

          leaf VRF-name {
            type string;
            description
              "VRF-name of the set of static routes";
          }

          leaf address-family {
            type string;
            description
              "Address-family of the set of static-routes";
          }

          uses staticrt-entry;
          uses staticrt-reachability-paras;

          leaf iterated-nexthop {
            type inet:ip-address;
            config false;
            description "The iterated nexthop.";
          }

          leaf iterated-output-interface {
            type string;
            config false;
            description "The iterated output interface name.";
          }

          leaf label {
            type uint32;
            config false;
            description "Specifies egress label.";
          }

          leaf route-state {
            type string;
            config false;
            description "Route state.";
          }

          leaf interface-state {
            type string;
            config false;
            description "The configured output interface state.";
          }
          uses staticrt-reachability-state;
        }
      }
      container staticrt-statistics {
        config false;
        description
          "Define the statistics of list of static routes.";
        list staticrt-stats {
          description
            "Statistics of list of static routes per VRF &
             Address-family & topology.";

          leaf topo-name {
            type string;
            description
              "The topology name of the destination ip prefix
               belonging to.";
          }

          leaf VRF-name {
            type string;
            description
              "Vrf-name of the set of static routes";
          }

          leaf address-family {
            type string;
            description
              "Address-family of the set of static-routes";
          }

          list static-route-stats {
            description
              "This defines the static route statistics of
               each static route.";

            uses staticrt-entry;

            leaf classified-pkts {
              type uint64;
              description
                " Number of total packets which matched
                  to the static route";
            }
            leaf classified-bytes {
              type uint64;
              description
                " Number of total bytes which matched
                  to the static route";
            }
          }
        }
      }
    }
  }

  container BFD-paras-cfg {
    description
      "This container defines the corresponding BFD session
       information for detecting the configured nexthop
       reachability of the static route.";

    leaf BFD-enable {
      type boolean;
      description
        "The flag indicates whether the router enable
         the corresponding BFD session for this static route.";
    }

    list BFD-session-paras {
      key "BFD-session-name";
      description "The BFD sessions for static routes";

      leaf BFD-session-name {
        type string;
        description "The BFD session name.";
      }

      leaf address-family {
        type identityref {
          base address-family;
        }
        description
          " address-family of the staticrt-entry";
      }

      leaf interface-name {
        type string;
        description "Interface name.";
      }

      leaf destination-VRF-name {
        type string;
        description "Destination vpn instance name for Gateway.";
      }

      leaf nexthop {
        type inet:ip-address;
        description "NextHop address.";
      }

      leaf local-ip-address {
        type inet:ip-address;
        description "The local ip address of the BFD session.";
      }

      leaf min-tx-interval {
        type uint32;
        description "Min transmit interval.";
      }

      leaf min-rx-interval {
        type uint32;
        description "Min receive interval.";
      }

      leaf multiplier {
        type uint32;
        description "Multiplier value.";
      }
    }
  }
}
