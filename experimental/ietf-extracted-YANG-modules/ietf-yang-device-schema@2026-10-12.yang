module ietf-yang-device-schema {
  yang-version 1.1;
  namespace "urn:ietf:params:xml:ns:yang:ietf-yang-device-schema";
  prefix yds;

  import ietf-yang-semver {
    prefix ys;
    reference "RFC XXXX: YANG Semantic Versioning";
  }
  import ietf-yang-package-types {
    prefix pkg-types;
    ys:recommended-min-version 0.10.0;
    reference "RFC XXXX: YANG Packages";
  }
  import ietf-datastores {
    prefix ds;
    reference "RFC 8342: Network Management Datastore Architecture";
  }
  import ietf-inet-types {
    prefix inet;
    reference "RFC 9911: Common YANG Data Types";
  }

  organization
    "IETF NETMOD (Network Modeling) Working Group";
  contact
    "WG Web:   <https://datatracker.ietf.org/wg/netmod/>
     WG List:  <mailto:netmod@ietf.org>

     Editor:   Robert Wilton
               <mailto:rwilton@cisco.com>";

  description
    "This module defines an advertisement of datastore schemas for
     a device or operating system release, using references to
     separate YANG package files. This module is generally expected
     to be used within an RFC 9195 YANG instance data set.
     Contact, organization, description, and document revision
     metadata are carried in that instance data set.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-10-12 {
    ys:version 0.1.0;
    description
      "Initial revision";
    reference
      "RFC XXXX: YANG Packages";
  }

  container device-schema {
    config false;
    description
      "A description of the datastore schemas for one device or
       operating system release.";

    leaf device {
      type string;
      mandatory true;
      description
        "The device, device family, or operating system schema
         that is being specified.";
    }
    leaf release {
      type string;
      mandatory true;
      description
        "The software release or version to which this
         advertisement applies. This is an opaque string and need
         not be a YANG Semantic Version.";
    }
    leaf yang-library {
      type inet:uri;
      description
        "A URI for an RFC 9195 instance data document containing
         equivalent RFC 8525 YANG library data for this device and
         release. Its datastore bindings and resolved schemas MUST
         match this advertisement.";
    }

    list schema {
      key "name";
      min-elements 1;
      description
        "A referentially complete datastore schema that may be
         shared by multiple datastores.";

      leaf name {
        type string;
        description
          "The name of the schema. This MUST be the same as the
           name advertised by the device in YANG library.";
      }
      list package {
        key "name version";
        min-elements 1;
        ordered-by user;
        description
          "References to separate YANG package files that
           collectively define this schema. The resolved package
           schema is constructed as per RFC XXXX, Section 5.4.3.
           The resolved schema MUST be referentially complete.";
        reference
          "RFC XXXX: YANG Packages, Section 5.4.3";

        uses pkg-types:yang-pkg-identification-leafs;
        uses pkg-types:yang-pkg-location;
      }
      leaf-list feature {
        type pkg-types:scoped-feature;
        description
          "Features enabled in addition to those enabled by the
           resolved packages, identified as
           '<module-name>:<feature-name>'. Each feature MUST be
           defined by an implemented module in this schema.
           Features already enabled by the packages MAY be listed.";
      }
    }

    list datastore {
      key "name";
      min-elements 1;
      description
        "All datastores supported by this device or operating
         system release, and their associated schemas. Datastores
         with the same schema SHOULD reference the same entry.";

      leaf name {
        type ds:datastore-ref;
        description
          "The identity of the datastore.";
      }
      leaf schema {
        type leafref {
          path "../../schema/name";
        }
        mandatory true;
        description
          "The schema supported by this datastore.";
      }
    }
  }
}
