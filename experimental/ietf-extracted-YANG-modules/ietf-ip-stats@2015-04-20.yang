module ietf-ip-stats {

  namespace "urn:ietf:params:xml:ns:yang:ietf-ip-stats";
  // replace with IANA namespace when assigned
  prefix ip-stats;

  import ietf-ip {
  prefix ip;  
  }
  import ietf-interfaces {
  prefix if;
  }
  import ietf-inet-types {
  prefix inet;
  }
  import ietf-yang-types {
  prefix yang;
  }
  import iana-if-type {
  prefix ianaift;
  }

  organization
    IETF NETMOD (NETCONF Data Modeling Language) Working Group";

  contact
    "WG Web:   <http://tools.ietf.org/wg/netmod/>
     WG List:  <mailto:netmod@ietf.org>

     WG Chair: Thomas Nadeau
               <mailto:tnadeau@lucidvision.com>

     WG Chair: Juergen Schoenwaelder
               <mailto:j.schoenwaelder@jacobs-university.de>

     Editor:   Steve Baillargeon
               <mailto:steve.baillargeon@ericsson.com>";

  description
    "This YANG module contains a collection of IP and ICMP statistics
     for monitoring IPv4 and IPv6 implementations.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of TBD; see
     the RFC itself for full legal notices.";

  revision 2015-04-20 {
    description
      "Initial revision.";
    reference
      "TBD";
  }
