module ietf-yang-revisions {
  yang-version 1.1;
  namespace "urn:ietf:params:xml:ns:yang:ietf-yang-revisions";
  prefix rev;

  // RFC Ed.: We need the bis version to get the new type revision-identifier
  // If 6991-bis is not yet an RFC we need to copy the definition here
  import ietf-yang-types {
    prefix yang;
    reference
      "XXXX [ietf-netmod-rfc6991-bis]: Common YANG Data Types";
  }

  organization
    "IETF NETMOD (Network Modeling) Working Group";
  contact
    "WG Web:   <https://datatracker.ietf.org/wg/netmod/>
    WG List:  <mailto:netmod@ietf.org>

    Author:   Joe Clarke
              <mailto:jclarke@cisco.com>

    Author:   Reshad Rahman
              <mailto:reshad@yahoo.com>

    Author:   Robert Wilton
              <mailto:rwilton@cisco.com>

    Author:   Balazs Lengyel
              <mailto:balazs.lengyel@ericsson.com>

    Author:   Jason Sterne
              <mailto:jason.sterne@nokia.com>";
  description
    "This YANG 1.1 module contains definitions and extensions to
    support updated YANG revision handling.

    Copyright (c) 2021 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX; see
    the RFC itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  // RFC Ed.: update the date below with the date of RFC publication
  // and remove this note.
  // RFC Ed.: replace XXXX (inc above) with actual RFC number and
  // remove this note.

  revision 2021-06-30 {
    rev:revision-label 1.0.0-draft-ietf-netmod-yang-module-versioning-04;
    description
      "Initial version.";
    reference
      "XXXX: Updated YANG Module Revision Handling";
  }

  typedef revision-label {
    type string {
      length "1..255";
      pattern '[a-zA-Z0-9,\-_.+]+';
      pattern '\d{4}-\d{2}-\d{2}' {
        modifier invert-match;
      }
    }
    description
      "A label associated with a YANG revision.

      Alphanumeric characters, comma, hyphen, underscore, period
      and plus are the only accepted characters. MUST NOT match
      revision-date.";
    reference
      "XXXX: Updated YANG Module Revision Handling;
      Section 3.3, Revision label";
  }

  typedef revision-date-or-label {
    type union {
      type yang:revision-identifier;
      type revision-label;
    }
    description
      "Represents either a YANG revision date or a revision label";
  }

  extension non-backwards-compatible {
    description
      "This statement is used to indicate YANG module revisions that
      contain non-backwards-compatible changes.

      The statement MUST only be a substatement of the 'revision'
      statement.  Zero or one 'non-backwards-compatible' statements
      per parent statement is allowed.  No substatements for this
      extension have been standardized.

      If a revision of a YANG module contains changes, relative to
      the preceding revision in the revision history, that do not
      conform to the backwards compatible module update rules defined
      in RFC-XXX, then the 'non-backwards-compatible' statement MUST
      be added as a substatement to the revision statement.

      Conversely, if a revision does not contain a
      'non-backwards-compatible' statement then all changes,
      relative to the preceding revision in the revision history,
      MUST be backwards-compatible.

      A new module revision that only contains changes that are
      backwards compatible SHOULD NOT include the
      'non-backwards-compatible' statement.  An example of when
      an author might add the 'non-backwards-compatible' statement
      is if they believe a change could negatively impact clients
      even though the backwards compatibility rules defined in
      RFC-XXXX classify it as a backwards-compatible change.

      Add, removing, or changing a 'non-backwards-compatible'
      statement is a backwards-compatible version change.";

    reference
      "XXXX: Updated YANG Module Revision Handling;
      Section 3.2, nbc-changes revision extension statement";
  }

  extension revision-label {
    argument revision-label;
    description
      "The revision label can be used to provide an additional
      versioning identifier associated with a module or submodule
      revision.  One such scheme that
      could be used is [XXXX: ietf-netmod-yang-semver].

      The format of the revision-label argument MUST conform to the
      pattern defined for the revision-label typedef in this module.

      The statement MUST only be a substatement of the revision
      statement.  Zero or one revision-label statements per parent
      statement are allowed.  No substatements for this extension
      have been standardized.

      Revision labels MUST be unique amongst all revisions of a
      module or submodule.

      Adding a revision label is a backwards-compatible version
      change.  Changing or removing an existing revision label in
      the revision history is a non-backwards-compatible version
      change, because it could impact any references to that
      revision label.";

    reference
      "XXXX: Updated YANG Module Revision Handling;
      Section 3.3, Revision label";
  }

  extension revision-label-scheme {
    argument revision-label-scheme-identity;
    description
      "The revision label scheme specifies which revision-label scheme
      the module or submodule uses.

      The mandatory revision-label-scheme-identity argument MUST be an
      identity derived from revision-label-scheme-base.

      This extension is only valid as a top-level statement, i.e.,
      given as as a substatement to 'module' or 'submodule'.  No
      substatements for this extension have been standardized.

      This extension MUST be used if there is a revision-label
      statement in the module or submodule.

      Adding a revision label scheme is a backwards-compatible version
      change.  Changing a revision label scheme is a
      non-backwards-compatible version change, unless the new revision
      label scheme is backwards-compatible with the replaced revision
      label scheme.  Removing a revision label scheme is a
      non-backwards-compatible version change.";
    reference
      "XXXX: Updated YANG Module Revision Handling;
      Section 3.3.1, Revision label scheme extension statement";
  }

  extension revision-or-derived {
    argument revision-date-or-label;
    description
      "Restricts the revision of the module that may be imported to
      one that matches or is derived from the specified
      revision-date or revision-label.

      The argument value MUST conform to the
      'revision-date-or-label' defined type.

      The statement MUST only be a substatement of the import
      statement.  Zero, one or more 'revision-or-derived' statements
      per parent statement are allowed.  No substatements for this
      extension have been standardized.

      If specified multiple times, then any module revision that
      satisfies at least one of the 'revision-or-derived' statements
      is an acceptable revision for import.

      An 'import' statement MUST NOT contain both a
      'revision-or-derived' extension statement and a
      'revision-date' statement.

      A particular revision of an imported module satisfies an
      import's 'revision-or-derived' extension statement if the
      imported module's revision history contains a revision
      statement with a matching revision date or revision label.

      The 'revision-or-derived' extension statement does not
      guarantee that all module revisions that satisfy an import
      statement are necessarily compatible, it only gives an
      indication that the revisions are more likely to be
      compatible.

      Adding, removing or updating a 'revision-or-derived'
      statement to an import is a backwards-compatible change.
      ";

    reference
      "XXXX: Updated YANG Module Revision Handling;
      Section 4, Import by derived revision";
  }

  identity revision-label-scheme-base {
    description
      "Base identity from which all revision label schemes are
      derived.";

      reference
        "XXXX: Updated YANG Module Revision Handling;
        Section 3.3.1, Revision label scheme extension statement";

  }
}
