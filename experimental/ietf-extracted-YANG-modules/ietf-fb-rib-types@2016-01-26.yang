module ietf-fb-rib-types {

 yang-version "1";

 // namespace
   namespace "urn:ietf:params:xml:ns:yang:ietf-fb-rib-types";
   prefix "fb-rib-t";
       import ietf-interfaces {prefix "if";}
       import ietf-access-control-list {prefix "acl";}
       import ietf-routing {prefix "rt";}
       import ietf-pkt-eca-policy {prefix "pkt-eca";}

 // meta
 organization
   "IETF";

 contact
    "email: sriganesh.kini@ericsson.com
     email: cengiz@packetdesign.com
     email: anoop@ieee.duke.edu
     email: ivandean@gmal.org
     email: shares@ndzh.com;
     email: linda.dunbar@huawei.com;
     email: russ@riw.com;
     email: Jeff.Tantsura@ericsson.com;
        ";

 description
   "This module describes a YANG model for the I2RS
   Filter-based RIB Types.  These types
   specify types for the Filter-Based RIB.

       Copyright (c) 2015 IETF Trust and the persons identified as
   the document authors.  All rights reserved.

   Redistribution and use in source and binary forms, with or
   without modification, is permitted pursuant to, and subject
   to the license terms contained in, the Simplified BSD
   License set forth in Section 4.c of the IETF Trust's Legal
   Provisions Relating to IETF Documents
   (http://trustee.ietf.org/license-info).";

 revision "2016-01-26" {
     description
       "Filter-Based RIB protocol ";
       reference "draft-hares-i2rs-fb-rib-data-model-01";
 }

   typedef fb-rib-policy-type-def {
          type identityref {
            base "fb-rib-policy-type";
                }
               description
               "This type is used to refer to FB-RIB type";
    }

       identity fb-rib-policy-type {
            description
            "Types of filter-based policies
                 acl and eca";
        }

          identity fb-rib-acl {
                 base fb-rib-policy-type;
             description
         "filter based policy based on access-lists";
           }

          identity fb-bnp-eca-rules {
                 base fb-rib-policy-type;
             description
         "filter based policy based on qos forwarding rules";
           }

       typedef fb-rules-status  {
          type identityref {
            base "fb-rule-opstat";
                }
               description
               "This type is used to refer to FB-RIB type";
        }

         identity fb-rule-opstat {
               description
               "operational statues for filter rules
                inactive and active";
                }

         identity fb-rule-inactive {
               base fb-rule-opstat;
               description
               "policy rule is inactive";
          }

         identity fb-rule-active {
               base fb-rule-opstat;
               description
               "policy rule is active";
          }

         grouping fb-rib-rule-order-status {
         leaf statement-order {
                 type uint16;
                 description "order identifier";
          }
          leaf statement-oper_status {
                  type fb-rules-status;
                  description "status of rule";
               }
               description "filter-rib
                 policy rule order and status";
       }

    grouping fb-rib-group-order-status {
         leaf group-order{
           type uint16;
           description "group order";
          }
         leaf group-refcnt {
           type uint16;
           description "refcnt for this group";
               }
          leaf group-installed {
           type uint16;
           description "number of rules installed";
               }
               description "fb-rib group list order
                  and status info.";
         }

       grouping fb-rib-status-info {
          leaf fb-rib-update-ref {
                type uint64;
            description
                "number of updates to this FB RIB
                 since last reboot";
          }
          description "FB-RIB update info";
        }

       grouping default-fb-rib {

               leaf default-rib {
                       type string;
                       description "default ribs for
                         normal and ephemeral filter-based rib
                         should use rt:routing:routing-instance:name";
               }

               leaf i2rs-instance {
                       type string;
                   description "default I2RS RIB
                         should use
              i2rs-rib:routing-instance:name";
               }
               leaf rib-name {
                       type string;
               description "name of RIB";
               }

               leaf fb-rib-update-ref {
                       type uint64;
                       description " number of
                         updates to this FB RIB
                     since last reboot";
                  }
           description "I2RS RIB which will be used
                  even if none of the policy match";
   }

   grouping fb-ribs {
         list fib-rib {
                  key fb-rib-name;
                  leaf fb-rib-name {
                       type string;
                               mandatory true;
                       description "RIB name";
          }
                 uses rt:address-family;
             list fb-rib-intf {
                         key "name";
                         leaf name {
                               type if:interface-ref;
                           description
                            "A reference to the name of a
                                configured network layer
                            interface.";
                          }
                         description "This represents
                           the list of interfaces
                           associated with this routing instance.
                           The interface list helps constrain the
                           boundaries of packet forwarding.
                           Packets coming on these interfaces are
                           directly associated with the given routing
                           instance. The interface list contains a
                           list of identifiers, with each identifier
                           uniquely identifying an interface.";
               }
                       uses default-fb-rib;
               list instance-using {
                         key instance-name;
                         leaf instance-name {
                           type string;
                           description
                               " name of instance using this fb-rib
                                rt:routing-instance";
                          }
                         description "instances using
                          this fb-rib";
                       }
                       list fb-rib-group {
                          key group-name;
                      leaf group-name {
                            type string;
                            description "policy-group name";
                          }
                          leaf fb-group-policy-type {
                           type fb-rib-policy-type-def;
                           description "Policy type (acl/eca)";
                          }
                      list acl-group {
                           key name;
              leaf name {
                                 type string;
                                 description "name of access list group";
                                }
                               list acls {
                                 key fb-acl-name;
                                 leaf fb-acl-name {
                                   type acl:access-control-list-ref;
                                   description "acl list name
                                         associated with FB-RIB list";
                                 }
                                 leaf fb-acl-type {
                                       type acl:acl-type;
                                       description "acl type";
                                 }
                 description "list of acls";
                               }
               description "acl group entry";
                         }
                         list pkt-eca-rules {
                           key name;
                           leaf eca-group-name {
                              type pkt-eca:pkt-eca-rule-ref;
                              description "ECA rule";
                                }
                               description "list of eca groups";
                         }
                         uses fb-rib-group-order-status;
                         description "list of ordered policy groups ";
                   }
               description  "Configuration of
                  an filter-based rib list";
          }
       description "fb-rib group";
  }
}
