module ietf-network-inventory {
  yang-version 1.1;
  namespace "urn:ietf:params:xml:ns:yang:ietf-network-inventory";
  prefix ni;

  import ietf-yang-types {
    prefix yang;
    reference
      "RFC6991: Common YANG Data Types.";
  }

  import iana-hardware {
    prefix ianahw;
    reference
      "RFC 8348: A YANG Data Model for Hardware Management.";
  }

  organization
    "IETF CCAMP Working Group";
  contact
    "WG Web:   <https://datatracker.ietf.org/wg/ccamp/>
     WG List:  <mailto:ccamp@ietf.org>

     Editor:   Chaode Yu
               <yuchaode@huawei.com>

     Editor:   Italo Busi
               <italo.busi@huawei.com>

     Editor:   Aihua Guo
               <aihuaguo.ietf@gmail.com>

     Editor:   Sergio Belotti
               <sergio.belotti@nokia.com>

     Editor:   Jean-Francois Bouquier
               <jeff.bouquier@vodafone.com>

     Editor:   Fabio Peruzzini
               <fabio.peruzzini@telecomitalia.it>";

  description
    "This module defines a model for retrieving network inventory.

    The model fully conforms to the Network Management
    Datastore Architecture (NMDA).

    Copyright (c) 2021 IETF Trust and the persons
    identified as authors of the code.  All rights reserved.

    Redistribution and use in source and binary forms, with or
    without modification, is permitted pursuant to, and subject
    to the license terms contained in, the Simplified BSD License
    set forth in Section 4.c of the IETF Trust's Legal Provisions
    Relating to IETF Documents
    (https://trustee.ietf.org/license-info).
    This version of this YANG module is part of RFC XXXX; see
    the RFC itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  // RFC Ed.: replace XXXX with actual RFC number and remove this
  // note.
  // RFC Ed.: update the date below with the date of RFC publication
  // and remove this note.

  revision 2021-11-10 {
    description
      "Initial revision.";
    reference
      "draft-yg3bp-ccamp-optical-inventory-yang-01: A YANG Data
      Model for Optical Network Inventory.";
  }

  container network-inventory {
    config false;
    description
      "The top-level container for the network inventory
      information.";
    uses equipment-rooms-grouping;
    uses network-elements-grouping;
  }

  grouping common-entity-attributes {
    description
      "A set of attributes which are common to all the entities
      (e.g., component, equipment room) defined in this module.";
    leaf uuid {
      type yang:uuid;
      description
        "Uniquely identifies an entity (e.g., component).";
    }
    leaf name {
      type string;
      description
        "A name for an entity (e.g., component), as specified by
        a network manager, that provides a non-volatile 'handle'
        for the entity and that can be modified anytime during the
        entity lifetime.
        If no configured value exists, the server MAY set the value
        of this node to a locally unique value in the operational
        state.";
    }
  }
  grouping network-elements-grouping {
    description
      "The attributes of the network elements.";
    container network-elements {
      description
        "The container for the list of network elements.";
      list network-element {
        key uuid;
        description
          "The list of network elements within the network.";
        uses common-entity-attributes;
        uses components-grouping;
      }
    }
  }

  grouping equipment-rooms-grouping {
    description
      "The attributes of the equipment rooms.";
    container equipment-rooms {
      description
        "The container for the list of equipment rooms.";
      list equipment-room {
        key uuid;
        description
          "The list of equipment rooms within the network.";
        uses common-entity-attributes;
        leaf location {
          type string;
          description
            "compared with the location information of the other
            inventory objects, a GIS address is preferred for
            equipment room";
        }
        list rack {
          key uuid;
          description
            "The list of racks within an equipment room.";
          uses common-entity-attributes;
          leaf row-number {
            type uint32;
            description
              "Identifies the row within the equipment room where
              the rack is located.";
          }
          leaf rack-number {
            type uint32;
            description
              "Identifies the physical location of the rack within
              the row.";
          }
          list shelves {
            key uuid;
            description
              "The list of shelves within a rack.";
            uses common-entity-attributes;
            leaf shelf-number {
              type uint8;
              description
                "Identifies the location of the shelf within the
                rack.";
            }
            container chassis-ref {
              description
                "The reference to the network element component
                representing this shelf.";
              leaf ne-ref {
                type leafref {
                  path "/ni:network-inventory/ni:network-elements"
                    + "/ni:network-element/ni:uuid";
                }
                description
                  "The reference to the network element containing
                  the component.";
              }
              leaf component-ref {
                type leafref {
                  path "/ni:network-inventory/ni:network-elements"
                     + "/ni:network-element[ni:uuid"
                     + "=current()/../ne-ref]/ni:components"
                     + "/ni:component/ni:uuid";
                }
                description
                  "The reference to the component within the network
                  element.";
              }
            }
          }
        }
      }
    }
  }

  grouping components-grouping {
    description
      "The attributes of the hardware components.";
    container components {
      description
        "The container for the list of components.";
      list component {
        key uuid;
        description
          "The list of components within a network element.";
        uses common-entity-attributes;
        leaf description {
          type string;
          description
            "A textual description of the component.";
          reference
            "RFC 8348: A YANG Data Model for Hardware Management.";
        }
        leaf class {
          type identityref {
            base ianahw:hardware-class;
          }
          description
            "An indication of the general hardware type of the
             component.";
          reference
            "RFC 8348: A YANG Data Model for Hardware Management.";
        }
        leaf  parent-rel-pos {
          type int32 {
            range "0 .. 2147483647";
          }
          description
            "An indication of the relative position of this child
             component among all its sibling components.  Sibling
             components are defined as components that:

               o share the same value of the 'parent' node and

               o share a common base identity for the 'class' node.";
          reference
            "RFC 8348: A YANG Data Model for Hardware Management.";
        }
        list children {
          key child-ref;
          description
            "The child components that are physically contained by
            this component.";

          leaf child-ref {
            type leafref {
              path "../../ni:uuid";
            }
            description
              "The reference to the child component.";
          }
        }
        container parent {
          description
            "The parent component that physically contains this
             component.

             If this container is not instantiated, it indicates
             that this component is not contained in any other
             component.

             In the event that a physical component is contained by
             more than one physical component (e.g., double-wide
             modules), this container contains the data of one of
             these components.  An implementation MUST use the same
             component every time this container is instantiated.";
          leaf parent-ref {
            type leafref {
              path "../../ni:uuid";
            }
            description
              "The reference to the parent component.";
          }
        }
      }
    }
  }
}
