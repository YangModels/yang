module service-function-path {

  namespace "urn:cisco:params:xml:ns:yang:sfc-path";

  prefix sfc-path;

  import ietf-inet-types { prefix inet; }
  import ietf-yang-types { prefix yang; }
  import service-function {prefix sfc-sf; }

  organization "Cisco Systems, Inc.";
  contact "Reinaldo Penno <repenno@cisco.com>";

  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-29-04 {
    description
    "Changes based on Opendaylight Testing";
  }

  // Service Function Path

  container service-function-path {
    description
      "A Service Function Path is an instantiation of a Service Chain. It
       specifies the actual firewall (say, firewall-3) that will be traversed by
       the packets. The Service Path needs to be known before hand or stitched
       run-time (given the dynamic LB decision) since a forwarding decision need
       to be made regardless.";
    leaf-list service-function-instance {
      type sfc-sf:service-function-ref;
      ordered-by user;
      description
        "A list of service function instances that compose the service chain";
    }
  }
}
