submodule ietf-bgp-common {
  yang-version "1.1";
  belongs-to ietf-bgp {
    prefix "bgp";
  }

  import ietf-bgp-types {
    prefix bt;
    reference
      "RFC XXXX: BGP Model for Service Provider Network.";
  }
  import ietf-inet-types {
    prefix inet;
    reference
      "RFC 6991: Common YANG Data Types.";
  }
  import ietf-yang-types {
    prefix yang;
    reference
      "RFC 6991: Common YANG Data Types.";
  }

  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com,
              Jeffrey Haas (jhaas at pfrc.org).";

  description
    "This sub-module contains common groupings that are common across
     multiple contexts within the BGP module. That is to say that
     they may be application to a subset of global, peer-group or
     neighbor contexts.";

  revision "2019-10-03" {
    description
      "Initial Version";
    reference
      "RFC XXXX, BGP Model for Service Provider Network.";
  }

  /*
   * Features.
   */
  feature damping {
    description
      "Weighted route dampening is supported.";
  }

  grouping neighbor-group-timers-config {
    description
      "Config parameters related to timers associated with the BGP
       peer";

    leaf connect-retry-interval {
      type uint16 {
        range "1..max";
      }
      units "seconds";
      default "120";
      description
        "Time interval (in seconds) for the ConnectRetryTimer. The
         suggested value for this timer is 120 seconds.";
      reference
        "RFC 4271, Section 8.2.2.  This is the value used
         to initialize the 'ConnectRetryTimer'.";
    }

    leaf hold-time {
      type uint16 {
        range "0 | 3..65535";
      }
      units "seconds";
      default "90";
      description
        "Time interval (in seconds) for the HoldTimer established
         with the peer.  When read as operational data (ro), the
         value of this object is calculated by this BGP speaker,
         using the smaller of the values in hold-time that was
         configured (rw) in the running datastore and the Hold Time
         received in the OPEN message.

         This value must be at least three seconds
         if it is not zero (0).

         If the Hold Timer has not been established
         with the peer this object MUST have a value
         of zero (0).

         If the configured value of hold-time object was
         a value of (0), then when read this object MUST have a
         value of (0) also.";
      reference
        "RFC 4271, Section 4.2.
         RFC 4271, Section 10.";
    }

    leaf keepalive {
      type uint16 {
        range "0..21845";
      }
      units "seconds";
      default "30";
      description
        "When used as a configuration (rw) value, this Time interval
         (in seconds) for the KeepAlive timer configured for this BGP
         speaker with this peer. The value of this object will only
         determine the KEEPALIVE messages' frequency relative to
         the value specified in configured value for hold-time.

         If the value of this object is zero (0), no periodical
         KEEPALIVE messages are sent to the peer after the BGP
         connection has been established.  The suggested value for
         this timer is 30 seconds.;

         The actual time interval for the KEEPALIVE messages is
         indicated by operational value of keepalive. That value
         of this object is calculated by this BGP speaker such that,
         when compared with hold-time, it has the same proportion
         that keepalive has, compared with hold-time. A
         reasonable maximum value for this timer would be one third
         of that of hold-time.";
      reference
        "RFC 4271, Section 4.4.
         RFC 4271, Section 10.";
    }

    leaf min-as-origination-interval {
      type uint16 {
        range "0..max";
      }
      units "seconds";
      default "15";
      description
        "Time interval (in seconds) for the MinASOriginationInterval
         timer. The suggested value for this timer is 15 seconds.";
      reference
        "RFC 4271, Section 9.2.1.2.
         RFC 4271, Section 10.";
    }

    leaf min-route-advertisement-interval {
      type uint16 {
        range "0..max";
      }
      units "seconds";
      description
        "Time interval (in seconds) for the
         MinRouteAdvertisementInterval timer.
         The suggested value for this timer is 30
         seconds for EBGP connections and 5
         seconds for IBGP connections.";
      reference
        "RFC 4271, Section 9.2.1.1.
         RFC 4271, Section 10.";
    }
  }

  grouping neighbor-group-config {
    description
      "Neighbor level configuration items.";

    leaf remote-as {
      type inet:as-number;
      description
        "The remote autonomous system number received in
         the BGP OPEN message.";
      reference
        "RFC 4271, Section 4.2.";
    }

    leaf peer-as {
      type inet:as-number;
      description
        "AS number of the peer.";
    }

    leaf local-as {
      type inet:as-number;
      description
        "The local autonomous system number that is to be used when
         establishing sessions with the remote peer or peer group, if
         this differs from the global BGP router autonomous system
         number.";
    }

    leaf peer-type {
        type bt:peer-type;
        description
          "Explicitly designate the peer or peer group as internal
           (iBGP) or external (eBGP).";
    }

    leaf remove-private-as {
      // could also make this a container with a flag to enable
      // remove-private and separate option.  here, option implies
      // remove-private is enabled.
      type bt:remove-private-as-option;
      description
        "Remove private AS numbers from updates sent to peers - when
         this leaf is not specified, the AS_PATH attribute should be
         sent to the peer unchanged";
    }

    container route-flap-damping {
      if-feature damping;

      leaf enable {
        type boolean;
        default false;
        description
          "Enable route flap damping.";
      }

      leaf suppress-above {
        type decimal64 {
          fraction-digits 1;
        }
        default "3.0";
        description
          "This is the value of the instability metric at which
           route suppression takes place. A route is not installed
           in the forwarding information base (FIB), or announced
           even if it is reachable during the period that it is
           suppressed.";
      }

      leaf reuse-above {
        type decimal64 {
          fraction-digits 1;
        }
        default "2.0";
        description
          "This is the value of the instability metric at which a
           suppressed route becomes unsuppressed if it is reachable
           but currently suppressed. The value assigned to
           reuse-below must be less than suppress-above.";
      }

      leaf max-flap {
        type decimal64 {
          fraction-digits 1;
        }
        default "16.0";
        description
          "This is the upper limit of the instability metric. This
           value must be greater than the larger of 1 and
           suppress-above.";
      }

      leaf reach-decay {
        type yang:gauge32;
        units "seconds";
        default "300";
        description
          "This value specifies the time desired for the instability
           metric value to reach one-half of its current value when
           the route is reachable. This half-life value determines
           the rate at which the metric value is decayed. A smaller
           half-life value makes a suppressed route reusable sooner
           than a larger value.";
      }

      leaf unreach-decay {
        type yang:gauge32;
        units "seconds";
        default "900";
        description
          "This value acts the same as reach-decay except that it
           specifies the rate at which the instability metric is
           decayed when a route is unreachable. It should have a
           value greater than or equal to reach-decay.";
      }

      leaf keep-history {
        type yang:gauge32;
        units "seconds";
        default "1800";
        description
          "This value specifies the period over which the route
           flapping history is to be maintained for a given route.
           The size of the configuration arrays described below is
           directly affected by this value.";
      }
      description
        "Routes learned via BGP are subject to weighted route
         dampening.";
    }

    leaf send-community {
      if-feature "bt:send-communities";
      type bt:community-type;
      description
        "When supported, this tells the router to propogate any
         prefixes that are attached to this community. The value
         of 0 implies 'none'.";
    }

    leaf description {
      type string;
      description
        "An optional textual description (intended primarily for use
         with a peer or group";
    }
  }

  grouping neighbor-group-transport-config {
    description
      "Configuration parameters relating to the transport protocol
       used by the BGP session to the peer";

    leaf tcp-mss {
      type uint16;
      description
        "Sets the max segment size for BGP TCP sessions.";
    }

    leaf mtu-discovery {
      type boolean;
      default false;
      description
        "Turns path mtu discovery for BGP TCP sessions on (true) or
         off (false)";
    }

    leaf passive-mode {
      type boolean;
      default false;
      description
        "Wait for peers to issue requests to open a BGP session,
         rather than initiating sessions from the local router.";
    }

    leaf local-address {
      type union {
        type inet:ip-address;
        type leafref {
          path "../../../../interfaces/interface/name";
        }
      }
      description
        "Set the local IP (either IPv4 or IPv6) address to use for
         the session when sending BGP update messages.  This may be
         expressed as either an IP address or reference to the name
         of an interface.";
    }

    // TODO: Better form of authentication of the BGP session should
    // be added here. It can be in the form of TCP-AO [RFC 5925],
    // IPsec, or any other protocol deemed desirable.
    leaf auth-password {
      type string;
      description
        "Configures an MD5 authentication password for use with
         neighboring devices.";
    }
  }

  grouping graceful-restart-config {
    description
      "Configuration parameters relating to BGP graceful restart.";

    leaf enabled {
      type boolean;
      description
        "Enable or disable the graceful-restart capability.";
    }

    leaf restart-time {
      type uint16 {
        range 0..4096;
      }
      description
        "Estimated time (in seconds) for the local BGP speaker to
         restart a session. This value is advertise in the graceful
         restart BGP capability.  This is a 12-bit value, referred to
         as Restart Time in RFC4724.  Per RFC4724, the suggested
         default value is <= the hold-time value.";
      reference
        "RFC 4724: Graceful Restart Mechanism for BGP.";
    }
    leaf stale-routes-time {
      type uint32;
      description
        "An upper-bound on the time that stale routes will be
         retained by a router after a session is restarted. If an
         End-of-RIB (EOR) marker is received prior to this timer
         expiring stale-routes will be flushed upon its receipt - if
         no EOR is received, then when this timer expires stale paths
         will be purged. This timer is referred to as the
         Selection_Deferral_Timer in RFC4724";
      reference
        "RFC 4724: Graceful Restart Mechanism for BGP.";
    }

    leaf helper-only {
      type boolean;
      default true;
      description
        "Enable graceful-restart in helper mode only. When this leaf
         is set, the local system does not retain forwarding its own
         state during a restart, but supports procedures for the
         receiving speaker, as defined in RFC4724.";
      reference
        "RFC 4724: Graceful Restart Mechanism for BGP.";
    }
  }

  grouping global-group-use-multiple-paths {
    description
      "Common grouping used for both global and groups which provides
       configuration and state parameters relating to use of multiple
       paths";

    container use-multiple-paths {
      description
        "Parameters related to the use of multiple paths for the
        same NLRI";

      leaf enabled {
        type boolean;
        default false;
        description
          "Whether the use of multiple paths for the same NLRI is
           enabled for the neighbor. This value is overridden by any
           more specific configuration value.";
      }

      container ebgp {
        description
          "Multi-Path parameters for eBGP";

        leaf allow-multiple-as {
          type boolean;
          default "false";
          description
            "Allow multi-path to use paths from different neighboring
             ASes.  The default is to only consider multiple paths
             from the same neighboring AS.";
        }

        leaf maximum-paths {
          type uint32;
          default 1;
          description
            "Maximum number of parallel paths to consider when using
             BGP multi-path. The default is use a single path.";
        }
      }

      container ibgp {
        description
          "Multi-Path parameters for iBGP";

        leaf maximum-paths {
          type uint32;
          default 1;
          description
            "Maximum number of parallel paths to consider when using
             iBGP multi-path. The default is to use a single path";
        }
      }
    }
  }

  grouping route-selection-options {
    description
      "Configuration and state relating to route selection options";

    container route-selection-options {
      description
        "Parameters relating to options for route selection";

      leaf always-compare-med {
        type boolean;
        default "false";
        description
          "Compare multi-exit discriminator (MED) value from
           different ASes when selecting the best route.  The default
           behavior is to only compare MEDs for paths received from
           the same AS.";
      }

      leaf ignore-as-path-length {
        type boolean;
        default "false";
        description
          "Ignore the AS path length when selecting the best path.
           The default is to use the AS path length and prefer paths
           with shorter length.";
      }

      leaf external-compare-router-id {
        type boolean;
        default "true";
        description
          "When comparing similar routes received from external BGP
           peers, use the router-id as a criterion to select the
           active path.";
      }

      leaf advertise-inactive-routes {
        type boolean;
        default "false";
        description
          "Advertise inactive routes to external peers.  The default
           is to only advertise active routes.";
        reference
          "I-D.ietf-idr-best-external: Advertisement of the best
           external route in BGP.";
      }

      leaf enable-aigp {
        type boolean;
        default false;
        description
          "Flag to enable sending / receiving accumulated IGP
           attribute in routing updates";
        reference
          "RFC 7311: AIGP Metric Attribute for BGP.";
      }

      leaf ignore-next-hop-igp-metric {
        type boolean;
        default "false";
        description
          "Ignore the IGP metric to the next-hop when calculating BGP
           best-path. The default is to select the route for which
           the metric to the next-hop is lowest";
      }

      leaf enable-med {
        type boolean;
        default false;
        description
          "Flag to enable sending/receiving of MED metric attribute
           in routing updates.";
      }
    }
  }

  grouping state {
    description
      "Grouping containing common counters relating to prefixes and
       paths";

    leaf total-paths {
      type uint32;
      config false;
      description
        "Total number of BGP paths within the context";
    }

    leaf total-prefixes {
      type uint32;
      config false;
      description
        "Total number of BGP prefixes received within the context";
    }
  }
}
