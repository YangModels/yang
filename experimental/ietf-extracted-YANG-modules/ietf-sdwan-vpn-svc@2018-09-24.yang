module ietf-sdwan-vpn-svc {
  yang-version 1.1;
  namespace "urn:ietf:params:xml:ns:yang:ietf-sdwan-vpn-svc";
  prefix sdwan-vpn-svc;

  import ietf-inet-types {
    prefix inet;
  }
  import ietf-yang-types {
    prefix yang;
  }

  organization
    "IETF foo Working Group.";
  contact
    "WG List: foo@ietf.org
     Editor:  ";
  description
    "The YANG module defines a generic service configuration
     model for SD-WAN VPN.";

  revision 2018-09-25 {
    description
      "Initial revision";
    reference "A YANG Data Model for SD-WAN VPN.";
  }

  typedef svc-id {
    type string;
    description
      "Type definition for servicer identifier";
  }

  typedef address-family {
    type enumeration {
      enum ipv4 {
        description
          "IPv4 address family.";
      }
      enum ipv6 {
        description
          "IPv6 address family.";
      }
    }
    description
      "Defines a type for the address family.";
  }

  identity vpn-topology {
    description
      "Base identity for vpn topology.";
  }

  identity any-to-any {
    base vpn-topology;
    description
      "Identity for any-to-any VPN topology.";
  }

  identity hub-spoke {
    base vpn-topology;
    description
      "Identity for Hub-and-Spoke VPN topology.";
  }

  identity site-role {
    description
      "Site Role in a VPN topology ";
  }

  identity any-to-any-role {
    base site-role;
    description
      "Site in an any-to-any IP VPN.";
  }

  identity hub {
    base site-role;
    description
      "Hub Role in Hub-and-Spoke IP VPN.";
  }

  identity spoke {
    base site-role;
    description
      "Spoke Role in Hub-and-Spoke IP VPN.";
  }

  identity access-type {
    description
      "Access type of a site in a connection to WAN network";
  }
  identity ge {
    base access-type;
    description
      "GE";
  }

  identity ef {
    base access-type;
    description
      "EF";
  }

  identity xge {
    base access-type;
    description
      "XGE";
  }

  identity lte {
    base access-type;
    description
      "LTE";
  }

  identity xdsl-atm {
    base access-type;
    description
      "xDSL(ATM)";
  }

  identity xdsl-ptm {
    base access-type;
    description
      "xDSL(PTM)";
  }

  identity routing-protocol-type {
    description
      "Base identity for routing protocol type.";
  }

  identity ospf {
    base routing-protocol-type;
    description
      "Identity for OSPF protocol type.";
  }

  identity bgp {
    base routing-protocol-type;
    description
      "Identity for BGP protocol type.";
  }

  identity static {
    base routing-protocol-type;
    description
      "Identity for static routing protocol type.";
  }

  identity addr-allocation {
    description
      "Base identity for address allocation";
  }

  identity addr-allocation-static {
    base addr-allocation;
    description
      "Static";
  }

  identity traffic-direction {
    description
      "Base identity for traffic direction";
  }

  identity inbound {
    base traffic-direction;
    description
      "Identity for inbound";
  }

  identity outbound {
    base traffic-direction;
    description
      "Identity for outbound";
  }

  identity both {
    base traffic-direction;
    description
      "Identity for both";
  }

  identity traffic-action {
    description
      "Base identity for traffic action";
  }

  identity permit {
    base traffic-action;
    description
      "Identity for permit action";
  }

  identity deny {
    base traffic-action;
    description
      "Identity for deny action";
  }

  identity bd-limit-type {
    description
      "base identity for bd limit type";
  }

  identity percent {
    base bd-limit-type;
    description
      "Identity for percent";
  }

  identity value {
    base bd-limit-type;
    description
      "Identity for value";
  }

  grouping qos-bandwidth-policy {
    list qos-bandwidth-policy {
      key "name";
      leaf name {
        type string;
        description
          "QoS name";
      }
      leaf priorty {
        type uint32;
        description
          "Priorty";
      }
      container qos {
        leaf classification-name {
          type leafref {
            path "/sdwan-vpn-svc/sdwan-vpn/classification-profile/name";
          }
          description
            "Qos Classification name";
        }
        leaf qos-profile-name {
          type leafref {
            path "/sdwan-vpn-svc/sdwan-vpn/qos-profile/name";
          }
          description
            "Qos profile name";
        }
        description
          "Container for QOS";
      }
      description
        "List for qos policy";
    }
    description
      "Gourping for qos-bandwidth-policy";
  }

  grouping qos-profile {
    list qos-profile {
      key "name";
      leaf name {
        type string;
        description
          "QOS profile name";
      }
      leaf bd-limit-type {
        type identityref {
          base bd-limit-type;
        }
        description
          "bd limit type";
      }
      container percent {
        when "../bd-limit-type = 'percent'";
        leaf width-percent {
          type uint32;
          description
            "Width percent";
        }
        description
          "Container for percent";
      }
      container value {
        when "../bd-limit-type = 'value'";
        leaf cir {
          type uint32;
          description
            "CIR";
        }
        leaf pir {
          type uint32;
          description
            "PIR";
        }
        description
          "Container for value";
      }
      description
        "List for qos profile";
    }
    description
      "Grouping for qos profile";
  }

  grouping application-group {
    list application-group {
      key "group-name";
      leaf group-name {
        type string;
        description
          "Gourp name";
      }
      leaf-list application-name {
        type string;
        description
          "Application name";
      }
      description
        "List for application group";
    }
    description
      "Grouping for application-group";
  }

  grouping path-selection-policy {
    list path-selection-policy {
      key "name";
      leaf name {
        type string;
        description
          "Policy name";
      }
      list rule {
        key "rule-id";
        leaf rule-id {
          type string;
          description
            "Rule id";
        }
        leaf priority {
          type uint32;
          description
            "Priority";
        }
        leaf classification-name {
          type leafref {
            path "/sdwan-vpn-svc/sdwan-vpn/classification-profile/name";
          }
          description
            "QOS Classification NAME";
        }
        list traffic-sla-profile {
          key "name";
          leaf name {
            type string;
            description
              "traffic sla profile";
          }
          leaf latency {
            type uint32;
            description
              "latency";
          }
          leaf jitter {
            type uint32;
            description
              "jitter";
          }
          leaf packet-loss-rate {
            type uint32;
            description
              "packet loss rate";
          }
          description
            "traffic sla profile";
        }
        leaf transport-network-primary {
          type string;
          description
            "Primary transport network preferred";
        }
        leaf transport-network-sencondry {
          type string;
          description
            "Sencondry transport network preferred";
        }
        description
          "List for Rule";
      }
      description
        "List for path selection policy";
    }
    description
      "Grouping for path-selection-policy";
  }

  grouping internet-access {
    container internet-access {
      leaf access-option {
        type uint32;
        description
          "internet access via local breakout or central gateway";
      }
      leaf-list internet-gateway-ip {
        type inet:ip-address;
        description
          "Internet gateway IP";
      }
      leaf nat {
        type uint32;
        description
          "NAT";
      }
      leaf nat44-ip-addr {
        type inet:ip-address;
        description
          "Static nat custom internet IP.
           Address to be used for network address translation from IPv4 to
           IPv4.  This is to be used if the customer is providing the IPv4
           address.  If the customer address is not set, the model assumes
           that the provider will allocate the address.";
      }
      description
        "Container for internet access";
    }
    description
      "Grouping for internet-access";
  }
  grouping vpn-interworking {
    container vpn-interworking {
      leaf-list site {
        type leafref {
          path "/sdwan-vpn-svc/sdwan-vpn/sites/site/site-id";
        }
        description
          "List for interworking gateway for traditional MPLS VPN  ";
      }
      description
        "List for traditional MPLS VPN interworking";
    }
    description
      "Grouping for vpn-interworking";
  }

  grouping traffic-filter-policy {
    list traffic-filter {
      key "site-id";
      leaf site-id {
        type leafref {
          path "/sdwan-vpn-svc/sdwan-vpn/sites/site/site-id";
        }
        description
          "Site id";
      }
      leaf classification-name {
        type leafref {
          path "/sdwan-vpn-svc/sdwan-vpn/classification-profile/name";
        }
        description
          "Classification profile name";
      }
      leaf direction {
        type identityref {
          base traffic-direction;
        }
        description
          "Traffic direction";
      }
      leaf action {
        type identityref {
          base traffic-action;
        }
        description
          "Action";
      }
      description
        "List for traffic filter";
    }
    description
      "Grouping for traffic filter";
  }

  grouping flow-definition {
    container match-flow {
      leaf dscp {
        type inet:dscp;
        description
          "DSCP value.";
      }
      leaf dot1p {
        type uint8 {
          range "0..7";
        }
        description
          "802.1p matching.";
      }
      leaf ipv4-src-prefix {
        type inet:ipv4-prefix;
        description
          "Match on IPv4 src address.";
      }
      leaf ipv6-src-prefix {
        type inet:ipv6-prefix;
        description
          "Match on IPv6 src address.";
      }
      leaf ipv4-dst-prefix {
        type inet:ipv4-prefix;
        description
          "Match on IPv4 dst address.";
      }
      leaf ipv6-dst-prefix {
        type inet:ipv6-prefix;
        description
          "Match on IPv6 dst address.";
      }
      leaf l4-src-port {
        type inet:port-number;
        must "'.' <= '../l4-src-port-range/lower-port' and'.'>= '../l4-src-port-range/upper-port'" {
          description
            " If l4-src-port and l4-src-port-range/lower-port and
                upper-port are set at the same time, l4-src-port
                should not overlap with l4-src-port-range. ";
        }
        description
          "Match on Layer 4 src port.";
      }
      container l4-src-port-range {
        leaf lower-port {
          type inet:port-number;
          description
            "Lower boundary for port.";
        }
        leaf upper-port {
          type inet:port-number;
          must '. >= ../lower-port' {
            description
              " Upper boundary for port. If it
                   exists, upper boundary must be
                       higher than lower boundary.";
          }
          description
            "Upper boundary for port.";
        }
        description
          "Match on Layer 4 src port range. When only lower-port
              is present, it represents a single port. When both
              lower-port and upper-port are specified, it implies
              a range inclusive of both values.";
      }
      leaf l4-dst-port {
        type inet:port-number;
        must '. <= ../l4-dst-port-range/lower-port and.>= ../l4-dst-port-range/upper-port' {
          description
            " If l4-dst-port and l4-dst-port-range/lower-port and
                upper-port are set at the same time, l4-dst-port
                should not overlap with l4-src-port-range. ";
        }
        description
          "Match on Layer 4 dst port.";
      }
      container l4-dst-port-range {
        leaf lower-port {
          type inet:port-number;
          description
            "Lower boundary for port.";
        }
        leaf upper-port {
          type inet:port-number;
          must '. >= ../lower-port' {
            description
              "Upper boundary must be
                  higher than lower boundary.";
          }
          description
            "Upper boundary for port. If it exists, upper boundary
                must be higher than lower boundary.";
        }
        description
          "Match on Layer 4 dst port range. When only lower-port is
              present, it represents a single port. When both lower-port
              and upper-port are specified, it implies a range inclusive
              of both values.";
      }
      leaf protocol-field {
        type union {
          type uint8;
          type identityref {
            base routing-protocol-type;
          }
        }
        description
          "Match on IPv4 protocol or IPv6 Next Header field.";
      }
      description
        "Describes flow-matching criteria.";
    }
    description
      "Flow definition based on criteria.";
  }

  grouping classification-profile {
    list classification-profile {
      key "name";
      leaf name {
        type string;
        description
          "classification name";
      }
      list rule {
        key "id";
        ordered-by user;
        leaf id {
          type string;
          description
            "A description identifying qos classification
             policy rule.";
        }
        choice match-type {
          default "match-flow";
          case match-flow {
            uses flow-definition;
          }
          case match-application-group {
            leaf match-application-group {
              type string;
              description
                "Defines the application to match.";
            }
          }
          description
            "Choice for classification.";
        }
        description
          "List of marking rules.";
      }
      description
        "List for classification profile";
    }
    description
      "Gourping for classification profile";
  }

  grouping routing-protocol {
    list routing-protocol {
      key "type";
      leaf type {
        type identityref {
          base routing-protocol-type;
        }
        description
          "Routing protocol type";
      }
      container ospf {
        when "derived-from-or-self(../type, 'sdwan-vpn-svc:ospf')" {
          description
            "Only applies when protocol is OSPF.";
        }
        leaf-list address-family {
          type address-family;
          min-elements 1;
          description
            "If OSPF is used on this site, this node
             contains a configured value.  This node
             contains at least one address family
             to be activated.";
        }
        leaf area-address {
          type yang:dotted-quad;
          mandatory true;
          description
            "Area address.";
        }
        leaf metric {
          type uint16;
          default "1";
          description
            "Metric of the PE-CE link.  It is used
             in the routing state calculation and
             path selection.";
        }
        description
          "OSPF-specific configuration.";
      }
      container bgp {
        when "derived-from-or-self(../type, 'sdwan-vpn-svc:bgp')" {
          description
            "Only applies when protocol is BGP.";
        }
        leaf autonomous-system {
          type uint32;
          mandatory true;
          description
            "Customer AS number in case the customer
             requests BGP routing.";
        }
        leaf-list address-family {
          type address-family;
          min-elements 1;
          description
            "If BGP is used on this site, this node
             contains a configured value.  This node
             contains at least one address family
             to be activated.";
        }
        description
          "BGP-specific configuration.";
      }
      container static {
        when "derived-from-or-self(../type, 'sdwan-vpn-svc:static')" {
          description
            "Only applies when protocol is static.
             BGP activation requires the SP to know
             the address of the customer peer.  When
             BGP is enabled, the 'static-address'
             allocation type for the IP connection
             MUST be used.";
        }
        list ip-lan-prefixes {
          key "lan next-hop";
          leaf lan {
            type inet:ip-prefix;
            description
              "LAN prefixes.";
          }
          leaf next-hop {
            type inet:ipv4-address;
            description
              "Next-hop address to use on the customer side.";
          }
          leaf priority {
            type uint16;
            description
              "Prority";
          }
          description
            "List of LAN prefixes for the site.";
        }
        description
          "Configuration specific to static routing.";
      }
      description
        "List for Routing Protocol";
    }
    description
      "Grouping for routing protocol";
  }

  container sdwan-vpn-svc {
    list sdwan-vpn {
      key "vpn-id";
      leaf vpn-id {
        type svc-id;
        description
          "VPN identifier. Local administration meaning.";
      }
      leaf customer-name {
        type svc-id;
        description
          "Id for customer";
      }
      list wan-transport-networks {
        key "wan-transport-name";
        leaf wan-transport-name {
          type string;
          description
            "WAN transport network name";
        }
        leaf wan-transport-type {
          type identityref {
            base access-type;
          }
          description
            "Access type";
        }
        description
          "WAN transport network type";
      }
      container security {
        leaf algorithm {
          type string;
          description
            "Encryption algorithm to be used";
        }
        leaf preshared-key {
          type string;
          description
            "Pre-Shared Key (PSK) from individual customer.";
        }
        description
          "Container for IPSEC VPN encryption parameters";
      }
      uses application-group;
      uses classification-profile;
      uses qos-profile;
      container sites {
        list site {
          key "site-id";
          leaf site-id {
            type svc-id;
            description
              "Site Name";
          }
          list location {
            key "email";
            leaf email {
              type string;
              description
                "List for email";
            }
            leaf postcode {
              type string;
              description
                "Post code";
            }
            leaf address {
              type string;
              description
                "Location address";
            }
            description
              "List for location";
          }
          list device {
            key "name";
            leaf name {
              type string;
              description
                "Device Name";
            }
            leaf type {
              type string;
              description
                "Device Type";
            }
            list transport-network-port {
              key "name";
              leaf name {
                type string;
                description
                  "transport network port name";
              }
              leaf access-type {
                type identityref {
                  base access-type;
                }
                description
                  "Access type";
              }
              container ip-connection {
                leaf type {
                  type identityref {
                    base addr-allocation;
                  }
                  description
                    "Address allocation type";
                }
                container static {
                  when "../type = 'addr-allocation-static'";
                  leaf customer-addr {
                    type inet:ip-address;
                    description
                      "Customer address";
                  }
                  leaf prefix {
                    type inet:ip-prefix;
                    description
                      "IP Prefix";
                  }
                  leaf provider-addr {
                    type inet:ip-address;
                    description
                      "Provider address";
                  }
                  description
                    "Container for static";
                }
                description
                  "Container for ip connection";
              }
              uses routing-protocol;
              container bandwidth {
                leaf input-bandwidth {
                  type uint64;
                  description
                    "input bandwidth";
                }
                leaf output-bandwidth {
                  type uint64;
                  description
                    "output bandwidth";
                }
                leaf mtu {
                  type uint16;
                  description
                    "MTU";
                }
                description
                  "Container for bandwidth profile";
              }
              description
                "List for transport network ports";
            }
            description
              "List for devices";
          }
          description
            "List for sites";
        }
        description
          "Container for sites";
      }
      list subvpn {
        key "subvpn-id";
        leaf subvpn-id {
          type svc-id;
          description
            "subVPN network identifier";
        }
        leaf topology {
          type identityref {
            base vpn-topology;
          }
          description
            "subVPN topology: hub&spoke or any-to-any";
        }
        list logical-access {
          key "site-id";
          leaf site-id {
            type leafref {
              path "/sdwan-vpn-svc/sdwan-vpn/sites/site/site-id";
            }
            description
              "The site that the logic-access attached.";
          }
          leaf site-role {
            type identityref {
              base site-role;
            }
            default "any-to-any-role";
            description
              "Role of the site in the subVPN.";
          }
          leaf vlan-tag {
            type uint16;
            description
              "VLAN TAG";
          }
          leaf ip-address {
            type inet:ip-address;
            description
              "IP Address";
          }
          leaf ip-prefix {
            type inet:ip-prefix;
            description
              "IP Prefix";
          }
          uses routing-protocol;
          description
            "container for logical access";
        }
        container policies {
          uses path-selection-policy;
          uses qos-bandwidth-policy;
          uses traffic-filter-policy;
          uses internet-access;
          uses vpn-interworking;
          description
            "container for policies";
        }
        description
          "List for subVPN network";
      }
      description
        "List for SD-WAN";
    }
    description
      "Container for SD-WAN VPN service";
  }
}
