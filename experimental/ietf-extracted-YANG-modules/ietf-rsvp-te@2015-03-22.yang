module ietf-rsvp-te {

    namespace "urn:ietf:params:xml:ns:yang:ietf-rsvp-te";

    prefix "rsvp-te";

    import ietf-rsvp {
        prefix rsvp;
    }

    /* Import TE packet specific types */
    import ietf-te-psc-types {
        prefix ietf-te-psc-types;
    }

    import ietf-te {
        prefix ietf-te;
    }

    import ietf-inet-types {
        prefix inet;
    }

    organization
        "IETF TEAS Working Group";

    contact "TBA";

    description
        "This module contains the RSVP YANG data model.";

    revision 2015-03-22 {
        description "Initial revision.";
        reference "RFC3209";
    }

    /* groupings for rsvp */
    grouping signaling {
        description
            "RSVP-TE signaling properties";
        container signaling {
            description "Configure RSVP signaling properties.";
            leaf egress-label {
                type ietf-te-psc-types:egress-label;
                description "Egress label type";
            }
        }

    }

    grouping lsp-attributes {
        description
            "RSVP-TE LSP attributes properties";
        leaf end-to-end-routing {
            type empty;
            description
                "End-to-end routing desired";
            reference "RFC4920, RFC5420";
        }
        leaf boundary-rerouting {
            type empty;
            description
                "Boundary rerouting desired";
            reference "RFC4920, RFC5420";
        }
        leaf segment-based-rerouting {
            type empty;
            description
                "Segment-based rerouting desired";
            reference "RFC4920, RFC5420";
        }
        leaf lsp-integrety-required {
            type empty;
            description "LSP integrity desired";
            reference "RFC4875";
        }
        leaf contiguous-lsp {
            type empty;
            description "Contiguous LSP";
            reference "RFC5151";
        }
        leaf lsp-stitching-desired {
            type empty;
            description "Stiticed LSP";
            reference "RFC5150";
        }
        leaf preplanned-lsp {
            type empty;
            description "Preplanned LSP";
            reference "RFC6001";
        }
        leaf non-php-desired {
            type empty;
            description
                "Non-PHP is desired";
            reference "RFC6511";
        }
        leaf oob-mapping {
            type empty;
            description
                "Mapping is done out-of-band";
            reference "RFC6511";
        }
        leaf entropy-label-cap {
            type empty;
            description "Entropy label capability";
            reference "RFC6790";
        }
        leaf oam-mep-entities-desired {
            type empty;
            description "OAM MEP entities desired";
            reference "RFC7260";
        }
        leaf oam-mip-entities-desired {
            type empty;
            description "OAM MIP entities desired";
            reference "RFC7260";
        }
    }

    grouping lsp-signaling-properties {
        description "LSP signaling properties.";
        uses lsp-attributes;
        leaf source {
            type inet:ip-address;
            description
                "LSP source address.";
        }
        container fast-reroute {
            presence "FRR local protection is desired.";
            description
                "FRR RSVP-TE properties container";
            reference
                "RFC4859: Registry for RSVP-TE Session Flags";
            leaf bandwidth-protection-desired {
                type empty;
                description
                    "Request FRR bandwidth protection on LSRs if
                     present.";
            }
            leaf node-protection-desired {
                type empty;
                description
                    "Request FRR node protection on LSRs if
                     present.";
            }
        }
        leaf se-style-desired {
            type empty;
            description "SE Style desired";
            reference "RFC3209";
        }
        leaf soft-preemption-desired {
            type empty;
            description "Soft-preemption is desired";
            reference "RFC5712";
        }
        leaf record-route-desired {
            type empty;
            description "Path recording is desired.";
            reference "RFC3209";
        }
        leaf signaled-name {
            type string;
            description
                "Sets the session name to use in the session
                 attribute object.";
        }
        container priority {
            description
                "Sets the setup/hold priority to use in the session
                 attribute object.";
            leaf setup {
                type uint8 {
                     range "0..7";
                }
                description
                    "RSVP session attributes setup priority";
            }
            leaf hold {
                type uint8 {
                     range "0..7";
                }
                description
                    "RSVP session attributes hold priority";
            }
        }
        leaf soft-preemption {
            type empty;
            description
                "Requests soft-preemption in session
                 attributes object at
                 at traversed LSR(s).";
        }
    }

    /* RSVP-TE global propeerties */
    augment "/rsvp:rsvp/rsvp:globals" {
        description
                "RSVP-TE augmentation to RSVP globals";
        container frr-local-revert {
            presence "Enable RSVP FRR local revertive recovery
                      mode.";
            description
                "RSVP-TE global properties container";
            leaf frr-local-revert-delay {
                type uint32;
                description
                    "Time to wait after primary link is restored
                     before node attempts local revertive
                     procedures.";
            }
        }
    }

    augment "/ietf-te:te/ietf-te:tunnels/ietf-te:tunnel" {
        description "TBD";
        uses lsp-signaling-properties;
    }

    /* Linkage to the base RSVP all links */
    augment "/rsvp:rsvp/rsvp:interfaces" {
        description "TBD";
        uses signaling;
    }

    /* Linkage to per RSVP link */
    augment "/rsvp:rsvp/rsvp:interfaces/rsvp:interface" {
        description "TBD";
        uses signaling;
    }
    /* TSAAD: add augmentation for sessions neighbors */
    augment "/rsvp:rsvp/rsvp:sessions" {
        description "TBD";
        /* To be added */
    }

    augment "/rsvp:rsvp/rsvp:neighbors" {
        description "TBD";
        /* To be added */
    }

    augment "/rsvp:rsvp/rsvp:sessions-state" {
        description "TBD";
        /* To be added */
    }

    augment "/rsvp:rsvp/rsvp:neighbors-state" {
        description "TBD";
        /* To be added */
    }
}
