module ietf-logical-network-element {
  yang-version "1";

  // namespace
  namespace "urn:ietf:params:xml:ns:yang:ietf-logical-network-element";

  prefix "lne";

  // import some basic types
  import ietf-interfaces {
    prefix if;
  }

  // meta
  organization "IETF Routing Area Working Group (rtgwg)";

  contact
      "Routing Area Working Group - <rtgwg@ietf.org>";

  description
    "This module is used to support multiple logical network
     elements on a single physical or virtual system.";

  revision "2016-06-23" {
    description
      "Initial revision.";
    reference "RFC TBD";
  }

  // feature statements
  feature bind-lne-name {
    description
      "Logical network element to which an interface is bound";
  }

  // top level device definition statements
  container logical-network-elements {
    description "Allows a network device to support multiple logical
                 network element (device) instances";
    list logical-network-element {
      key name;
      description "List of logical network elements";
      leaf name {
        type string;
        description "Device-wide unique identifier for the
                     logical network element";
      }
      leaf managed {
        type boolean;
        description
          "True if the host can manage the LNE using the root mount
           point";
      }
      leaf description {
        type string;
        description
          "Description of the logical network element";
      }
      leaf root {
        type schema-mount;
        description "Root for models supported per logical
                     network element";
      }
    }
  }

  // augment statements
  augment "/if:interfaces/if:interface" {
    description
        "Add a node for the identification of the logical network
        element associated with an interface. Applies to interfaces
        that can be assigned on a per logical network element basis.
        A <TBD> error is returned when the interface type cannot be
        assigned.";

    leaf bind-lne-name {
      type string;
      description
        "Logical network element ID to which interface is bound";
    }
  }

  // rpc statements

  // notification statements

}
