submodule snmp-agent {

  belongs-to snmp {
    prefix snmp;
  }

  import ietf-yang-types {
    prefix yang;
  }
  import ietf-inet-types {
    prefix inet;
  }

  include snmp-common;

  revision 2010-10-17 {
    description
      "Initial revision.";
  }

  augment /snmp:snmp {

    container agent {

      description
        "Configuration of the SNMP agent";

      leaf enabled {
        type boolean;
        default "false";
        description
          "Enables the SNMP agent.";
      }

      // FIXME: support multiple endpoints

      leaf ip {
        type inet:ip-address;
        default "0.0.0.0";
        description
          "The IPv4 or IPv6 address to which the agent listens.";
      }

      leaf udp-port {
        type inet:port-number;
        default "161";
        description
          "The UDP port to which the agent listens.";
      }

      container version {
        description
          "SNMP version used by the agent";
        leaf v1 {
          type empty;
        }
        leaf v2c {
          type empty;
        }
        leaf v3 {
          type empty;
          must "../../engine-id" {
            error-message
              "when v3 is configured, an engine-id must be set";
          }
        }
      }

      container engine-id {
        presence "Sets the local engine-id.";

        description
          "The local SNMP engine's administratively-assigned unique
           identifier.";
        reference "SNMP-FRAMEWORK-MIB.snmpEngineID";

        leaf enterprise-number {
          type uint32;
          mandatory true;
        }
        choice method {
          mandatory true;
          leaf from-ip {
            type inet:ip-address;
          }
          leaf from-mac-address {
            type yang:mac-address;
          }
          leaf from-text {
            type string {
              length 1..27;
            }
          }
          leaf other {
            type string {
              pattern "[0-9a-fA-F]{2}(:[0-9a-fA-F]{2}){0,27}";
            }
          }
        }
      }
    }

    container system {

      description
        "System group configuration.";

      leaf contact {
        type admin-string;
        default "";
        reference "SNMPv2-MIB.sysContact";
      }

      leaf name {
        type admin-string;
        default "";
        reference "SNMPv2-MIB.sysName";
      }

      leaf location {
        type admin-string;
        default "";
        reference "SNMPv2-MIB.sysLocation";
      }

    }

  }
}
