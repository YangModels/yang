module spn-inband-oam {
  namespace urn:cmcc:yang:spn-inband-oam ;
  prefix inband-oam;
  import ietf-inet-types {
    prefix inet ;
    revision-date 2013-07-15 ;
  }
  import ietf-yang-types {
    prefix yang ;
    revision-date 2013-07-15 ;
  }
  organization 'China Mobile Communications Corporation (CMCC)'
               ;
  contact 'zhangtingting <mailto:wangminxue@chinamobile.com>'
          ;
  description 'This module describes device management.'+"\n"
            + 'Copyright (c) CMCC. All rights reserved'
              ;
  revision 2022-05-11 {
    description 'First draft.'
                ;
  }

  typedef alternate-marking-period {
    type enumeration {
      enum 1s {
        value 1 ;
        description 'Alternate marking period is 1s.'
                    ;
      }
      enum 10s {
        value 2 ;
        description 'Alternate marking period is 10s.'
                    ;
      }
      enum 30s {
        value 3 ;
        description 'Alternate marking period is 30s.'
                    ;
      }
      enum 60s {
        value 4 ;
        description 'Alternate marking period is 60s.'
                    ;
      }
      enum 5min {
        value 5 ;
        description 'Alternate marking period is 5min.'
                    ;
      }
    }
    description 'Alternate marking period,including 1s,10s,30s,60s,5min.'
                ;
  }
  typedef enable-status {
    type enumeration {
      enum enable {
        value 1 ;
        description 'Enables the function.'
                    ;
      }
      enum disable {
        value 0 ;
        description 'Disables the function.'
                    ;
      }
    }
    description 'Enable status,including enable and disable.'
                ;
  }
  container configuration {
    description 'Configuration of inband OAM model Info.'
                ;
    container inband-oam {
      description 'Inband OAM flow alternate marking configuration.'
                  ;
      container global {
        description 'Global configuration.'
                    ;
        leaf label {
          description 'The label ranges from 4 to 6 and 8 to 12(default:12).'
                      ;
          type uint32 {
            range '4..6 | 8..12'
                  {
              description 'The range of the label.'
                          ;
            }
          }
          default 12 ;
        }
        leaf fii-mode {
          description 'Position ID of the guide label.'
                      ;
          type enumeration {
            enum non-bottom {
              value 0 ;
            }
            enum bottom {
              value 1 ;
            }
          }
          default non-bottom ;
        }
      }
      container head-node {
        description 'Configure inband OAM flow coloring.'
                    ;
        list flow {
          description 'Configure inband OAM flow coloring.'
                      ;
          key flow-id ;
          leaf flow-id {
            description 'The flow id to identify a specific flow,ranges from 1 '
                      + 'to 1048575.'
                        ;
            type uint32 {
              range 1..1048575 {
                description 'The range of flow id.'
                            ;
              }
            }
          }
          leaf alternate-status {
            description 'The status of flow alternate marking,including enable '
                      + 'and disable(default:enable).'
                        ;
            type enable-status ;
            default enable ;
          }
          leaf period {
            description 'The period of flow coloring,including 1s,10s,30s,60s a'
                      + 'nd  5min(default:30s).'
                        ;
            type alternate-marking-period ;
            default 30s ;
          }
          leaf hop-by-hop-status {
            description 'The status of hop-by-hop coloring,including enable and'
                      + ' disable(default:enable).'
                        ;
            type enable-status ;
            default disable ;
          }
          leaf source-mac {
            description 'The source MAC address.'
                        ;
            type yang:mac-address ;
          }
          leaf dest-mac {
            description 'The destination MAC address.'
                        ;
            type yang:mac-address ;
          }
          leaf vlan-id {
            description 'The value of vlan ID,ranges from 1 to 4094.'
                        ;
            type uint16 {
              range 1..4094 {
                description 'The range of VLAN ID.'
                            ;
              }
            }
          }
          leaf internal-vlan-id {
            description 'The value of internal vlan ID,ranges from 1 to 4094.'
                        ;
            type uint16 {
              range 1..4094 {
                description 'The range of internal VLAN ID.'
                            ;
              }
            }
          }
          leaf priority-8021p {
            description 'The value of priority-8021p,ranges from 0 to 7.'
                        ;
            type uint8 {
              range 0..7 {
                description 'The range of priority-8021p.'
                            ;
              }
            }
          }
          leaf sip {
            description 'The source ip address.'
                        ;
            type inet:ip-prefix ;
          }
          leaf dip {
            description 'The destination ip address.'
                        ;
            type inet:ip-prefix ;
          }
          leaf protocol {
            description 'The protocol number,ranges from 1 to 255.'
                        ;
            type uint8 {
              range 1..255 {
                description 'The range of protocol.'
                            ;
              }
            }
          }
          leaf source-port {
            description 'The source port,ranges from 1 to 65535.'
                        ;
            type uint16 {
              range 1..65535 {
                description 'The range of port number.'
                            ;
              }
            }
          }
          leaf dest-port {
            description 'The destination port,ranges from 1 to 65535.'
                        ;
            type uint16 {
              range 1..65535 {
                description 'The range of port number.'
                            ;
              }
            }
          }
          leaf vpn-type {
            description 'The VPN type of the UNI interface.'
                        ;
            type enumeration {
              enum l3vpn {
                value 0 ;
              }
              enum l2vpn {
                value 1 ;
              }
            }
            default l3vpn ;
          }
          leaf vpn-name {
            description 'The access VPN name of ip flow.'
                        ;
            type string {
              length 1..31 {
                description 'The range of VRF name length.'
                            ;
              }
            }
          }
          leaf if-name {
            description 'The UNI interface name of ip flow.'
                        ;
            type string {
              length 1..31 ;
            }
            mandatory true ;
          }
          leaf member-port {
            description 'The member port of the UNI interface.'
                        ;
            type string ;
          }
        }
      }
      container end-node {
        description 'Configure the relation between Flowid and VPN.'
                    ;
        list relation {
          description 'Configure the relation between Flowid and VPN.'
                      ;
          key flow-id ;
          leaf flow-id {
            description 'The flow id to identify a specific flow,ranges from 1 '
                      + 'to 1048575.'
                        ;
            type uint32 {
              range 1..1048575 {
                description 'The range of flow-id.'
                            ;
              }
            }
          }
          choice vpn-type {
            description 'Choose one from vrf and vpws.'
                        ;
            case vrf {
              description 'Type is VRF.'
                          ;
              leaf vrf-name {
                description 'The name of VRF,this string length ranges from 1 t'
                          + 'o 32.'
                            ;
                type string {
                  length 1..32 {
                    description 'This string length ranges from 1 to 32.'
                                ;
                  }
                }
                mandatory true ;
              }
            }
            case vpws {
              description 'Type is vpws.'
                          ;
              leaf vpws-name {
                description 'The name of VPWS,this string length ranges from 1 '
                          + 'to 32.'
                            ;
                type string {
                  length 1..32 {
                    description 'This string length ranges from 1 to 32.'
                                ;
                  }
                }
                mandatory true ;
              }
            }
            case vpls {
              description 'Type is VPLS.'
                          ;
              leaf vpls-name {
                description 'The name of VPLS,this string length ranges from 1 '
                          + 'to 32.'
                            ;
                type string {
                  length 1..32 {
                    description 'This string length ranges from 1 to 32.'
                                ;
                  }
                }
                mandatory true ;
              }
            }
          }
          leaf period {
            description 'The flip period of relation,including 1s,10s,30s,60s,5'
                      + 'min(default:30s).'
                        ;
            type alternate-marking-period ;
            units ms ;
            default 30s ;
          }
          leaf hop-by-hop-status {
            description 'The status of hop-by-hop,including enable and disable('
                      + 'default:disable).'
                        ;
            type enable-status ;
            default disable ;
          }
          leaf if-name {
            description 'The UNI interface name of relation.'
                        ;
            type string {
              length 1..31 ;
            }
          }
        }
      }
    }
  }
}
