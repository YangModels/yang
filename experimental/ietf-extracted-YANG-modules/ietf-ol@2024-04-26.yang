module ietf-ol {
  yang-version 1.1;
  namespace "urn:ietf:params:xml:ns:yang:ietf-ol";
  prefix ol;

  import ietf-inet-types {
    prefix inet;
    reference
      "RFC 6991: Common Yang Data Types, Section 4";
  }
  import ietf-mud {
    prefix ietf-mud;
    reference
      "RFC 8520: Manufacturer Usage Description Specification";
  }

  organization
    "IETF OPSAWG (Ops Area) Working Group";
  contact
    "WG
     Web: http://tools.ietf.org/wg/opsawg/
     WG List: opsawg@ietf.org
     Author: Eliot Lear lear@cisco.com
     Author: Carsten Bormann <cabo@tzi.org>";
  description
    "This YANG module to indicate ownership and licensing.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX);
     see the RFC itself for full legal notices.";

  revision 2024-04-26 {
    description
      "Initial revision.";
    reference
      "RFC XXXX: Ownership and Licensing Statements in YANG";
  }

  grouping owner-license-grouping {
    description
      "A grouping expression ownership and license information";
    container ol {
      description
        "container relating to ownership and licensing.";
      list license {
        key "owner-name";
        description
          "list of licenses that may be applied.";
        leaf owner-name {
          type string {
            length "1..128";
          }
          description
            "name of the owner";
        }
        choice license-type {
          description
            "Either choose a standard license type or point
             to one of your own.";
          case spdx-lt {
            leaf-list spdx-tag {
              type string;
              min-elements 1;
              description
                "SPDX License Identifier, as indicated at
                 https://spdx.org/licenses/";
            }
          }
          case url {
            leaf-list license-info {
              type inet:uri;
              min-elements 1;
              description
                "A URL pointing to licensing information.";
            }
          }
        }
      }
    }
  }

  augment "/ietf-mud:mud" {
    description
      "Add extension for Ownership and licensing.";
    uses owner-license-grouping;
  }
}
