module service-function-forwarder {

  namespace "urn:cisco:params:xml:ns:yang:sfc-sff";

  prefix sfc-sff;

  import ietf-inet-types { prefix inet; }
  import ietf-yang-types { prefix yang; }

  organization "Cisco Systems, Inc.";
  contact "Reinaldo Penno <repenno@cisco.com>";

  description
    "This module contains a collection of YANG definitions for
     managing service function forwarders.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-05-08 {
    description
    "Initial revision.";
  }

  // Service Function Forwarding Map

  container service-forwarding-map {
    description
      "This dictionary holds the configuration for a service function forwarder.
      For each service function, it has the location information.

      Example of a working Python Implementation of a SFF Map. A service function
      can be reached through IP:port or internal function call. ";
      //sfi_map = {"fw1": {"function": "fw1_process_packet", "ip_address":"", "port":""}, \
      //           "fw2": {"function": "", "ip_address": "192.168.0.2", "port":""}, \
      //           "dpi1":{"function": "", "ip_address": "192.168.0.4", "port":10000}, \
      //           "nat1":{"function": "nat1_process_packet", "ip_address": "", "port":""}}

    list service-map {
        ordered-by user;
        key "service-function-name";
        leaf service-function-name {
            type string;
        }
        container service-function-location {
            leaf ip {
                type inet:ip-address;
            }
            leaf port {
                type inet:port-number;
            }
        }
    }
  }
}
