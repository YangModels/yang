module ietf-math-types {

   namespace "urn:ietf:params:xml:ns:yang:ietf-math-types";
   prefix "mt";

   organization "NETMOD WG";
   contact "Editor: Sudhanshu Kumar Srivastav
                    <sk.srivastav@samsung.com>";
   description
      "YANG extensions for math types.";
   revision 2017-09-12 {
           description "Initial revision.";
           reference "RFC 6080";
       }
   extension math {
       argument name;      
       description "Define a mathematical expression node";
   }
   extension addition {
       argument name;      
       description "Define a addition expression node";
   }
   extension addend {
       argument name;      
       description "Define a addend node";
   }
   extension subtraction {
       argument name;      
       description "Define a subtraction expression node";
   }
   extension minuend {
       argument name;      
       description "Define a minuend node";
   }
   extension subtrahend {
       argument name;      
       description "Define a subtrahend node";
   }
   extension multiplication {
       argument name;
       description "Define a multiplication expression node";
   }
   extension multiplier {
       argument name;      
       description "Define a multiplier node";
   }
   extension division {
       argument name;      
       description "Define a division expression node";
   }
   extension divisor {
       argument name;      
       description "Define a divisor node";
   }
   extension dividend {
       argument name;      
       description "Define a dividend node";
   }
   extension event {
       argument name;      
       description "Define a event node";
   }
   extension loop {
       argument name;      
       description "Define a loop node";
   }
   extension min {
       argument name;      
       description "Define a min node";
   }
   extension max {
       argument name;      
       description "Define a max node";
   }
   extension const {
       argument name;      
       description "Define a const node";
   }
}
