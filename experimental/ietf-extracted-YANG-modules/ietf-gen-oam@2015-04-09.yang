module ietf-gen-oam {
namespace "urn:ietf:params:xml:ns:yang:ietf-gen-oam";
prefix goam;

import ietf-interfaces {
  prefix if;
}
import ietf-yang-types {
  prefix yang;
}
import ietf-inet-types {
  prefix inet;
}

organization "IETF LIME Working Group";
contact
  "Tissa Senevirathne tsenevir@cisco.com";
description
  "This YANG module defines the generic configuration,
   statistics and rpc for OAM to be used within IETF in
   a protocol indpendent manner. Functional level
   abstraction is indendent with YANG modeling. It is
   assumed that each protocol maps corresponding
   abstracts to its native format.
   Each protocol may extend the YANG model defined
   here to include protocol specific extensions";

revision 2015-04-09 {
  description
    "Initial revision. - 04 version";
  reference "draft-tissa-lime-oam";
}

/* features */
feature connectivity-verification {
  description
    "This feature indicates that the server supports
     executing connectivity verification OAM command and
     returning a response. Servers that do not advertise
     this feature will not support executing
     connectivity verification command or rpc model for
     connectivity verification command.";
}

/* Identities */

identity technology-types {
  description
    "this is the base identy of technology types which are
     vpls, nvo3, TRILL, ipv4, ipv6, mpls, etc";
}

identity ipv4 {
  base technology-types;
  description
    "technology of ipv4";
}

identity ipv6 {
  base technology-types;
  description
    "technology of ipv6";
}

identity command-sub-type {
  description
    "defines different rpc command subtypes, e.g rfc792 IP
     ping, rfc4379 LSP ping, rfc6905 trill OAM, this is
     optional for most cases";
}

identity icmp-rfc792 {
  base command-sub-type;
  description
    "Defines the command subtypes for ICMP ping";
  reference "RFC 792";
}

identity name-format {
  description
    "This defines the name format, IEEE 8021Q CFM defines varying
    styles of names. It is expected name format as an identity ref
    to be extended with new types.";
}

identity name-format-null {
  base name-format;
  description
    "defines name format as null";
}

identity identifier-format {
  description
    "identifier-format identity can be augmented to define other
   format identifiers used in MEPD-ID etc";
}

identity identifier-format-integer {
  base identifier-format;
  description
    "defines identifier-format to be integer";
}

identity defect-types {
  description
    "defines different defect types, e.g. remote rdi,
     mis-connection defect, loss of continuity";
}
identity remote-rdi {
  base defect-types;
  description
    " Indicates the aggregate health of the remote MEPs. ";
}

identity remote-mep-error{
  base defect-types;
  description
    " Indicates that one or more of the remote MEPs is
reporting a failure ";
  }
  identity invalue-oam-error{
    base defect-types;
    description
 "Indicates that one or more invalid OAM messages has been
received and that 3.5 times that OAM message transmission
interval has not yet expired.
";
  }
  identity cross-connect-error{
    base defect-types;
    description
" Indicates that one or more cross-connect oam messages has been
received and that 3.5 times that OAM message transmission
interval has not yet expired.
";
  }

  /* typedefs */
  typedef MEP-direction {
    type enumeration {
      enum "Up" {
        value 0;
description
  "Indicates when OAM frames are transmitted towards and
received from the bridging/routing function.";
      }
      enum "Down" {
        value 1;
description
  "Indicates when OAM frames are transmitted towards and
received from the wire.";
      }
    }
    description
      "MEP direction.";
  }

  typedef MEP-name {
    type string;
    description
      "Generic administrative name for a MEP";
  }

  typedef Interval {
    type uint32;
    units "milliseconds";
    default "1000";
    description
      "Interval between packets in milliseconds.
       0 means no packets are sent.";
  }

  typedef ecmp-choices {
    type enumeration {
      enum "ecmp-use-platform-hash" {
        value 0;
description
  "Use Platform hashing.";
      }
      enum "ecmp-use-round-robin" {
        value 1;
description
  "Use round robin hashing.";
      }
    }
    description
      "Equal cost multi Path Choices";
  }

  typedef MD-name-string {
    type string;
    default "";
    description
      "Generic administrative name for an MD";
  }

  typedef MA-name-string {
    type string;
    default "";
    description
      "Generic administrative name for an MA";
  }

  typedef oam-counter32 {
    type yang:zero-based-counter32;
    description
      "defines 32 bit counter for OAM";
  }

  typedef MD-level {
    type uint32 {
      range "0..255";
    }
    description
      "Maintenance Domain level.  The level may be restricted in
       certain protocols (eg to 0-7)";
  }

  /* groupings */

  grouping topology {
    choice topology {
      case topo-null {
        description
          "this is a placeholder when no topology is needed";
        leaf topo-null {
           type empty;
           description
             "there is no topology define, it will be defined
              in technology specific model.";
        }
      }
      description
        "Topology choices";
    }
    description
      "Topology";
  }

  grouping error-message {
    choice error {
      case error-null {
        description
          "this is a placeholder when no error status is needed";
        leaf error-null {
           type empty;
           description
             "there is no error define, it will be defined in
              technology specific model.";
        }
      }
      case error-code {
        description
          "this is a placeholder to display error code.";
        leaf error-code {
           type int32;
           description
             "error code is integer value specific to technology.";
        }
      }
      description
        "Error Message choices.";
    }
    description
      "Error Message.";
  }

  grouping mp-address {
    choice mp-address {
      case mac-address {
        leaf mac-address {
          type yang:mac-address;
  description
    "MAC Address";
        }
description
  "MAC Address based MP Addressing.";
      }
      case ipv4-address {
        leaf ipv4-address {
          type inet:ipv4-address;
  description
    "Ipv4 Address";
        }
description
  "Ip Address based MP Addressing.";
      }
      case ipv6-address {
        leaf ipv6-address {
          type inet:ipv6-address;
  description
    "Ipv6 Address";
        }
description
  "ipv6 Address based MP Addressing.";
      }
      description
        "MP Addressing.";
    }
    description
      "MP Address";
  }

  grouping maintenance-domain-id {
    description
      "Grouping containing leaves sufficient to identify an MD";
    leaf technology {
      type identityref {
        base technology-types;
      }
      mandatory true;

      description
        "Defines the technology";
    }
    leaf MD-name-string {
      type MD-name-string;
      mandatory true;
      description
        "Defines the generic administrative maintenance domain name";
    }
  }

  grouping MD-name {
    leaf MD-name-format {
      type identityref {
        base name-format;
      }
      description
        "Name format.";
    }
    choice MD-name {
      case MD-name-null {
        leaf MD-name-null {
  when "../../../MD-name-format = name-format-null" {
     description
       "MD name format is equal to null format.";
  }
          type empty;
  description
    "MD name Null.";
        }
      }
      description
        "MD name.";
    }
    description
      "MD name";
  }
  grouping ma-identifier {
    description
      "Grouping containing leaves sufficient to identify an MA";
    leaf MA-name-string {
      type MA-name-string;
      description
        "MA name string.";
    }
  }

  grouping MA-name {
    description
      "MA name";
    leaf MA-name-format {
      type identityref {
        base name-format;
      }
      description
        "Ma name format";
    }
    choice MA-name {
      case MA-name-null {
        leaf MA-name-null {
          when "../../../MA-name-format = name-format-null" {
  description
    "MA";
  }
  type empty;
  description
    "empty";
        }
      }
      description
        "MA name";
    }
  }

  grouping MEP-ID {
    choice MEP-ID {
      default "MEP-ID-int";
      case MEP-ID-int {
        leaf MEP-ID-int {
          type int32;
  description
    "MEP ID in integer format";
        }
      }
      case MEP-ID-tlv {
         leaf MEP-ID-type {
   type int16;
   description
     "Type of MEP-ID";
         }
 leaf MEP-ID-len {
   type int16;
   description
     "Length of MEP-ID value";
 }
 leaf MEP-ID-value {
    type binary {
      length "12..255";
    }
    description
      "Value please refer RFC6428.";
 }
      }
      description
        "MEP-ID";
    }
    leaf MEP-ID-format {
      type identityref {
        base identifier-format;
      }
      description
        "MEP ID format.";
    }
    description
      "MEP-ID";
  }

  grouping MEP {
    description
      "Defines elements within the MEP";
    leaf mep-name {
      type MEP-name;
      mandatory true;
      description
        "Generic administrative name of the MEP";
    }
    uses MEP-ID;

    uses mp-address;
    uses connectivity-context;
    leaf Interface {
      type if:interface-ref;
      description
        "Interface name as defined by ietf-interfaces";
    }
    uses topology;
  }

  grouping session-type {
    description
      "This object indicates the current session
       definition.";
    leaf session-type-enum {
      type enumeration {
        enum proactive {
          description
            "The current session is proactive";
        }
        enum on-demand {
          description
            "The current session is on-demand.";
        }
      }
      description
        "session type enum";
    }
  }

  grouping monitor-stats {
    leaf tx-packt-count {
      type oam-counter32;
      description
        "Transmitted Packet count";
    }
    leaf rx-packet-count {
      type oam-counter32;
      description
        "Received packet count";
    }
    leaf min-delay {
      type oam-counter32;
      units milliseconds;
      description
        "Delay is specified in milliseconds";
    }
    leaf average-delay {
      type oam-counter32;
      units millisecond;
      description
        "average delay in milliseconds";
    }
    leaf max-delay {
      type oam-counter32;
      units millisecond;
      description
        "Maximum delay in milliseconds";
    }
    description
      "Monitor Statistics";
  }

  grouping MIP {
    description
      "defines MIP";
    leaf interface {
      type if:interface-ref;
      description
         "Interface";
    }
  }

  grouping related-oam-layer {
    leaf offset {
      type int32 {
        range "-255..255";
      }
      description
        "defines offset (in MD levels) to a related OAM layer
         +1 is the layer immediately above
         -1 is the layer immediately below";
    }
    uses maintenance-domain-id;
    uses ma-identifier;
    description
      "related OAM layer";
  }

  grouping interface-status {
    description
      "collection of interface related status";
    leaf admin-status {
      type leafref {
        path "/if:interfaces-state/if:interface/if:admin-status";
      }
      config false;
      description
        "oper status from ietf-interface module";
    }
    leaf oper-status {
      type leafref {
        path "/if:interfaces-state/if:interface/if:oper-status";
      }
      config false;
      description
        "oper status from ietf-interface module";
    }
  }

  grouping connectivity-context {
    description
      "Grouping defining the connectivity context for an MA; for
       example, a VRF for IP, or an LSP for MPLS.  This will be
       augmented by each protocol who use this component";
    choice connectivity-context {
      default "context-null";
      case context-null {
        description
          "this is a place holder when no context is needed";
        leaf context-null {
          type empty;
          description
            "there is no context define";
        }
      }
      description
        "connectivity context";
    }
  }

  grouping priority {
    description
      "Priority used in transmitted packets; for example, in the
       TOS/DSCP field in IP or the Traffic Class field in MPLS";
    leaf priority {
      type uint8;
      description
        "priority";
    }
  }

  grouping flow-entropy {
    description
      "defines the grouping statement for flow-entropy";
    choice flow-entropy {
      default "flow-entropy-null";
      case flow-entropy-null {
        description
          "this is a place holder when no flow entropy is needed";
        leaf flow-entropy-null {
          type empty;
          description
            "there is no flow entropy defined";
        }
      }
      description
        "Flow entropy";
    }
  }

  grouping measurement-timing-group {
     description
     "This grouping includes objects used for
      proactive and on-demand
      scheduling of PM measurement sessions.";

     container start-time {
        description
"This container defines the session start time.";
choice start-time {
  description
  "Measurement sessions tart time can be immediate, relative, or
  absolute.";
  container immediate {
            presence "Start the measurement session immediately.";
            description
            "Start Time of probe immediately.";
  }
  leaf absolute {
    type yang:date-and-time;
    description
    "This objects specifies the scheduled start time
     to perform the on-demand monitoring operations.";
  }
        }
     }

     container stop-time {
description
"This container defines the session stop time.";
choice stop-time {
   description
   "Measurement session stop time can be none, or absolute.";
   container none {
              presence "Never end the measurement session.";
              description
              "Stop time is never to end.";

   }

   leaf absolute {
     type yang:date-and-time;
     description
       "This objects specifies the scheduled stop time
         to perform the on-demand monitoring operations.";
   }
        }
     }
  }

  container domains {
    description
      "Contains configuration related data. Within the container
       is list of fault domains. Wihin each domian has List of MA.";
    list domain {
      key "technology MD-name-string";
      ordered-by system;
      description
        "Define the list of Domains within the IETF-OAM";
      uses maintenance-domain-id;
      uses MD-name;
      leaf md-level {
        type MD-level;
        description
          "Defines the MD-Level";
      }
      container MAs {
        description
          "This container defines MA, within that have multiple MA
           and within MA have MEP, MIP";
        list MA {
  key "MA-name-string";
          ordered-by system;
          uses ma-identifier;
          uses MA-name;
          uses connectivity-context;
          leaf mep-direction {
            type MEP-direction;
            mandatory true;
            description
              "Direction for MEPs in this MA";
          }
          leaf interval {
    type Interval;
            default "0";
            description
              "Defines default Keepalive/CC Interval.  May be
               overridden for specific sessions if supported by the
               protocol.";
          }
          leaf loss-threshold {
    type uint32;
            default "3";
            description
              "number of consecutive Keepalive/CC messages missed
               before declaring loss of continuity fault. This is
               monitored per each remote MEP session";
          }
          leaf ttl {
            type uint8;
            default "255";
    description
      "Time to Live";
          }
          uses flow-entropy {
            description
              "Default flow entropy in this MA, which may be
               overridden for particular MEPs, sessions or
               operations";
          }
          uses priority {
            description
              "Default priority for this MA, which may be overridden
               for particular MEPs, sessions or operations.";
          }
          list MEP {
            key "mep-name";
            ordered-by system;
            description
              "contain list of MEPS";
            uses MEP;
            uses interface-status {
              description
                "status of associated interface";
            }
            uses flow-entropy;
            uses priority;
            list session {
              key "session-cookie";
              ordered-by user;
              description
                "Monitoring session to/from a particular remote MEP.
                 Depending on the protocol, this could represent CC
                 messages received from a single remote MEP (if the
                 protocol uses multicast CCs) or a target to which
                 unicast echo request CCs are sent and from which
                 responses are received (if the protocol uses a
                 unicast request/response mechanism).";
              leaf session-cookie {
                type uint32;
                description
                  "Cookie to identify different sessions, when there
                   are multiple remote MEPs or multiple sessions to
                   the same remote MEP.";
              }
              leaf ttl {
                type uint8;
                default "255";
  description
    "Time to Live.";
              }
              leaf interval {
                type Interval;
                description
                  "Transmission interval for CC packets for this
                   session.";
              }
              leaf enable {
         type boolean;
                default "false";
                description
                  "enable or disable a monitor session";
              }
              leaf ecmp-choice {
                type ecmp-choices;
                description
                  "0 means use the specified interface
                   1 means use round robin";
              }
              leaf source-mep {
                type MEP-name;
                description
                  "Source MEP for this session, if applicable";
              }
              container destination-mep {
                uses MEP-ID;
  description
     "Destination MEP";
              }
              container destination-mep-address {
                uses mp-address;
  description
     "Destination MEP Address";
              }
              uses connectivity-context;
              uses flow-entropy;
              uses priority;
              list outgoing-interface {
                key "interface";
                leaf interface {
                  type if:interface-ref;
    description
      "Outgoing Interface";
                }
  description
    "outgoing interfaces";
              }
            }
          }
          list MIP {
            key "interface";
            uses MIP;
    description
      "Maintenance Intermediate Point";
          }
          list related-oam-layer {
            key "offset";
            description
              "List of OAM layers above and below that are related to
               current MA. This allow users to easily navigate up and
               down to efficiently troubleshoot a connectivity
               issue";
            uses related-oam-layer;
          }
  description
     "Maintenance Association list";
        }
      }
    }
  }

  notification defect-condition-notification {
    description
      "When defect condition is met this notificiation is sent";
   uses maintenance-domain-id {
      description
        "defines the MD (Maintenance Domain) identifier, which is the
         Generic MD-name-string and the technology.";
    }
    uses ma-identifier;
    leaf mep-name {
      type MEP-name;
      description
        "Indicate which MEP is seeing the error";
    }
    leaf defect-type {
      type identityref {
        base defect-types;
      }
      description
        "The currently active defects on the specific MEP.";
    }
    container generating-mepid {
      uses MEP-ID;
      description
        "Who is generating the error (if known) if
         unknown make it 0.";
    }
    uses error-message {
      description
         "Error message to indicate more details.";
    }
  }
  rpc continuity-check {
    description
      "Generates continuity-check as per RFC7276 Table 4.";
    input {
      uses maintenance-domain-id {
        description
          "defines the MD (Maintenance Domain) identifier, which is
           the generic
           MD-name-string and the technology.";
      }
      uses ma-identifier {
        description
          "identfies the Maintenance association";
      }
      uses flow-entropy;
      uses priority;
      leaf ttl {
        type uint8;
        default "255";
 description
   "Time to Live";
      }
      uses session-type;
      leaf ecmp-choice {
        type ecmp-choices;
        description
          "0 means use the specified interface
           1 means use round robin";
      }
      leaf sub-type {
        type identityref {
          base command-sub-type;
        }
        description
          "defines different command types";
      }
      list outgoing-interfaces {
        key "interface";
        leaf interface {
          type if:interface-ref;
  description
    "outgoing interface";
        }
description
  "outgoing Interfaces";
      }
      leaf source-mep {
        type MEP-name;
description
  "Source MEP";
      }
      container destination-mp {
        uses mp-address;
        uses MEP-ID {
          description "Only applicable if the destination is a MEP";
        }
description
  "Destination MEP";
      }
      leaf count {
        type uint32;
        default "3";
        description

          "Number of ping echo request message to send";
      }
      leaf interval {
        type Interval;
        description
          "Interval between echo requests";
      }
      leaf packet-size {
        type uint32 {
          range "64..10000";
        }
        default "64";
        description
          "Size of ping echo request packets, in octets";
      }
    }
    output {
      uses monitor-stats {
        description
          "Stats of continuity check.";
      }
    }
  }

  rpc continuity-verification {
    if-feature connectivity-verification;
    description
      "Generates continuity-verification as per RFC7276 Table 4.";
    input {
      uses maintenance-domain-id {
        description
          "defines the MD (Maintenance Domain) identifier, which is
           the generic
           MD-name-string and the technology.";
      }
      uses ma-identifier {
        description
          "identfies the Maintenance association";
      }
      uses flow-entropy;
      uses priority;
      leaf ttl {
        type uint8;
        default "255";
description
  "Time to Live";
      }
      uses session-type;
      leaf ecmp-choice {
        type ecmp-choices;
        description
          "0 means use the specified interface
           1 means use round robin";
      }
      leaf sub-type {
        type identityref {
          base command-sub-type;
        }
        description
          "defines different command types";
      }
      list outgoing-interfaces {
        key "interface";
        leaf interface {
          type if:interface-ref;
  description
    "outgoing interface";
        }
description
  "outgoing Interfaces";
      }
      leaf source-mep {
        type MEP-name;
description
  "Source MEP";
      }
      container destination-mp {
        uses mp-address;
        uses MEP-ID {
          description "Only applicable if the destination is a MEP";
        }
description
  "Destination MEP";
      }
      leaf count {
        type uint32;
        default "3";
        description
          "Number of ping echo request message to send";
      }
      leaf interval {
        type Interval;
        description
          "Interval between echo requests";
      }
      leaf packet-size {
        type uint32 {
          range "64..10000";
        }
        default "64";
        description
          "Size of ping echo request packets, in octets";
      }
    }
    output {
      uses monitor-stats {
        description
          "Stats of continuity check.";
      }
    }
  }
  rpc path-discovery {
    description
      "Generates Trace-route or Path Trace and return response.
       Referencing RFC7276 for common Toolset name, for IP it's
       Traceroute, for MPLS OAM it's Traceroute mode, for
       MPLS-TP OAM it's Route Tracing, for Pseudowire OAM it's
       LSP Ping, and for TRILL OAM It's Path Tracing tool.
       Starts with TTL
       of one and increment by one at each hop. Untill destination
       reached or TTL reach max valune";
    input {
      uses maintenance-domain-id {
        description
          "defines the MD (Maintenance Domain) identifier, which is
           the generic MD-name-string and the technology.";
      }
      uses ma-identifier {
        description
          "identfies the Maintenance association";
      }
      uses flow-entropy;
      uses priority;
      leaf ttl {
        type uint8;
        default "255";
description
  "Time to Live";
      }
      uses session-type;
      leaf command-sub-type {
        type identityref {

          base command-sub-type;
        }
        description
          "defines different command types";
      }
      leaf ecmp-choice {
        type ecmp-choices;
        description
          "0 means use the specified interface
           1 means use round robin";
      }
      list outgoing-interfaces {
        key "interface";
        leaf interface {
          type if:interface-ref;
  description
    "Interface.";
        }
description
  "Outgoing interface list.";
      }
      leaf source-mep {
        type MEP-name;
description
  "Source MEP";
      }
      container destination-mp {
        uses mp-address;
        uses MEP-ID {
          description "Only applicable if the destination is a MEP";
        }
description
  "Destination MEP";
      }
      leaf count {
        type uint32;
        default "1";
        description
          "Number of traceroute probes to send.  In protocols where a
           separate message is sent at each TTL, this is the number
           of packets to send at each TTL.";
      }
      leaf interval {
        type Interval;
        description
          "Interval between echo requests";
      }
    }
    output {
      list response {
        key "response-index";
        leaf response-index {
  type uint8;
          description
            "Arbitrary index for the response.  In protocols that
             guarantee there is only a single response at each TTL
             (eg IP Traceroute), the TTL can be used as the response
             index.";
        }
        leaf ttl {
          type uint8;
  description
    "Time to Live";
        }
description
   "Time to Live";
        container destination-mp {
          description "MP from which the response has been received";
          uses mp-address;
          uses MEP-ID {
            description
              "Only applicable if the destination is a MEP";
          }
        }
        uses monitor-stats {
          description
            "If count is 1, there is a single delay value reported.";
        }
      }
      description
        "List of response.";
    }
  }
}
