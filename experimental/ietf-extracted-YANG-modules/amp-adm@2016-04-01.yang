module amp-adm {
        namespace "urn:ietf:params:xml:ns:yang:amp-adm";
        prefix "amp";

        include amp-types;
        include amp-extensions;
        include amp-instances;

        organization
                "IETF Delay Tolerant Networking Working Group";
        contact
                "WG Web: <http://tools.ietf.org/wg/dtn/>
        WG List: <mailto:dtn@ietf.org>

        WG Chairs: Brian Haberman
                   <mailto:brian@innovationslab.net>
                   Marc Blanchet
                   <mailto:Marc.Blanchet@viagenie.ca>

        Editor: Brian Sipos
                <mailto:BSIpos@rkf-eng.com>";

        description
                "This module implements the "
                +"Asynchornous Management Protocol (AMP) "
                +"Application Data Model (ADM) profile within YANG";
    reference "draft Asynchronous Management Protocol";

    revision "2016-04-01" {
        description "Updated to fix typos.";
        reference "I-D draft-bsipos-dtn-amp-yang";
    }
        revision "2016-03-14" {
                description "Initial draft release.";
                reference "I-D draft-bsipos-dtn-amp-yang";
        }
}
