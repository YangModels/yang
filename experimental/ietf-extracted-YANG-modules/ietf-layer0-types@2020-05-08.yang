module ietf-layer0-types {
  yang-version 1.1;
  namespace "urn:ietf:params:xml:ns:yang:ietf-layer0-types";
  prefix "l0-types";

  organization
    "IETF CCAMP Working Group";
  contact
    "WG Web: <http://tools.ietf.org/wg/ccamp/>
     WG List: <mailto:ccamp@ietf.org>

     Editor: Haomian Zheng
       <mailto:zhenghaomian@huawei.com>

     Editor: Young Lee
       <mailto:younglee.tx@gmail.com>

     Editor: Aihua Guo
       <mailto:aihuaguo@futurewei.com>

     Editor: Victor Lopez
       <mailto:victor.lopezalvarez@telefonica.com>

     Editor: Daniel King
       <mailto:d.king@lancaster.ac.uk>";

  description
    "This module defines Optical Layer 0 types. This module
     provides groupings that can be applicable to Layer 0
     Fixed Optical Networks (e.g., CWDM (Coarse Wavelength
     Division Multiplexing) and DWDM (Dense Wavelength Division
     Multiplexing)) and Flexi-grid Optical Networks.

     Copyright (c) 2020 IETF Trust and the persons identified
     as authors of the code.  All rights reserved.

     Redistribution and use in source and binary forms, with
     or without modification, is permitted pursuant to, and
     subject to the license terms contained in, the Simplified
     BSD License set forth in Section 4.c of the IETF Trust's
     Legal Provisions Relating to IETF Documents
     (http://trustee.ietf.org/license-info).

     This version of this YANG module is part of RFC XXXX; see
     the RFC itself for full legal notices.";

  revision "2020-05-08" {
    description
      "Initial Version";
    reference
      "RFC XXXX: A YANG Data Model for Layer 0 Types";
  }

  typedef dwdm-n {
    type int16;
    description
      "The given value 'N' is used to determine the nominal
      central frequency.
      The nominal central frequency, 'f' is defined by,
        f = 193100.000 GHz + N x channel-spacing (measured in GHz),
      where 193100.000 GHz (193.100000 THz) is the ITU-T 'anchor
        frequency' for transmission over the C band; and
      where 'channel-spacing' is defined by the dwdm-ch-spc-type.";
    reference
      "RFC6205: Generalized Labels for
      Lambda-Switch-Capable (LSC) Label Switching Routers,
      ITU-T G.694.1 (02/2012): Spectral grids for WDM applications:
      DWDM frequency grid";
  }

  typedef cwdm-n {
    type int16;
    description
      "The given value 'N' is used to compute the channel
      wavelength as per the formula:
        Wavelength (nm) = 1471 + N x channel-spacing (measured in nm),
      where 1471 nm is the ITU-T 'anchor wavelength'
        for transmission over the C band; and
      where 'channel-spacing' is defined by the cwdm-ch-spc-type. ";
    reference
      "RFC6205: Generalized Labels for
      Lambda-Switch-Capable (LSC) Label Switching Routers,
      ITU-T G.694.2 (12/2003): Spectral grids for WDM applications:
      CWDM wavelength grid";
  }

  typedef flexi-n {
    type int16;
    description
      "The given value 'N' is used to determine the nominal
      central frequency.
      The nominal central frequency, 'f' is defined by,
        f = 193100.000 GHz + N x channel-spacing (measured in GHz),
      where 193100.000 GHz (193.100000 THz) is the ITU-T 'anchor
        frequency' for transmission over the C band; and
      where 'channel-spacing' is defined by the flexi-ch-spc-type.

      Note that the term 'chanel-spacing' can be alternated by the
      term 'nominal central frequency granularity' defined in
      clause 7 of ITU-T G.694.1.";
    reference
      "RFC7698: Framework and Requirements for GMPLS-Based Control
      of Flexi-Grid Dense Wavelength Division Multiplexing (DWDM)
      Networks.
      ITU-T G.694.1 (02/2012): Spectral grids for WDM applications:
      DWDM frequency grid";
  }

  typedef flexi-m {
    type int16;
    description
      "M is used to determine the slot width. A slot width is
       constrained to be M x SWG (that is, M x 12.500 GHz),
       where M is a positive integer.";
    reference
      "RFC7698: Framework and Requirements for GMPLS-Based Control
      of Flexi-Grid Dense Wavelength Division Multiplexing (DWDM)
      Networks.
      ITU-T G.694.1 (02/2012): Spectral grids for WDM applications:
      DWDM frequency grid";
  }

  identity l0-grid-type {
    description
      "Layer 0 grid type";
    reference
      "RFC6163:Framework for GMPLS and Path Computation Element
      (PCE) Control of Wavelength Switched Optical Networks (WSONs),
      ITU-T G.694.1 (02/2012): Spectral grids for WDM applications:
      DWDM frequency grid,
      ITU-T G.694.2 (12/2003): Spectral grids for WDM applications:
      CWDM wavelength grid";
  }

  identity flexi-grid-dwdm {
    base l0-grid-type;
    description
      "Flexi-grid";
    reference
      "RFC7698: Framework and Requirements for GMPLS-Based Control
      of Flexi-Grid Dense Wavelength Division Multiplexing (DWDM)
      Networks,
      ITU-T G.694.1 (02/2012): Spectral grids for WDM applications:
      DWDM frequency grid";
  }

  identity wson-grid-dwdm {
    base l0-grid-type;
    description
      "DWDM grid";
    reference
      "RFC6163:Framework for GMPLS and Path Computation Element
      (PCE) Control of Wavelength Switched Optical Networks (WSONs),
      ITU-T G.694.1 (02/2012): Spectral grids for WDM applications:
      DWDM frequency grid";
  }

  identity wson-grid-cwdm {
    base l0-grid-type;
    description
      "CWDM grid";
    reference
      "RFC6205: Generalized Labels for
      Lambda-Switch-Capable (LSC) Label Switching Routers,
      ITU-T G.694.2 (12/2003): Spectral grids for WDM applications:
      CWDM wavelength grid";
  }

  identity dwdm-ch-spc-type {
    description
      "DWDM channel spacing type";
    reference
      "RFC6205: Generalized Labels for
      Lambda-Switch-Capable (LSC) Label Switching Routers,
      ITU-T G.694.1 (02/2012): Spectral grids for WDM applications:
      DWDM frequency grid";
  }

  identity dwdm-100ghz {
    base dwdm-ch-spc-type;
    description
      "100GHz channel spacing";
  }

  identity dwdm-50ghz {
    base dwdm-ch-spc-type;
    description
      "50GHz channel spacing";
  }

  identity dwdm-25ghz {
    base dwdm-ch-spc-type;
    description
      "25GHz channel spacing";
  }

  identity dwdm-12p5ghz {
    base dwdm-ch-spc-type;
    description
      "12.5GHz channel spacing";
  }

  identity flexi-ch-spc-type {
    description
      "Flexi-grid channel spacing type";
    reference
      "RFC7698: Framework and Requirements for GMPLS-Based Control
      of Flexi-Grid Dense Wavelength Division Multiplexing (DWDM)
      Networks
      ITU-T G.694.1 (02/2012): Spectral grids for WDM applications:
      DWDM frequency grid";
  }

  identity flexi-ch-spc-6p25ghz {
    base flexi-ch-spc-type;
    description
      "6.25GHz channel spacing";
  }

  identity flexi-slot-width-granularity {
    description
      "Flexi-grid slot width granularity";
  }

  identity flexi-swg-12p5ghz {
    base flexi-slot-width-granularity;
    description
      "12.5GHz slot width granularity";
  }

  identity cwdm-ch-spc-type {
    description
      "CWDM channel spacing type";
    reference
      "RFC6205: Generalized Labels for
      Lambda-Switch-Capable (LSC) Label Switching Routers,
      ITU-T G.694.2 (12/2003): Spectral grids for WDM applications:
      CWDM wavelength grid";
  }

  identity cwdm-20nm {
    base cwdm-ch-spc-type;
    description
      "20nm channel spacing";
  }

  /* Groupings. */

  grouping wson-label-start-end {
    description
      "The WSON label-start or label-end used to
      specify WSON label range.";
    choice grid-type {
      description
        "Label for DWDM or CWDM grid";
      case dwdm {
        leaf dwdm-n {
          type l0-types:dwdm-n;
          description
           "The central frequency of DWDM. ";
          reference
            "RFC6205: Generalized Labels for
             Lambda-Switch-Capable (LSC) Label Switching Routers";
        }
      }
      case cwdm {
        leaf cwdm-n {
          type l0-types:cwdm-n;
          description
            "Channel wavelength computing input. ";
          reference
            "RFC6205: Generalized Labels for
             ambda-Switch-Capable (LSC) Label Switching Routers";
        }
      }
    }
    reference
      "RFC6205: Generalized Labels for
      Lambda-Switch-Capable (LSC) Label Switching Routers";
  }

  grouping wson-label-hop {
    description
      "Generic label hop information for WSON";
    choice grid-type {
      description
        "Label for DWDM or CWDM grid";
      case dwdm {
        choice single-or-super-channel {
          description "single or super channel";
          case single {
            leaf dwdm-n {
              type l0-types:dwdm-n;
              description
               "The central frequency of DWDM. ";
             }
          }
          case super {
           leaf-list subcarrier-dwdm-n {
              type l0-types:dwdm-n;
              description
                "List of center frequencies for each subcarrier
                 channels.";
              reference
                "ITU-T Recommendation G.694.1: Spectral grids for
                WDM applications: DWDM frequency grid";
           }
          }
        }
      }
      case cwdm {
        leaf cwdm-n {
          type l0-types:cwdm-n;
          description
            "Channel wavelength computing input. ";
          reference
            "RFC6205: Generalized Labels for
             Lambda-Switch-Capable (LSC) Label Switching Routers";
        }
      }
    }
    reference
      "RFC6205: Generalized Labels for
      Lambda-Switch-Capable (LSC) Label Switching Routers";
  }

  grouping l0-label-range-info {
    description
      "Information for layer 0 label range.";
    leaf grid-type {
      type identityref {
        base l0-grid-type;
      }
      description "Grid type";
    }
    leaf priority {
      type uint8;
      description
        "Priority in Interface Switching Capability
        Descriptor (ISCD).";
      reference "RFC4203.";
    }
    reference
      "RFC6205: Generalized Labels for
      Lambda-Switch-Capable (LSC) Label Switching Routers";
  }

  grouping wson-label-step {
    description "Label step information for WSON";
    choice l0-grid-type {
      description
        "Grid type: DWDM, CWDM, etc.";
      case dwdm {
        leaf wson-dwdm-channel-spacing {
          type identityref {
            base dwdm-ch-spc-type;
          }
          description
            "Label-step is the channel-spacing (GHz), e.g.,
             100.000, 50.000, 25.000, or 12.500 GHz for DWDM";
          reference
            "RFC6205: Generalized Labels for
             Lambda-Switch-Capable (LSC) Label Switching Routers";
        }
      }
      case cwdm {
        leaf wson-cwdm-channel-spacing {
          type identityref {
            base cwdm-ch-spc-type;
          }
          description
            "label-step is the channel-spacing (nm), i.e., 20 nm
             for CWDM, which is the only value defined for CWDM";
          reference
            "RFC6205: Generalized Labels for
             Lambda-Switch-Capable (LSC) Label Switching Routers";
        }
      }
    }
    reference
      "RFC6205: Generalized Labels for
      Lambda-Switch-Capable (LSC) Label Switching Routers
      ITU-T G.694.2 (12/2003): Spectral grids for WDM applications:
      CWDM wavelength grid";
  }

  grouping flexi-grid-label-start-end {
    description
      "Label-start and Label-end information for Flexi-grid.";
    leaf flexi-n {
      type l0-types:flexi-n;
      description
        "The central frequency in Flexi-grid.";
    }
    reference
      "RFC7698: Framework and Requirements for GMPLS-Based Control
      of Flexi-Grid Dense Wavelength Division Multiplexing (DWDM)
      Networks";
  }

  grouping flexi-grid-frequency-slot {
    description "Flexi-grid frequency slot grouping.";
    uses flexi-grid-label-start-end;
    leaf flexi-m {
      type l0-types:flexi-m;
      description
        "M is used to determine the slot width. A slot width is
         constrained to be M x SWG (that is, M x 12.500 GHz),
         where M is a positive integer.";
    }
    reference
      "RFC7698: Framework and Requirements for GMPLS-Based Control
      of Flexi-Grid Dense Wavelength Division Multiplexing (DWDM)
      Networks";
  }
  grouping flexi-grid-label-hop {
    description "Flexi-grid path label.";
      choice single-or-super-channel {
       description "single of super channel";
        case single {
          uses flexi-grid-frequency-slot;
       }
        case super {
         list subcarrier-flexi-n {
         key flexi-n;
         uses flexi-grid-frequency-slot;
         description
            "List of subcarrier channels for flexi-grid
             super channel.";
          }
        }
      }
    reference
      "RFC7698: Framework and Requirements for GMPLS-Based Control
      of Flexi-Grid Dense Wavelength Division Multiplexing (DWDM)
      Networks";
  }

  grouping flexi-grid-label-range-info {
    description
      "Info of Flexi-grid-specific label range";
    uses l0-label-range-info;
    container flexi-grid {
      description "flexi-grid definition";
      leaf slot-width-granularity {
        type identityref {
          base flexi-slot-width-granularity;
        }
        default flexi-swg-12p5ghz;
        description
          "Minimum space between slot widths. Default is
           12.500 GHz";
        reference
          "RFC7698: Framework and Requirements for GMPLS-Based Control
          of Flexi-Grid Dense Wavelength Division Multiplexing (DWDM)
          Networks";
      }
      leaf min-slot-width-factor {
        type uint16 {
          range "1..max";
        }
        default 1;
        description
          "Slot width range: two multipliers of the slot width ,
           granularity, each indicating the minimal and maximal slot
           width supported by a port, respectively.

           Minimum slot width is calculated by:
             Minimum slot width (GHz) =
               min-slot-width-factor * slot-width-granularity";
        reference
          "RFC8363: GMPLS OSPF-TE Extensions in Support of Flexi-Grid
          Dense Wavelength Division Multiplexing (DWDM) Networks";
      }

      leaf max-slot-width-factor {
        type uint16 {
          range "1..max";
        }
        description
          "Slot width range: two multipliers of the slot width ,
           granularity, each indicating the minimal and maximal slot
           width supported by a port, respectively.

           Maximum slot width is calculated by:
             Maximum slot width (GHz) =
               max-slot-width-factor * slot-width-granularity";
        reference
          "RFC8363: GMPLS OSPF-TE Extensions in Support of Flexi-Grid
          Dense Wavelength Division Multiplexing (DWDM) Networks";
      }
    }
  }

  grouping flexi-grid-label-step {
    description "Label step information for flexi-grid";
    leaf flexi-grid-channel-spacing {
      type identityref {
        base flexi-ch-spc-type;
      }
      default flexi-ch-spc-6p25ghz;
      description
        "Label-step is the nominal central frequency
         granularity (GHz), e.g., 6.25 GHz";
      reference
         "RFC7699: Generalized Labels for the Flexi-Grid in
          Lambda Switch Capable (LSC) Label Switching Routers";
    }
    leaf flexi-n-step {
      type uint8;
      description
        "This attribute defines the granularity of supported values
        for the nominal central frequency as a multiplier of the
        channel-spacing.

        For example, given a grid with a nominal central frequency
        granularity of 6.25 GHz, the granularity of the supported
        values of the nominal central frequency could be 12.5 GHz.
        In this case, the values of flexi-n should be even and this
        constraints is reported by setting the flexi-n-step to 2.

        This attribute is also known as central frequency granularity
        in RFC8363. ";
      reference
        "RFC8363: GMPLS OSPF-TE Extensions in Support of Flexi-Grid
         Dense Wavelength Division Multiplexing (DWDM) Networks";
    }
  }
}
