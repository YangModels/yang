module ietf-srv6-topology {
  yang-version "1.1";
  namespace "urn:ietf:params:xml:ns:yang:ietf-srv6-topology";
  prefix "srv6-topo";

  import ietf-inet-types {
    prefix "inet";
    reference
      "RFC 6991: Common YANG Data Types";
  }
  import ietf-network {
    prefix "nw";
    reference "RFC 8345: A YANG Data Model for Network Topologies";
  }
  import ietf-network-topology {
    prefix "nt";
    reference "RFC 8345: A YANG Data Model for Network Topologies";
  }
  import ietf-l3-unicast-topology {
    prefix "l3t";
    reference "RFC 8346: A YANG Data Model for Layer 3 Topologies";
  }
  import ietf-srv6-types {
    prefix "srv6-types";
    reference "RFC XXXX: YANG Data Model for SRv6 Base and Static";
  }
  import ietf-srv6-base {
    prefix "srv6-base";
    reference "RFC XXXX: YANG Data Model for SRv6 Base and Static";
  }
  import ietf-sr-mpls-topology {
    prefix "sr-mpls-topo";
    reference
      "RFC XXXX: YANG Data Model for SR and SR TE Topologies on
       MPLS Data Plane";
  }

  organization
    "IETF TEAS Working Group";
  contact
    "TBD";

  description
    "This module describes a YANG model for representing and
     manipulating Segment Routing Topologies on IPv6 Data Plane.";

  revision 2023-10-16 {
    description
      "Initial Version";
    reference
      "RFC XXXX, YANG Data Model for SR and SR TE Topologies on
       IPv6 Data Plane";
  }

  grouping srv6-topology-type {
    description
      "Identifies the SRv6 topology type. This type of network
       topologies use Segment Routing (SR) technology over the IPv6
       data plane";
    container srv6 {
      presence "Indicates SRv6 topology";
      description
        "Its presence identifies the SRv6 topology type.";
    }
  }

  grouping srv6-node-attributes {
    description "SRv6 node scope attributes.";
    container srv6 {
      presence "Presence indicates SRv6 is enabled.";
      description
        "Containing SRv6 attributes.";
      container node-capabilities {
        config false;
        description
          "SRv6 capabilities of the node.";
        uses srv6-base:srv6-msd-signaled;
      }
      list supported-algorithms {
        key "algorithm";
        description
          "Supported algorithms of the node.";
        leaf algorithm {
          type uint8 {
            range "128..255";
          }
          mandatory true;
          description
            "Algorithm Id (for Flex-Algo).";
        }
      }
      container locators {
        description "SRv6 locators of the node.";
        list locator {
          key "prefix-addr prefix-len";
          description
            "An SRv6 locator";
          leaf prefix-addr {
            type inet:ipv6-address;
            mandatory true;
            description
              "IPv6 address";
          }
          leaf prefix-len {
            type srv6-types:srv6-locator-len;
            mandatory true;
            description
              "Locator (prefix) length";
          }
          leaf algorithm {
            type uint8 {
              range "128..255";
            }
            description
              "Algorithm Id (for Flex-Algo).";
          }
          leaf anycast {
            type boolean;
            default false;
            description
              "Set to true if the locator is anycast.";
          }
          leaf is-readvertisment {
            type boolean;
            config false;
            description
              "Set to true if the locator has been
               readvertising from another topology.";
          }
          container sids {
            description
              "SRv6 SIDs covered by the locator";
            list sid {
              key "sid-value";
              description
                "An SRv6 SID";
              leaf sid-value {
                type srv6-types:srv6-sid;
                description
                  "The SID value";
              }
              leaf end-behavior-type {
                type identityref {
                  base srv6-types:srv6-endpoint-type;
                }
                description "Type of SRv6 end behavior.";
              }
            }
          }
        }
      }
      uses sr-mpls-topo:information-source-attributes;
    }
  }

  grouping srv6-link-attributes {
    description "SRv6 link scope attributes";
    container srv6 {
      presence "Presence indicates SRv6 is enabled.";
      description
        "Containing SRv6 attributes.";
      container link-capabilities {
        config false;
        description
          "SRv6 capabilities of the link.";
        uses srv6-base:srv6-msd-signaled;
      }
      container sids {
        description
          "SRv6 SIDs covered by the locator";
        list sid {
          key "sid-value";
          description
            "An SRv6 SID";
          leaf sid-value {
            type srv6-types:srv6-sid;
            description
              "The SID value";
          }
          leaf end-behavior-type {
            type identityref {
              base srv6-types:srv6-endpoint-type;
            }
            description "Type of SRv6 end behavior.";
          }
          leaf algorithm {
            type uint8 {
              range "128..255";
            }
            config false;
            description
              "Algorithm Id (for Flex-Algo).";
          }
          leaf is-eligible-for-protection {
            type boolean;
            default false;
            description
              "Set to true if the SID is eligible for protection.";
            reference
              "RFC 8402: Segment Routing Architecture. Sec. 3.4.";
          }
          leaf is-part-of-set {
            type boolean;
            default false;
            description
              "Set to true if the SID is part of a set.";
          }
          leaf is-persistent {
            type boolean;
            default true;
            description
              "Set to true if the SID is persistently allocated.";
          }
          leaf is-on-lan {
            type boolean;
            default false;
            description
              "Set to true if on a LAN.";
          }
          leaf weight {
            type uint8;
            description
              "The value represents the weight of the SID for the
               purpose of load balancing.  The use of the weight
               is defined in RFC 8402.";
            reference
              "RFC 8402: Segment Routing Architecture. Sec. 3.4.";
          }
        }
      }
      uses sr-mpls-topo:information-source-attributes;
    }
  }

  augment "/nw:networks/nw:network/nw:network-types/"
    + "l3t:l3-unicast-topology" {
    description
      "Defines the SRv6 topology type.";
    uses srv6-topology-type;
  }

  augment "/nw:networks/nw:network/nw:node/l3t:l3-node-attributes" {
    when "../../nw:network-types/l3t:l3-unicast-topology/"
      + "srv6-topo:srv6" {
      description "Augment only for SRv6 topology.";
    }
    description "Augment node configuration.";
    uses srv6-node-attributes;
  }

  augment "/nw:networks/nw:network/nt:link/l3t:l3-link-attributes" {
    when "../../nw:network-types/l3t:l3-unicast-topology/"
      + "srv6-topo:srv6" {
      description "Augment only for SRv6 topology.";
    }
    description "Augment link configuration";
    uses srv6-link-attributes;
  }
}
