module ietf-l3vpn-svc {
    namespace "urn:ietf:params:xml:ns:yang:ietf-l3vpn-svc";

    prefix l3vpn-svc;

    import ietf-routing {
            prefix "rt";
        }

    import ietf-inet-types {
        prefix inet;
    }

    import ietf-yang-types {
        prefix yang;
    }

    organization
     "IETF L3SM Working Group";

    contact
        "WG List:   &lt;mailto:l3sm@ietf.org&gt;

        Editor:

        ";

    description
        "The YANG module defines a generic service configuration
        model for Layer 3 VPN common across all of the vendor
        implementations.";

    revision 2015-08-03 {
        description
         " * Creating multiple reusable groupings
           * Added mpls leaf in vpn-svc for carrier's carrier case
           * Modify identity single to single-site
           * Modify site-type to site-role and also child identities.
           * Creating OAM container under site and moved BFD in.
           * Creating flow-definition grouping to be reused
           in ACL, QoS ...
           * Simplified VPN policy.
           * Adding multicast static group to RP mappings.
           * Removed native-vpn and site-role from global site
           cfg, now managed within the VPN policy.
           * Creating a separate list for site templates.
         ";
        reference "";
    }
    revision 2015-07-02 {
        reference "draft-ietf-l3sm-l3vpn-service-yang-00";
    }
    revision 2015-04-24 {
        description "
        * Add encryption parameters
        * Adding holdtime for BFD.
        * Add postal address in location
        ";
        reference "draft-lstd-l3sm-l3vpn-service-yang-00";
    }
    revision 2015-02-05 {
        description "Initial revision.";
        reference "draft-l3vpn-service-yang-00";
    }

    identity management {
        description
         "Base identity for site management scheme.";
    }
    identity comanaged {
        base management;
        description
         "Base identity for comanaged site.";
    }
    identity customer-managed {
        base management;
        description
         "Base identity for customer managed site.";
    }
    identity provider-managed {
        base management;
        description
         "Base identity for provider managed site.";
    }

    identity address-allocation-type {
        description
         "Base identity for address-allocation-type
         for PE-CE link.";
    }
    identity pe-dhcp {
        base address-allocation-type;
        description
         "PE router provides DHCP service to CE.";
    }
    identity static-address {
        base address-allocation-type;
        description
         "PE-CE addressing is static.";
    }
    identity slaac {
        base address-allocation-type;
        description
         "Use IPv6 SLAAC.";
    }

    identity site-availability {
        description
         "Base identity for site availability.";
    }
    identity loadsharing {
            base site-availability;
            description
             "Identity for loadsharing site.";
    }
    identity loadsharing-ibgp {
            base loadsharing;
            description
             "Identity for ECMP ibgp based loadsharing site.";
    }
    identity loadsharing-eibgp {
            base loadsharing;
            description
             "Identity for ECMP eibgp based loadsharing site.";
    }
    identity primary-backup {
            base site-availability;
            description
             "Identity for primary-backup site.";
    }
    identity single-site {
            base site-availability;
            description
             "Identity for single site.";
    }
    identity access-availability-type {
        description
         "base identity for access-availability-type";
    }
    identity primary-access {
        base access-availability-type;
        description
         "Identity for primary access type.";
    }
    identity backup-access {
        base access-availability-type;
        description
         "Identity for backup access type.";
    }
    identity single-access {
        base access-availability-type;
        description
         "Identity for single access type.";
    }
    identity loadsharing-access {
        base access-availability-type;
        description
         "Identity for loadsharing access type.";
    }

    identity site-role {
        description
         "Base identity for site type.";
    }
    identity any-to-any-role {
        base site-role;
        description
         "Site in a any to any IPVPN.";
    }
    identity spoke-role {
        base site-role;
        description
         "Spoke Site in a Hub & Spoke IPVPN.";
    }
    identity hub-role {
        base site-role;
        description
         "Hub Site in a Hub & Spoke IPVPN.";
    }

    identity vpn-topology {
        description
         "Base identity for VPN topology.";
    }
    identity any-to-any {
        base vpn-topology;
        description
         "Identity for any to any VPN topology.";
    }
    identity hub-spoke {
        base vpn-topology;
        description
         "Identity for Hub'n'Spoke VPN topology.";
    }
    identity hub-spoke-disjoint {
        base vpn-topology;
        description
         "Identity for Hub'n'Spoke VPN topology
          where Hubs cannot talk between each other.";
    }

    identity multicast-tree-type {
        description
         "Base identity for multicast tree type.";
    }

    identity ssm-tree-type {
        base multicast-tree-type;
        description
         "Identity for SSM tree type.";
    }
    identity asm-tree-type {
        base multicast-tree-type;
        description
         "Identity for ASM tree type.";
    }
    identity bidir-tree-type {
        base multicast-tree-type;
        description
         "Identity for BiDir tree type.";
    }

    identity multicast-rp-discovery-type {
        description
         "Base identity for rp discovery type.";
    }
    identity auto-rp {
        base multicast-rp-discovery-type;
        description
         "Base identity for auto-rp discovery type.";
    }
    identity static-rp {
        base multicast-rp-discovery-type;
        description
         "Base identity for static type.";
    }
    identity anycast-rp {
        base multicast-rp-discovery-type;
        description
         "Base identity for anycast rp type.";
    }
    identity bsr-rp {
        base multicast-rp-discovery-type;
        description
         "Base identity for BDR discovery type.";
    }

    identity routing-protocol-type {
        description
         "Base identity for routing-protocol type.";
    }

    identity ospf {
        base routing-protocol-type;
        description
         "Identity for OSPF protocol type.";
    }

    identity bgp {
        base routing-protocol-type;
        description
         "Identity for BGP protocol type.";
    }

    identity static {
        base routing-protocol-type;
        description
         "Identity for static routing protocol type.";
    }

    identity rip {
        base routing-protocol-type;
        description
         "Identity for RIP protocol type.";
    }

    identity rip-ng {
        base routing-protocol-type;
        description
         "Identity for RIPng protocol type.";
    }

    identity vrrp {
        base routing-protocol-type;
        description
         "Identity for VRRP protocol type.
         This is to be used when LAn are directly connected
         to provider Edge routers.";
    }

    identity direct {
        base routing-protocol-type;
        description
         "Identity for direct protocol type.
        .";
    }

    identity protocol-type {
        description
         "Base identity for protocol field type.";
    }

    identity tcp {
        base protocol-type;
        description
         "TCP protocol type.";
    }
    identity udp {
        base protocol-type;
        description
         "UDP protocol type.";
    }
    identity icmp {
        base protocol-type;
        description
         "icmp protocol type.";
    }
    identity icmp6 {
        base protocol-type;
        description
         "icmp v6 protocol type.";
    }
    identity gre {
        base protocol-type;
        description
         "GRE protocol type.";
    }
    identity ipip {
        base protocol-type;
        description
         "IPinIP protocol type.";
    }
    identity hop-by-hop {
        base protocol-type;
        description
         "Hop by Hop IPv6 header type.";
    }
    identity routing {
        base protocol-type;
        description
         "Routing IPv6 header type.";
    }
    identity esp {
        base protocol-type;
        description
         "ESP header type.";
    }
    identity ah {
        base protocol-type;
        description
         "AH header type.";
    }

    /* Groupings */

    grouping vpn-svc-cfg {
        description
         "Configuration block for l3vpn svc.";

        leaf name {
            type string;
            description
             "Name of the VPN.";
        }
        leaf id {
            type uint32;
            description
            "VPN identifier. Local administration meaning.";
        }
        leaf customer-name {
            type string;
            description
             "Name of the customer.";
        }
        leaf topology {
            type identityref {
                base vpn-topology;
            }
            description
             "VPN topology.";
        }

        list cloud-access {
            key cloud-identifier;

            leaf cloud-identifier {
                type string;
                description
                 "Identification of cloud service. Local
                 admin meaning.";
            }
            list authorized-sites {
                key site-id;

                leaf site-id {
                    type leafref {
                        path "../../../../sites/site-id";
                    }
                    description
                     "Site ID.";
                }
                description
                 "List of authorized sites.";
            }
            list denied-sites {
                key site-id;

                leaf site-id {
                    type leafref {
                        path "../../../../sites/site-id";
                    }
                    description
                     "Site ID.";
                }
                description
                 "List of denied sites.";
            }
            leaf nat-enabled {
                type boolean;
                description
                 "Control if NAT is required or not.";
            }
            leaf customer-nat-address {
                type inet:ipv4-address;
                description
                 "NAT address to be used in case of public
                 or shared cloud.
                 This is to be used in case customer is providing
                 the public address.";
            }
            description
             "Cloud access configuration.";
        }

        leaf mpls {
            type boolean;
            default false;
            description
             "The VPN is using Carrier Supporting Carrier,
             and so MPLS is required.";
        }

        container multicast {
            leaf-list tree-flavor {
                type identityref {
                    base multicast-tree-type;
                }
                description
                 "Type of tree to be used.";
            }
            container rp {
                list static-rps {
                    key "rp-address group";

                    leaf rp-address {
                        type union {
                            type inet:ipv4-address;
                            type inet:ipv6-address;
                        }
                        description
                        "Defines the address of the RendezvousPoint.";
                    }
                    leaf group {
                        type union {
                            type inet:ipv4-address;
                            type inet:ipv6-address;
                        }
                        description
                        "Defines the address of the multicast group
                        handled by the RP.";
                    }
                    description
                     "List of RP to group mappings.";
                }
                leaf rp-discovery {
                    type identityref {
                        base multicast-rp-discovery-type;
                    }
                    description
                     "Type of RP discovery used.";
                }
                leaf-list anycast-rp-location {
                    type string;
                    description
                     "Encodes the location of the RPs in anycast RP
                     deployment.";
                }
                description
                 "RendezvousPoint parameters.";
            }
            description
                "Multicast global parameters for the VPN service.";
        }
    }

    grouping customer-location-info {
        container location {
                leaf address {
                    type string;
                    description
                    "Address (number and street)
                    of the site.";

                }
                leaf zip-code {
                    type string;
                    description
                    "ZIP code of the site.";
                }
                leaf city {
                    type string;
                    description
                     "City of the site.";
                }
                leaf country-code {
                    type string;
                    description
                     "Country of the site.";
                }
                description
                    "Location of the site.";
        }
        description
         "This grouping defines customer location
          parameters";
    }

    grouping site-diversity {
        container site-diversity {
                leaf type {
                    type enumeration {
                        enum "pop-diverse" {
                            description
                             "The access must use another PoP
                             compared
                             to other accesses in the same group.";
                        }
                        enum "pe-diverse" {
                            description
                             "The access must use another PE
                             compared
                             to other accesses in the same group.";
                        }
                    }
                    description
                     "Diversity constraint type.";
                }

                leaf-list site-group {
                    type uint32;
                    description
                     "IDs of group.";
                }
                description
                     "Diversity constraint type.";
            }
        description
         "This grouping defines site diversity
          parameters";
    }

    grouping operational-requirements {
          leaf requested-site-start {
               type yang:date-and-time;
               description
                "Optional leaf indicating requested date
                and time
                when the service at a particular site is
                expected
                to start";
           }

           leaf requested-site-stop {
               type yang:date-and-time;
               description
                "Optional leaf indicating requested date
                and time
                when the service at a particular site is
                expected
                to stop";
           }

           leaf actual-site-start {
               type yang:date-and-time;
               description
                "Optional leaf indicating actual date
                and time
                when the service at a particular site
                actually
                started";
           }
           leaf actual-site-stop {
               type yang:date-and-time;
               description
                "Optional leaf indicating actual date
                and time
                when the service at a particular site
                actually
                stopped";
           }
        description
         "This grouping defines some operational parameters
          parameters";
    }

    grouping site-availability {
        container availability {
                container availability-type {
                    leaf service-type {
                        type identityref {
                            base site-availability;
                        }
                        description
                         "Type of availability,
                         ex : single, backup, loadsharing";
                    }
                    leaf access-type {
                        type identityref {
                            base access-availability-type;
                        }
                        description
                         "Access type within the service.";
                    }
                    description
                        "Availability solution parameters";
                }
                leaf loadsharing-type {
                    type identityref {
                        base loadsharing;
                    }
                    description
                     "Loadsharing flavor.";
                }
                description
                 "Site availability parameters.";
            }
        description
         "This grouping defines site availability
          parameters";
    }

    grouping flow-definition {
        container match-flow {
            leaf ipv4-src-prefix {
                type inet:ipv4-prefix;
                description
                 "Match on IPv4 src address.";
            }
            leaf ipv6-src-prefix {
                type inet:ipv6-prefix;
                description
                 "Match on IPv6 src address.";
            }
            leaf ipv4-dst-prefix {
                type inet:ipv4-prefix;
                description
                 "Match on IPv4 dst address.";
            }
            leaf ipv6-dst-prefix {
                type inet:ipv6-prefix;
                description
                 "Match on IPv6 dst address.";
            }
            leaf l4-src-port {
                type uint16;
                description
                 "Match on layer 4 src port.";
            }
            leaf l4-dst-port {
                type uint16;
                description
                 "Match on layer 4 dst port.";
            }
            leaf protocol-field {
                type union {
                    type uint8;
                    type identityref {
                        base protocol-type;
                    }
                }
                description
                 "Match on IPv4 protocol or
                  Ipv6 Next Header
                 field.";
            }

            description
             "Describe flow matching
             criterions.";
        }
        description
         "Flow definition based on criteria.";
    }
        grouping site-service-basic {
        leaf svc-input-bandwidth {
               type uint32;
               units bps;
               description
                "From the PE perspective, the service input
                bandwidth of the connection.";
        }
        leaf svc-output-bandwidth {
           type uint32;
           units bps;
           description
            "From the PE perspective, the service output
            bandwidth of the connection.";
        }
        leaf svc-mtu {
            type uint16;
            units bytes;
            description
             "MTU at service level.
             If the service is IP,
             it refers to the IP MTU.";
        }
        description
         "Defines basic service parameters for a site.";
    }
    grouping site-service-protection {
        container traffic-protection {
            leaf link-local-protection {
                type boolean;
                description
                 "Enables protection of PE-CE link.";
            }
            leaf node-local-protection {
                type boolean;
                description
                 "Enables protection against local
                 PE node failure.";
            }
            leaf node-global-protection {
                type boolean;
                description
                "Enables protection against remote
                PE node failure.
                This is also called PIC Edge.
                ";
            }
            description
             "Fast reroute service parameters
             for the site.";
        }
        description
         "Defines protection service parameters for a site.";
    }
    grouping site-service-mpls {
        container mpls {
            leaf signalling-type {
                type enumeration {
                    enum "ldp" {
                        description
                            "Use LDP as signalling
                            protocol between PE and CE.";
                    }
                    enum "bgp" {
                        description
                            "Use BGP 3107 as signalling
                            protocol between PE and CE.
                            In this case, bgp must be also
                            configured
                            as routing-protocol.
                            ";
                    }
                }
                description
                 "MPLS signalling type.";
            }
            description
             "This container is used when customer provides
             MPLS based services.
             This is used in case of Carrier
             Supporting Carrier.";
        }
        description
         "Defines MPLS service parameters for a site.";
    }
    grouping site-service-qos-profile {
        container qos {
            container qos-classification-policy {
                list rules {
                    key id;

                    leaf id {
                        type uint16;
                        description
                         "ID of the rule.";
                    }
                    uses flow-definition;

                    leaf target-class-id {
                        type string;
                        description
                         "Identification of the
                         class of service.
                         This identifier is internal to
                         the administration.";
                    }
                    description
                     "List of marking rules.";
                }
                description
                 "Need to express marking rules ...";
            }
            leaf std-qos-profile {
                type string;
                description
                 "QoS profile to be used";
            }
            container custom-qos-profile {
                list class {
                    key class-id;

                    leaf class-id {
                        type string;
                        description
                         "Identification of the
                         class of service.
                         This identifier is internal to
                         the administration.";
                    }
                    leaf rate-limit {
                        type uint8;
                        units percent;
                        description
                         "To be used if class must
                         be rate
                         limited. Expressed as
                         percentage of the svc-bw.";
                    }
                    leaf priority-level {
                        type uint8;
                        description
                         "Defines the level of the
                         class in
                         term of priority queueing.
                          The higher the level is the
                          higher
                          is the priority.";
                    }
                    leaf guaranteed-bw-percent {
                        type uint8;
                        units percent;
                        description
                         "To be used to define the
                         guaranteed
                         BW in percent of the svc-bw
                         available at the priority-level.";
                    }
                    description
                     "List of class of services.";
                }
                description
                 "Custom qos profile.";
            }
            description
             "QoS configuration.";
        }
        description
         "This grouping defines QoS parameters
         for a site";

    }

    grouping site-security-authentication {
        container authentication {
            description
             "Authentication parameters";
        }
        description
         "This grouping defines authentication
         parameters
         for a site";

    }
    grouping site-security-encryption {
        container encryption {
            leaf enabled {
                type boolean;
                description
                 "If true, access encryption is required.";
            }
            leaf layer {
                type enumeration {
                    enum layer2 {
                        description
                         "Encryption will occur at layer2.";
                    }
                    enum layer3 {
                        description
                         "IPSec is requested.";
                    }
                }
                description
                 "Layer on which encryption is applied.";
            }
            container encryption-profile {
                choice profile {
                    case provider-profile {
                        leaf profile-name {
                            type string;
                            description
                             "Name of the SP profile
                             to be applied.";
                        }
                    }
                    case customer-profile {
                        leaf algorithm {
                            type string;
                            description
                             "Encryption algorithm to
                             be used.";
                        }
                        choice key-type {
                            case psk {
                                leaf preshared-key {
                                    type string;
                                    description
                                     "Key coming from
                                     customer.";
                                }
                            }
                            case pki {

                            }
                            description
                             "Type of keys to be used.";
                        }
                    }
                    description
                     "Choice of profile.";
                }
                description
                 "Profile of encryption to be applied.";
            }
            description
             "Encryption parameters.";
        }
        description
         "This grouping defines encryption parameters
         for a site";
    }
    grouping site-security-acl {
        container access-control-list {
            description
             "Access control list.";
        }

        description
         "This grouping defines ACL security parameters
         for a site";
    }

    grouping site-attachment-bearer {
        container bearer {
            leaf type {
                type string;
                description
                 "Type of bearer Ethernet, DSL, Wireless ...
                 Operator specific.";
            }
            leaf bearer-reference {
                type string;
                description
                 "This is an internal reference for the
                 service provider.";
            }
            description
             "Bearer specific parameters.
             To be augmented.";
        }
        description
         "Defines physical properties of
         a site attachment.";
    }

    grouping site-attachment-ip-connection {
        container ip-connection {
            container ipv4 {
                leaf address-allocation-type {
                    type identityref {
                        base address-allocation-type;
                    }
                    description
                     "Defines how addresses are allocated.
                     Need to be detailed further.";
                }
                leaf subnet-prefix {
                    type inet:ipv4-prefix;
                    description
                     "Interco subnet.";
                }
                description
                 "IPv4 specific parameters";

            }
            container ipv6 {
                leaf address-allocation-type {
                    type string;
                    description
                     "Defines how addresses are allocated.
                     Need to be detailled further.";
                }
                leaf subnet-prefix {
                    type inet:ipv6-prefix;
                    description
                     "Interco subnet.";
                }
                description
                 "IPv6 specific parameters";

            }
            container oam {
                container bfd {
                    leaf bfd-enabled {
                        type boolean;
                        description
                         "BFD activation";
                    }

                    choice holdtime {
                        case profile {
                            leaf profile-name {
                                type string;
                                description
                                 "Service provider well
                                 known profile.";
                            }
                            description
                                 "Service provider well
                                 known profile.";
                        }
                        case fixed {
                            leaf fixed-value {
                                type uint32;
                                units msec;
                                description
                                 "Expected holdtime
                                 expressed
                                 in msec.";
                            }
                        }
                        description
                         "Choice for holdtime flavor.";
                    }
                    description
                     "Container for BFD.";
                }
                description
                 "Define the OAM used on the connection.";
            }
            list routing-protocols {
                key type;

                leaf type {
                    type identityref {
                        base routing-protocol-type;
                    }
                    description
                     "Type of routing protocol.";
                }

                container ospf {
                    when "type = 'ospf'" {
                        description
                         "Only applies
                         when protocol is OSPF.";
                    }
                    leaf-list address-family {
                        type identityref {
                            base rt:address-family;
                        }
                        description
                         "Address family to be activated.";
                    }
                    leaf area-address {
                        type yang:dotted-quad;
                        description
                         "Area address.";
                    }
                    leaf metric {
                        type uint16;
                        description
                         "Metric of PE-CE link.";
                    }
                    list sham-link {
                        key target-site;

                        leaf target-site {
                            type leafref {
                                path "../../../../../../"
                                +"../sites/site-id";
                            }
                            description
                             "Target site for the sham link
                              connection.";
                        }
                        leaf metric {
                            type uint16;
                            description
                             "Metric of the sham link.";
                        }
                        description
                         "Creates a shamlink with another
                         site";
                    }
                    description
                     "OSPF specific configuration.";
                }

                container bgp {
                    when "type = 'bgp'" {
                        description
                         "Only applies when
                         protocol is BGP.";
                    }
                    leaf-list address-family {
                        type identityref {
                            base rt:address-family;
                        }
                        description
                         "Address family to be activated.";
                    }
                    description
                     "BGP specific configuration.";
                }
                container static {
                    when "type = 'static'" {
                        description
                         "Only applies when protocol
                         is static.";
                    }
                    leaf-list address-family {
                        type identityref {
                            base rt:address-family;
                        }
                        description
                         "Address family to be activated.";
                    }
                    description
                     "Static routing
                     specific configuration.";
                }
                container rip {
                    when "type = 'rip'" {
                        description
                         "Only applies when
                         protocol is RIP.";
                    }
                    leaf-list address-family {
                        type identityref {
                            base rt:address-family;
                        }
                        description
                         "Address family to be
                         activated.";
                    }

                    description
                     "RIP routing specific
                     configuration.";
                }

                container vrrp {
                    when "type = 'vrrp'" {
                        description
                         "Only applies when
                         protocol is VRRP.";
                    }
                    leaf-list address-family {
                        type identityref {
                            base rt:address-family;
                        }
                        description
                         "Address family to be activated.";
                    }
                    description
                     "VRRP routing specific configuration.";
                }

                description
                 "List of routing protocols used
                 on the site.
                 Need to be augmented.";
            }
            description
             "Defines connection parameters.";
        }
        description
         "This grouping defines IP connection parameters.";
    }

    grouping site-service-multicast {
        container multicast {
            leaf multicast-site-type {
                type enumeration {
                    enum receiver-only {
                        description
                         "The site has only receivers.";
                    }
                    enum source-only {
                        description
                         "The site has only sources.";
                    }
                    enum source-receiver {
                        description
                         "The site has both
                         sources & receivers.";
                    }
                }
                default "source-receiver";
                description
                 "Type of multicast site.";
            }
            container multicast-transport-protocol {
                leaf ipv4 {
                    type boolean;
                    default true;
                    description
                        "Enables ipv4 multicast transport";
                }
                leaf ipv6 {
                    type boolean;
                    default false;
                    description
                        "Enables ipv6 multicast transport";
                }
                description
                 "Defines protocol to transport multicast.";
            }
            leaf protocol-type {
                type enumeration {
                    enum host {
                        description
                         "
                         Hosts are directly connected
                         to the provider network.
                         Host protocols like IGMP, MLD
                         are required.
                         ";
                    }
                    enum router {
                        description
                         "
                         Hosts are behind a customer router.
                         PIM will be implemented.
                         ";
                    }
                    enum both {
                        description
                         "Some Hosts are behind a customer
                         router and some others are directly
                         connected to the provider network.
                         Both host and routing protocols must be
                         used. Typically IGMP and PIM will be
                         implemented.
                         ";
                    }
                }
                default "both";
                description
                 "Multicast protocol type to be used
                 with the customer site.";
            }

            description
             "Multicast parameters for the site.";
        }
        description
          "Multicast parameters for the site.";
    }

    grouping site-management {
        container management {
            leaf type {
                type identityref {
                    base management;
                }
                description
                "Management type of the connection.";
            }
            leaf management-transport {
                type identityref {
                    base rt:address-family;
                }
                description
                 "Transport protocol used for management.";
            }
            leaf address {
                type union {
                    type inet:ipv4-address;
                    type inet:ipv6-address;
                }
                description
                 "Management address";
            }

            description
             "Management configuration";
        }
        description
          "Management parameters for the site.";
    }

    grouping site-vpn-policy {
        container vpn-policy {
            list entries {
                key id;

                leaf id {
                        type uint32;
                        description
                         "Unique identifier for
                          the policy entry.";
                }
                container filter {
                    container lan-prefixes {
                        list ipv4-lan-prefixes {
                            key lan;

                            leaf lan {
                                type inet:ipv4-prefix;
                                description
                                 "Lan prefixes.";
                            }
                            description "
                                List of LAN prefixes
                                for the site.
                                ";
                        }
                        list ipv6-lan-prefixes {
                            key lan;

                            leaf lan {
                                type inet:ipv6-prefix;
                                description
                                 "Lan prefixes.";
                            }
                            description "
                                List of LAN prefixes
                                for the site.
                                ";
                        }
                        description
                         "LAN prefixes from the customer.";
                    }
                    leaf-list lan-tag {
                        type string;
                        description
                         "List of lan-tags to be matched.";
                    }
                    description
                     "If used, it permit to split site LANs
                     among multiple VPNs.
                     If no filter used, all the LANs will be
                     part of the same VPNs with the same
                     role.";
                }
                container vpn {
                    leaf vpn {
                        type leafref {
                            path "../../../../../vpn-svc/name";
                        }
                        description
                         "Reference to an IPVPN.";
                    }
                    leaf site-role {
                        type identityref {
                            base site-role;
                        }
                        description
                         "Role of the site in the IPVPN.";
                    }
                    description
                     "List of VPNs the LAN is associated to.";
                }
                description
                 "List of entries for export policy.";
            }
            description
                 "VPN policy.";
        }
        description
          "VPN policy parameters for the site.";
    }

    grouping site-customer-routing-specific-information {
        container customer-specific-information {
            leaf name {
                type string;
                description
                 "Name of the customer router.";
            }
            leaf autonomous-system {
                type uint32;
                description
                 "AS number.";
            }
            leaf interface {
                type string;
                description
                 "Interface reference of the access.";
            }
            list customer-lan-connection {
                key "address";
                leaf address {
                    type union {
                        type inet:ipv4-address;
                        type inet:ipv6-address;
                    }
                    description
                     "Address given by the customer on its LAN
                    for the SP router.";
                }
                leaf lan-protocol {
                    type identityref {
                        base rt:address-family;
                    }
                    description
                     "Transport protocol used on LAN.";
                }
                description
                 "List of customer LAN to be connected
                 directly on the CE.";
            }
            container cascaded-lan-prefixes {
                list ipv4-lan-prefixes {
                    key lan;

                    leaf lan {
                        type inet:ipv4-prefix;
                        description
                         "Lan prefixes.";
                    }
                    leaf lan-tag {
                        type string;
                        description
                         "Internal tag to be used in vpn
                         policies.";
                    }
                    leaf next-hop {
                        type inet:ipv4-address;
                        description
                         "Nexthop address to use at customer
                         side.";
                    }
                    description "
                        List of LAN prefixes for
                        the site.
                        ";
                }
                list ipv6-lan-prefixes {
                    key lan;

                    leaf lan {
                        type inet:ipv6-prefix;
                        description
                         "Lan prefixes.";
                    }
                    leaf lan-tag {
                        type string;
                        description
                         "Internal tag to be used
                         in vpn policies.";
                    }
                    leaf next-hop {
                        type inet:ipv6-address;
                        description
                         "Nexthop address to use at
                         customer side.";
                    }
                    description "
                        List of LAN prefixes for the site.
                        ";
                }
                description
                    "LAN prefixes from the customer.";
            }

            description
             "Customer premise configuration.";
        }
        description
         "Customer routing specific information.";
    }

    grouping site-maximum-routes {
        container maximum-routes {
            list address-family {
                key af;

                leaf af {
                    type identityref {
                        base rt:address-family;
                    }
                    description
                     "Address-family.";
                }
                leaf maximum-routes {
                    type uint32;
                    description
                     "Maximum prefixes the VRF can
                     accept for this
                     address-family.";
                }
                description
                 "List of address families.";
            }

            description
             "Define maximum-routes for the VRF.";
        }
        description
        "Define maximum-routes for the site.";
    }

    /* Main blocks */

    container l3vpn-svc {
        list vpn-svc {
            key name;

            uses vpn-svc-cfg;

            description "
                List of VPN services.
                ";
        }

        list sites {
            key site-id;

            leaf site-id {
                type string;
                description
                    "Identifier of the site.";
            }

            leaf apply-template {
                type leafref {
                    path "../../sites/site-id";
                }
                description
                 "It we would be good to ensure that
                 site-id is template type";
            }

            uses operational-requirements;
            uses customer-location-info;
            uses site-diversity;
            uses site-availability;
            uses site-management;
            uses site-vpn-policy;
            uses site-maximum-routes;
            uses site-customer-routing-specific-information;

            container security {
                leaf apply-template {
                    type leafref {
                        path "../../../sites/site-id";
                    }
                    description
                     "It we would be good to ensure that site-id is
                     template type";
                }
                uses site-security-authentication;
                uses site-security-encryption;
                uses site-security-acl;

                description
                 "Site specific security parameters.";
            }

            container attachment {
                leaf apply-template {
                    type leafref {
                        path "../../../sites/site-id";
                    }
                    description
                     "It we would be good to ensure
                     that site-id is
                     template type";
                }
                uses site-attachment-bearer;
                uses site-attachment-ip-connection;

                description
                 "Parameters of the attachement.";
            }

            container service {
                leaf apply-template {
                    type leafref {
                        path "../../../sites/site-id";
                    }
                    description
                     "It we would be good to ensure that site-id is
                     template type";
                }
                uses site-service-basic;
                uses site-service-qos-profile;
                uses site-service-protection;
                uses site-service-mpls;
                uses site-service-multicast;

                description
                 "Service parameters on the attachement.";
            }

            description "List of sites.";
        }
        list site-templates {
            key site-template-id;

            leaf site-template-id {
                type string;
                description
                    "Identifier of the site.";
            }

            uses operational-requirements;
            uses customer-location-info;
            uses site-diversity;
            uses site-availability;
            uses site-management;
            uses site-vpn-policy;
            uses site-maximum-routes;
            uses site-customer-routing-specific-information;

            container security {
                uses site-security-authentication;
                uses site-security-encryption;
                uses site-security-acl;

                description
                 "Site specific security parameters.";
            }

            container attachment {
                uses site-attachment-bearer;
                uses site-attachment-ip-connection;

                description
                 "Parameters of the attachement.";
            }

            container service {
                uses site-service-basic;
                uses site-service-qos-profile;
                uses site-service-protection;
                uses site-service-mpls;
                uses site-service-multicast;

                description
                 "Service parameters on the attachement.";
            }

            description "List of sites.";
        }
        description
         "Main container for L3VPN service configuration.";
    }

}
