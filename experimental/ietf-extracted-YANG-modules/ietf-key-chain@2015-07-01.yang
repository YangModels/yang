module ietf-key-chain {
  namespace "urn:ietf:params:xml:ns:yang:ietf-key-chain";
  // replace with IANA namespace when assigned
  prefix "key-chain";

  import ietf-yang-types {
    prefix "yang";
  }

  organization
    "IETF RTG (Routing) Working Group";
  contact
    "Acee Lindem - acee@cisco.com";

  description
    "This YANG module defines the generic configuration
     data for key-chain. It is intended that the module
     will be extended by vendors to define vendor-specific
     key-chain configuration parameters.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2015-07-01 {
    description
      "Updated version. Added Operation State following
       draft-openconfig-netmod-opstate-00.";
    reference
      "RFC XXXX: A YANG Data Model for key-chain";
  }
  revision 2015-02-24 {
    description
      "Initial revision.";
    reference
      "RFC XXXX: A YANG Data Model for key-chain";
  }

  typedef key-chain-ref {
    type leafref {
      path "/key-chain:key-chains/key-chain:key-chain-list/"
         + "key-chain:name";
    }
    description
      "This type is used by data models that need to reference
       configured key-chains.";
  }

  feature hex-key-string {
    description
      "Support hexadecimal key string.";
  }

  feature accept-tolerance {
    description
      "To specify the tolerance or acceptance limit.";
  }

  feature independent-send-accept-lifetime {
    description
      "Support for independent send and accept key lifetimes.";
  }

  feature crypto-hmac-sha-1-12 {
    description
      "Support for TCP HMAC-SHA-1 12 byte digest hack.";
  }

  grouping lifetime {
    description
      "Key lifetime specification.";
    choice lifetime {
      default always;
      description
        "Options for specifying key accept or send lifetimes";
      case always {
        leaf always {
          type empty;
            description
              "Indicates key lifetime is always valid.";
        }
      }
      case start-end-time {
        leaf start-date-time {
          type yang:date-and-time;
          description "Start time.";
        }
        choice end-time {
          default infinite;
          description
            "End-time setting.";
          case infinite {
        leaf no-end-time {
              type empty;
            description
              "Indicates key lifetime end-time in infinite.";
            }
          }
          case duration {
            leaf duration {
              type uint32 {
                range "1..2147483646";
              }
              units seconds;
              description "Key lifetime duration, in seconds";
            }
          }
          case end-date-time {
            leaf end-date-time {
              type yang:date-and-time;
              description "End time.";
            }
          }
        }
      }
    }
  }

 grouping crypto-algorithm-types {
     description "Cryptographic algorithm types.";
   choice algorithm {
     description
         "Options for crytographic algorithm specification.";
     case hmac-sha-1-12 {
         if-feature crypto-hmac-sha-1-12;
         leaf hmac-sha1-12 {
             type empty;
             description "The HMAC-SHA1-12 algorithm.";
         }
     }
     case md5 {
         leaf md5 {
             type empty;
             description "The MD5 algorithm.";
         }
     }
     case sha-1 {
         leaf sha-1 {
             type empty;
             description "The SHA-1 algorithm.";
         }
     }
     case hmac-sha-1 {
         leaf hmac-sha-1 {
             type empty;
             description "HMAC-SHA-1 authentication algorithm.";
         }
     }
     case hmac-sha-256 {
         leaf hmac-sha-256 {
             type empty;
             description "HMAC-SHA-256 authentication algorithm.";
         }
     }
     case hmac-sha-384 {
         leaf hmac-sha-384 {
             type empty;
             description "HMAC-SHA-384 authentication algorithm.";
         }
     }
     case hmac-sha-512 {
         leaf hmac-sha-512 {
             type empty;
             description "HMAC-SHA-512 authentication algorithm.";
         }
     }
   }
 }

  grouping key-chain {
    description
      "key-chain specification grouping.";
    leaf name {
      type string;
      description "Name of the key-chain.";
    }

    leaf name-state {
      type string;
      config false;
      description "Configured name of the key-chain.";
    }

    container accept-tolerance {
      if-feature accept-tolerance;
      description
        "Tolerance for key lifetime acceptance (seconds).";
      leaf duration {
        type uint32;
        units seconds;
        default "0";
        description
          "Tolerance range, in seconds.";
      }
    }

    container accept-tolerance-state {
      config false;
      description
        "Configured tolerance for key lifetime
         acceptance (seconds).";
      leaf duration {
        type uint32;
        description
          "Configured tolerance range, in seconds.";
      }
    }

    list key-chain-entry {
      key "key-id";
      description "One key.";
      leaf key-id {
        type uint64;
        description "Key id.";
      }
      leaf key-id-state {
        type uint64;
        config false;
        description "Configurd key id.";
      }
      container key-string {
        description "The key string.";
        choice key-string-style {
           description
             "Key string styles";
           case keystring {
             leaf keystring {
               type string;
               description "Key string in ASCII format.";
             }
           }
           case hexadecimal {
             if-feature hex-key-string;
             leaf hexadecimal-string {
               type yang:hex-string;
               description
                 "Key in hexadecimal string format.";
             }
           }
         }
      }
      container lifetime {
        description "Specify a key's lifetime.";
        choice lifetime {
          description
            "Options for specification of send and accept
             lifetimes.";
          case send-and-accept-lifetime {
            description
              "Send and accept key have the same lifetime.";
            container send-accept-lifetime {
              uses lifetime;
              description
                "Single lifetime specification for both send and
                 accept lifetimes.";
            }
          }
          case independent-send-accept-lifetime {
            if-feature independent-send-accept-lifetime;
            description
              "Independent send and accept key lifetimes.";
            container send-lifetime {
              uses lifetime;
              description
                "Separate lifetime specification for send
                 lifetime.";
            }
            container accept-lifetime {
              uses lifetime;
              description
                "Separate lifetime specification for accept
                 lifetime.";
            }
          }
        }
      }
      container lifetime-state {
        config false;
        description "Configured key's lifetime.";
        container send-lifetime {
          uses lifetime;
          description
            "Configured send-lifetime.";
        }
        leaf send-valid {
          type boolean;
          description
            "Status of send-lifetime.";
        }
        container accept-lifetime {
          uses lifetime;
          description
            "Configured accept-lifetime.";
        }
        leaf accept-valid {
          type boolean;
          description
            "Status of accept-lifetime.";
        }
      }
      container crypto-algorithm {
        uses crypto-algorithm-types;
        description "Cryptographic algorithm associated with key.";
      }
      container crypto-algorithm-state {
        config false;
        uses crypto-algorithm-types;
        description "Configured cryptographic algorithm.";
      }
    }
  }

  container key-chains {
    list key-chain-list {
      key "name";
      description
        "List of key-chains.";
      uses key-chain;
    }
    description "All configured key-chains for the device.";
  }
}
