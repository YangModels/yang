module ietf-vtn-ntw {
  yang-version 1.1;
  namespace "urn:ietf:params:xml:ns:yang:ietf-vtn-ntw";
  prefix vtn-ntw;

  import ietf-network {
    prefix nw;
    reference
      "RFC 8345: A YANG Data Model for Network Topologies";
  }
  import ietf-network-topology {
    prefix nt;
    reference
      "RFC 8345: A YANG Data Model for Network Topologies";
  }
  import ietf-routing-types {
    prefix rt-types;
    reference
      "RFC 8294: Common YANG Data Types for the Routing Area";
  }
  import ietf-te-types {
    prefix te-types;
    reference
      "RFC 8776: Traffic Engineering Common YANG Types";
  }
  import ietf-te-packet-types {
    prefix te-packet-types;
    reference
      "RFC 8776: Traffic Engineering Common YANG Types";
  }

  organization
    "IETF TEAS Working Group";
  contact
    "
     WG Web: <http://tools.ietf.org/wg/teas/>
     WG List:<mailto:teas@ietf.org>

     Editor: Bo Wu <lana.wubo@huawei.com>
           : Dhruv Dhody <dhruv.ietf@gmail.com>";
  description
    "This YANG module defines a network data module for
     VTN(Virtual Transport Network)";

  revision 2021-06-04 {
    description
      "This is the initial version of VTN network yang module";
    reference
      "RFC XXX: YANG Data module for VTN network";
  }

  identity interface-partition-capability {
    description
      "Base identity for interface partition capability.";
  }

  identity flexe-partition {
    base interface-partition-capability;
    description
      "Identity for FlexE partition capability.";
  }

  identity queue-partition {
    base interface-partition-capability;
    description
      "Identity for queue partition capability.";
  }

  identity vtn-data-plane-type {
    description
      "Base identity for VTN data plane type.";
  }

  identity vtn-data-plane-vtn-ipv6 {
    base vtn-data-plane-type;
    description
      "Identity for VTN based packet forwarding of IPv6.";
  }

  identity vtn-data-plane-vtn-mpls {
    base vtn-data-plane-type;
    description
      "Identity for VTN based packet forwarding of MPLS.";
  }

  identity vtn-data-plane-sr-mpls {
    base vtn-data-plane-type;
    description
      "Identity for SR MPLS forwarding mechanism.";
  }

  identity vtn-data-plane-srv6 {
    base vtn-data-plane-type;
    description
      "Identity for SRv6 forwarding mechanism.";
  }

  /*
   * Groupings
   */

  grouping traffic-steering-policy {
    description
      "Configuration of the traffic mapping policy.";
    container steering-policy {
      description
        "Policy set that matches to a VTN.";
      leaf vtn-color-id {
        type uint32;
        description
          "VTN color ID for VTN traffic steering";
      }
    }
  }

  grouping vtn-bandwidth-reservation {
    description
      "Grouping for VTN bandwidth reservation.";
    container bandwidth-reservation {
      description
        "Container for VTN bandwidth reservation.";
      choice bandwidth-type {
        description
          "Choice of bandwidth reservation type.";
        case bandwidth-value {
          leaf bandwidth-value {
            type uint64;
            units "bps";
            description
              "Bandwidth allocation for the VTN as absolute value.";
          }
        }
        case bandwidth-percentage {
          leaf bandwidth-percent {
            type rt-types:percentage;
            description
              "Bandwidth allocation for the VTN as a percentage of a link.";
          }
        }
      }
    }
  }

  grouping vtn-control-plane-attributes {
    description
      "VTN topology control plane attributes.";
    container control-plane {
      description
        "vtn control plane mechanism.";
      choice vtn-cp-type {
        description
          "Choice of vtn control plane.";
        case flex-algo {
          container flex-algo {
            description
              "A VTN could use flex-algo as a control plane
               mechanism.";
            leaf flex-algo-id {
              type uint32;
              description
                "flex-algo-id for VTN";
            }
          }
        }
        case multi-topology {
          description
            "A VTN could use MT (Multi-Topology) as a control
             plane mechanism.";
          leaf multi-topology-id {
            type uint32;
            description
              "MT-id for VTN";
          }
        }
      }
    }
  }

  grouping vtn-data-plane-attributes {
    description
      "Grouping for VTN topology data plane attributes.";
    container data-plane {
      description
        "VTN data plane mechanism.";
      leaf vtn-global-identifier {
        type uint32;
        description
          "The global VTN identifier for multi-domain is specified.";
      }
      container domain-data-plane {
        description
          "VTN data plane mechanism per network domain.";
        leaf data-plane-type {
          type identityref {
            base vtn-data-plane-type;
          }
          description
            "Specifies the data plane forwarding mechanism of the VTN.
             The mechanism consists of VTN based Packet Forwarding or
             existing Segment Routing with MPLS data plane or IPv6 data
             plane.";
        }
        leaf vtn-domain-identifier {
          type uint32;
          description
            "The domain VTN identifier is specified for
             VTN based Packet Forwarding of a network domain.
             The forwarding plane could be with
             the MPLS Data Plane or IPv6";
          reference
            "draft-li-mpls-enhanced-vpn-vtn-id?
             Carrying Virtual Transport Network identifier
             in MPLS Packet
             draft-dong-6man-enhanced-vpn-vtn-id
             Carrying Virtual Transport Network Identifier
             in IPv6 Extension Header";
        }
      }
    }
  }

  grouping vtn-topology-attributes {
    description
      "VTN topology scope attributes.";
    container vtn {
      description
        "Containing VTN topology attributes.";
      leaf vtn-id {
        type uint32;
        description
          "VTN identifier";
      }
      leaf vtn-name {
        type string;
        description
          "VTN Name";
      }
      uses vtn-bandwidth-reservation;
      uses vtn-control-plane-attributes;
      uses vtn-data-plane-attributes;
      uses traffic-steering-policy;
    }
    // vtn
  }

  // vtn-node-attributes

  grouping vtn-node-attributes {
    description
      "VTN node scope attributes.";
    container vtn {
      description
        "Containing VTN attributes.";
    }
  }

  // vtn-node-attributes

  grouping vtn-link-attributes {
    description
      "VTN link scope attributes";
    container vtn {
      description
        "Containing VTN attributes.";
      leaf interface-partition-capability {
        type identityref {
          base interface-partition-capability;
        }
        description
          "Describes different resource partition type of a link.";
      }
      uses vtn-bandwidth-reservation;
    }
  }

  // vtn-statistics

  grouping statistics-per-vtn {
    description
      "Statistics attributes per VTN.";
  }

  // vtn-node-statistics

  grouping statistics-per-node {
    description
      "Statistics attributes per VTN node.";
  }

  // one-way-performance-metrics

  grouping one-way-performance-bandwidth {
    description
      "Grouping for one-way performance bandwidth .";
    leaf one-way-available-bandwidth {
      type rt-types:bandwidth-ieee-float32;
      units "bytes per second";
      default "0x0p0";
      description
        "Available bandwidth that is defined to be VTN link
         bandwidth minus bandwidth utilization.  For a
         bundled link, available bandwidth is defined to be the
         sum of the component link available bandwidths.";
    }
    leaf one-way-utilized-bandwidth {
      type rt-types:bandwidth-ieee-float32;
      units "bytes per second";
      default "0x0p0";
      description
        "Bandwidth utilization that represents the actual
         utilization of the link (i.e. as measured in the router).
         For a bundled link, bandwidth utilization is defined to
         be the sum of the component link bandwidth
         utilizations.";
    }
  }

  // vtn-link-statistics

  grouping vtn-statistics-per-link {
    description
      "Statistics attributes per VTN link.";
    container statistics {
      config false;
      description
        "Statistics for VTN link.";
      leaf admin-status {
        type te-types:te-admin-status;
        description
          "The administrative state of the link.";
      }
      leaf oper-status {
        type te-types:te-oper-status;
        description
          "The current operational state of the link.";
      }
      uses one-way-performance-bandwidth;
      uses te-packet-types:one-way-performance-metrics-packet;
    }
  }

  augment "/nw:networks/nw:network/nw:network-types" {
    description
      "Defines the VTN topology type.";
    container vtn {
      presence "Indicates VTN topology";
      description
        "Its presence identifies the VTN type.";
    }
  }

  augment "/nw:networks/nw:network" {
    when 'nw:network-types/vtn-ntw:vtn' {
      description
        "Augment only for VTN topology.";
    }
    description
      "Augment VTN configuration and state.";
    uses vtn-topology-attributes;
  }

  augment "/nw:networks/nw:network/nw:node" {
    when '../nw:network-types/vtn-ntw:vtn' {
      description
        "Augment only for VTN topology.";
    }
    description
      "Augment node configuration and state.";
    uses vtn-node-attributes;
  }

  augment "/nw:networks/nw:network/nt:link" {
    when '../nw:network-types/vtn-ntw:vtn' {
      description
        "Augment only for VTN topology.";
    }
    description
      "Augment link configuration and state.";
    uses vtn-link-attributes;
    uses vtn-statistics-per-link;
  }
}
