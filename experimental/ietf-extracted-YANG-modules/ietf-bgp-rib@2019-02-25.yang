module ietf-bgp-rib {
  yang-version "1.1";
  namespace "urn:ietf:params:xml:ns:yang:ietf-bgp-rib";
  prefix "br";

  /*
   * Import and Include
   */
  import ietf-routing {
    prefix "rt";
    reference
      "RFC 8349: YANG Route Management.";
  }

  import ietf-bgp-types {
    prefix "bt";
    reference
      "RFC XXXX: BGP YANG Model for Service Provider Networks.";
  }

  include ietf-bgp-rib-tables;
  include ietf-bgp-rib-shared-attributes;

  // groupings of attributes in three categories:
  //  - shared across multiple routes
  //  - common to LOC-RIB and Adj-RIB, but not shared across routes
  //  - specific to LOC-RIB or Adj-RIB
  include ietf-bgp-rib-attributes;

  // groupings of annotations for each route or table
  include ietf-bgp-rib-table-attributes;

  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "Defines a data model for representing BGP routing table (RIB)
     contents.  The model supports 5 logical RIBs per address family:

     loc-rib: This is the main BGP routing table for the local routing
     instance, containing best-path selections for each prefix. The
     loc-rib table may contain multiple routes for a given prefix,
     with an attribute to indicate which was selected as the best
     path.  Note that multiple paths may be used or advertised even if
     only one path is marked as best, e.g., when using BGP
     add-paths.  An implementation may choose to mark multiple
     paths in the RIB as best path by setting the flag to true for
     multiple entries.

     adj-rib-in-pre: This is a per-neighbor table containing the NLRI
     updates received from the neighbor before any local input policy
     rules or filters have been applied.  This can be considered the
     'raw' updates from a given neighbor.

     adj-rib-in-post: This is a per-neighbor table containing the
     routes received from the neighbor that are eligible for
     best-path selection after local input policy rules have been
     applied.

     adj-rib-out-pre: This is a per-neighbor table containing routes
     eligible for sending (advertising) to the neighbor before output
     policy rules have been applied.

     adj-rib-out-post: This is a per-neighbor table containing routes
     eligible for sending (advertising) to the neighbor after output
     policy rules have been applied.";

  revision "2019-02-25" {
    description
      "Initial Version";
    reference
      "RFC XXXX, BGP YANG Model for Service Provider Network.";
  }

  augment "/rt:routing/rt:ribs" {
    when "derived-from-or-self(../rt:control-plane-protocols/" +
      "rt:control-plane-protocol/rt:type, 'bgp')" {
      description
        "This augmentation is only valid for routes whose control
         plane protocol is BGP.";
    }
    description
      "Support for RIBS.";

    container rib {
      config false;
      description
        "Top level container for BGP RIB";

      uses attribute-sets;
      uses community-sets;
      uses ext-community-sets;

      container afi-safis {
        config false;
        description
          "Enclosing container for address family list";

        list afi-safi {
          key "afi-safi-name";
          description
            "List of afi-safi types.";

          leaf afi-safi-name {
            type identityref {
              base bt:afi-safi-type;
            }
            description "AFI,SAFI name.";
          }

          container ipv4-unicast {
            when "../afi-safi-name = 'bt:ipv4-unicast'" {
              description
                "Include this container for IPv4 unicast RIB";
            }
            description
              "Routing tables for IPv4 unicast -- active when the
             afi-safi name is ipv4-unicast";

            uses ipv4-loc-rib;
            uses ipv4-adj-rib;
          }

          container ipv6-unicast {
            when "../afi-safi-name = 'bt:ipv6-unicast'" {
              description
                "Include this container for IPv6 unicast RIB";
            }
            description
              "Routing tables for IPv6 unicast -- active when the
             afi-safi name is ipv6-unicast";

            uses ipv6-loc-rib;
            uses ipv6-adj-rib;
          }

          container ipv4-srte-policy {
            when "../afi-safi-name = 'bt:srte-policy-ipv4'" {
              description
                "Include this container only for the IPv4 AFI, SR-TE
               Policy SAFI.";
            }
            description
              "Routing tables for the IPv4 Unicast, SR-TE Policy
             SAFI.";

            uses ipvX-srte-policy-locrib;
            uses ipvX-srte-policy-adjrib;
          }

          container ipv6-srte-policy {
            when "../afi-safi-name = 'bt:srte-policy-ipv6'" {
              description
                "Include this container only for the IPv6 AFI,
               SR-TE Policy SAFI.";
            }
            description
              "Routing tables for the IPv6 Unicast, SR-TE Policy
             SAFI.";

            uses ipvX-srte-policy-locrib;
            uses ipvX-srte-policy-adjrib;
          }
        }
      }
    }
  }
}
