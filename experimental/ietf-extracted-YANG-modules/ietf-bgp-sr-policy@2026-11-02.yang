module ietf-bgp-sr-policy {
  yang-version 1.1;
  namespace "urn:ietf:params:xml:ns:yang:ietf-bgp-sr-policy";
  prefix bsp;

  /*
   * Import and Include
   */

  import ietf-routing {
    prefix rt;
    reference
      "RFC 8349: A YANG Data Model for Routing Management
                 (NMDA Version)";
  }
  import ietf-inet-types {
    prefix inet;
    reference
      "RFC 9911: Common YANG Data Types";
  }
  import ietf-yang-semver {
    prefix ysv;
    reference
      "RFC ZZZZ: YANG Semantic Versioning";
  }
  import ietf-bgp {
    prefix bgp;
    reference
      "RFC XXXX: YANG Model for Border Gateway Protocol (BGP-4)";
  }
  import iana-bgp-afi-safi-types {
    prefix bast;
    reference
      "RFC XXXX: YANG Model for Border Gateway Protocol (BGP-4)";
  }

  organization
    "IETF Inter-Domain Routing (IDR) Working Group";
  contact
    "WG Web:   <https://datatracker.ietf.org/wg/idr/>
     WG List:  IDR <mailto:idr@ietf.org>

     Author:   Changwang Lin
               <mailto:linchangwang.04414@h3c.com>";

  description
    "This module contains YANG definitions for the BGP Segment
     Routing (SR) Policy address families.  It extends the BGP
     YANG model defined in RFC XXXX with the IPv4 SR Policy
     (AFI, SAFI = 1, 73) and IPv6 SR Policy (AFI, SAFI = 2, 73)
     address families, per RFC 9830, and adds the corresponding
     RIB contents and the decoded SR Policy candidate path
     information.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC YYYY; see the
     RFC itself for full legal notices.

     All revisions of IETF and IANA published modules can be found
     at the YANG Parameters registry group
     (https://www.iana.org/assignments/yang-parameters).";

  revision 2026-11-02 {
    description
      "Initial Version";
    ysv:version 0.0.1;
    reference
      "RFC YYYY: YANG Model for BGP Segment Routing Policy";
  }

  /*
   * Features.
   */

  feature sr-mpls {
    description
      "The implementation supports SR-MPLS Binding SIDs and
       SR-MPLS label segments of an SR Policy candidate path.";
    reference
      "RFC 8660: Segment Routing with the MPLS Data Plane";
  }

  feature srv6 {
    description
      "The implementation supports SRv6 Binding SIDs and SRv6 SID
       segments of an SR Policy candidate path.";
    reference
      "RFC 8986: Segment Routing over IPv6 (SRv6) Network
                 Programming";
  }

  /*
   * Identities.
   */

  identity ipv4-sr-policy {
    base bast:afi-safi-type;
    description
      "IPv4 SR Policy (AFI, SAFI = 1, 73).";
    reference
      "RFC 9830: Advertising Segment Routing Policies in BGP";
  }

  identity ipv6-sr-policy {
    base bast:afi-safi-type;
    description
      "IPv6 SR Policy (AFI, SAFI = 2, 73).";
    reference
      "RFC 9830: Advertising Segment Routing Policies in BGP";
  }

  /*
   * Typedefs.
   */

  typedef sr-policy-enlp {
    type enumeration {
      enum push-ipv4-null {
        value 1;
        description
          "Push an IPv4 Explicit NULL label on an unlabeled IPv4
           packet but do not push an IPv6 Explicit NULL label on
           an unlabeled IPv6 packet.";
      }
      enum push-ipv6-null {
        value 2;
        description
          "Push an IPv6 Explicit NULL label on an unlabeled IPv6
           packet but do not push an IPv4 Explicit NULL label on
           an unlabeled IPv4 packet.";
      }
      enum push-both-null {
        value 3;
        description
          "Push an IPv4 Explicit NULL label on an unlabeled IPv4
           packet and push an IPv6 Explicit NULL label on an
           unlabeled IPv6 packet.";
      }
      enum no-push {
        value 4;
        description
          "Do not push an Explicit NULL label.";
      }
    }
    description
      "Explicit NULL Label Policy (ENLP) for unlabeled IP packets
       that are steered into an SR Policy for the MPLS data
       plane.  The value of the enumeration corresponds to the
       ENLP value defined in RFC 9830.";
    reference
      "RFC 9830: Advertising Segment Routing Policies in BGP,
                 Section 2.4.5";
  }

  /*
   * Groupings.
   */

  grouping srv6-endpoint-behavior-sid-structure {
    description
      "SRv6 Endpoint Behavior and SID Structure encoding, as
       defined in Section 2.4.4.2.4 of RFC 9830.  The presence of
       these leaves corresponds to the B-Flag of the SR Policy
       Segment Flags or of the SR Policy SRv6 Binding SID Flags.";
    leaf endpoint-behavior {
      type uint16;
      description
        "SRv6 Endpoint Behavior code point for this SRv6 SID as
         defined in Section 10.2 of RFC 8986.  The value 65535
         (Opaque) leaves the choice of the SRv6 Endpoint Behavior
         to the headend.";
      reference
        "RFC 8986: Segment Routing over IPv6 (SRv6) Network
                   Programming, Section 10.2";
    }
    leaf locator-block-length {
      type uint8;
      units "bits";
      description
        "SRv6 SID Locator Block length in bits.";
      reference
        "RFC 8986: Segment Routing over IPv6 (SRv6) Network
                   Programming, Section 3.2";
    }
    leaf locator-node-length {
      type uint8;
      units "bits";
      description
        "SRv6 SID Locator Node length in bits.";
      reference
        "RFC 8986: Segment Routing over IPv6 (SRv6) Network
                   Programming, Section 3.2";
    }
    leaf function-length {
      type uint8;
      units "bits";
      description
        "SRv6 SID Function length in bits.";
      reference
        "RFC 8986: Segment Routing over IPv6 (SRv6) Network
                   Programming, Section 3.2";
    }
    leaf argument-length {
      type uint8;
      units "bits";
      description
        "SRv6 SID Arguments length in bits.  The total of the
         locator block, locator node, function, and argument
         lengths must be less than or equal to 128.";
      reference
        "RFC 8986: Segment Routing over IPv6 (SRv6) Network
                   Programming, Section 3.2";
    }
  }

  grouping sr-policy-segment {
    description
      "A single segment of a segment list, i.e., a single element
       of the explicit path of an SR Policy candidate path, as
       encoded in a Segment sub-TLV of the Segment List sub-TLV
       (Section 2.4.4.2 of RFC 9830).  The segment types defined
       in RFC 9830 (Type A: SR-MPLS label, Type B: SRv6 SID) are
       modeled; the additional segment types specified in
       RFC 9831 are left to future revisions of this document.
       A mix of SR-MPLS and SRv6 segments makes the segment list
       invalid, per Section 5.1 of RFC 9256.";
    leaf index {
      type uint32;
      description
        "Position of the segment in the explicit path.  The
         segments are reported in the order in which they
         are encoded in the Segment List sub-TLV, starting with
         index 1; this is the order in which the segments are
         pushed on the packets steered into the SR Policy.";
    }
    leaf sid-verification {
      type boolean;
      description
        "When true (V-Flag of the SR Policy Segment Flags), the
         originator requested SID verification of this segment,
         which is used by the SRPM as described in Section 5.1
         of RFC 9256.";
      reference
        "RFC 9830: Advertising Segment Routing Policies in BGP,
                   Section 2.4.4.2.3";
    }
    choice segment-type {
      description
        "The segment type.  Only the Segment Type A (SR-MPLS
         label) and Type B (SRv6 SID) sub-TLVs of RFC 9830 are
         modeled in this revision.";
      case type-a {
        if-feature "sr-mpls";
        description
          "SR-MPLS label segment (Segment Type A, Section
           2.4.4.2.1 of RFC 9830).";
        leaf mpls-label {
          type uint32 {
            range "16..1048575";
          }
          description
            "The 20-bit label value.  The reserved MPLS label
             values (0-15) are not valid values.";
          reference
            "RFC 3032: MPLS Label Stack Encoding,
             RFC 5462: Multiprotocol Label Switching (MPLS)
                       Label Stack Entry: 'EXP' Field Renamed to
                       'Traffic Class' Field";
        }
        leaf traffic-class {
          type uint8 {
            range "0..7";
          }
          description
            "Traffic Class (TC) field of the label.  The value
             0 indicates that the originator wants the receiver
             to choose the TC value.";
        }
        leaf ttl {
          type uint8;
          description
            "TTL field of the label.  The value 255 indicates
             that the originator wants the receiver to choose
             the TTL value.";
        }
      }
      case type-b {
        if-feature "srv6";
        description
          "SRv6 SID segment (Segment Type B, Section 2.4.4.2.2
           of RFC 9830).";
        leaf srv6-sid {
          type inet:ipv6-address;
          description
            "The SRv6 SID of the segment.";
        }
        uses srv6-endpoint-behavior-sid-structure;
      }
    }
  }

  grouping sr-policy-binding-sid {
    description
      "Binding SID information of an SR Policy candidate path, as
       encoded in the Binding SID sub-TLV (Section 2.4.2 of
       RFC 9830).";
    leaf specified-bsid-only {
      type boolean;
      description
        "When true (S-Flag), encodes the 'Specified-BSID-Only'
         behavior: the SR Policy is not instantiated unless the
         specified BSID is available.";
      reference
        "RFC 9256: Segment Routing Policy Architecture,
                   Section 6.2.3.";
    }
    leaf drop-upon-invalid {
      type boolean;
      description
        "When true (I-Flag), encodes the 'Drop-Upon-Invalid'
         behavior: the SR Policy is to drop traffic steered over
         it when no valid candidate path is available, per
         Section 8.2 of RFC 9256.";
      reference
        "RFC 9256: Segment Routing Policy Architecture,
                   Section 8.2.";
    }
    choice bsid {
      description
        "The Binding SID value.  When no BSID is present (sub-TLV
         length 2), the 'none' case is selected.";
      case none {
        leaf none {
          type empty;
          description
            "No BSID is present.";
        }
      }
      case mpls {
        if-feature "sr-mpls";
        leaf mpls-label {
          type uint32 {
            range "16..1048575";
          }
          description
            "SR-MPLS Binding SID label value.  The reserved
             MPLS label values (0-15) are not valid values.  The
             TC, S, and TTL bits of the label encoding are
             reserved and are not modeled.";
        }
      }
      case srv6 {
        if-feature "srv6";
        leaf srv6-sid {
          type inet:ipv6-address;
          description
            "SRv6 Binding SID.  The support for the use of the
             Binding SID sub-TLV for the signaling of an SRv6
             BSID is retained primarily for backward
             compatibility; it is recommended to signal an SRv6
             BSID using the SRv6 Binding SID sub-TLV instead
             (Section 2.4.2 of RFC 9830).";
        }
      }
    }
  }

  grouping sr-policy-srv6-binding-sid {
    description
      "An entry of the SRv6 Binding SID sub-TLVs (Section 2.4.3 of
       RFC 9830).  More than one SRv6 Binding SID sub-TLV may be
       signaled in the same SR Policy encoding to indicate one or
       more SRv6 SIDs, each with potentially different SRv6
       Endpoint Behaviors to be instantiated.";
    leaf sid {
      type inet:ipv6-address;
      description
        "The SRv6 Binding SID.  The unspecified address (::) may
         be used when the originator wants to indicate the
         desired SRv6 Endpoint Behavior, SID Structure, or flags
         without specifying the BSID.";
    }
    leaf specified-bsid-only {
      type boolean;
      description
        "When true (S-Flag), encodes the 'Specified-BSID-Only'
         behavior, per Section 6.2.3 of RFC 9256.";
    }
    leaf drop-upon-invalid {
      type boolean;
      description
        "When true (I-Flag), encodes the 'Drop-Upon-Invalid'
         behavior, per Section 8.2 of RFC 9256.";
    }
    uses srv6-endpoint-behavior-sid-structure;
  }

  grouping sr-policy-segment-lists {
    description
      "Segment List sub-TLVs of an SR Policy candidate path
       (Section 2.4.4 of RFC 9830).  Each entry encodes a single
       explicit path towards the Endpoint as described in
       Section 5.1 of RFC 9256.  The ordering of Segment List
       sub-TLVs does not matter; the 'index' is an
       implementation-assigned identifier.";
    container segment-lists {
      description
        "Enclosing container for the list of segment lists of the
         candidate path.";
      list segment-list {
        key "index";
        description
          "A single explicit path towards the Endpoint,
           per Section 5.1 of RFC 9256.";
        leaf index {
          type uint32;
          description
            "Implementation-assigned identifier of this segment
             list within the candidate path.";
        }
        container weight {
          description
            "Weight of the segment list, as encoded in the Weight
             sub-TLV (Section 2.4.4.1 of RFC 9830).  This
             container is absent when no Weight sub-TLV was
             received; the weight of a segment list without a
             Weight sub-TLV is then a matter of local policy.";
          leaf value {
            type uint32 {
              range "1..4294967295";
            }
            description
              "Weight associated with the segment list, used for
               load balancing across the segment lists of the SR
               Policy as described in Section 2.11 of RFC 9256.
               A weight value of zero is invalid.";
          }
        }
        container segments {
          description
            "Enclosing container for the segments of the explicit
             path.";
          list segment {
            key "index";
            uses sr-policy-segment;
            description
              "Ordered list of the segments of the explicit path.
               A mix of SR-MPLS and SRv6 segments makes the
               segment list invalid, per Section 5.1 of
               RFC 9256.";
          }
        }
      }
    }
  }

  grouping sr-policy-candidate-path {
    description
      "Decoded SR Policy candidate path information, obtained
       from the SR Policy Tunnel Type (code point 15) of the
       Tunnel Encapsulation Attribute (Sections 2.2 and 2.4 of
       RFC 9830).  All sub-TLVs are optional; a leaf or container
       that is absent indicates that the corresponding sub-TLV
       was not present in the SR Policy encoding.  Where more
       than one instance of a single-instance sub-TLV was
       received, only the first instance is reported, per
       Section 2.4 of RFC 9830.";
    container candidate-path {
      config false;
      description
        "SR Policy candidate path information.";
      leaf preference {
        type uint32;
        description
          "Preference of the SR Policy candidate path, as encoded
           in the Preference sub-TLV (Section 2.4.1 of
           RFC 9830).  It is used by the SRPM for the selection
           of the active candidate path as described in
           Section 2.7 of RFC 9256.";
      }
      leaf priority {
        type uint8;
        description
          "Priority of the SR Policy, as encoded in the Priority
           sub-TLV (Section 2.4.6 of RFC 9830).  It indicates the
           order in which the SR policies are recomputed upon
           topological change, as described in Section 2.12 of
           RFC 9256.";
      }
      leaf policy-name {
        type string;
        description
          "Symbolic name of the SR Policy, as encoded in the SR
           Policy Name sub-TLV (Section 2.4.8 of RFC 9830).";
      }
      leaf candidate-path-name {
        type string;
        description
          "Symbolic name of the SR Policy candidate path, as
           encoded in the SR Policy Candidate Path Name sub-TLV
           (Section 2.4.7 of RFC 9830).";
      }
      leaf enlp {
        type sr-policy-enlp;
        description
          "Explicit NULL Label Policy of the SR Policy, as
           encoded in the ENLP sub-TLV (Section 2.4.5 of
           RFC 9830).  This leaf is absent when no ENLP sub-TLV
           was received; the decision of whether to push an
           Explicit NULL label on unlabeled IP packets steered
           into the SR Policy is then a matter of local
           configuration.";
      }
      container binding-sid {
        description
          "Binding SID of the SR Policy candidate path, as
           encoded in the Binding SID sub-TLV (Section 2.4.2 of
           RFC 9830).  This container is absent when no Binding
           SID sub-TLV was received.";
        uses sr-policy-binding-sid;
      }
      container srv6-binding-sids {
        if-feature "srv6";
        description
          "Enclosing container for the SRv6 Binding SID sub-TLVs
           (Section 2.4.3 of RFC 9830).  More than one SRv6
           Binding SID sub-TLV may be signaled in the same SR
           Policy encoding.";
        list srv6-binding-sid {
          key "sid";
          uses sr-policy-srv6-binding-sid;
          description
            "An SRv6 Binding SID, together with the SRv6 Endpoint
             Behavior and SID Structure to be instantiated on the
             headend node.  The presence of the SRv6 Endpoint
             Behavior and SID Structure leaves corresponds to the
             B-Flag of the SR Policy SRv6 Binding SID Flags.";
        }
      }
      uses sr-policy-segment-lists;
    }
  }

  grouping sr-policy-nlri-keys {
    description
      "Key leaves identifying an SR Policy NLRI, per Section 2.1
       of RFC 9830.  The SR Policy NLRI is the tuple
       <Distinguisher, Color, Endpoint>.";
    leaf distinguisher {
      type uint32;
      description
        "The Distinguisher field of the SR Policy NLRI.  It has no
         semantic value; it is used by the SR Policy originator to
         differentiate multiple candidate paths of the same SR
         Policy, and candidate paths meant for different headends
         but having the same Color and Endpoint.";
    }
    leaf color {
      type uint32 {
        range "1..4294967295";
      }
      description
        "The Color of the SR Policy, an unsigned non-zero integer
         value.  The Color is used to match the Color of the
         destination prefixes to steer traffic into the SR Policy
         as specified in Section 8 of RFC 9256.";
    }
    leaf endpoint {
      type inet:ip-address;
      description
        "The Endpoint of the SR Policy, an IPv4 (4-octet) or IPv6
         (16-octet) address according to the AFI of the NLRI.  It
         identifies the Endpoint of the SR Policy, which may
         represent a single node or a set of nodes (e.g., an
         anycast address).  The unspecified address (0.0.0.0 for
         IPv4, :: for IPv6) is the null Endpoint.";
    }
  }

  grouping sr-policy-adj-rib {
    description
      "Common structural grouping for each SR Policy Adj-RIB
       table.";
    container routes {
      config false;
      description
        "Enclosing container for the list of SR Policy routes in
         the routing table.";
      list route {
        key "distinguisher color endpoint path-id";
        description
          "List of SR Policy routes in the table, keyed by the
           SR Policy NLRI and path-id to distinguish multiple
           routes for the same NLRI (e.g., when BGP add-paths is
           enabled).";
        uses sr-policy-nlri-keys;
        uses bgp:bgp-adj-rib-attr-state;
        uses bgp:bgp-adj-rib-common-attr-refs;
        uses bgp:bgp-common-route-annotations-state;
        uses bgp:bgp-unknown-attr-top;
        uses bgp:rib-ext-route-annotations;
        uses sr-policy-candidate-path;
      }
    }
  }

  grouping sr-policy-adj-rib-in-post {
    description
      "Common structural grouping for the SR Policy Adj-RIB-In
       post-policy table.";
    container routes {
      config false;
      description
        "Enclosing container for the list of SR Policy routes in
         the routing table.";
      list route {
        key "distinguisher color endpoint path-id";
        description
          "List of SR Policy routes in the table, keyed by the
           SR Policy NLRI and path-id to distinguish multiple
           routes for the same NLRI (e.g., when BGP add-paths is
           enabled).";
        uses sr-policy-nlri-keys;
        uses bgp:bgp-adj-rib-attr-state;
        uses bgp:bgp-adj-rib-common-attr-refs;
        uses bgp:bgp-common-route-annotations-state;
        uses bgp:bgp-adj-rib-in-post-route-annotations-state;
        uses bgp:bgp-unknown-attr-top;
        uses bgp:rib-ext-route-annotations;
        uses sr-policy-candidate-path;
      }
    }
  }

  /*
   * Data nodes.
   */

  augment "/rt:routing/rt:control-plane-protocols/"
        + "rt:control-plane-protocol/bgp:bgp/bgp:global/"
        + "bgp:afi-safis/bgp:afi-safi" {
    when "derived-from-or-self(bgp:name, 'bsp:ipv4-sr-policy') or "
       + "derived-from-or-self(bgp:name, 'bsp:ipv6-sr-policy')" {
      description
        "This augmentation is valid for an SR Policy AFI/SAFI
         instance.";
    }
    description
      "BGP SR Policy specific configuration that applies to the
       global AFI/SAFI.";

    container sr-policy {
      description
        "SR Policy specific configuration for the AFI/SAFI.";
      uses bgp:mp-all-afi-safi-common;
      leaf propagate-to-ebgp {
        type boolean;
        default "false";
        description
          "When false (the default), received SR Policy NLRIs are
           not propagated to any EBGP neighbor, per Section 4.2.3
           of RFC 9830.  When true, valid SR Policy NLRIs may be
           propagated to EBGP neighbors, which is applicable when
           the SR domain comprises multiple ASes within a single
           service provider domain.";
        reference
          "RFC 9830: Advertising Segment Routing Policies in
                     BGP, Section 4.2.3.";
      }
      leaf ignore-unsupported-subtlvs {
        type boolean;
        default "false";
        description
          "When false (the default), an SR Policy update whose
           SR Policy tunnel type includes a sub-TLV that is
           unrecognized or unsupported is not considered usable,
           per Section 4.2.2 of RFC 9830.  When true, unsupported
           sub-TLVs are ignored, so that an update containing
           unrecognized or unsupported sub-TLVs may still be
           considered usable and passed to the SRPM.";
        reference
          "RFC 9830: Advertising Segment Routing Policies in
                     BGP, Section 4.2.2.";
      }
    }
  }

  augment "/rt:routing/rt:control-plane-protocols/"
        + "rt:control-plane-protocol/bgp:bgp/bgp:rib/"
        + "bgp:afi-safis/bgp:afi-safi" {
    when "derived-from-or-self(bgp:name, 'bsp:ipv4-sr-policy') or "
       + "derived-from-or-self(bgp:name, 'bsp:ipv6-sr-policy')" {
      description
        "This augmentation is valid for an SR Policy AFI/SAFI
         instance.";
    }
    description
      "BGP SR Policy RIB augmentation.";

    container sr-policy {
      config false;
      description
        "Container for the BGP SR Policy RIB.";
      container loc-rib {
        description
          "The SR Policy Loc-RIB: the set of SR Policy candidate
           paths selected by the BGP best-path selection
           algorithm and eligible to be passed to the SRPM.";
        container routes {
          config false;
          description
            "Enclosing container for the list of SR Policy
             routes.";
          list route {
            key "distinguisher color endpoint";
            description
              "List of SR Policy routes in the Loc-RIB, keyed by
               the <Distinguisher, Color, Endpoint> tuple of the
               SR Policy NLRI.";
            uses sr-policy-nlri-keys;
            leaf active {
              type boolean;
              description
                "Indicates whether the SR Policy candidate path
                 is usable (Section 4.2.2 of RFC 9830) and has
                 been passed to the SRPM for candidate path
                 selection as described in Section 2.9 of
                 RFC 9256.";
            }
            uses bgp:bgp-common-route-annotations-state;
            uses bgp:bgp-loc-rib-common-attr-refs;
            uses bgp:rib-ext-route-annotations;
            uses sr-policy-candidate-path;
          }
        }
      }

      container neighbors {
        description
          "Enclosing container for the neighbor list.";
        list neighbor {
          key "neighbor-address";
          description
            "List of SR Policy neighbors of the local BGP
             speaker.";
          leaf neighbor-address {
            type inet:ip-address;
            description
              "IP address of the BGP neighbor or peer.";
          }
          container adj-rib-in-pre {
            description
              "Per-neighbor table containing the SR Policy NLRI
               updates received from the neighbor before any
               local input policy rules have been applied.";
            uses sr-policy-adj-rib;
          }
          container adj-rib-in-post {
            description
              "Per-neighbor table containing the SR Policy paths
               received from the neighbor that are eligible for
               best-path selection after local input policy
               rules have been applied.";
            uses sr-policy-adj-rib-in-post;
          }
          container adj-rib-out-pre {
            description
              "Per-neighbor table containing SR Policy paths
               eligible for sending to the neighbor before
               output policy rules have been applied.";
            uses sr-policy-adj-rib;
          }
          container adj-rib-out-post {
            description
              "Per-neighbor table containing SR Policy paths
               eligible for sending to the neighbor after output
               policy rules have been applied.";
            uses sr-policy-adj-rib;
          }
        }
      }
    }
  }
}
