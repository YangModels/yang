module ietf-ose-path-svc {
  namespace "urn:ietf:params:xml:ns:yang:ietf-ose-path-svc";
  prefix ose-path-svc;

  import ietf-inet-types {
    prefix inet;
  }

  organization
    "IETF foo Working Group.";
  contact
    "WG List: foo@ietf.org
     Editor:  ";
  description
    "The YANG module defines a generic service configuration
     model for interworking between different SD-WAN domains.";

  revision 2019-06-10 {
    description
      "Initial revision";
    reference
      "A YANG Data Model for SD-WAN service configuration of
       path-svc.";
  }

  identity traffic-direction {
    description
      "Base identity for traffic direction.";
  }

  identity upstream {
    base traffic-direction;
    description
      "Identity for Site-to-WAN direction.";
  }

  identity downstream {
    base traffic-direction;
    description
      "Identity for WAN-to-Site direction.";
  }

  identity both {
    base traffic-direction;
    description
      "Identity for both WAN-to-Site direction
       and Site-to-WAN direction.";
  }

  identity protocol-type {
    description
      "Base identity for protocol field type.";
  }

  identity tcp {
    base protocol-type;
    description
      "TCP protocol type.";
  }

  identity udp {
    base protocol-type;
    description
      "UDP protocol type.";
  }

  identity icmp {
    base protocol-type;
    description
      "ICMP protocol type.";
  }

  identity icmp6 {
    base protocol-type;
    description
      "ICMPv6 protocol type.";
  }

  identity gre {
    base protocol-type;
    description
      "GRE protocol type.";
  }

  identity ipip {
    base protocol-type;
    description
      "IP-in-IP protocol type.";
  }

  identity hop-by-hop {
    base protocol-type;
    description
      "Hop-by-Hop IPv6 header type.";
  }

  identity routing {
    base protocol-type;
    description
      "Routing IPv6 header type.";
  }

  identity esp {
    base protocol-type;
    description
      "ESP header type.";
  }

  identity ah {
    base protocol-type;
    description
      "AH header type.";
  }

  container path-svc {
    description
      "Container for application aware path selection policy.";
    list path-policy {
      key "policy-name";
      description
        "List for path selection policy.";
      leaf policy-name {
        type string;
        description
          "Policy name.";
      }
      list flow-classification {
        key "class-name";
        description
          "List for traffic classification.";
        leaf class-name {
          type string;
          description
            "Traffic classification name.";
        }
        leaf dscp {
          type inet:dscp;
          description
            "DSCP value.";
        }
        leaf ipv4-src-prefix {
          type inet:ipv4-prefix;
          description
            "Match on IPv4 src address.";
        }
        leaf ipv6-src-prefix {
          type inet:ipv6-prefix;
          description
            "Match on IPv6 src address.";
        }
        leaf ipv4-dst-prefix {
          type inet:ipv4-prefix;
          description
            "Match on IPv4 dst address.";
        }
        leaf ipv6-dst-prefix {
          type inet:ipv6-prefix;
          description
            "Match on IPv6 dst address.";
        }
        leaf l4-src-port {
          type inet:port-number;
          must 'current() < ../l4-src-port-range/lower-port or '+
          'current() > ../l4-src-port-range/upper-port' {
            description
              "If l4-src-port and l4-src-port-range/lower-port and
               upper-port are set at the same time, l4-src-port
               should not overlap with l4-src-port-range.";
          }
          description
            "Match on Layer 4 src port.";
        }
        container l4-src-port-range {
          leaf lower-port {
            type inet:port-number;
            description
              "Lower boundary for port.";
          }
          leaf upper-port {
            type inet:port-number;
            must '. >= ../lower-port' {
              description
                "Upper boundary for port.  If it
                 exists, the upper boundary must be
                 higher than the lower boundary.";
            }
            description
              "Upper boundary for port.";
          }
          description
            "Match on Layer 4 src port range.  When
             only the lower-port is present, it represents
             a single port.  When both the lower-port and
             upper-port are specified, it implies
             a range inclusive of both values.";
        }
        leaf l4-dst-port {
          type inet:port-number;
          must 'current() < ../l4-dst-port-range/lower-port or '+
          'current() > ../l4-dst-port-range/upper-port' {
            description
              "If l4-dst-port and l4-dst-port-range/lower-port
               and upper-port are set at the same time,
               l4-dst-port should not overlap with
               l4-src-port-range.";
          }
          description
            "Match on Layer 4 dst port.";
        }
        container l4-dst-port-range {
          leaf lower-port {
            type inet:port-number;
            description
              "Lower boundary for port.";
          }
          leaf upper-port {
            type inet:port-number;
            must '. >= ../lower-port' {
              description
                "Upper boundary must be
                 higher than lower boundary.";
            }
            description
              "Upper boundary for port.  If it exists,
               upper boundary must be higher than lower
               boundary.";
          }
          description
            "Match on Layer 4 dst port range.  When only
             lower-port is present, it represents a single
             port.  When both lower-port and upper-port are
             specified, it implies a range inclusive of both
             values.";
        }
        leaf protocol-field {
          type union {
            type uint8;
            type identityref {
              base protocol-type;
            }
          }
          description
            "Match on IPv4 protocol or IPv6 Next Header field.";
        }
      }
      list application-classification {
        key "application-class-name";
        description
          "List for application.";
        leaf application-class-name {
          type string;
          description
            "Application classification name.";
        }
        leaf category-id {
          type uint32;
          description
            "Describe the application category, e.g. Media,
             Peer2Peer.";
        }
        leaf application-id {
          type uint32;
          description
            "Describe the application and sub-application flows
              as well.";
        }
      }
      list user {
        key "list-name";
        description
          "List for User.";
        leaf list-name {
          type string;
          description
            "User list name.";
        }
        leaf-list user-id {
          type string;
          description
            "User list.";
        }
        leaf-list user-group {
          type string;
          description
            "User group list.";
        }
      }
      leaf-list site {
        type uint32;
        description
          "Describe the enterprise site or set of sites.";
      }
      container link-path-policy {
        description
          "Container for path selection policy.";
        leaf business-priority {
          type enumeration {
            enum high {
              description
                "Refers to high priority.";
            }
            enum normal {
              description
                "Refers to normal priority.";
            }
            enum low {
              description
                "Refers to low priority..";
            }
            enum voice {
              description
                "Refers to voice priority.";
            }
            enum critical_data {
              description
                "Refers to critical_data priority.";
            }
            enum transactional {
              description
                "Refers to transactional priority.";
            }
            enum user-defined {
              description
                "Refers to user-defined priority.";
            }
          }
          description
            "Describes the business priority for the matched traffic or
             application.";
        }
        container link-selection-mode {
          description
            "Describes the policy for how links should be selected for
            the specified traffic flow.";
          leaf mode {
            type enumeration {
              enum automatic {
                description
                  "Refers to automatic mode with all the WAN link
                  service.";
              }
              enum primary {
                description
                  "For certain traffic requiring high security or to
                  use a limited usage based circuit.";
              }
              enum lowest-cost {
                description
                  "For certain traffic only low cost WAN link could
                   be used.";
              }
            }
            description
              "Automatic option needs to take the SLA profile into
               consideration; Primary and lowest-cost are NOT
               automatic.";
          }
          leaf physical-port {
            type uint32;
            description
              "When in NOT automatic mode, specify the physical-port.";
          }
          leaf service-type {
            type enumeration {
              enum commodity {
                description
                  "Refers to broadband Internet links.";
              }
              enum wireless {
                description
                  "Refers to subset of 3G/4G/LTE and upcoming 5G.";
              }
              enum private {
                description
                  "Refers to private circuits such as Ethernet, T1,
                   etc.";
              }
            }
            description
              "When in NOT automatic mode, specify the physical-port,
               service-type.";
          }
          leaf service-provider {
            type string;
            description
              "When in NOT automatic mode, specify the name of
              provider.";
          }
        }
        leaf path-selection-mode {
          type enumeration {
            enum drop {
              description
                "Specify to drop the traffic.";
            }
            enum underlay {
              description
                "Specify the underlay path.";
            }
            enum overlay {
              description
                "Specify the overlay path.";
            }
          }
          default "overlay";
          description
            "Describes the policy for how paths should be selected for
             the specified traffic flow. If a destination for a traffic
             flow can be reached through both the overlay as well as
             the underlay,specify a preference .";
        }
      }
    }
  }
  container traffic-sla {
    description
      "Container for traffic SLA measurement.";
    list traffic-sla {
      key "custom_sla_name";
      description
        "List for traffic sla profile";
      leaf custom_sla_name {
        type string;
        description
          "customer traffic sla name";
      }
      leaf direction {
        type identityref {
          base traffic-direction;
        }
        default "both";
        description
          "The direction to which the QoS profile
           is applied: upstream or downstream.";
      }
      leaf latency {
        type uint32;
        units "msec";
        description
          "Downstream or upstream latency observed on the path in msec";
      }
      leaf jitter {
        type uint32;
        units "msec";
        description
          "Jitter observed on the path in msec";
      }
      leaf packet-loss-rate {
        type uint32 {
          range "0..100";
        }
        units "percent";
        description
          "Percentage of packet loss observed on the  path for the
           upstream and downstream";
      }
    }
  }
}
