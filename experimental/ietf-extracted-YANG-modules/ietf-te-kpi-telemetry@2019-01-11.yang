module ietf-te-kpi-telemetry {
  namespace "urn:ietf:params:xml:ns:yang:ietf-te-kpi-telemetry";
  prefix te-tel;

  import ietf-te {
    prefix te;
  }
  import ietf-te-types {
    prefix te-types;
  }
  import ietf-routing-types {
    prefix rt-types;
  }

  organization
    "IETF Traffic Engineering Architecture and Signaling (TEAS)
     Working Group";
  contact
    "Editor: Young Lee <leeyoung@huawei.com>
     Editor: Dhruv Dhody <dhruv.ietf@gmail.com>
     Editor: Ricard Vilalta <ricard.vilalta@cttc.es>
     Editor: Satish Karunanithi <satish.karunanithi@gmail.com>";
  description
    "This module describes telemetry for teas tunnel model";

  revision 2019-01-11 {
    description
      "Initial revision. This YANG file defines
       the reusable base types for TE telemetry.";
    reference "Derived from earlier versions of base YANG files";
  }

  identity telemetry-param-type {
    description
      "Base identity for telemetry param types";
  }

  identity one-way-delay {
    base telemetry-param-type;
    description
      "To specify average Delay in one (forward)
       direction";
  }

  identity two-way-delay {
    base telemetry-param-type;
    description
      "To specify average Delay in both (forward and reverse)
       directions";
  }

  identity one-way-delay-variation {
    base telemetry-param-type;
    description
      "To specify average Delay Variation in one (forward) direction";
  }

  identity two-way-delay-variation {
    base telemetry-param-type;
    description
      "To specify average Delay Variation in both (forward and reverse)
       directions";
  }

  identity utilized-bandwidth {
    base telemetry-param-type;
    description
      "To specify utilized bandwidth over the specified source
       and destination.";
  }

  identity utilized-percentage {
    base telemetry-param-type;
    description
      "To specify utilization percentage of the entity
       (e.g., tunnel, link, etc.)";
  }
  typedef scaling-criteria-operation {
    type enumeration {
      enum AND {
        description
          "AND operation";
      }
      enum OR {
        description
          "OR operation";
      }
    }
    description
      "Operations to analize list of scaling criterias";
  }

  grouping scaling-duration {
    description
      "Base scaling criteria durations";
    leaf threshold-time {
      type uint32;
      units "seconds";
      description
        "The duration for which the criteria must hold true";
    }
    leaf cooldown-time {
      type uint32;
      units "seconds";
      description
        "The duration after a scaling-in/scaling-out action has been
         triggered, for which there will be no further operation";
    }
  }

  grouping scaling-criteria {
    description
      "Grouping for scaling criteria";
    leaf performance-type {
      type identityref {
        base telemetry-param-type;
      }
      description
        "Reference to the tunnel level telemetry type";
    }
    leaf threshold-value {
      type string;
      description
        "Scaling threshold for the telemetry parameter type";
    }
    leaf te-telemetry-tunnel-ref {
      type leafref {
        path "/te:te/te:tunnels/te:tunnel/te:name";
      }
      description
        "Reference to tunnel";
    }
  }

  grouping scaling-in-intent {
    description
      "Basic scaling in intent";
    uses scaling-duration;
    leaf scale-in-operation-type {
      type scaling-criteria-operation;
      default "AND";
      description
        "Operation to be applied to check between
         scaling criterias to check if the scale in
         threshold condition has been met.
         Defaults to AND";
    }
    list scaling-condition {
      key "performance-type";
      description
        "Scaling conditions";
      uses scaling-criteria;
    }
  }

  grouping scaling-out-intent {
    description
      "Basic scaling out intent";
    uses scaling-duration;
    leaf scale-out-operation-type {
      type scaling-criteria-operation;
      default "OR";
      description
        "Operation to be applied to check between
         scaling criterias to check if the scale out
         threshold condition has been met.
         Defauls to OR";
    }
    list scaling-condition {
      key "performance-type";
      description
        "Scaling conditions";
      uses scaling-criteria;
    }
  }

  augment "/te:te/te:tunnels/te:tunnel" {
    description
      "Augmentation parameters for config scaling-criteria
       TE tunnel topologies. Scale in/out criteria might be used
       for network autonomics in order the controller
       to react to a certain set of monitored params.";
    container te-scaling-intent {
      description
        "scaling intent";
      container scale-in-intent {
        description
          "scale-in";
        uses scaling-in-intent;
      }
      container scale-out-intent {
        description
          "scale-out";
        uses scaling-out-intent;
      }
    }
    container te-telemetry {
      config false;
      description
        "telemetry params";
      leaf id {
        type string;
        description
          "Id of telemetry param";
      }
      uses te-types:performance-metrics-attributes;
      leaf te-ref {
        type leafref {
          path "/te:te/te:tunnels/te:tunnel/te:name";
        }
        description
          "Reference to measured te tunnel";
      }
    }
  }
}
