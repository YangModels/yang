module ietf-igmp-mld {
   yang-version 1.1;
   namespace "urn:ietf:params:xml:ns:yang:ietf-igmp-mld";
   // replace with IANA namespace when assigned
   prefix igmp-mld;

   import ietf-inet-types {
     prefix "inet";
   }

   import ietf-yang-types {
     prefix "yang";
   }

   import ietf-routing-types {
     prefix "rt-types";
   }

   import ietf-access-control-list {
     prefix "acl";
   }

   import ietf-routing {
     prefix "rt";
   }

   import ietf-interfaces {
     prefix "if";
   }

   import ietf-ip {
     prefix ip;
   }

   organization
     "IETF PIM Working Group";

   contact
     "WG Web:   <http://tools.ietf.org/wg/pim/>
      WG List:  <mailto:pim@ietf.org>

      WG Chair: Stig Venaas
                <mailto:stig@venaas.com>

      WG Chair: Mike McBride
                <mailto:mmcbride7@gmail.com>
      Editor:   Xufeng Liu
                <mailto:xufeng.liu.ietf@gmail.com>

      Editor:   Feng Guo
                <mailto:guofeng@huawei.com>

      Editor:   Mahesh Sivakumar
                <mailto:sivakumar.mahesh@gmail.com>

      Editor:   Pete McAllister
                <mailto:pete.mcallister@metaswitch.com>

      Editor:   Anish Peter
                <mailto:anish.ietf@gmail.com>";

   description
     "The module defines a collection of YANG definitions common for
     IGMP and MLD.";

   revision 2018-09-15 {
     description
       "Updated yang data model for default value, address type and
        repeated leaf definition.";
     reference
       "RFC XXXX: A YANG Data Model for IGMP and MLD";
   }
   revision 2018-06-21 {
     description
       "Updated yang data model for parameter range and description.";
     reference
       "RFC XXXX: A YANG Data Model for IGMP and MLD";
   }
   revision 2017-10-20 {
     description
       "Updated yang data model for adding explicit-tracking and
        lightweight IGMPv3 and MLDv2 function.";
     reference
       "RFC XXXX: A YANG Data Model for IGMP and MLD";
   }
   revision 2017-09-19 {
     description
       "Updated yang data model for NMDA version and errata.";
     reference
       "RFC XXXX: A YANG Data Model for IGMP and MLD";
   }

   /*
    * Features
    */
   feature feature-igmp {
     description
       "Support IGMP protocol for IPv4 group membership record.";
   }
   feature feature-mld {
     description
       "Support MLD protocol for IPv6 group membership record.";
   }
   feature global-admin-enable {
     description
       "Support global configuration to enable or disable protocol.";
   }

   feature global-interface-config {
     description
       "Support global configuration applied for all interfaces.";
   }

   feature global-max-entries {
     description
       "Support configuration of global max-entries.";
   }

   feature global-max-groups {
     description
       "Support configuration of global max-groups.";
   }

   feature intf-admin-enable {
     description
       "Support configuration of interface administrative enabling.";
   }

   feature intf-immediate-leave {
     description
       "Support configuration of interface immediate-leave.";
   }

   feature intf-join-group {
     description
       "Support configuration of interface join-group.";
   }

   feature intf-max-groups {
     description
       "Support configuration of interface max-groups.";
   }
   feature intf-max-group-sources {
     description
       "Support configuration of interface max-group-sources.";
   }

   feature intf-require-router-alert {
     description
       "Support configuration of interface require-router-alert.";
   }

   feature intf-source-policy {
     description
       "Support configuration of interface source policy.";
   }

   feature intf-ssm-map {
     description
       "Support configuration of interface ssm-map.";
   }

   feature intf-static-group {
     description
       "Support configuration of interface static-group.";
   }

   feature intf-verify-source-subnet {
     description
       "Support configuration of interface verify-source-subnet.";
   }

   feature intf-explicit-tracking {
     description
       "Support configuration of interface explicit-tracking hosts.";
   }

   feature intf-exclude-lite {
     description
       "Support configuration of interface exclude-lite.";
   }

   feature per-interface-config {
     description
       "Support per interface configuration.";
   }

   feature rpc-clear-groups {
     description
       "Support rpc's to clear groups.";
   }
   /*
    * Typedefs
    */
   typedef ssm-map-ipv4-addr-type {
     type union {
       type enumeration {
         enum 'policy' {
           description
           "Source address is specified in SSM map policy.";
         }
       }
       type inet:ipv4-address;
     }
     description
       "Multicast source IP address type for SSM map.";
   } // source-ipv4-addr-type

   typedef ssm-map-ipv6-addr-type {
     type union {
       type enumeration {
         enum 'policy' {
           description
           "Source address is specified in SSM map policy.";
         }
       }
       type inet:ipv6-address;
     }
     description
       "Multicast source IP address type for SSM map.";
   } // source-ipv6-addr-type

   /*
    * Identities
    */

   /*
    * Groupings
    */
   grouping global-config-attributes {
     description "Global IGMP and MLD configuration.";

     leaf enable {
       if-feature global-admin-enable;
       type boolean;
       default false;
       description
         "true to enable IGMP or MLD in the routing instance;
          false to disable IGMP or MLD in the routing instance.";
     }

     leaf max-entries {
       if-feature global-max-entries;
       type uint32;
       description
         "The maximum number of entries in IGMP or MLD.";
     }
     leaf max-groups {
       if-feature global-max-groups;
       type uint32;
       description
         "The maximum number of groups that IGMP
          or MLD can join.";
     }
   } // global-config-attributes

   grouping global-state-attributes {

     description "Global IGMP and MLD state attributes.";

     leaf entries-count {
       type uint32;
       config false;
       description
         "The number of entries in IGMP or MLD.";
     }
     leaf groups-count {
       type uint32;
       config false;
       description
         "The number of groups that IGMP or MLD can join.";
     }

     container statistics {
       config false;
       description "Global statistics.";

       leaf discontinuity-time {
         type yang:date-and-time;
         description
           "The time on the most recent occasion at which any one
           or more of the statistic counters suffered a
           discontinuity. If no such discontinuities have occurred
           since the last re-initialization of the local
           management subsystem, then this node contains the time
           the local management subsystem re-initialized itself.";
       }
       container error {
         description "Statistics of errors.";
         uses global-statistics-error;
       }

       container received {
         description "Statistics of received messages.";
         uses global-statistics-sent-received;
       }
       container sent {
         description "Statistics of sent messages.";
         uses global-statistics-sent-received;
       }
     } // statistics
   } // global-state-attributes

   grouping global-statistics-error {
     description
       "A grouping defining statistics attributes for errors.";
     uses global-statistics-sent-received;
     leaf checksum {
       type yang:counter64;
       description
         "The number of checksum errors.";
     }
     leaf too-short {
       type yang:counter64;
       description
         "The number of messages that are too short.";
     }
   } // global-statistics-error

   grouping global-statistics-sent-received {
     description
       "A grouping defining statistics attributes.";
     leaf total {
       type yang:counter64;
       description
         "The number of total messages.";
     }
     leaf query {
       type yang:counter64;
       description
         "The number of query messages.";
     }
     leaf report {
       type yang:counter64;
       description
         "The number of report messages.";
     }
     leaf leave {
       type yang:counter64;
       description
         "The number of leave messages.";
     }
   } // global-statistics-sent-received

   grouping interface-global-config-attributes {
     description
       "Configuration attributes applied to the interface global level
        whose per interface attributes are not existing.";

     leaf max-groups-per-interface {
       if-feature intf-max-groups;
       type uint32;
       description
         "The maximum number of groups that IGMP or MLD can join.";
     }
   } //interface-global-config-attributes

   grouping interface-common-config-attributes {
     description
       "Configuration attributes applied to both the interface global
        level and interface level.";

     leaf last-member-query-interval {
       type uint16 {
         range "1..1023";
       }
       units seconds;
       default 1;
       description
         "Last Member Query Interval, which may be tuned to modify the
          leave latency of the network.";
        reference "RFC3376. Sec. 8.8.";
     }

     leaf query-interval {
       type uint16 {
         range "1..31744";
       }
       units seconds;
       default 125;
       description
         "The Query Interval is the interval between General Queries
          sent by the Querier.In RFC3376, Querier's Query Interval(QQI) is
          represented from the Querier's Query Interval Code in query
          message as follows:
          If QQIC < 128, QQI = QQIC
          If QQIC >= 128, QQIC represents a floating-point value as follows:
           0 1 2 3 4 5 6 7
          +-+-+-+-+-+-+-+-+
          |1| exp | mant  |
          +-+-+-+-+-+-+-+-+
          QQI = (mant | 0x10) << (exp + 3)
          The maximum value of QQI is 31744.";
       reference "RFC3376. Sec. 4.1.7, 8.2, 8.14.2.";
     }

     leaf query-max-response-time {
       type uint16 {
         range "1..1023";
       }
       units seconds;
       default 10;
       description
         "Query maximum response time specifies the maximum time
          allowed before sending a responding report.";
       reference "RFC3376. Sec. 4.1.1, 8.3, 8.14.3.";
     }

     leaf require-router-alert {
       if-feature intf-require-router-alert;
       type boolean;
       default false;
       description
         "Protocol packets should contain router alert IP option.";
     }

     leaf robustness-variable {
       type uint8 {
         range "1..7";
       }
       default 2;
       description
         "Querier's Robustness Variable allows tuning for the expected
          packet loss on a network.";
       reference "RFC3376. Sec. 4.1.6, 8.1, 8.14.1.";
     }

   } // interface-common-config-attributes

   grouping interface-common-config-attributes-igmp {
     description
       "Configuration attributes applied to both the interface global
        level and interface level for IGMP.";
     uses interface-common-config-attributes;
     leaf version {
       type uint8 {
         range "1..3";
       }
       default 2;
       description "IGMP version.";
       reference "RFC1112, RFC2236, RFC3376.";
     }
   }

   grouping interface-common-config-attributes-mld {
     description
       "Configuration attributes applied to both the interface global
        level and interface level for MLD.";
     uses interface-common-config-attributes;
     leaf version {
       type uint8 {
         range "1..2";
       }
       default 2;
       description "MLD version.";
       reference "RFC2710, RFC3810.";
     }
   }

   grouping interfaces-config-attributes-igmp {
     description
       "Configuration attributes applied to the interface global
        level for IGMP.";
     uses interface-common-config-attributes-igmp;
     uses interface-global-config-attributes;
   }

   grouping interfaces-config-attributes-mld {
     description
       "Configuration attributes applied to the interface global
        level for MLD.";
     uses interface-common-config-attributes-mld;
     uses interface-global-config-attributes;
   }

   grouping interface-specific-config-attributes {
     description
       "Per interface configuration attributes for both IGMP and MLD
        whose are not existing in interface global level.";

     leaf enable {
       if-feature intf-admin-enable;
       type boolean;
       default false;
       description
         "true to enable IGMP or MLD on the interface;
          false to disable IGMP or MLD on the interface.";
     }
     leaf group-policy {
       type leafref {
         path "/acl:acls/acl:acl/acl:name";
       }
       description
         "Name of the access policy used to filter IGMP or MLD
          membership.A device can restrict the length
          and value of this name, possibly space and special
          characters are not allowed.";
     }
     leaf immediate-leave {
       if-feature intf-immediate-leave;
       type empty;
       description
         "If present, IGMP or MLD perform an immediate leave upon
          receiving an IGMPv2 or MLDv1 leave message.
          If the router is IGMP-enabled or MLD-enabled, it sends an
          IGMP or MLD last member query with a last member query
          response time. However, the router does not wait for
          the response time before it prunes off the group.";
     }
     leaf max-groups {
       if-feature intf-max-groups;
       type uint32;
       description
         "The maximum number of groups that IGMP ro MLD can join.";
     }
     leaf max-group-sources {
       if-feature intf-max-group-sources;
       type uint32;
       description
         "The maximum number of group sources.";
     }

     leaf source-policy {
       if-feature intf-source-policy;
       type leafref {
         path "/acl:acls/acl:acl/acl:name";
       }
       description
         "Name of the access policy used to filter sources.
          A device can restrict the length
          and value of this name, possibly space and special
          characters are not allowed.";
     }
     leaf verify-source-subnet {
       if-feature intf-verify-source-subnet;
       type empty;
       description
         "If present, the interface accepts packets with matching
          source IP subnet only.";
     }
     leaf explicit-tracking {
       if-feature intf-explicit-tracking;
       type empty;
       description
         "If present, IGMP/MLD-based explicit membership tracking function
          for multicast routers and IGMP/MLD proxy devices
          supporting IGMPv3/MLDv2. The explicit membership tracking
          function contributes to saving network resources and
          shortening leave latency.";
     }
     leaf exclude-lite {
       if-feature intf-exclude-lite;
       type empty;
       description
         "If present, lightweight IGMPv3 and MLDv2 protocols will run on the
          which simplify the standard versions of IGMPv3 and MLDv2.";
       reference "RFC5790";
     }

   } // interface-specific-config-attributes

   grouping interface-config-attributes-igmp {
     description
       "Per interface configuration attributes for IGMP.";

     uses interface-common-config-attributes-igmp;
     uses interface-specific-config-attributes;

     leaf-list join-group {
       if-feature intf-join-group;
       type rt-types:ipv4-multicast-group-address;
       description
         "The router joins this multicast group on the interface.";
     }

     list ssm-map {
       if-feature intf-ssm-map;
       key "ssm-map-source-addr ssm-map-group-policy";
       description "The policy for (*,G) mapping to (S,G).";
       leaf ssm-map-source-addr {
         type ssm-map-ipv4-addr-type;
         description
           "Multicast source IPv4 address.";
       }
       leaf ssm-map-group-policy {
         type string;
         description
           "Name of the policy used to define ssm-map rules.
            A device can restrict the length
            and value of this name, possibly space and special
            characters are not allowed. ";
       }
     }

     list static-group {
       if-feature intf-static-group;
       key "group-addr source-addr";
       description
         "A static multicast route, (*,G) or (S,G).";

       leaf group-addr {
         type rt-types:ipv4-multicast-group-address;
         description
           "Multicast group IPv4 address.";
       }
       leaf source-addr {
         type rt-types:ipv4-multicast-source-address;
         description
           "Multicast source IPv4 address.";
       }
     }
   } // interface-config-attributes-igmp

   grouping interface-config-attributes-mld {
     description
       "Per interface configuration attributes for MLD.";

     uses interface-common-config-attributes-mld;
     uses interface-specific-config-attributes;

     leaf-list join-group {
       if-feature intf-join-group;
       type rt-types:ipv6-multicast-group-address;
       description
         "The router joins this multicast group on the interface.";
     }

     list ssm-map {
       if-feature intf-ssm-map;
       key "ssm-map-source-addr ssm-map-group-policy";
       description "The policy for (*,G) mapping to (S,G).";
       leaf ssm-map-source-addr {
         type ssm-map-ipv6-addr-type;
         description
           "Multicast source IPv6 address.";
       }
       leaf ssm-map-group-policy {
         type string;
         description
           "Name of the policy used to define ssm-map rules.
            A device can restrict the length
            and value of this name, possibly space and special
            characters are not allowed.";
       }
     }

     list static-group {
       if-feature intf-static-group;
       key "group-addr source-addr";
       description
         "A static multicast route, (*,G) or (S,G).";

       leaf group-addr {
         type rt-types:ipv6-multicast-group-address;
         description
           "Multicast group IPv6 address.";
       }
       leaf source-addr {
         type rt-types:ipv6-multicast-source-address;
         description
           "Multicast source IPv6 address.";
       }
     }
   } // interface-config-attributes-mld

   grouping interface-state-attributes-igmp-mld {
     description
       "Per interface state attributes for both IGMP and MLD.";

     leaf oper-status {
       type enumeration {
         enum up {
           description
           "Ready to pass packets.";
         }
         enum down {
           description
           "The interface does not pass any packets.";
         }
       }
       config false;
       mandatory true;
       description
         "Interface up or down state for IGMP or MLD protocol";
     }
   } // interface-config-attributes-igmp-mld

   grouping interface-state-attributes-igmp {

     description
       "Per interface state attributes for IGMP.";

     uses interface-state-attributes-igmp-mld;

     leaf querier {
       type inet:ipv4-address;
       config false;
       mandatory true;
       description "The querier address in the subnet";
     }
     leaf-list joined-group {
       if-feature intf-join-group;
       type rt-types:ipv4-multicast-group-address;
       config false;
       description
         "The routers that joined this multicast group.";
     }

     list group {
       key "group-address";
       config false;
       description
         "Multicast group membership information
         that joined on the interface.";

       leaf group-address {
         type rt-types:ipv4-multicast-group-address;
         description
           "Multicast group address.";
       }
       uses interface-state-group-attributes-igmp-mld;

       leaf last-reporter {
         type inet:ipv4-address;
         description
           "The last host address which has sent the
            report to join the multicast group.";
       }
       list source {
         key "source-address";
         description
           "List of multicast source information
            of the multicast group.";

         leaf source-address {
           type inet:ipv4-address;
           description
             "Multicast source address in group record.";
         }
         uses interface-state-source-attributes-igmp-mld;
         leaf last-reporter {
           type inet:ipv4-address;
           description
             "The last host address which has sent the
              report to join the multicast source and group.";
         }
         list host {
           if-feature intf-explicit-tracking;
           key "host-address";
           description
             "List of multicast membership hosts
              of the specific multicast source-group.";

           leaf host-address {
             type inet:ipv4-address;
             description
               "Multicast membership host address.";
           }
           uses interface-state-host-attributes-igmp-mld;
         }// list host
       } // list source
     } // list group
   } // interface-state-attributes-igmp

   grouping interface-state-attributes-mld {

     description
       "Per interface state attributes for MLD.";

     uses interface-state-attributes-igmp-mld;

     leaf querier {
       type inet:ipv6-address;
       config false;
       mandatory true;
       description
         "The querier address in the subnet.";
     }
     leaf-list joined-group {
       if-feature intf-join-group;
       type rt-types:ipv6-multicast-group-address;
       config false;
       description
         "The routers that joined this multicast group.";
     }

     list group {
       key "group-address";
       config false;
       description
         "Multicast group membership information
         that joined on the interface.";

       leaf group-address {
         type rt-types:ipv6-multicast-group-address;
         description
           "Multicast group address.";
       }
       uses interface-state-group-attributes-igmp-mld;
       leaf last-reporter {
         type inet:ipv6-address;
         description
           "The last host address which has sent the
            report to join the multicast group.";
       }
       list source {
         key "source-address";
         description
           "List of multicast source information
            of the multicast group.";

         leaf source-address {
           type inet:ipv6-address;
           description
             "Multicast source address in group record";
         }
         uses interface-state-source-attributes-igmp-mld;
         leaf last-reporter {
           type inet:ipv6-address;
           description
             "The last host address which has sent the
              report to join the multicast source and group.";
         }
         list host {
           if-feature intf-explicit-tracking;
           key "host-address";
           description
             "List of multicast membership hosts
              of the specific multicast source-group.";

           leaf host-address {
             type inet:ipv6-address;
             description
               "Multicast membership host address.";
           }
           uses interface-state-host-attributes-igmp-mld;
         }// list host
       } // list source
     } // list group
   } // interface-state-attributes-mld

   grouping interface-state-group-attributes-igmp-mld {
     description
       "Per interface state attributes for both IGMP and MLD
        groups.";

     leaf expire {
       type uint32;
       units seconds;
       mandatory true;
       description
         "The time left before multicast group state expires.";
     }
     leaf filter-mode {
       type enumeration {
         enum "include" {
           description
             "In include mode, reception of packets sent
              to the specified multicast address is requested
              only from those IP source addresses listed in the
              source-list parameter";
         }
         enum "exclude" {
           description
             "In exclude mode, reception of packets sent
              to the given multicast address is requested
              from all IP source addresses except those
              listed in the source-list parameter.";
         }
       }
       mandatory true;
       description
         "Filter mode for a multicast group,
          may be either include or exclude.";
     }
     leaf up-time {
       type uint32;
       units seconds;
       mandatory true;
       description
         "The elapsed time since the device created multicast group record.";
     }
   } // interface-state-group-attributes-igmp-mld

   grouping interface-state-source-attributes-igmp-mld {
     description
       "Per interface state attributes for both IGMP and MLD
        source-group records.";

     leaf expire {
       type uint32;
       units seconds;
       mandatory true;
       description
         "The time left before multicast source-group state expires.";
     }
     leaf up-time {
       type uint32;
       units seconds;
       mandatory true;
       description
         "The elapsed time since the device created multicast
          source-group record.";
     }
     leaf host-count {
       if-feature intf-explicit-tracking;
       type uint32;
       description
         "The number of host addresses.";
     }
   } // interface-state-source-attributes-igmp-mld

   grouping interface-state-host-attributes-igmp-mld {
     description
       "Per interface state attributes for both IGMP and MLD
        hosts of source-group records.";

     leaf host-filter-mode {
       type enumeration {
         enum "include" {
           description
             "In include mode";
         }
         enum "exclude" {
           description
             "In exclude mode.";
         }
       }
       mandatory true;
       description
         "Filter mode for a multicast membership
          host may be either include or exclude.";
     }
   }// interface-state-host-attributes-igmp-mld

   /*
    * Configuration and Operational state data nodes (NMDA version)
    */
   augment "/rt:routing/rt:control-plane-protocols"
   {
     description
       "IGMP augmentation to routing control plane protocol
        configuration and state.";

     container igmp {
       if-feature feature-igmp;
       description
         "IGMP configuration and operational state data.";

       container global {
         description
           "Global attributes.";
         uses global-config-attributes;
         uses global-state-attributes;
       }

       container interfaces {
         description
           "Containing a list of interfaces.";

         uses interfaces-config-attributes-igmp {
           if-feature global-interface-config;
         }

         list interface {
           key "interface-name";
           description
             "List of IGMP interfaces.";
           leaf interface-name {
             type if:interface-ref;
             must "/if:interfaces/if:interface[if:name = current()]/"
                + "ip:ipv4" {
               description
                 "The interface must have IPv4 enabled.";
             }
             description
               "Reference to an entry in the global interface list.";
           }
           uses interface-config-attributes-igmp {
             if-feature per-interface-config;
           }
           uses interface-state-attributes-igmp;
         } // interface
       } // interfaces
     } // igmp
   }//augment

   augment "/rt:routing/rt:control-plane-protocols"
   {
     description
       "MLD augmentation to routing control plane protocol
        configuration and state.";

     container mld {
       if-feature feature-mld;
       description
         "MLD configuration and operational state data.";

       container global {
         description
           "Global attributes.";
         uses global-config-attributes;
         uses global-state-attributes;
       }

       container interfaces {
         description
           "Containing a list of interfaces.";

         uses interfaces-config-attributes-mld {
           if-feature global-interface-config;
         }

         list interface {
           key "interface-name";
           description
             "List of MLD interfaces.";
           leaf interface-name {
             type if:interface-ref;
             must "/if:interfaces/if:interface[if:name = current()]/"
                + "ip:ipv6" {
               description
                 "The interface must have IPv6 enabled.";
             }
             description
               "Reference to an entry in the global interface list.";
           }
           uses interface-config-attributes-mld {
             if-feature per-interface-config;
           }
           uses interface-state-attributes-mld;
         } // interface
       } // interfaces
     } // mld
   } // augment

   /*
    * RPCs
    */
   rpc clear-igmp-groups {
     if-feature rpc-clear-groups;
     description
       "Clears the specified IGMP cache entries.";

     input {
       leaf interface-name {
         if-feature feature-igmp;
         type leafref {
           path "/rt:routing/rt:control-plane-protocols/"
             + "igmp-mld:igmp/igmp-mld:interfaces/"
             + "igmp-mld:interface/igmp-mld:interface-name";
         }
         description
           "Name of the IGMP interface.
            If it is not specified, groups from all interfaces are
            cleared.";
       }
       leaf group-address {
         type rt-types:ipv4-multicast-group-address;
         description
           "Multicast group IPv4 address.
            If it is not specified, all IGMP group entries are
            cleared.";
       }
       leaf source-address {
         type rt-types:ipv4-multicast-source-address;
         description
           "Multicast source IPv4 address.
            If it is not specified, all IGMP source-group entries are
            cleared.";
       }
     }
   } // rpc clear-igmp-groups

   rpc clear-mld-groups {
     if-feature rpc-clear-groups;
     description
       "Clears the specified MLD cache entires.";

     input {
       leaf interface-name {
         if-feature feature-mld;
         type leafref {
           path "/rt:routing/rt:control-plane-protocols/"
             + "igmp-mld:mld/igmp-mld:interfaces/"
             + "igmp-mld:interface/igmp-mld:interface-name";
         }
         description
           "Name of the MLD interface.
            If it is not specified, groups from all interfaces are
            cleared.";
       }
       leaf group-addrss {
         type rt-types:ipv6-multicast-group-address;
         description
           "Multicast group IPv6 address.
            If it is not specified, all MLD group entries are
            cleared.";
       }
       leaf source-address {
         type rt-types:ipv6-multicast-source-address;
         description
           "Multicast source IPv6 address.
            If it is not specified, all MLD source-group entries are
            cleared.";
       }
     }
   } // rpc clear-mld-groups

   /*
    * Notifications
    */
 }
