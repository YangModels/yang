module ietf-performance-monitoring {
  yang-version 1.1;
  namespace "urn:ietf:params:xml:ns:yang:ietf-performance-monitoring";
  prefix pm;

  import ietf-yang-types {
    prefix "yang";
  }

  import ietf-performance-monitoring-types {
    prefix "pm-types";
  }

  organization
    "IETF CCAMP Working Group";
  contact
    "WG Web:   <https://datatracker.ietf.org/wg/ccamp/>
     WG List:  <mailto:ccamp@ietf.org>

     Editor:   Chaode Yu
               <yuchaode@huawei.com>";

  description
    "This module defines a model for optical performance
    monitoring.

    The model fully conforms to the Network Management
    Datastore Architecture (NMDA).

    Copyright (c) 2022 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  revision 2022-10-24 {
    description  "Initial revision.";
    reference "draft-yu-performance-monitoring-yang-00";
  }

  container monitor-tasks {
    description "the root node.";

    list monitor-task {
      key resource;
      description "monitoring task list";
      uses task-instance-grouping;
    }
  }

  grouping task-instance-grouping {
    description "none";
    leaf resource {
      type union {
        type instance-identifier {
          require-instance false;
        }
        type yang:object-identifier;
        type string;
        type yang:uuid;
      }
      description "the identifier of network resource which is monitored.";
    }

    leaf resource-type {
      type identityref {
        base pm-types:resource-type;
      }
      description "the type of resource, such as NE, board or port";
    }

    leaf task-name {
      type string;
      description "the name of monitoring task";
    }

    leaf task-status {
      type enumeration {
        enum running;

        enum suspended;

        enum abnormal;
      }
      config false;
      description "the status of monitoring task.";
    }

    uses task-configuration-grouping;
  }

  grouping task-configuration-grouping {
    description "none";
    container task-cfg {
      description "Configuration of the monitoring task";

      leaf period {
        type identityref {
          base pm-types:period;
        }
        description "this period is used to indicate how long is the
          monitoring task";
      }

      container indicators {
        description "performance indicators";
        list indicator {
          key indicator-name;
          description "none";
          uses indicator-grouping;
        }
      }
    }
  }

  grouping indicator-grouping {
    description "none";
    leaf indicator-name {
      type string;
      description "performance indicator's name";
    }

    container tca {
      //TO BE ADDED
      description "configuration of TCA";
    }
  }

  rpc get-all-current-pm-data {
    description "This RPC is used to retrieve current PM data.";
    input {
      leaf-list resources {
        type leafref {
          path "/pm:monitor-tasks/pm:monitor-task/pm:resource";
        }
        description "resouces' identifier";
      }
    }
    output {
      container pm-data {
        description "none";
        list pm-data-list {
          key resource;
          description "none";
          uses pm-data-instance-grouping;
        }
      }
    }
  }

  rpc get-history-pm-data {
    description "This RPC is used to retrieve historic PM data.";
    input {
      leaf-list resources {
        type leafref {
          path "/pm:monitor-tasks/pm:monitor-task/pm:resource";
        }
        description "identifier of resources";
      }

      leaf start-time {
        type yang:date-and-time;
        description "the starttime of performance data needed to be retrieved";
      }

      leaf end-time {
        type yang:date-and-time;
        description "the endtime of performance data needed to be retrieved";
      }
    }
    output {
      container pm-data {
        description "none";
        list pm-data-list {
          key resource;
          description "none";
          uses pm-data-instance-grouping;
        }
      }
    }
  }

  grouping pm-data-instance-grouping {
    description "none";
    leaf resource {
      type leafref {
        path "/pm:monitor-tasks/pm:monitor-task/pm:resource";
      }
      description "the identifier of network resource which is monitored.";
    }

    leaf collect-time {
      type yang:date-and-time;
      description "the time of this data is collected";
    }

    leaf resource-type {
      type identityref {
        base pm-types:resource-type;
      }
      description "the type of resource, such as NE, board or port";
    }

    container indicator-data {
      description "none";
      list indicator-data-list {
        key indicator-name;
        description "none";
        uses indicator-data-instance-grouping;
      }
    }
  }

  grouping indicator-data-instance-grouping {
    description "none";
    leaf indicator-name {
      type string;
      description "name of performance data indicator";
    }

    leaf indicator-value {
      type string;
      description "value of performance data";
    }

    leaf indicator-value-unit {
      type string;
      description "unit of performance data value";
    }
  }
}
