module ietf-dots-signal {
      yang-version 1.1;
      namespace "urn:ietf:params:xml:ns:yang:ietf-dots-signal";
      prefix "signal";

      import ietf-inet-types {
          prefix "inet";
      }

    organization "IETF DOTS Working Group";

    contact
      "Konda, Tirumaleswar Reddy <TirumaleswarReddy_Konda@McAfee.com>
       Mohamed Boucadair <mohamed.boucadair@orange.com>
       Prashanth Patil <praspati@cisco.com>
       Andrew Mortensen <amortensen@arbor.net>
       Nik Teague <nteague@verisign.com>";

     description
       "This module contains YANG definition for DOTS
        signal sent by the DOTS client to the DOTS server.

        Copyright (c) 2017 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

     revision 2017-11-27 {
       description
         "Initial revision.";
       reference
         "RFC XXXX: A Distributed Denial-of-Service Open Threat
                    Signaling (DOTS) Signal Channel";
     }

     container mitigation-scope {
          description
             "Specifies the scope of the mitigation request.";

          leaf-list client-identifier {
             type binary;
             description
               "The client identifier may be conveyed by
                the DOTS gateway to propagate the DOTS client
                identity from the gateway's client-side to the
                gateway's server-side, and from the gateway's
                server-side to the DOTS server.

                It allows the final DOTS server to accept
                mitigation requests with scopes which the DOTS
                client is authorized to manage.";
          }

          list scope {
             key mitigation-id;
             description
               "The scope of the request.";

             leaf mitigation-id {
                type int32;
                description
                  "Mitigation request identifier.

                  This identifier must be unique for each mitigation
                  request bound to the DOTS client.";
              }

              leaf-list target-ip {
                  type inet:ip-address;
                  description
                    "IPv4 or IPv6 address identifying the target.";
              }

              leaf-list target-prefix {
                  type inet:ip-prefix;
                  description
                    "IPv4 or IPv6 prefix identifying the target.";
              }

              list target-port-range {
                  key "lower-port upper-port";

                  description
                    "Port range. When only lower-port is
                     present, it represents a single port.";

                  leaf lower-port {
                     type inet:port-number;
                     mandatory true;
                     description "Lower port number.";
                  }

                  leaf upper-port {
                     type inet:port-number;
                       must ". >= ../lower-port" {
                         error-message
                           "The upper port number must be greater than
                            or equal to lower port number.";
                       }
                     description "Upper port number.";
                  }
              }

              leaf-list target-protocol {
                  type uint8;
                  description
                    "Identifies the target protocol number.

                     The value '0' means 'all protocols'.

                     Values are taken from the IANA protocol registry:
                     https://www.iana.org/assignments/protocol-numbers/
                     protocol-numbers.xhtml

                     For example, 6 for a TCP or 17 for UDP.";
              }
              leaf-list fqdn {
                   type inet:domain-name;
                   description "FQDN";
              }

              leaf-list uri {
                  type inet:uri;
                  description "URI";
              }

              leaf-list alias-name {
                  type string;
                  description "alias name";
              }

              leaf lifetime {
                  type int32;
                  units "seconds";
                  default 3600;
                  description
                    "Indicates the lifetime of the mitigation request.";
              }
          }
     }
  }
