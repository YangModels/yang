module ietf-rdnm-types {
  yang-version 1.1;
  namespace "urn:ietf:params:xml:ns:yang:ietf-rdnm-types";
  prefix rdnm-types;

  organization
    "IETF CCAMP Working Group";
  contact
    "WG Web: <http://tools.ietf.org/wg/ccamp/>
     WG List: <mailto:ccamp@ietf.org>

     Editor: Chaode Yu
             <mailto:yuchaode@huawei.com>
             Xing Zhao 
             <mailto:zhaoxing@caict.ac.cn>
             Yanxia Tan
             <mailto:tanyx11@chinaunicom.cn>
             Nigel Davis
             <mailto:ndavis@ciena.com>
             Daniel King
             <mailto:daniel@olddog.co.uk>";

  description
    "This module defines Rich-Detail Network Management (RDNM) YANG types.";

  revision 2025-02-22 {
    description
      "Revision 1.0";
    reference
      "draft-yu-ccamp-rdnm-yang-00";
  }  

  grouping explicit-ttp-hop {
    container ttp-hop {
      description 
        "TTP Hop";

      leaf node-id {
        type nw:node-id;
        description
          "identifier of node for this TTP hop.";
      }

      choice id-or-name {
        description 
          "The server can choose to display the identifier or 
          the name of TTP.";

        case id {
          leaf ttp-id {
            type binary;
          }
          description
            "the identifier of TTP for this TTP hop.";
        }
        case name {
          leaf ttp-name {
            type string;
          }
          description
            "the name of TTP for this TTP hop.";
        }
      }
    }
  }

}
