module ietf-pcp-client {
  namespace "urn:ietf:params:xml:ns:yang:ietf-pcp-client";
  prefix pcp-client;

  import ietf-inet-types { prefix inet; }
  import ietf-pcp { prefix pcp; }

  organization "N/A Working Group";
  contact
     "Mohamed Boucadair <mohamed.boucadair@orange.com>
      Christian Jacquenet <christian.jacquenet@orange.com>";

  description
       "This module contains a collection of YANG definitions for
        PCP client implementations.

        Copyright (c) 2015 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

  revision 2015-08-05 {
      description "Changes tbc.";
       reference "tbc";
   }

/*
  *PCP Configuration
  */

    container pcp-client-config {
       description
         "PCP client configuration";

        leaf enable {
            type boolean;
            description
                    "Enable/disable the PCP client.";
        }

        leaf description {
          type string;
          description
            "Associated a description with the module.";
        }

        container pcp-client-instances {
           description
             "A set of PCP client instances.";

            list pcp-client-instance {
                key "id";

                description
                    "A PCP client instance.";

               leaf id {
                  type uint32;
                  description
                    "An identifier of the PCP client instance.";
               }

               leaf name {
                  type string;
                  description
                     "A name of the PCP client instance.";
               }

               list version {
                  key version;
                  description
                   "Indicates the set of supported PCP versions
                     (0, 1, 2)";

                  uses pcp:pcp-version;
               }

               list pcp-servers {
                  key "pcp-server-id";
                  description
                    "List of provisioned PCP servers.";
                  uses pcp:pcp-server-address;
               }

               leaf authentication-enable {
                  type boolean;
                  description
                   "Enable/Disable PCP authentication.";
               }

                container opcode-configuration {
                    description
                      "Opcode-related configuration";
                    uses pcp:opcode;
                }

                container option-configuration {
                    description
                      "Options-related configuration.";
                    uses pcp:option;
                }

                container mapping-table {
                    description
                      "Mapping table maintained by a PCP client
                        instance.";

                    list mapping-entry {
                        key "index";
                        description
                            "PCP Mapping entry.";
                        uses pcp:mapping-entry;
                    }
                }
            }
        }
}

/*
 * PCP state
 */

    container pcp-client-state {

        config false;

        description
            "PCP client state";

        container pcp-client-instances {
            description
                   "PCP client instances";

            list pcp-client-instance {

              key "id";

              description
                   "PCP client instance";

              leaf id {
                type int32;
                description
                   "PCP client instance identifier.";
              }

              leaf name {
                type string;
                description
                   "A name associated with the PCP client instance.";
              }

         list pcp-client-ip-address {

         key address-id;

           description
             "list of configured PCP client addresses.";

         leaf address-id {
              type uint32;
              description
                  "Address identifier";
           }
         leaf ip-address {
              type inet:ipv6-address;
              description
               "IP address";
           }
         }

               list supported-version {
                  key version;
                  description
                  "list of supported PCP versions";
                  uses pcp:pcp-version;
               }

               leaf preferred-version {
                  type uint8;
                  description
                    "The preferred version configured
                      by an administrator.";
               }

               list pcp-server-address {
                  key "pcp-server-id";
                  description
                    "list of provisioned PCP server.";

                  uses pcp:pcp-server-address-status;
               }

              leaf authentication-support {
                type boolean;
                description
                  "Indicates whether PCP authentication is
                    supported.";
              }

              container opcode-capability {
                description
                  "Opcode-related capabilities.";
                uses pcp:opcode;
              }

              container option-capability {
                description
                  "Option-related capabilities";
                uses pcp:option;
              }

              container opcode-configuration {
                description
                  "Opcode-related configuration.";
                uses pcp:opcode;
              }

             container option-configuration {
                description
                  "Option-related configuration.";

                uses pcp:option;
              }

              leaf authentication-enabled {
                type boolean;
                description
                  "Enable/disable PCP authentication";
              }

           container mapping-table {
              description
                 "Mapping table";

                list mapping-entry {
                    key "index";
                    description
                        "Mapping entry";

                    uses pcp:mapping-entry;
                    uses pcp:status-code;
                }
           }

            container traffic-statistics {
                description
                    "traffic statistics.";

                uses pcp:traffic-stat;

                container mapping-table {
                    description
                        "mapping table related statistics.";

                    uses pcp:mapping-table-stats;
                }
                }
            }
        }
   }
}
