module ietf-dhcp {
  namespace "urn:ietf:params:xml:ns:yang:ietf-dhcp";
  prefix "dhcp";
  import ietf-inet-types {
    prefix "inet";
  }
  organization "IETF dhc (Dynamic Host Configuration Protocol)
                Working Group";
  contact
    "leo.liubing@huawei.com
     loukunkun@huawei.com";
  description "The module for implementing DHCP protocol";
  revision 2015-12-23 {
    description
    "version-03, minor grammar revision according to pyang validation.";
    reference
      "draft-liu-dhc-dhcp-yang-model-03";
  }

        container relay {
          description
            "This is a top level container for DHCP relay entity.
             It can have one or more relay configurations.";
          container dhcpRelayIfCfgs {
            description
              "This is relay configuration on a specific interface.";
            list dhcpRelayIfCfg {
              key "ifName";
              description
                "Relay could be configured on different interfaces.";

                                leaf ifName {
                                        type "string";
                                        description "Specify the interface name that dhcp relay configured on";
                                }

                                leaf enable {
                                        type "boolean";
                                        default "false";
                                        description "Enable or disable dhcp relay function";
                                }

                                leaf serverGroupName {
                                        type "string";
                                        description "Server Group Name";
                                }

                                leaf-list serverAddress {
                                        type inet:ipv4-address;
                                        description "DHCP relay destination server IP address";
                                }

                        }

                }

                container dhcpRelayServerGroups {
                        description "Server Grouping is an important feature for carrier grade DHCP Servers.
                                     It is mostly for reliability consideration.";

                        list dhcpRelayServerGroup {

                                key "serverGroupName";

                                 description "DHCP relay server group ";

                                 leaf serverGroupName {
                                        type "string";

                                        description "name of server group";
                                }

                                leaf vpnName {
                                        type "string";

                                        description "VPN name for server group";
                                }

                                leaf gateway {
                                        type inet:ipv4-address;

                                        description "gateway for server group";
                                }

                                leaf-list serverAddress {
                                        type inet:ipv4-address;

                                        description "DHCP relay destination server IP address";
                                }

                                container dhcpRelaySerGrpStats {
                                  description "DHCP relay server group packet statistics ";

                                        list dhcpRelaySerGrpStats {
                                            key "serverIpAddr";
                                            description "DHCP relay server group packet statistics ";
                                                    leaf serverIpAddr {
                                                    type inet:ipv4-address;
                                                    description "Server IP Address";
                                                }
                                                leaf pktsReceiveFromClient {
                                                    type "uint32";
                                                    config "false";
                                                    description "Packets count received from DHCP Client.";
                                                }
                                                leaf discoverPktsReceive {
                                                    type "uint32";
                                                    config "false";
                                                    description "Received Discovery packets count.";
                                                }
                                                leaf requestPktsReceive {
                                                    type "uint32";
                                                        config "false";
                                                        description "Received Request packets count.";
                                                }
                                                leaf releasePktsReceive {
                                                    type "uint32";
                                                        config "false";
                                                        description "Received Release packets count.";
                                                }
                                                leaf informPktsRecevie {
                                                    type "uint32";
                                                        config "false";
                                                        description "Received Inform packets count.";
                                                }
                                                leaf declinePktsReceive {
                                                    type "uint32";
                                                        config "false";
                                                        description "Received Decline packets count.";
                                                }
                                                leaf pktsReceiveFromServers {
                                                    type "uint32";
                                                        config "false";
                                                        description "Count of all packets received from server.";
                                                }
                                                leaf offerPktsReceive {
                                                    type "uint32";
                                                        config "false";
                                                        description "Offer packets count.";
                                                }
                                                leaf ackPktsReceive {
                                                    type "uint32";
                                                        config "false";
                                                        description "Received Ack packets count.";
                                                }
                                                leaf nakPktsReceive {
                                                    type "uint32";
                                                        config "false";
                                                        description "Received Nak packets count.";
                                                }
                                                leaf pktsSentToServers {
                                                    type "uint32";
                                                        config "false";
                                                        description "Packets sent to DHCP Servers.";
                                                }
                                                leaf pktsSentToClients {
                                                    type "uint32";
                                                        config "false";
                                                        description "Packets sent to DHCP Clients.";
                                                }
                                                leaf unicastPktsSentToClients {
                                                    type "uint32";
                                                        config "false";
                                                        description "Unicast packets sent to DHCP Clients.";
                                                }
                                                leaf broadcastPktsSentToClients {
                                                    type "uint32";
                                                        config "false";
                                                        description "Broadcast packets sent to DHCP Clients.";
                                                }
                                        }
                                }

                        }

                }

                container dhcpRelayStatistics {
                  description "This is the state data of the running situation of the relay devices/interfaces.";

                         leaf badPacketsRecvd {
                            type "uint32";
                                config "false";
                                description "Received bad packets count.";
                        }
                        leaf packetsRecvdFromClient {
                            type "uint32";
                                config "false";
                                description "Packets received from DHCP Client.";
                        }
                        leaf discoverPacketsRecvd {
                            type "uint32";
                                config "false";
                                description "Received Discovery packets count.";
                        }
                        leaf requestPacketsRecvd {
                            type "uint32";
                                config "false";
                                description "Received Request packets count.";
                        }
                        leaf informPacketsRecvd {
                            type "uint32";
                                config "false";
                                description "Received Inform packets count.";
                        }
                        leaf declinePacketsRecvd {
                            type "uint32";
                                config "false";
                                description "Received Decline packets count.";
                        }
                        leaf releasePacketsRecvd {
                            type "uint32";
                                config "false";
                                description "Received Release packets count.";
                        }
                        leaf packetsRecvdFromServers {
                            type "uint32";
                                config "false";
                                description "Packets received from DHCP Servers.";
                        }
                        leaf offerPacketsRecvd {
                            type "uint32";
                                config "false";
                                description "Received Offer packets count.";
                        }
                        leaf ackPacketsRecvd {
                            type "uint32";
                                config "false";
                                description "Received Ack packets count.";
                        }
                        leaf nakPacketsRecvd {
                            type "uint32";
                                config "false";
                                description "Received Nak packets count.";
                        }
                        leaf packetsSentToServers {
                            type "uint32";
                                config "false";
                                description "Packets sent to DHCP Servers.";
                        }
                        leaf packetsSentToClients {
                            type "uint32";
                                config "false";
                                description "Packets sent to DHCP Clients.";
                        }
                        leaf unicastPacketsSentToClients {
                            type "uint32";
                                config "false";
                                description "Unicast packets sent to DHCP Clients.";
                        }
                        leaf broadcastPacketsSentToClients {
                            type "uint32";
                                config "false";
                                description "Broadcast packets sent to DHCP Clients.";
                        }
                        leaf releasePacketsSentToServers {
                            type "uint32";
                                config "false";
                                description "Release packets sent to DHCP Servers.";
                        }
                        leaf sendRenewPacket {
                            type "uint32";
                                config "false";
                                description "Renew packets sent.";
                        }
                }

        }

        container server {
          description "This is the top level container. Server is configured parallel with Relay.";

                container common {
                  description "This is some basic configuration of DHCP Server.";

                         leaf pingPacketNumber{
                                type uint8 {
                                        range "0..10";
                                }

                                default "0";
                                description "Ping packet number";
                        }
                        leaf pingPacketTimeOut {
                                type uint16 {
                                        range "0..10000";
                                }

                                default "500";
                                description "Ping packet timeout";
                        }
                }

                container globalIpPool {
                  description "This is the global IP pool could be used by the DHCP Server.";

                        list globalIpPool {
                          key "ipPoolName";
                          description "Multiple global IP pools could be used by a single DHCP Server.";

                                leaf ipPoolName {
                                        type string {
                                                length "1..64";
                                        }

                                        description "IP pool name";
                                }
                                leaf vpnInstance {
                                        type string {
                                                length "1..31";
                                        }

                                        description "VPN name";
                                }
                                container gatewayIp {
                                  description "Gateway IP addresses.";
                                         leaf gatewayIp {
                                                type inet:ipv4-address;

                                                description "Gateway IP Address";
                                        }
                                        leaf gatewayMask {
                                                type inet:ipv4-address;

                                                description "Gateway IP Address Mask";
                                        }
                                }

                                container sections {
                                  description "An address pool could be contrusted by multiple address sections.";

                                        list section {
                                          key "sectionIndex";
                                          description "An address section.";

                                                leaf sectionIndex {
                                                        type uint16 {
                                                                range "0..255";
                                                        }

                                                        description "Section Index";

                                                }
                                                leaf sectionStartIp {
                                                        type inet:ipv4-address;

                                                        mandatory "true";
                                                        description "IP Address";
                                                }
                                                leaf sectionEndIp {

                                                        type inet:ipv4-address;
                                                        description "IP Address";
                                                }

                                                container ipPoolSectionStat {
                                                  description "Statistics of the usage of the address sections.";

                                                         leaf usedIpCount {
                                                                type uint32;
                                                                config "false";
                                                                description "Used Ip Count";
                                                        }
                                                        leaf idleIpCount {
                                                                type uint32;
                                                                config "false";
                                                                description "Idle Ip Count";
                                                        }
                                                        leaf conflictIpCount {
                                                                type uint32;
                                                                config "false";
                                                                description "Conflict Ip Count";
                                                        }
                                                        leaf totalIpCount {
                                                                type uint32;
                                                                config "false";
                                                                description "Total Ip Count";
                                                        }
                                                }

                                        }

                                }

                                container leaseTime {
                                    description "Specifies the lease time, option code is 51.";
                                         leaf day {
                                                type uint16 {
                                                        range "0..49710";
                                                }

                                                default "1";
                                                description "Day";
                                        }
                                        leaf hour {
                                                type uint8  {
                                                        range "0..23";
                                                }

                                                default "0";
                                                description "Hour";
                                        }
                                        leaf minute {
                                                type uint8 {
                                                        range "0..59";
                                                }

                                                default "0";
                                                description "Minute";
                                        }
                                }

                                leaf-list domainNameServer {
                                        type inet:ipv4-address;

                                        description "Specifies the domain name server, option code is 5.";
                                }

                                leaf domainName {
                                        type string {
                                                length "1..255";
                                        }

                                        description "Specifies the domain name, option code is 15.";
                                }

                                leaf-list NbnsServer {
                                        type inet:ipv4-address;

                                        description "Specifies the NetBIOS name server, option code is 44.";
                                }

                                leaf NbNodeType {
                                       type enumeration {
                                                enum B-node {
                                                        value "1";
                                                        description "NetBIOS node type B.";
                                                }
                                                enum P-node {
                                                        value "2";
                                                        description "NetBIOS node type P.";
                                                }
                                                enum M-node {
                                                    value "4";
                                                    description "NetBIOS node type M.";
                                                }
                                                enum H-node {
                                                    value "8";
                                                    description "NetBIOS node type H.";
                                                }
                                        }

                                        description "Specifies the NetBIOS node type, option code is 46.";
                                }

                            container UserDefOptions {
                              description "This model supports user defined DHCP options";

                                    list UserDefOption {
                                            key "optionCode";
                                            description "Specifieds the user defined DHCP options";

                                             leaf optionCode {
                                                    type uint8 {
                                                            range "2 | 4..5 | 7..14 | 16..43 | 47..49 | 56 | 62..81 | 83..254";
                                                    }

                                                    description "The option code of the user defined option";
                                            }

                                            leaf-list ipAddress {
                                                    type inet:ipv4-address;

                                                    description "IP address list";
                                            }

                                            leaf optionString {
                                                        type string {
                                                        length "1..254";
                                                }

                                                    description "User defined option string";
                                            }

                                            leaf optionHex {
                                                        type string {
                                                        length "2..508";
                                                }

                                                    description "User defined option HEX string";
                                            }

                                    }
                            }

                                container ipPoolStat {
                                  description "Statistics of the IP address pool.";

                                         leaf usedIpCount {
                                                type uint32;
                                                config "false";
                                                description "Used Ip Count";
                                        }
                                        leaf idleIpCount {
                                                type uint32;
                                                config "false";
                                                description "Idle Ip Count";
                                        }
                                        leaf conflictIpCount {
                                                type uint32;
                                                config "false";
                                                description "Conflict Ip Count";
                                        }
                                        leaf totalIpCount {
                                                type uint32;
                                                config "false";
                                                description "Total Ip Count";
                                        }
                                }

                        }

                }

                container packetStatistics {
                  description "Packet statistics.";

                         leaf clientRequestCount {
                                type uint32;
                                config "false";
                                description "Client Request Count";
                        }
                        leaf discoverCount {
                                type uint32;
                                config "false";
                                description "Discover Count";
                        }
                        leaf requestCount {
                                type uint32;
                                config "false";
                                description "Request Count";
                        }
                        leaf declineCount {
                                type uint32;
                                config "false";
                                description "Decline Count";
                        }
                        leaf releaseCount {
                                type uint32;
                                config "false";
                                description "Release Count";
                        }
                        leaf informCount {
                                type uint32;
                                config "false";
                                description "Inform Count";
                        }
                        leaf serverReplyCount {
                                type uint32;
                                config "false";
                                description "Server Reply Count";
                        }
                        leaf offerCount {
                                type uint32;
                                config "false";
                                description "Offer Count";
                        }
                        leaf ackCount {
                                type uint32;
                                config "false";
                                description "Ack Count";
                        }
                        leaf nakCount {
                                type uint32;
                                config "false";
                                description "Nak Count";
                        }
                }

        }

        container client {
          description "This is the top container. Client is configured in parallel with DHCP Relay and Server.";

                container dhcpClientIf {
                  description "Client is also configured per interface.";

                        list dhcpClientIf {
                          key "ifName";
                          description "Client configuration elements of one interface.";

                                leaf ifName {
                                        type "string";

                                        description "Specify the interface name that dhcp client configured on";
                                }

                                leaf enable {
                                        type "boolean";
                                        default "false";

                                        description "Enable or disable dhcp client function";
                                }

                                container dhcpClientStatus {

                                    description "Specify the status of DHCP client on the interface";

                                    leaf status {
                                            type enumeration {
                                                    enum Init {
                                                     description "Initial packets count.";
                                                    }
                                                    enum Discoverying {
                                                     description "Discovery packets count.";
                                                    }
                                                    enum Offered {
                                                     description "Offer packets count.";
                                                    }
                                                    enum Requesting {
                                                     description "Request packets count.";
                                                    }
                                                    enum Acked {
                                                     description "Ack packets count.";
                                                    }
                                                }
                                                config "false";
                                                description "Specify the status of DHCP client on the interface";
                                        }

                                    leaf clientIpAddr {
                                                type inet:ipv4-address;
                                                config "false";
                                                description "Specify the IP address obtained from DHCP server on the interface";
                                        }

                                        leaf-list dnsServerIpAddr {
                                                type inet:ipv4-address;
                                                config "false";
                                                description "Specify the DNS server IP address obtained from DHCP server on the interface";
                                    }

                                }

                                container dhcpClientIfStatistics {

                                        description "Specify the statistics of DHCP client send or receive packets on the interface";

                                    leaf discoverCount {
                                        type uint32;
                                        config "false";
                                        description "Discover Count";
                                }

                                        leaf requestCount {
                                                type uint32;
                                                config "false";
                                                description "Request Count";
                                        }

                                        leaf declineCount {
                                                type uint32;
                                                config "false";
                                                description "Decline Count";
                                        }

                                        leaf releaseCount {
                                                type uint32;
                                                config "false";
                                                description "Release Count";
                                        }

                                        leaf informCount {
                                                type uint32;
                                                config "false";
                                                description "Inform Count";
                                        }

                                    leaf offerCount {
                                                type uint32;
                                                config "false";
                                                description "Offer Count";
                                        }

                                        leaf ackCount {
                                                type uint32;
                                                config "false";
                                                description "Ack Count";
                                        }

                                        leaf nakCount {
                                                type uint32;
                                                config "false";
                                                description "Nak Count";
                                        }

                                }
                        }

                }

        }

}
