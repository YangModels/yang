module ietf-system-aaa {
  yang-version 1.1;
  namespace "urn:ietf:params:xml:ns:yang:ietf-system-aaa";
  prefix sys-aaa;

  import ietf-system {
    prefix sys;
    reference "RFC 7317: A YANG Data Model for System Management";
  }
  import ietf-netconf-acm {
    prefix nacm;
  }

  organization
    "IETF Opsawg (Operations and Management Area Working Group)";
  contact
    "WG Web:   <http://tools.ietf.org/wg/opsawg/>
     WG List:  <mailto:opsawg@ietf.org>

     Editor:   Guangying Zheng
               <mailto:zhengguangying@huawei.com>";
  description
    "This module provides configuration of system AAA.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see the RFC
      itself for full legal notices.";

  revision 2019-03-06 {
    description
      "Initial revision.";
    reference "foo";
  }

  feature authorization {
    description
      "Indicates that the device supports configuration of
       user authorization.";
  }

  feature accouting {
    description
      "Indicates that the device supports configuration of
       user accouting.";
  }

  identity authorization-method {
    description
      "Base identity for user authorization methods.";
  }

  identity accouting-method {
    description
      "Base identity for user accouting methods.";
  }

  identity tacacs {
    base sys:authentication-method;
    base authorization-method;
    base accouting-method;
    description
      "Indicates AAA operation using TACACS+.";
    reference "draft-ietf-opsawg-tacacs-11: The TACACS+ Protocol";
  }

  identity local-users {
    base sys:authentication-method;
    base authorization-method;
    base accouting-method;
    description
      "Indicates accouting of locally
       configured users.";
  }

  identity aaa_accounting_event_type {
    description
      "Base identity for specifying events types that should be
       sent to AAA server for accounting";
  }

  identity aaa_accounting_event_command {
    base aaa_accounting_event_type;
    description
      "Specifies interactive command events for AAA accounting";
  }

  identity aaa_authorization_event_type {
    description
      "Base identity for specifying activities that should be
       sent to AAA server for authorization";
  }

  identity aaa_authorization_event_command {
    base aaa_authorization_event_type;
    description
      "Specifies interactive command events for AAA authorization";
  }

  augment "/sys:system" {
    description
      "Augment the system model with authorization and accounting
         attribuets
       Augment the system model with the tacacs model";
    container authorization {
      nacm:default-deny-write;
      if-feature "authorization";
      description
        "The authorization configuration subtree.";
      leaf-list user-authorization-order {
        type identityref {
          base authorization-method;
        }
        ordered-by user;
        description
          "When the device authorize a user, it tries the authorization
           methods in this leaf-list in order.  If authorization with
           one method fails, the next method is used. If no method
           succeeds, the user is denied access.

           If the 'tacacs-authentication' feature is advertised by
           the NETCONF server, the 'tacacs' identity can be added to
           this list.
           If the 'local-users' feature is advertised by the
           NETCONF server, the 'local-users' identity can be
           added to this list.";
      }
      container events {
        description
          "The container contains an set of authorization events";
        list event {
          key "event-type";
          description
            "List of events of AAA authorization";
          leaf event-type {
            type identityref {
              base aaa_authorization_event_type;
            }
            description
              "The type of event to record at the AAA authorization
               server";
          }
        }
      }
    }
    container accouting {
      nacm:default-deny-write;
      if-feature "accouting";
      description
        "The accouting configuration subtree.";
      leaf-list user-accouting-order {
        type identityref {
          base accouting-method;
        }
        ordered-by user;
        description
          "When the device audit a user with a password,
           it tries the accouting methods in this leaf-list in
           order. The accouting method may be specified as TACACS+
           servers, or the local.";
      }
      container events {
        description
          "The container contains an set of accouting events";
        list event {
          key "event-type";
          description
            "List of events of accounting";
          leaf event-type {
            type identityref {
              base aaa_accounting_event_type;
            }
            description
              "The type of activity to record at the AAA accounting
               server";
          }
          leaf record {
            type enumeration {
              enum start_stop {
                description
                  "Send START record to the accounting server at the
                   beginning of the activity, and STOP record at the
                   end of the activity.";
              }
              enum stop {
                description
                  "Send STOP record to the accounting server when the
                   user activity completes";
              }
            }
            description
              "Type of record to send to the accounting server for this
               activity type";
          }
        }
      }
    }
  }
}
