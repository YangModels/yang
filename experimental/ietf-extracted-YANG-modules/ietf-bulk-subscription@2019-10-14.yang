module ietf-bulk-subscription {
  yang-version 1.1;
  namespace "urn:ietf:params:xml:ns:yang:ietf-bulk-subscription";
  prefix bs;

  import ietf-subscribed-notifications {
    prefix sn;
  }
  import ietf-yang-types {
    prefix yang;
  }

  organization
    "IETF NETCONF (Network Configuration) Working Group";
  contact
    "";
  description
    "NETCONF Protocol Data Types and Protocol Operations.

     Copyright (c) 2011 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6241; see
     the RFC itself for full legal notices.";

  revision 2019-10-14 {
    description
      "Initial revision";
    reference
      "FOO";
  }

  container groups {
    list group {
      key "group-id";
      leaf group-id {
        type string;
        description
          "This group ID is used as an index within the bulk subscription module";
      }
      leaf-list stream {
        type string;
        description
          "A continuous, chronologically ordered set of events aggregated under some context";
      }
      description
        "List for group that classify different event streams into groups.";
    }
    description
      "Container for event stream group";
  }
  augment "/sn:subscriptions/sn:subscription/sn:target" {
   case stream-group {
    leaf group-id {
      type leafref {
        path "/bs:groups/bs:group/bs:group-id";
      }
      description
        "This group ID is used to associate subscription with a group of streams";
    }
    description
      "Augment the subscribed-notifications module with event stream group inforamtion.";
   }
  }
  augment "/sn:establish-subscription/sn:input/sn:target" {
   case stream-group {
    leaf group-id {
      type leafref {
        path "/bs:groups/bs:group/bs:group-id";
      }
      description
        "This group ID is used to associate subscription with a group of streams";
    }
    description
      "Augment the establish-subscription RPC with event stream group inforamtion.";
   }
  }
}
