module ietf-bfd-stability {
  yang-version 1.1;
  namespace "urn:ietf:params:xml:ns:yang:ietf-bfd-stability";
  prefix "bfds";

  import ietf-yang-types {
    prefix "yang";
    reference
      "RFC 6991: Common YANG Data Types";
  }

  import ietf-routing {
    prefix "rt";
    reference
      "RFC 8349: A YANG Data Model for Routing Management
       (NMDA version)";
  }

  import ietf-bfd {
    prefix bfd;
    reference
      "I-D.ietf-bfd-yang: YANG Data Model for Bidirectional
       Forwarding Detection.";
  }

  import ietf-bfd-ip-sh {
    prefix bfd-ip-sh;
    reference
      "I-D.ietf-bfd-yang: YANG Data Model for Bidirectional
       Forwarding Detection.";
  }

  import ietf-bfd-ip-mh {
    prefix bfd-ip-mh;
    reference
      "I-D.ietf-bfd-yang: YANG Data Model for Bidirectional
       Forwarding Detection.";
  }

  import ietf-bfd-lag {
    prefix bfd-lag;
    reference
      "I-D.ietf-bfd-yang: YANG Data Model for Bidirectional
       Forwarding Detection.";
  }

  import ietf-te {
    prefix te;
    reference
      "I-D.ietf-teas-yang: TE YANG Data Model.";
  }

  import ietf-bfd-mpls {
    prefix bfd-mpls;
    reference
      "I-D.ietf-bfd-yang: YANG Data Model for Bidirectional
       Forwarding Detection.";
  }

  organization
    "IETF BFD Working Group";

  contact
    "WG Web:   <http://tools.ietf.org/wg/bfd>
     WG List:  <bfd@ietf.org>

     Authors: Mahesh Jethanandani (mjethanandani at gmail dot com)
              Ashesh Mishra (mishra dot ashesh at gmail dot com)
              Ankur Saxena (ankurpsaxena at gmail dot com)
              Santosh Pallagatti (santosh dot pallagati at gmail dot
              com)
              Mach Chen (mach dot chen at huawei dot com)
              Peng Fan (fanp08 at gmail dot com).";

  description
    "This YANG module augments the base BFD YANG model to add
     attributes related to BFD Stability. In particular it adds a
     a per session count for BFD packets that are lost.

     Copyright (c) 2021 IETF Trust and the persons identified as
     the document authors.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "2021-02-24" {
    description
      "Initial Version.";
    reference
      "RFC XXXX, BFD Stability.";
  }

  augment "/rt:routing/rt:control-plane-protocols/" +
          "rt:control-plane-protocol/bfd:bfd/bfd-ip-sh:ip-sh/" +
          "bfd-ip-sh:sessions/bfd-ip-sh:session/" +
          "bfd-ip-sh:session-statistics" {
    leaf lost-packet-count {
      type yang:counter32;
      description
        "Number of BFD packets that were lost without bringing the
         session down.";
    }
    description
      "Augment the 'bfd' container to add attributes related to BFD
       stability.";
  }

  augment "/rt:routing/rt:control-plane-protocols/" +
          "rt:control-plane-protocol/bfd:bfd/bfd-ip-mh:ip-mh/" +
          "bfd-ip-mh:session-groups/bfd-ip-mh:session-group/" +
          "bfd-ip-mh:sessions/bfd-ip-mh:session-statistics" {
    leaf lost-packet-count {
      type yang:counter32;
      description
        "Number of BFD packets that were lost without bringing the
         session down.";
    }
    description
      "Augment the 'bfd' container to add attributes related to BFD
       stability.";
  }

  augment "/rt:routing/rt:control-plane-protocols/" +
          "rt:control-plane-protocol/bfd:bfd/bfd-lag:lag/" +
          "bfd-lag:sessions/bfd-lag:session/bfd-lag:member-links/" +
          "bfd-lag:micro-bfd-ipv4" {
    leaf lost-packet-count {
      type yang:counter32;
      description
        "Number of BFD packets that were lost without bringing the
         session down.";
    }
    description
      "Augment the 'bfd' container to add attributes related to BFD
       stability.";
  }

  augment "/rt:routing/rt:control-plane-protocols/" +
          "rt:control-plane-protocol/bfd:bfd/bfd-lag:lag/" +
          "bfd-lag:sessions/bfd-lag:session/bfd-lag:member-links/" +
          "bfd-lag:micro-bfd-ipv6" {
    leaf lost-packet-count {
      type yang:counter32;
      description
        "Number of BFD packets that were lost without bringing the
         session down.";
    }
    description
      "Augment the 'bfd' container to add attributes related to BFD
       stability.";
  }

  augment "/te:te/te:lsps/te:lsp" {
    leaf lost-packet-count {
      type yang:counter32;
      description
        "Number of BFD packets that were lost without bringing the
         session down.";
    }
    description
      "Augment the 'bfd' container to add attributes related to BFD
       stability.";
  }

  augment "/rt:routing/rt:control-plane-protocols/" +
          "rt:control-plane-protocol/bfd:bfd/bfd-mpls:mpls/" +
          "bfd-mpls:session-groups/bfd-mpls:session-group/" +
          "bfd-mpls:sessions" {
    leaf lost-packet-count {
      type yang:counter32;
      description
        "Number of BFD packets that were lost without bringing the
         session down.";
    }
    description
      "Augment the 'bfd' container to add attributes related to BFD
       stability.";
  }
}
