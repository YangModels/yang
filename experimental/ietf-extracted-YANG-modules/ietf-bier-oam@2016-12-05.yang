module ietf-bier-oam {
    namespace "urn:ietf:params:xml:ns:yang:ietf-bier-oam";
    prefix bieroam;

    import ietf-bier {
      prefix bier;
    }

    import ietf-connectionless-oam {
      prefix coam;
    }
        import ietf-network{
      prefix nd;
    }

     organization
       "IETF BIER(Bit Indexed Explicit Replication ) Working Group";

     contact
        "WG List:  <mailto:bier@ietf.org>
        WG Chair: Tony Przygienda
                  <mailto:tonysietf@gmail.com>
        WG Chair: Greg Shepherd
                  <mailto:gjshep@gmail.com>
        Editor:   Fangwei Hu
                   <mailto:hu.fangwei@zte.com.cn>
        Editor:   Ran Chen
                   <mailto:chen.ran@zte.com.cn>
        Editor:   Rong Gu
                   <mailto:gurong@chinamobile.com>
        ";

        description
         "The YANG module defines BIER OAM data model.";

         revision 2016-12-05{
         description
           "00 revision";
         reference
           "draft-hu-bier-oam-yang-00";
       }

      typedef bier-bsl {
       type leafref {
                path "/bier:bier/bier:bier-global/bier:sub-domain/bier:bitstringlength";
                }
         description "bsl type";
     }

     typedef bier-subdomainid {
       type leafref {
                path "/bier:bier/bier:bier-global/bier:sub-domain/bier:sub-domain-id";
         }
         description "sub-domain-id type";
      }

      typedef bier-bfrid {
       type leafref {
                path "/bier:bier/bier:bier-global/bier:sub-domain/bier:bfr-id";
                }
         description "bfr-id type";

     }

    identity bier-type {
      base coam:tp-address-type;
      description "bier type";
    }

     augment "/nd:networks/nd:network/nd:node/coam:location-type/coam:ip-prefix-location-type"
         +"/coam:test-point-ip-prefix-location-list/coam:test-point-locations" {
           container bier-test-point-location-list {
             list test-point-locations {
                key "bier-bsl bier-subdomainid bier-bfrid";

                leaf bier-bsl {
                   type bier-bsl;
                   description "bier bsl";
                 }

                leaf bier-subdomainid {
                    type bier-subdomainid;
                    description "bier sub-domain id";
                 }

                leaf bier-bfrid {
                     type bier-bfrid;
                     description "bfr id";
                 }

               description "test point locations list ";
             }
             description "bier-test-point-location-list";
            }
           description "bier-location-type";
    }

     augment "/nd:networks/nd:network/nd:node/coam:location-type/coam:ip-prefix-location-type"
         +"/coam:test-point-ip-prefix-location-list/coam:test-point-locations/coam:technology" {
      case bier-oam-string{
           leaf bier-icmp{
            type string;
                description
                "bier icmp";
           }
           description  "bier oam icmp case.";
          }
      description "bier icmp technology.";
        }

    augment "/nd:networks/nd:network/nd:node/coam:location-type/coam:ip-prefix-location-type"
         +"/coam:test-point-ip-prefix-location-list/coam:test-point-locations/coam:oam-layers" {
        container af {
          list ipv4 {
           key "bitstringlength bier-mpls-label-base";
           uses bier:bier-mpls-cfg;
           description
           "Defines the necessary label ranges per bitstring length in ipv4.";
          }
           list ipv6 {
            key "bitstringlength bier-mpls-label-base";
            uses bier:bier-mpls-cfg;
            description
            "Defines the necessary label ranges per bitstring length in ipv6.";
          }
             description    "Bier mapping entries.";
        }
             description "bier af.";
   }
  }
