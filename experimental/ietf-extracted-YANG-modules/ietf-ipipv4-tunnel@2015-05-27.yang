module ietf-ipipv4-tunnel {

  namespace "urn:ietf:params:xml:ns:yang:ietf-ipipv4-tunnel";

  prefix "v4tln";

  import ietf-interfaces {

    prefix "if";

  }

  import ietf-inet-types {
    prefix inet;

  }

  import ietf-routing {

    prefix "rt";

  }

  organization

    "Ericsson.";

  contact

    "Mandy.Liu@ericsson.com

   Adam.Foldes@ericsson.com";

  description

    "This YANG model defines the configuration data

   and operational state data for generic IPv4/6-in-IPv4 tunnel.

   It includes the IPv4 in IPv4, IPv6 to IPv4

   auto and IPv6 over IPv4 manual tunnels.";

  revision 2015-05-27 {

    description

      "Initial revision.";

    reference
      "RFC XXXX: A YANG Data Model for IPv4 Tunnel.";

  }

  /* Grouping for tunnel */

  grouping tunnel-components {

    description

      "Specify the IP addresses of the local and

      remote tunnel endpoint interfaces. Bind the

      tunnel circuit interface to the tunnel. Enable

      the tunnel.";

    leaf name {

      type string {

        length "1..50";

      }

      description

        "Name of the tunnel.";

    }

    leaf description {

      type string {

        length "1..255";

      }

      description

        "Textual description for a tunnel. Can be any "+

        "alphanumeric string, including spaces, not to exceed "+
        "255 ASCII characters.";

    }

    leaf bind-interface {

      type if:interface-ref;

      description

         "Bind to an interface.";

    }

    leaf clear-df {

      type empty;

      description

        "Clears the IP header Don't Fragment (DF) flag

        in all packets that are transmitted on a tunnel.";

    }

    leaf shutdown {

      type empty;

      description

        "Disable/enable the tunnel.";

    }

    leaf mtu {

      type uint16 {

        range "256..16384";

      }

      description

        "Sets the Maximum Transmission Unit (MTU) size for
        packets sent in a tunnel. The default MTU is the MTU

        for the interface to which the tunnel is bound.";

    }

   leaf mirror-destination {

      type string {

        length "1..39";

      }

      description

        "Designate the name of a tunnel as a circuit

      mirror destination. ";

    }

  }

  /*Configuration Data*/

  container tunnels {

    description

     "Configuration data for tunnels.";

    list ip-in-ip {

      key "name";

      description

        "Configuration of ip-in-ip tunnel.";

      uses tunnel-components;

     container peer-end-point {

        description

         "Assigns IP addresses to tunnel endpoints.";
        leaf local {

          type inet:ipv4-address-no-zone;

          description

            "IP address of the local end of the tunnel.";

        }

        leaf remote {

          type inet:ipv4-address-no-zone;

          description

            "IP address of the remote end of the tunnel.";

        }

       leaf routing-instance {

          type rt:routing-instance-ref;

          description

            "Name of the reference routing instance. ";

        }

      }

    }

    list ipv6to4-auto {

      key "name";

      description

        "Configuration of the 6to4-auto model tunnel.";

      uses tunnel-components;

     container peer-end-point {

        description
         "Assigns IP addresses to tunnel endpoints.";

        leaf local {

          type inet:ipv4-address-no-zone;

          description

            "IP address of the local end of the tunnel.";

        }

      }

    }

    list ipv6v4-manual {

      key "name";

      description

        "Configuration of IPv6-over-v4 manual model tunnel.";

      uses tunnel-components;

     container peer-end-point {

        description

         "Assigns IP addresses to tunnel endpoints.";

        leaf local {

          type inet:ipv4-address-no-zone;

          description

            "IP address of the local end of the tunnel.";

        }

        leaf remote {

          type inet:ipv4-address-no-zone;

          description
            "IP address of the remote end of the tunnel.";

        }

       leaf routing-instance {

          type rt:routing-instance-ref;

          description

            "Name of the reference routing instance. ";

        }

      }

    }

  }

  /*Operational state data*/

  grouping tunnel-state-components {

    description

     "The basic tunnel information to be displayed.";

    leaf name {

      type string {

        length "1..50";

      }

      description

        "Name of the tunnel.";

    }

    leaf local-ip {

      type inet:ipv4-address-no-zone;

      description

        "IP address of the local end of the tunnel.";

    }

    leaf remote-ip {

      type inet:ipv4-address-no-zone;

      description

        "IP address of the remote end of the tunnel.";

    }

    leaf state {

      type enumeration {

        enum Down {

        description

          "Tunnel down state.";

        }

        enum Up {

          description

            "Tunnel up state.";

        }

        enum Shutdown {

          description

            "Tunnel shutdown state.";

        }
      }

      description

        "Indicate the state of the tunnel.";

    }

    leaf bind-interface {

      type if:interface-state-ref;

      description

        "Bind to an interface.";

    }

    leaf user-configured {

      type boolean;

       description

        "Indicate the tunnel is user-configured or dynamic.

        False is for dynamic.";

    }

    leaf routing-instance {

          type rt:routing-instance-ref;

          description

            "Name of the reference routing instance. ";

    }

    leaf mtu {

      type uint16;

      description

        "The Maximum Transmission Unit (MTU) size for
      packets sent in a tunnel.";

    }

    leaf clear-df {

      type empty;

      description

        "Indicate that the DF bit is cleared.";

    }

    leaf tunnel-id {

      type uint32;

      description

        "Tunnel id.";

    }

    leaf down-reason {

      type string;

      description

        "The reason of the tunnel is down.";

    }

    leaf resolved-interface-name{

      type string;

      description

        "The egress interface name of the tunnel.";

    }

  }

  container tunnel-state {

    config "false";

    description

      "Contain the information currently configured tunnels.";

    list ip-in-ip {

      description

        "Operational state data of ip-in-ip tunnel.";

      uses tunnel-state-components;

    }

    list ipv6to4-auto {

      description

        "Operational state data of the 6to4-auto tunnel.";

      uses tunnel-state-components;

    }

    list ipv6v4-manual {

      description

        "Operational state data of IPv6v4-manual tunnel.";

      uses tunnel-state-components;

    }

  }

  //Augment operational state data of IP interfaces

  augment "/if:interfaces-state/if:interface" {

    when "if:type = 'ianaift:tunnel'" {
      description

        "Augment IP interface.";

    }

    description

      "Augment operational state data of IP interfaces.";

    leaf tunnel {

      type enumeration {

        enum ip-ip {

          description

            "IPv4-in-IPv4 tunnel interface.";

        }

        enum ipv6v4-manual {

          description

            "IPv6v4-manual tunnel interface.";

        }

        enum ipv6to4-auto {

          description

            "The 6to4-auto tunnel interface.";

        }

      }

      description

        "Indicate the type of the IP tunnel interface.";

    }

  }
}// end of module ietf-ipipv4-tunnel
