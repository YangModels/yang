module alps {
     yang-version 1;
     namespace "urn:TBD:params:xml:ns:yang:ietf-alps";
     prefix alps;
     import ietf-yang-types { prefix yang;}
     organization "";
     contact "@huawei.com";
     description
       "This module defines alps yang data model";

    typedef alps-demand-type {
        type string;
        description "demand type";
    }

    typedef alps-demand-group-oper-type {
        type string;
        description "demand group operation type";
    }

    typedef alps-endpoint-type {
        type string;
        description "endpoint type";
    }

    typedef alps-endpoint-group-type {
        type string;
        description "endpoint group type";
    }

    typedef alps-connection-direction-type {
        type string;
        description "connection direction type";
    }
    list demand {
	    description "defines a list of demand.";
        key "name";
		leaf name {
		    type string;
            description "";
		}
		leaf demand-type {
		    type alps-demand-type;
            description "";
		}
		leaf priority {
		    type uint32;
            description "";
		}
		container clause {
		}
                  container event {
		}
    }

    list demand-group {
	    description "defines a list of demand group.";
        key "name";
		leaf name {
		    type string;
            description "";
		}
		leaf-list demand-name {
		    type string;
            description "";
		}
		container operation {
		    leaf all {
                           type boolean;
            description "";
                      }
                      container expression {
                      } 
		}
    }

    list endpoint {
	    description "defines a list of endpoint.";
        key "name";
		leaf name {
		    type string;
            description "";
		}
		leaf endpoint-type {
		    type alps-endpoint-type;
            description "";
		}
		leaf demand-group-name {
		    type string;
            description "";
		}
		container attribute {
		}
    }

	list endpoint-group {
	    description "defines a list of endpoint group.";
        key "name";
		leaf name {
		    type string;
            description "";
		}
		leaf endpoint-group-type {
		    type alps-endpoint-group-type;
            description "";
		}
		leaf-list endpoint-name {
		    type string;
            description "";
		}
		leaf demand-group-name {
		    type string;
            description "";
		}
    }

	list connection {
	    description "defines a list of endpoint connection.";
        key "name";
		leaf name {
		    type string;
            description "";
		}
		leaf direction {
		    type alps-connection-direction-type;
            description "";
		}
		leaf-list endpoint-group-name {
		    type string;
            description "";
		}
		leaf demand-group-name {
		    type string;
            description "";
		}
    }
}
