module ietf-te-service-mapping {

       namespace "urn:ietf:params:xml:ns:yang:ietf-te-service-mapping";

       prefix "tm";

       import ietf-l3vpn-svc {
           prefix "l3";
       }

       import ietf-l2vpn-svc {
           prefix "l2";
       }

       import ietf-l1csm {
           prefix "l1";
       }

       import ietf-actn-vn {
           prefix "vn";
       }

       organization
           "IETF Traffic Engineering Architecture and Signaling (TEAS)
           Working Group";

       contact
           "Editor: Young Lee <leeyoung@huawei.com>
                    Dhruv Dhody <dhruv.ietf@gmail.com>";
       description
           "This module contains a YANG module for the mapping of
           service (e.g. L3VPN) to the TE tunnels or ACTN VN.";

       revision 2018-02-21 {
           description
               "initial version.";
           reference
               "TBD";
       }

       /*
        * Identities
        */
       identity service-type {
           description
               "Base identity from which specific service types are
               derived.";
       }

       identity l3vpn-service {
           base service-type;
           description
               "L3VPN service type.";
       }

       identity l2vpn-service {
           base service-type;
           description
               "L2VPN service type.";
       }
       identity l1vpn-service {
           base service-type;
           description
               "L1VPN connectivity service type.";
       }
       /*
        * Enum
        */
       typedef map-type {
           type enumeration {
               enum "new" {
                   description
                       "The new VN/tunnels are binded to the service. Customer
could request a VN with a new VN/Tunnel not shared with other existing
services. This is to meet VPN isolation requirement. ";
               }
               enum "select" {
                   description
                       "The VPN service selects an existing tunnel with no
modification";
               }
               enum "modify" {
                   description
                       "The VPN service selects an existing tunnel and allows
to modify the properties of the tunnel (e.g., b/w) ";
                  }
           }
           description
               "The map-type";
       }

       /*
        * Groupings
        */
       grouping service-ref{
           description
               "The reference to the service.";
            choice service {
               description
                   "The service";
               case l3vpn {
                   leaf l3vpn-ref {
                       type leafref {
                           path "/l3:l3vpn-svc/l3:vpn-services/"
                           + "l3:vpn-service/l3:vpn-id";
                       }
                       description
                           "The reference to L3VPN Service Yang Model";
                   }
               }
               case l2vpn {
                   leaf l2vpn-ref {
                       type leafref {
                           path "/l2:l2vpn-svc/l2:vpn-services/"
                           + "l2:vpn-svc/l2:vpn-id";
                       }
                       description
                           "The reference to L2VPN Service Yang Model";
                   }

               }
               case l1vpn {
                   leaf l1vpn-ref {
                       type leafref {
                           path "/l1:l1cs/l1:service/"
                           + "l1:service-list/l1:subscriber-l1vc-id";
                       }
                       description
                           "The reference to L1VPN Service Yang Model";
                   }

               }
            }
       }

       grouping site-ref {
           description
               "The reference to the site.";
            choice service {
               description
                   "The service choice";
               case l3vpn {
                   leaf l3vpn-ref{
                       type leafref {
                           path "/l3:l3vpn-svc/l3:sites/l3:site/"
                           + "l3:site-id";
                       }
                       description
                           "The reference to L3VPN Service Yang Model";
                   }
               }
               case l2vpn {
                   leaf l2vpn-ref{
                       type leafref {
                           path "/l2:l2vpn-svc/l2:sites/l2:site/"
                           + "l2:site-id";
                       }
                       description
                           "The reference to L2VPN Service Yang Model";
                   }

               }
               case l1vpn {
                   leaf l1vpn-ref{
                       type leafref {
                           path "/l1:l1cs/l1:access/l1:uni-list/"
                           + "l1:UNI-ID";
                       }
                       description
                           "The reference to L1VPN Connectivity Service Yang
Model";
                   }

               }

            }
       }

       grouping actn-vn-ref {
           description
               "The reference to ACTN VN.";
           leaf actn-vn-ref {
                type leafref {
                    path "/vn:actn/vn:vn/vn:vn-list/vn:vn-id";
                }
                description
                    "The reference to ACTN VN";
           }
       }

       grouping actn-ap-ref {
           description
               "The reference to ACTN endpoints (AP).";
           leaf actn-ap-ref {
                type leafref {
                    path "/vn:actn/vn:ap/vn:access-point-list"
                           + "/vn:access-point-id";
                    }
                    description
                        "The reference to ACTN AP";
           }
       }

       grouping service-mapping {
           description
               "Mapping between Services and TE";
           container service-mapping {
               description
                   "Mapping between Services and TE";

               list mapping-list {
                   key "map-id";
                   description
                       "Mapping identified via a map-id";
                   leaf map-id {
                       type uint32;
                       description
                           "a unique mapping identifier";
                   }
                   leaf map-type {
                       type map-type;
                       description
                           "Tunnel Bind or Tunnel Selection";
                   }
                   uses service-ref;

                   uses actn-vn-ref ;
               }
           }
       }
       grouping site-mapping {
           description
               "Mapping between VPN access site and ACTN AP";
           container site-mapping {
               description
                   "Mapping between VPN access site and ACTN AP";
               list mapping-list {
                   key "map-id";
                   description
                       "Mapping identified via a map-id";
                   leaf map-id {
                       type uint32;
                       description
                           "a unique mapping identifier";
                   }
                   uses site-ref;

                   uses actn-ap-ref ;
               }

           }
       }

       /*
        * Configuration data nodes
        */
       container te-service-mapping {
           description
               "Mapping between Services and TE";

           uses service-mapping;

           uses site-mapping;
       }

   }
