submodule ietf-bgp-common-structure {
  yang-version 1.1;
  belongs-to ietf-bgp {
    prefix bgp;
  }

  import ietf-routing-policy {
    prefix rt-pol;
    reference
      "RFC 9067: A YANG Data Model for Routing Policy Management.";
  }
  import iana-bgp-types {
    prefix bt;
    reference
      "RFC XXXX: YANG Model for Border Gateway Protocol (BGP-4).";
  }
  import ietf-inet-types {
    prefix inet;
    reference
      "RFC 6991: Common YANG Data Types.";
  }
  include ietf-bgp-common-multiprotocol;

  // meta

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jhaas at juniper.net).";

  description
    "This sub-module contains groupings that are common across
     multiple BGP contexts and provide structure around other
     primitive groupings.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2024-10-21 {
    description
      "Initial Version";
    reference
      "RFC XXXX: YANG Model for Border Gateway Protocol (BGP-4).";
  }

  grouping structure-neighbor-group-route-reflector {
    description
      "Structural grouping used to include route reflector
       configuration and state for both BGP neighbors and peer
       groups";
    container route-reflector {
      description
        "Route reflector parameters for the BGP peer-group";
      reference
        "RFC 4456: BGP Route Reflection.";
      leaf cluster-id {
        type bt:rr-cluster-id-type;
        description
          "Route Reflector cluster id to use when local router is
           configured as a route reflector.  Commonly set at the
           group level, but allows a different cluster id to be set
           for each neighbor.";
        reference
          "RFC 4456: BGP Route Reflection: An Alternative to
                     Full Mesh.";
      }
      leaf client {
        type boolean;
        default "false";
        description
          "Configure the neighbor as a route reflector client.";
        reference
          "RFC 4456: BGP Route Reflection: An Alternative to
                     Full Mesh.";
      }
    }
  }

  grouping structure-neighbor-group-as-path-options {
    description
      "Structural grouping used to include AS_PATH manipulation
       configuration and state for both BGP neighbors and peer
       groups";
    container as-path-options {
      description
        "AS_PATH manipulation parameters for the BGP neighbor or
         group";
      leaf allow-own-as {
        type uint8;
        default "0";
        description
          "Specify the number of occurrences of the local BGP
           speaker's AS that can occur within the AS_PATH before it
           is rejected as looped.";
      }
      leaf replace-peer-as {
        type boolean;
        default "false";
        description
          "Replace occurrences of the peer's AS in the AS_PATH with
           the local autonomous system number";
      }
      leaf disable-peer-as-filter {
        type boolean;
        default "false";
        description
          "When set to true, the system advertises routes to a peer
           even if the peer's AS was in the AS path.  The default
           behavior (false) suppresses advertisements to peers if
           their AS number is in the AS path of the route.";
      }
    }
  }

  grouping structure-add-paths {
    description
      "Structural grouping used to include ADD-PATHs configuration
       and state.";
    container add-paths {
      if-feature "bt:add-paths";
      description
        "Parameters relating to the advertisement and receipt of
         multiple paths for a single NLRI (add-paths)";
      reference
        "RFC 7911: Advertisements of Multiple Paths in BGP.";
      leaf receive {
        type boolean;
        default "false";
        description
          "Enable ability to receive multiple path advertisements for
           an NLRI from the neighbor or group";
      }
      choice send {
        description
          "Choice of sending the max. number of paths or to send
           all.";
        case max {
          leaf max {
            type uint8;
            description
              "The maximum number of paths to advertise to neighbors
               for a single NLRI";
          }
        }
        case all {
          leaf all {
            type empty;
            description
              "Send all the path advertisements to neighbors for a
               single NLRI.";
          }
        }
      }
      leaf eligible-prefix-policy {
        type leafref {
          path "/rt-pol:routing-policy/rt-pol:policy-definitions/"
             + "rt-pol:policy-definition/rt-pol:name";
        }
        description
          "A reference to a routing policy which can be used to
           restrict the prefixes for which add-paths is enabled";
      }
    }
  }

  grouping structure-dynamic-peers {
    description
      "Structural grouping to contain dyamic BGP peers. Dynamic
       peers are configured from a list of IP prefixes matching the
       IP source address of the dynamic peer.";

    container dynamic-peers {
      description
        "Configuration and operational state for dynamically
         configured peers.";

      list dynamic-peer-list {
        key "prefix";
        description
          "List of peers by IP prefix for this configuration scope
           that are dynamically configured.";

        leaf prefix {
          type inet:ip-prefix;
          description
            "Prefix for dynamic peer at this configuration scope.";
        }
      }
    }
  }
}
