module ietf-qos-policy {
  yang-version 1.1;
  namespace "urn:ietf:params:xml:ns:yang:ietf-qos-policy";
  prefix policy;

  import ietf-qos-classifier {
    prefix classifier;
  }

  organization
    "IETF Routing Area Working Group";

  contact
    "WG Web:   <https://datatracker.ietf.org/wg/rtgwg/>
     WG List:  <mailto:rtgwg@ietf.org>

     Editor:   Aseem Choudhary
               <mailto:asechoud@cisco.com>
     Editor:   Mahesh Jethanandani
               <mailto:mjethanandani@gmail.com>";

  description
    "This module contains a collection of YANG definitions for
     configuring qos specification implementations.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2022-03-06 {
    description
      "Initial version";
    reference
      "RFC XXXX: YANG Models for Quality of Service (QoS).";
  }

  identity policy-type {
    description
      "This base identity type defines policy-types";
  }
  grouping generic-attr {
    description
      "Policy Attributes";
    leaf name {
      type string;
      description
        "policy name";
    }
    leaf type {
      type identityref {
        base policy-type;
      }
      description
        "policy type";
    }
    leaf description {
      type string;
      description
        "policy description";
    }
  }
  identity action-type {
    description
      "This base identity type defines action-types";
  }
  grouping classifier-action-entry {
    description
      "List of Configuration of classifier & associated actions";
    list action {
      key "type";
      ordered-by user;
      description
        "Configuration of classifier & associated actions";
      leaf type {
        type identityref {
          base action-type;
        }
        description
          "This defines action type ";
      }
      choice action-params {
        description
          "Choice of action types";
      }
    }
  }
  container policies{
    description
      "list of policy templates";
    list policy{
      key "name type";
      description
        "policy template";
      uses generic-attr;
      list classifier{
        key "name";
        ordered-by user;
        description
          "Classifier entry configuration in a policy";
        leaf name {
          type string;
          description
            "classifier entry name";
        }
        uses classifier:inline-attr;
        uses classifier-action-entry;
      }
    }
  }
}
