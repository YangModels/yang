module policy-yang-types {
  yang-version "1";

  namespace "urn:TBD:params:xml:ns:yang:policy-yang-types";

  prefix "py";

  import ietf-inet-types { prefix inet; }
  import ietf-yang-types { prefix yang; }

  organization "IETF Netmod Working Group";

  contact "wangzitao@huawei.com";

  description
    "This module defines general data definitions for policy.";

  typedef policy-decision-strategy {
   description
     "The policy-decision-strategy is used to specify the matching
     strategy for the policies of the policy rule.  There are two
     matching strategies: First-Matching and All-Matching.";
   type enumeration{
    enum FirstMatching {
     description
     "The FirstMatching strategy is used to cause the evaluation of
     the rules in a set such that the only actions enforced on a
     given examination of the Policy Set are those for the first rule
     that has its conditions evaluate to TRUE.";}
    enum AllMatching {
     description
      "The AllMatching strategy is used to cause the evaluation of
      all rules in a set; for all of the rules whose conditions
      evaluate to TRUE, the actions are enforced.";}
    }
    default FirstMatching;
  }

  typedef policy-sequenced-actions {

   type enumeration{
    enum mandatory{
     description
      "Do the actions in the indicated order, or don't do them at
      all.";}
    enum recommended{
     description
      "Do the actions in the indicated order if you can, but if you
      can't do them in this order, do them in another order if you
      can.";}
    enum dontCare{
     description
      "I don't care about the order.";}
    }
    default dontCare;
  }

  typedef policy-execution-strategy {

   type enumeration{
    enum DoUntilSuccess {
     description
      "Execute actions according to predefined order, until
      successful execution of a single action.";}
    enum DoAll{
     description
      "Execute ALL actions which are part of the modeled set,
      according to their predefined order.  Continue doing this, even
      if one or more of the actions fails.";}
    enum DoUntilFailure{
     description
      "Execute actions according to predefined order, until the first
      failure in execution of a single sub-action.";}
    }
    default DoAll;
  }

  typedef policy-conditionlist-type {

   type enumeration{
    enum DNF;
    enum CNF;
   }
   default DNF;
  }

  //policy values

  typedef policy-IPv4-addr{
   description
    "The IPv4 address. of the outermost IP packet header.";
   type inet:ipv4-address;
  }

  typedef policy-IPv6-addr{
   description
    "The IPv6 address. of the outermost IP packet header.";
   type inet:ipv6-address;
  }

  typedef policy-port{
   description
    "For TCP and UDP flows, the PolicySourcePortVariable is logically
    bound to the source port field of the outermost UDP or TCP packet
    header.";
   type inet:port-number;
  }

  typedef policy-protocol{
   description
    "The IP protocol number.";
   type uint16{
    range "0..65535";}
  }
  typedef policy-ip-version{
   description
    "The IP version number.";
   type inet:ip-version;
  }

  typedef policy-dscp{
   description
    "The 6 bit Differentiated Service Code Point.";
   type inet:dscp;
  }

  typedef policy-flow-label{
   description
    "The flow identifier of the outermost IPv6 packet header.";
   type uint32{
    range "0..1048575";}
  }

  typedef policy-mac-addr{
   description
    "The source MAC address.";
   type yang:mac-address;
  }

  typedef policy-vlan{
   description
    "The virtual Bridged Local Area Network Identifier, a 12-bit
    field as defined in the IEEE 802.1q standard.";
   type uint16{
    range "0..4095";}
  }

  typedef policy-cos{
   description
    "A 3-bit field, used in the layer 2 header to select the
    forwarding treatment.  Bound to the IEEE 802.1q user-priority
    field.";
   type uint8{
    range "0..7";}
  }

  typedef policy-ether-type{
   description
    "The Ethertype protocol number of Ethernet frames.";
   type uint16{
    range "0..65535";}
  }
  typedef policy-sap{
   description
    "The Source Service Access Point (SAP) number of thev IEEE 802.2
    LLC header.";
   type uint8{
    range "0..255";}
  }

  typedef policy-snap-oui{
   description
    "The value of the first three octets of the Sub-Network Access
    Protocol (SNAP) Protocol Identifier field for 802.2 SNAP
    encapsulation, containing an Organizationally Unique Identifier
    (OUI).  The value 00-00-00 indicates the encapsulation of
    Ethernet frames (RFC 1042).  OUI value 00-00-F8 indicates the
    special encapsulation of Ethernet frames by certain types of
    bridges (IEEE 802.1H).  Other values are supported, but are not
    further defined here.  These OUI values are to be interpreted
    according to the endian-notation conventions of IEEE 802.  For
    either of the two Ethernet encapsulations, the remainder of the
    Protocol Identifier field is represented by the
    PolicySNAPTypeVariable.";
   type uint32{
    range "0..16777215";}
  }

  typedef policy-flow-direction {
   type enumeration{
    enum IN;
    enum OUT;
    enum BOTH;
   }
   default BOTH;
  }

  typedef policy-ip-address{
   type inet:ip-address;
  }

  typedef policy-addr-range {
   type union{
    type inet:ipv4-prefix;
    type inet:ipv6-prefix;
    }
  }

  typedef policy-addr-length{
   description
    "simple range covers both ipv4 and ipv6.";
   type uint8{
    range 1..128;}
  }
}
