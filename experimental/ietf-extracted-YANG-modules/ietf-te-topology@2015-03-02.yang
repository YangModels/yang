module ietf-te-topology { 
  yang-version 1; 
  namespace "urn:ietf:params:xml:ns:yang:ietf-te-topology"; 
  // replace with IANA namespace when assigned 

  prefix "tet"; 

  import ietf-yang-types {  
    prefix "yang";  
  } 

  import ietf-inet-types { 
    prefix "inet"; 
  } 

  import ted { 
    prefix "ted"; 
  } 

  import ietf-interfaces { 
    prefix "if"; 
  } 

  organization "TBD"; 
  contact "TBD"; 
  description "TE topology model"; 

  revision "2015-03-02" { 
    description "Initial revision"; 
    reference "TBD"; 
  } 

  /* 
   * Features 
   */ 

  feature te-topology-hierarchy { 
    description 
      "This feature indicates that the system allows underlay 
       and/or overlay TE topology hierarchy."; 
  } 

  /* 
   * Typedefs 
   */ 

  typedef te-topology-id { 
    type string { 
      pattern '/?([a-zA-Z0-9\-_.]+)(/[a-zA-Z0-9\-_.]+)*'; 
    } 
    description 
      "An identifier for a topology."; 
  } 

  typedef te-node-id { 
    type inet:ip-address; 
    description 
      "An identifier for a node in a topology. 
       The identifier is represented as an IPv4 or IPv6 address. 
       The identifier SHOULD be chosen such that the same node in a 
       real network topology will always be identified through the 
       same identifier, even if the model is instantiated in  
       separate datastores. An implementation MAY choose to capture  
       semantics in the identifier, for example to indicate the type  
       of node and/or the type of topology that the node is a part  
       of."; 
  } 

  typedef te-link-id { 
    type union { 
      type uint32;          // Unnumbered 
      type inet:ip-address; // IPv4 or IPv6 address 
    } 
    description 
      "An identifier for a TE link on a node. 
       The identifier may be opaque. 
       The identifier SHOULD be chosen such that the same TP in a 
       real network topology will always be identified through the 
       same identifier, even if the model is instantiated in  
       separate datastores. An implementation MAY choose to capture  
       semantics in the identifier, for example to indicate the type  
       of TP and/or the type of node and topology that the TP is a  
       part of."; 
  } 

  typedef te-topology-event-type { 
    type enumeration { 
      enum "add" { 
        value 0; 
        description  
          "A TE node or te-link has 
          been added"; 
      } 
      enum "remove" { 
        value 1; 
        description  
          "A TE node or te-link has 
          been removed"; 
      } 
      enum "update" { 
        value 2; 
        description  
          "A TE node or te-link has 
          been updated"; 
      } 
    } 
    description "TE  Event type for notifications"; 
  } // te-topology-event-type 

  /* 
   * Identities 
   */ 

  identity flag-identity { 
    description "Base type for flags"; 
  } 

  identity undefined-flag { 
    base "flag-identity"; 
    description "Undefined flag"; 
  } 
  typedef flag-type { 
    type identityref { 
      base "flag-identity"; 
    } 
    description "Type for flags"; 
  } 

  /* 
   * Groupings 
   */ 

  grouping topo-ref { 
    description 
      "Grouping for an absolute reference to a topology instance."; 
    leaf topo-ref { 
      type leafref { 
        path "/tet:te-topologies/tet:topology/tet:te-topology-id"; 
      } 
      description 
        "An absolute reference to a topology instance."; 
    } 
  } 

  grouping link-ref { 
    description 
      "Grouping for an absolute reference to a link instance."; 
    leaf source-te-node-id-ref { 
      type leafref { 
        path "/tet:te-topologies/tet:link/tet:source-te-node-id"; 
      } 
      description 
        "An absolute reference to a link instance."; 
    } 
    leaf source-te-link-id-ref { 
      type leafref { 
        path "/tet:te-topologies/tet:link/tet:source-te-link-id"; 
      } 
      description 
        "An absolute reference to a link instance."; 
    } 
    leaf dest-te-node-id-ref { 
      type leafref { 
        path "/tet:te-topologies/tet:link/tet:dest-te-node-id"; 
      } 
      description 
        "An absolute reference to a link instance."; 
    } 
    leaf dest-te-link-id-ref { 
      type leafref { 
        path "/tet:te-topologies/tet:link/tet:dest-te-link-id"; 
      } 
      description 
        "An absolute reference to a link instance."; 
    } 
  } 

  grouping node-ref { 
    description 
      "Grouping for an absolute reference to a node instance."; 
    leaf node-ref { 
      type leafref { 
        path "/tet:te-topologies/tet:node/tet:te-node-uu-id"; 
      } 
      description 
        "An absolute reference to a node instance."; 
    } 
  } 

  grouping link-end-ref { 
    description 
      "Grouping for an absolute reference to a TE link end, which is 
      the local representation of a TE link on a node."; 
    uses node-ref; 
    leaf link-end-ref { 
      type leafref { 
        path "/tet:te-topologies" 
          +"/tet:node[tet:te-node-uu-id = current()/../node-ref]" 
          +"/tet:te-node-attributes/tet:te-link/tet:te-link-id"; 
      } 
      description 
        "Grouping for an absolute reference to a TE link end."; 
    } 
  } 

  grouping te-topology-type { 
    description 
      "Identifies the TE topology type."; 
    container te-topology { 
      presence "indicates TE topology"; 
      description 
        "Its presence identifies the TE topology type."; 
    } 
  } 

  grouping te-path-element { 
    description 
      "A group of attributes defining an element in a TE path 
      such as TE node, TE link, TE aotomic resource or label."; 
    leaf loose { 
      type boolean; 
      description "true if the element is loose."; 
    } 
    choice element-type { 
      description "Attributes for various element types."; 
      case numbered-link { 
        leaf link-ip-address { 
          type inet:ip-address; 
          description "IPv4 or IPv6 address."; 
        } 
      } 
      case unnumbered-link { 
        leaf link-node-id { 
          type uint32; 
          description  
            "Node ID of the node where the link end point resides."; 
        } 
        leaf te-link-id { 
          type uint32; 
          description "Identifies the link end point."; 
        } 
      } 
      case node { 
        leaf te-node-id { 
          type uint32; 
          description "Identifies the node."; 
        } 
      } 
      case label { 
        leaf label { 
          type uint32; 
          description "Identifies atomic TE resource or label."; 
        } 
      } 
    } 
  } // te-path-element 

  grouping config-schedule-attributes { 
    description 
      "A list of schedules defining when a particular  
       configuration takes effect."; 
    list schedules { 
      key "schedule-id"; 
      description "A list of schedule elements."; 

      leaf schedule-id { 
        type uint32; 
        description "Identifies the schedule element."; 
      } 
      leaf start { 
        type yang:date-and-time; 
        description "Start time."; 
      } 
      leaf schedule-duration { 
        type string { 
          pattern  
            'P(\d+Y)?(\d+M)?(\d+W)?(\d+D)?T(\d+H)?(\d+M)?(\d+S)?'; 
        } 
        description "Schedule duration in ISO 8601 format."; 
      } 
      leaf repeat-interval { 
        type string { 
          pattern  
            'R\d*/P(\d+Y)?(\d+M)?(\d+W)?(\d+D)?T(\d+H)?(\d+M)?' 
            + '(\d+S)?'; 
        } 
        description "Repeat interval in ISO 8601 format."; 
      } 
    } 
  } 

  grouping information-source-attributes { 
    description 
      "The attributes identifying source that has provided the  
      related information, and the source credibility."; 
    leaf information-source { 
      type enumeration { 
        enum "unknown" { 
          description "The source is unknown"; 
        } 
        enum "locally-configured" { 
          description "Configured TE link"; 
        } 
        enum "ospfv2" { 
          description "OSPFv2"; 
        } 
        enum "ospfv3" { 
          description "OSPFv3"; 
        } 
        enum "isis" { 
          description "ISIS"; 
        } 
        enum "other" { 
          description "Other source"; 
        } 
      } 
      description  
        "Indicates the source of the information."; 
    } 
    leaf credibility-preference { 
      type uint16; 
      description 
        "The preference value to calculate the traffic  
        engineering database credibility value used for  
        tie-break selection between different  
        information-source values. 
        Higher value is more preferable."; 
    } 
  } 

  grouping te-node-attributes { 
    description "Node attributes in a TE topology."; 
    container te-node-attributes { 
      description "Node attributes in a TE topology."; 
      uses config-schedule-attributes; 
      leaf name { 
        type inet:domain-name; 
        description "Node name."; 
      } 
      leaf-list signaling-address { 
        type inet:ip-address; 
        description "Node signaling address."; 
      } 
      leaf-list flag { 
        type flag-type; 
        description "Node operational flags."; 
      }       
      leaf is-abstract { 
        type boolean; 
        description  
          "true if the node is abstract, false when the node is 
          actual."; 
      } 
      leaf underlay-topology { 
        if-feature te-topology-hierarchy; 
        type leafref { 
          path "/tet:te-topologies/tet:topology/tet:te-topology-id"; 
        } 
        description  
          "When an abstract node encapsulates a topology,  
           this reference points to said topology."; 
      } 
      list te-link { 
        key "te-link-id"; 
        description 
          "The local representation of a TE link, which 
            interconnect TE nodes."; 
        leaf te-link-id { 
          type te-link-id; 
          description 
            "TE link identifier."; 
        } 
        choice stack-level { 
          description  
            "The TE link can be partitioned into bundled 
              links, or component links."; 
          case bundle { 
            container bundled-links { 
              description 
                "A set of bundled links"; 
              list bundled-link { 
                key "sequence"; 
                description 
                  "Specify a bundled interfface that is 
                    further partitioned."; 
                leaf sequence { 
                  type uint32; 
                  description 
                    "Identify the sequence in the bundle."; 
                } 
                leaf te-link-ref { 
                  type leafref { 
                    path "../../../te-link-id"; 
                    require-instance "true"; 
                  } 
                  description 
                    "Reference to TE link on this node."; 
                } 
              } 
            } 
          } 
          case component { 
            container component-links { 
              description 
                "A set of component links"; 
              list component-link { 
                key "sequence"; 
                description 
                  "Specify a component interfface that is 
                   sufficient to unambiguously identify the 
                    appropriate resources"; 

               leaf sequence { 
                  type uint32; 
                  description 
                    "Identify the sequence in the bundle."; 
                } 
                leaf component-link-ref { 
                  type leafref { 
                    path "/if:interfaces/if:interface/if:name"; 
                    require-instance "false"; 
                  } 
                  description 
                    "Reference to component link on this 
                      node."; 
                } 
              } 
            } 
          } 
        } 
      } 
      list connectivity-matrix { 
        key "id"; 
        description 
          "Represents node's switching limitations, i.e. limitations 
           in interconnecting network TE links across the node."; 
        leaf id { 
          type uint32; 
          description "Identifies the connectivity-matrix entry."; 
        } 
        container from-link { 
          uses tet:link-end-ref; 
          description  
            "Reference to source NTP."; 
        } 
        container to-link { 
          uses tet:link-end-ref; 
          description  
            "Reference to destination NTP."; 
        } 
        leaf is-allowed { 
          type boolean; 
          description 
            "true  - switching is allowed,  
             false - switching is disallowed."; 
        } 
      } 
      container ted { 
        description "Includes TE node attributes."; 
        uses ted:ted-node-attributes; 
      } 
    } 
  } // te-node-attributes 

  grouping te-node-state-attributes { 
    description "Node state attributes in a TE topology."; 
    container te-node-state-attributes { 
      description "Node state attributes in a TE topology."; 
      uses information-source-attributes; 
    } 
  } // te-node-state-attributes 

  grouping te-link-underlay-attributes { 
    description "Attributes for  te-link underlay."; 
    container underlay-path { 
      description  
        "The service path on the underlay topology that 
         supports this link."; 
      leaf topology-id { 
        type leafref { 
          path "/tet:te-topologies/tet:topology/tet:te-topology-id"; 
          require-instance false; 
        } 
        description  
          "Identifies the topology where the path belongs."; 
      } 
      list path-element { 
        key "path-element-id"; 
        description  
          "A list of path elements describing the service path"; 
        leaf path-element-id { 
          type uint32; 
          description "To identify the element in a path."; 
        } 
        uses te-path-element; 
      } 
    } // underlay-path 
    container underlay-backup-path { 
      description  
        "The backup service path on the underlay topology that 
         supports this link."; 
      leaf topology-id { 
        type leafref { 
          path "/tet:te-topologies/tet:topology/tet:te-topology-id"; 
          require-instance false; 
        } 
        description  
          "Identifies the topology where the path belongs."; 
      } 
      list path-element { 
        key "path-element-id"; 
        description  
          "A list of path elements describing the backup service  
          path"; 
        leaf path-element-id { 
          type uint32; 
          description "To identify the element in a path."; 
        } 
        uses te-path-element; 
      } 
    } // underlay-backup-path 
    leaf underlay-protection-type { 
      type uint16; 
      description 
        "Underlay protection type desired for this link"; 
    } 
    container underlay-trail-src { 
      uses tet:link-end-ref; 
      description 
        "Source TE link of the underlay trail."; 
    } 
    container underlay-trail-des { 
      uses tet:link-end-ref; 
      description 
        "Destination TE link of the underlay trail."; 
    } 
  } // te-link-underlay-attributes 

  grouping te-link-state-underlay-attributes { 
    description "State attributes for te-link underlay."; 
    leaf dynamic { 
      type boolean; 
      description  
        "true if the underlay is dynamically created."; 
    } 
    leaf committed { 
      type boolean; 
      description  
        "true if the underlay is committed."; 
    } 
  } // te-link-state-underlay-attributes 

  grouping te-link-attributes { 
    description  
      "Link attributes in a TE topology."; 
    container te-link-attributes { 
      description "Link attributes in a TE topology."; 
      uses config-schedule-attributes; 
      leaf name { 
        type string; 
        description "Link Name"; 
      } 
      leaf-list flag { 
        type flag-type; 
        description "Link flags"; 
      } 
      leaf is-abstract { 
        type boolean; 
        description "true if the link is abstract."; 
      } 
      container underlay { 
        if-feature te-topology-hierarchy; 
        presence  
          "Indicates the underlay exists for this link."; 
        description "State of the underlay of this link."; 

        uses te-link-underlay-attributes; 
      } // underlay 
      container ted { 
        description "Includes TE link attributes."; 
        uses ted:ted-link-attributes; 
      }       
    } 
  } // te-link-attributes 

  grouping te-link-state-attributes { 
    description  
      "Link state attributes in a TE topology."; 
    container te-link-state-attributes { 
      description "Link state attributes in a TE topology."; 
      uses information-source-attributes; 
    } 
  } // te-link-state-attributes 

  /* 
   * Configuration data nodes 
   */ 

  container te-topologies { 
    description 
      "This container acts as the top-level data element of  
       configuration data."; 
    list topology { 
      key "te-topology-id"; 
      description 
        "This is the model of an abstract topology. A topology 
        contains nodes and links. Each topology MUST be identified 
        by a unique te-topology-id for reason that a network could 
        contain many topologies."; 
      leaf te-topology-id { 
        type te-topology-id; 
        description 
          "It is presumed that a datastore will contain many 
          topologies. To distinguish between topologies it is 
          vital to have UNIQUE topology identifiers."; 
      } 
      container topology-types { 
        description 
          "This container is used to identify the type, or types (as 
          a topology can support several types simultaneously), of 
          the topology. 
          Topology types are the subject of several integrity 
          constraints that an implementing server can validate in 
          order to maintain integrity of the datastore. 
          Topology types are indicated through separate data nodes; 
          the set of topology types is expected to increase over 
          time. 
          To add support for a new topology, an augmenting module 
          needs to augment this container with a new empty optional 
          container to indicate the new topology type. 
          The use of a container allows to indicate a 
          subcategorization of topology types. 
          The container SHALL NOT be augmented with any data nodes 
          that serve a purpose other than identifying a particular 
          topology type."; 
        uses te-topology-type; // Defines the TE topology type. 
      } 
      choice abstract-type { 
        description 
          "Different structures for abstract or provider 
          topologies."; 
        case abstract { 
          container abstract { 
            description 
              "The structure for an abstract topology."; 
            list node { 
              key "te-node-id"; 
              leaf te-node-uu-id { 
                type leafref { 
                  path "../../../../node/te-node-uu-id"; 
                } 
                mandatory true; 
                description 
                  "The reference to the te-node."; 
              } 
              leaf te-node-id { 
                type leafref { 
                  path "../../../../node[te-node-uu-id = " 
                    + "current()/../te-node-uu-id]/te-node-id"; 
                } 
                description 
                  "The identifier of a node in the topology. 
                  A node is specific to a topology to which it 
                  belongs."; 
              } 
              description 
                "The list of network nodes defined for the 
                topology."; 
            } 
            list link { 
              key "source-te-node-id source-te-link-id " 
                + "dest-te-node-id dest-te-link-id"; 
              leaf source-te-node-id { 
                type leafref { 
                  path "../../../../link/source-te-node-id"; 
                } 
                description 
                  "Source node identifier."; 
              } 
              leaf source-te-link-id { 
                type leafref { 
                  path "../../../../link/source-te-link-id"; 
                } 
                description 
                  "Source TE link identifier."; 
              } 
              leaf dest-te-node-id { 
                type leafref { 
                   path "../../../../link/dest-te-node-id"; 
                } 
                description 
                  "Destination node identifier."; 
              } 
              leaf dest-te-link-id { 
                type leafref { 
                  path "../../../../link/dest-te-link-id"; 
                } 
                description 
                  "Destination TE link identifier."; 
              } 
              description 
                "TE links in this topology."; 
            } // link 
          } // abstract 
        } 
        case provider { 
          container provider { 
            description 
              "The structure for a provider topology."; 
            list node { 
              key "te-node-id"; 
              leaf te-node-id { 
                type te-node-id; 
                description 
                  "The identifier of a node in the topology. 
                  A node is specific to a topology to which it 
                  belongs."; 
               } 
              description 
                "The list of network nodes defined for the 
                topology."; 
              uses te-node-attributes; 
            } 
            list link { 
              key "source-te-node-id source-te-link-id " 
                + "dest-te-node-id dest-te-link-id"; 
              leaf source-te-node-id { 
                type leafref { 
                  path "../../node/te-node-id"; 
                } 
                mandatory true; 
                description 
                  "Source node identifier, must be in same 
                  topology."; 
              } 
              leaf source-te-link-id { 
                type leafref { 
                  path "../../node[te-node-id = " 
                    + "current()/../source-te-node-id]/" 
                    + "te-node-attributes/te-link/te-link-id"; 
                } 
                mandatory true; 
                description 
                  "Source TE link identifier, must be in same 
                  topology."; 
              } 
              leaf dest-te-node-id { 
                type leafref { 
                  path "../../node/te-node-id"; 
                } 
                mandatory true; 
                description 
                  "Destination node identifier, must be in the same 
                  topology."; 
              } 
              leaf dest-te-link-id { 
                type leafref { 
                  path "../../node[te-node-id = " 
                    + "current()/../dest-te-node-id]/" 
                    + "te-node-attributes/te-link/te-link-id"; 
                } 
                mandatory true; 
                description 
                  "Destination TE link identifier, must be in same 
                  topology."; 
              } 
              description 
                "TE link is a logical construct that represents a  
                way to group/map information about certain physical 
                resources (and their properties) that interconnect  
                TE nodes. 
                A Network Link connects a by Local (Source) node and 
                a Remote (Destination) Network Nodes via a set of  
                the nodes' TE links. 
                As it is possible to have several links between the 
                same source and destination nodes, and as a link 
                could potentially be re-homed, to ensure that we 
                would always know to distinguish between 
                links, every link is identified by a dedicated link 
                identifier. 
                Note that a link models a point-to-point link, not a 
                multipoint link."; 
              uses te-link-attributes; 
            } // link 
          } // basic 
        } 
      } // choice abstract-type 
    } // topology 

    list node { 
      key "te-node-uu-id"; 
      leaf te-node-uu-id { 
        type yang:uuid; 
        description 
          "The universally unique identifier of a node."; 
      } 
      leaf te-node-id { 
        type te-node-id; 
        description 
          "The identifier of a node in the topology. 
          A node is specific to a topology to which it belongs."; 
       } 
       description 
        "The list of network nodes defined for the topology."; 
      uses te-node-attributes; 
    } // node 

    list link { 
      key "source-te-node-id source-te-link-id " 
        + "dest-te-node-id dest-te-link-id"; 
      leaf source-te-node-id { 
        type leafref { 
          path "../../node/te-node-uu-id"; 
        } 
        mandatory true; 
        description 
          "Source node identifier, must be in same topology."; 
      } 
      leaf source-te-link-id { 
        type leafref { 
          path "../../node[te-node-uu-id = " 
            + "current()/../source-te-node-id]/" 
            + "te-node-attributes/te-link/te-link-id"; 
        } 
        mandatory true; 
        description 
          "Source TE link identifier, must be in same 
          topology."; 
      } 
      leaf dest-te-node-id { 
         type leafref { 
          path "../../node/te-node-uu-id"; 
        } 
        mandatory true; 
        description 
              "Destination node identifier, must be in the same 
              topology."; 
      } 
      leaf dest-te-link-id { 
        type leafref { 
          path "../../node[te-node-uu-id = " 
            + "current()/../dest-te-node-id]/" 
            + "te-node-attributes/te-link/te-link-id"; 
        } 
        mandatory true; 
        description 
          "Destination TE link identifier, must be in same 
          topology."; 
      } 
      description 
        "TE link is a logical construct that represents a way to  
        group/map information about certain physical resources  
        (and their properties) that interconnect TE nodes. 
        A Network Link connects a by Local (Source) node and 
        a Remote (Destination) Network Nodes via a set of the 
        nodes' TE links. 
        As it is possible to have several links between the same 
        source and destination nodes, and as a link could 
        potentially be re-homed, to 
        ensure that we would always know to distinguish between 
        links, every link is identified by a dedicated link 
        identifier. 
        Note that a link models a point-to-point link, not a 
        multipoint link."; 
      uses te-link-attributes; 
    } // link 
  } // te-topologies 

  /* 
   * Operational state data nodes 
   */ 

  container te-topologies-state { 
    config "false"; 
    description 
      "This container acts as the top-level state data element of  
       operational data."; 
    list topology { 
      key "te-topology-id"; 
      description 
        "This is the model of an abstract topology. A topology 
        contains nodes and links. Each topology MUST be identified 
        by a unique te-topology-id for reason that a network could 
        contain many topologies."; 
      leaf te-topology-id { 
        type te-topology-id; 
        description 
          "It is presumed that a datastore will contain many 
          topologies. To distinguish between topologies it is 
          vital to have UNIQUE topology identifiers."; 
      } 
      leaf server-provided { 
        type boolean; 
        config false; 
        description 
          "Indicates whether the topology is client-configurable 
           or whether it is provided by the server.  This leaf is 
           populated by the server implementing the model. 
           It is set to false for topologies that are created by a 
           client; it is set to true otherwise.  If it is set to 
           true, any attempt to edit the topology MUST be
          rejected."; 
      } 
      container topology-types { 
        description 
          "This container is used to identify the type, or types (as 
          a topology can support several types simultaneously), of 
          the topology. 
          Topology types are the subject of several integrity 
          constraints that an implementing server can validate in 
          order to maintain integrity of the datastore. 
          Topology types are indicated through separate data nodes; 
          the set of topology types is expected to increase over 
          time. 
          To add support for a new topology, an augmenting module 
          needs to augment this container with a new empty optional 
          container to indicate the new topology type. 
          The use of a container allows to indicate a 
          subcategorization of topology types. 
          The container SHALL NOT be augmented with any data nodes 
          that serve a purpose other than identifying a particular 
          topology type."; 
        uses te-topology-type; // Defines the TE topology type. 
      } 
      choice abstract-type { 
        description 
          "Different structures for abstract or provider 
          topologies."; 
        case abstract { 
          container abstract { 
            description 
              "The structure for an abstract topology."; 
            list node { 
              key "te-node-id"; 
              leaf te-node-uu-id { 
                type leafref { 
                  path "../../../../node/te-node-uu-id"; 
                } 
                mandatory true; 
                description 
                  "The reference to the te-node."; 
              } 
              leaf te-node-id { 
                type leafref { 
                  path "../../../../node[te-node-uu-id = " 
                    + "current()/../te-node-uu-id]/te-node-id"; 
                } 
                    description 
                      "The identifier of a node in the topology. 
                      A node is specific to a topology to which it 
                      belongs."; 
                  } 
                  description 
                    "The list of network nodes defined for the 
                    topology."; 
                } 
                list link { 
                  key "source-te-node-id source-te-link-id " 
                    + "dest-te-node-id dest-te-link-id"; 
                  leaf source-te-node-id { 
                    type leafref { 
                      path "../../../../link/source-te-node-id"; 
                    } 
                    description 
                      "Source node identifier."; 
                  } 
                  leaf source-te-link-id { 
                    type leafref { 
                      path "../../../../link/source-te-link-id"; 
                    } 
                    description 
                      "Source TE link identifier."; 
                  } 
                  leaf dest-te-node-id { 
                    type leafref { 
                      path "../../../../link/dest-te-node-id"; 
                    } 
                    description 
                      "Destination node identifier."; 
                  } 
                  leaf dest-te-link-id { 
                    type leafref { 
                      path "../../../../link/dest-te-link-id"; 
                    } 
                    description 
                      "Destination TE link identifier."; 
                  } 
                  description 
                    "TE links in this topology."; 
                } // link 
              } // abstract 
            } 
            case provider { 
              container provider { 
                description 
                  "The structure for a provider topology."; 
                list node { 
                  key "te-node-id"; 
                  leaf te-node-id { 
                    type te-node-id; 
                    description 
                      "The identifier of a node in the topology. 
                      A node is specific to a topology to which it 
                      belongs."; 
                  } 
                  description 
                    "The list of network nodes defined for the 
                    topology."; 
                  uses te-node-attributes; 
                  uses te-node-state-attributes; 
                } 
                list link { 
                  key "source-te-node-id source-te-link-id " 
                    + "dest-te-node-id dest-te-link-id"; 
                  leaf source-te-node-id { 
                    type leafref { 
                      path "../../node/te-node-id"; 
                    } 
                    mandatory true; 
                    description 
                      "Source node identifier, must be in same 
                      topology."; 
                  } 
                  leaf source-te-link-id { 
                    type leafref { 
                      path "../../node[te-node-id = " 
                        + "current()/../source-te-node-id]/" 
                        + "te-node-attributes/te-link/te-link-id"; 
                    } 
                    mandatory true; 
                    description 
                      "Source TE link identifier, must be in same 
                      topology."; 
                  } 
                  leaf dest-te-node-id { 
                    type leafref { 
                      path "../../node/te-node-id"; 
                    } 
                    mandatory true; 
                description 
                  "Destination node identifier, must be in the same 
                  topology."; 
              } 
              leaf dest-te-link-id { 
                type leafref { 
                  path "../../node[te-node-id = " 
                    + "current()/../dest-te-node-id]/" 
                    + "te-node-attributes/te-link/te-link-id"; 
                } 
                mandatory true; 
                description 
                  "Destination TE link identifier, must be in same 
                  topology."; 
              } 
              description 
                "TE link is a logical construct that represents a  
                way to group/map information about certain physical 
                resources (and their properties) that interconnect  
                TE nodes. A Network Link connects a by Local  
                (Source) node and a Remote (Destination) Network  
                Nodes via a set of the nodes' TE links. 
                As it is possible to have several links between the 
                same source and destination nodes, and as a link 
                could potentially be re-homed, to ensure that we 
                would always know to distinguish between 
                links, every link is identified by a dedicated link 
                identifier. 
                Note that a link models a point-to-point link, not a 
                multipoint link."; 
              uses te-link-attributes; 
              uses te-link-state-attributes; 
            } // link 
          } // basic 
        } 
      } // choice abstract-type 
    } 

    list node { 
      key "te-node-uu-id"; 
      leaf te-node-uu-id { 
        type yang:uuid; 
        description 
          "The universally unique identifier of a node."; 
      } 
      leaf te-node-id { 
        type te-node-id; 
        description 
          "The identifier of a node in the topology. 
          A node is specific to a topology to which it belongs."; 
      } 
      description 
        "The list of network nodes defined for the topology."; 
      uses te-node-attributes; 
      uses te-node-state-attributes; 
    } // node 

    list link { 
      key "source-te-node-id source-te-link-id " 
        + "dest-te-node-id dest-te-link-id"; 
      leaf source-te-node-id { 
        type leafref { 
          path "../../node/te-node-uu-id"; 
        } 
        mandatory true; 
        description 
          "Source node identifier, must be in same topology."; 
      } 
      leaf source-te-link-id { 
        type leafref { 
          path "../../node[te-node-uu-id = " 
            + "current()/../source-te-node-id]/" 
            + "te-node-attributes/te-link/te-link-id"; 
        } 
        mandatory true; 
        description 
          "Source TE link identifier, must be in same 
          topology."; 
      } 
      leaf dest-te-node-id { 
        type leafref { 
          path "../../node/te-node-uu-id"; 
        } 
        mandatory true; 
        description 
          "Destination node identifier, must be in the same 
          topology."; 
      } 
      leaf dest-te-link-id { 
        type leafref { 
          path "../../node[te-node-uu-id = " 
            + "current()/../dest-te-node-id]/" 
            + "te-node-attributes/te-link/te-link-id"; 
        } 
        mandatory true; 
        description 
          "Destination TE link identifier, must be in same 
          topology."; 
      } 
      description 
        "TE link is a logical construct that represents a way to  
        group/map information about certain physical resources  
        (and their properties) that interconnect TE nodes. 
        A Network Link connects a by Local (Source) node and 
        a Remote (Destination) Network Nodes via a set of the 
        nodes' TE links. 
        As it is possible to have several links between the same 
        source and destination nodes, and as a link could 
        potentially be re-homed, to 
        ensure that we would always know to distinguish between 
        links, every link is identified by a dedicated link 
        identifier. 
        Note that a link models a point-to-point link, not a 
        multipoint link."; 
      uses te-link-attributes; 
      uses te-link-state-attributes; 
    } // link 
  } // te-topologies 

  augment "/te-topologies-state/topology/abstract-type/provider/" 
    + "provider/link/te-link-attributes/underlay" { 
    description "Add state attributes to te-link underlay."; 
    uses te-link-state-underlay-attributes; 
  } 

  /* 
   * Notifications 
   */ 

  notification te-node-event { 
    description "Notification event for TE node"; 
    leaf event-type { 
      type te-topology-event-type; 
      description "Event type"; 
    } 
    uses node-ref; 
    uses te-topology-type; 
    uses tet:te-node-attributes; 
  } 

  notification te-link-event { 
    description "Notification event for TE link"; 
    leaf event-type { 
      type te-topology-event-type; 
      description "Event type"; 
    } 
    uses link-ref; 
    uses te-topology-type; 
    uses tet:te-link-attributes; 
  } 

  augment "/te-link-event/te-link-attributes/underlay" { 
    description "Add state attributes to te-link underlay."; 
    uses te-link-state-underlay-attributes; 
  } 
}
