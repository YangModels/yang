module TapiTopologyService {

  namespace "urn:onf:Tapi:TopologyService:yang";
  prefix TapiTopologyService;

  organization "ONF T-API Group";

  contact "mailto:info@opennetworking.org";

  description
    "This module contains a collection of YANG definitions for
     Topology Service. It is part of the T-API
     specification.
     Authors List:
     Ricard Vilalta (CTTC)
     Victor Lopez (Telefonica)
     (T-API Team)";

  revision 2015-09-11 {
    description
      "First draft for Transport API Topology Service";
  }

  /*****************************************************************
  * Groupings
  *****************************************************************/

  grouping LayerProtocol {
    leaf layerProtocol {
      type string;
    }
  }

  grouping LayerProtocolName {
    leaf layerProtocolName {
      type string;
    }
  }

  grouping EndLtpRole {
    leaf endLtpRole {
      type string;
    }
  }

  grouping NodeEdgePoint {
    description
    "The LogicalTerminationPoint (LTP) object class encapsulates the
    termination and adaptation functions of one or more transport
    layers. The structure of LTP supports all transport protocols
    including circuit and packet forms.";

    leaf nodeEdgePointId {
      type string;
    }

    list ipList{
      key "layerProtocol";
      uses LayerProtocol;
    }
  }

  grouping Node {
    description
      "The ForwardingDomain (FD) object class models the
ForwardingDomain topological component which is used to effect
forwarding of transport characteristic information and offers
the potential to enable forwarding.
      At the lowest level of recursion, an FD (within a network
element (NE)) represents a switch matrix (i.e., a fabric). Note
that an NE can encompass multiple switch matrices (FDs). ";

    leaf nodeId {
      type string;
    }

    leaf-list _encapTopologyRef {
      type leafref {
        path "/Topology/topologyId";
      }
      max-elements "1";
    }

    list edgeLtpList { // Differs from UML
      key "nodeEdgePointId";
      uses NodeEdgePoint;
    }

    list layerProtocolNameList {
      key "layerProtocolName";
      uses LayerProtocolName;
      min-elements "1";
    }
  }
  grouping Link {
    description
    "The Link object class models effective adjacency between two or
more ForwardingDomains (FD).";

    leaf linkId {
      type string;
    }

    leaf-list _nodeRefList{
      type leafref {
        path "/Topology/node/nodeId";
      }
    }

    leaf-list _endLtpRefList {
      type leafref {
        path "/Topology/node/edgeLtpList/nodeEdgePointId";
      }
      min-elements "2";
    }

    list endLtpRoleList {
      key "endLtpRole";
      uses EndLtpRole;
      min-elements "2";
    }

    list layerProtocolNameList {
      key "layerProtocolName";
      uses LayerProtocolName;
      min-elements "1";
    }
  }

  grouping Topology {
    leaf topologyId {
      type string;
    }

    list node {
      key "nodeId";
      uses Node;
    }

    list link {
      key "linkId";
      uses Link;
    }

    uses LayerProtocolName;
  }

  /*****************************************************************
  * Main containers
  *****************************************************************/

  list Topology {
    description
    "The ForwardingConstruct (FC) object class models enabled
potential for forwarding between two or more LTPs and like the
LTP supports any transport protocol including all circuit and
packet forms.
    At the lowest level of recursion, a FC represents a
cross-connection within an NE.";

    key "topologyId";
    uses Topology;
  }

  /*****************************************************************
  * RPC definitions
  *****************************************************************/

  rpc getTopologyDetails {
    input {
      leaf topologyId {
        description "topology id";
        type string;
      }
    }

    output {
      container topology {
          uses Topology;
      }
    }
  }
  rpc getLinkDetails {
    input {
      leaf linkId {
        description "link id";
        type string;
        }
    }
    output {
      container link{
        uses Link;
      }
    }
  }

  rpc getNodeDetails {
    input {
      leaf nodeId {
        description "node id";
        type string;
        }
    }
    output {
      container node{
        uses Node;
      }
    }
  }

  rpc getNodeEdgePointDetails {
    input {
      leaf nodeEdgePointId {
        description "node edge point id";
        type string;
        }
    }
    output {
      container nodeEdgePoint{
        uses NodeEdgePoint;
      }
    }
  }
 }
