module ietf-segment-routing {
  namespace "urn:ietf:params:xml:ns:"
          + "yang:ietf-segment-routing";
  prefix sr;

  import ietf-inet-types {
    prefix "inet";
  }

  import ietf-routing {
    prefix "rt";
  }

  import ietf-interfaces {
  prefix "if";
  }

  import ietf-isis {
  prefix "isis";
  }

  import ospf {
  prefix "ospf";
  }

  organization
   "IETF SPRING Working Group";

  contact
    "WG List:  &lt;mailto:spring@ietf.org&gt;

    Editor:    Stephane Litkowski
          &lt;mailto:stephane.litkowski@orange.com&gt;

        Acee Lindem
          &lt;mailto:acee@cisco.com&gt;
        Pushpasis Sarkar
          &lt;mailto:psarkar@juniper.net&gt;
        Ing-Wher Chen
          &lt;mailto:ing-wher.chen@ericsson.com&gt;
    ";

  description
    "The YANG module defines a generic configuration model for
    Segment routing common across all of the vendor
    implementations.";

  revision 2015-02-27 {
    description "Initial";
    reference "draft-litkowski-spring-sr-yang-00";
  }

  /* Identities */
  identity segment-routing-transport {
    description
    "Base identity for segment routing transport.";
  }
  identity segment-routing-transport-mpls {
    base segment-routing-transport;
    description
    "This identity represents MPLS transport for segment
    routing.";
  }

  /* Features */

  feature mapping-server {
    description
     "Support of SRMS.";
  }

  /* Groupings */

  grouping controlplane-cfg {
    container segment-routing {
      leaf enabled {
        type boolean;
        default false;
        description
         "Enables segment-routing
         protocol extensions.";
      }
      container bindings {
        leaf advertise {
          type boolean;
          default true;
          description
          "Authorize the advertise
          of local mappings in binding TLV.";
        }
        leaf receive {
          type boolean;
          default true;
          description
          "Authorize the reception and usage
          of binding TLV.";
        }
        description
         "Control of binding advertisement
         and reception.";
      }

      description
      "segment routing global config.";
    }
    description
     "Defines protocol configuration.";
  }

  grouping prefix-sid-cfg {
    list prefix-sid {
      key value;
      leaf value-type {
        type enumeration {
          enum index {
            description
               "The value will be
               interpreted as an index.";

          }
          enum absolute {

            description
               "The value will become
               interpreted as an absolute
               value.";
          }
        }
        default index;
        description
          "This leaf defines how value
           must be interpreted.";
      }

      leaf value {
        type uint32;
        mandatory true;
        description
        "Value associated with
        prefix. The value must
        be interpreted in the
        context of value-type.";
      }
      leaf node-flag {
        type boolean;
        default true;
        description
        "Set prefix as a node
         representative prefix.";
      }
      leaf last-hop-behavior {
        type enumeration {
          enum explicit-null {
            description
             "Use explicit-null for the SID.";
          }
          enum no-php {
            description
             "Do no use PHP for the SID.";
          }
          enum php {
            description
             "Use PHP for the SID.";
          }
        }
        description
         "Configure last hop behavior.";
      }
      description
       "List of prefix SID.";
    }
    description
     "This grouping defines cfg of prefix SID.";
  }

  /* Cfg */

  augment "/rt:routing/rt:routing-instance" {
    description
     "This augments routing-instance
     configuration with segment-routing.";
    container segment-routing {
      leaf transport-type {
        type identityref {
          base segment-routing-transport;
        }
        default "segment-routing-transport-mpls";
        description "Dataplane to be used.";
      }
      container bindings {
        container mapping-server {
          if-feature mapping-server;
          container ipv4 {
            list mapping-entry {
              key prefix;

              leaf prefix {
                type inet:ipv4-prefix;
                description
                 "Base prefix used for mapping.";
              }
              leaf start-sid {
                type uint32;
                description
                 "Starting SID value to be associated
                 with prefix.";
              }
              leaf range {
                type uint32;
                description
                 "Describes how many SIDs could be
                 allocated.";
              }
              description
               "Mapping entries.";
            }
            description
             "IPv4 mapping entries.";
          }
          container ipv6 {
            list mapping-entry {
              key prefix;

              leaf prefix {
                type inet:ipv6-prefix;
                description
                 "Base prefix used for mapping.";
              }
              leaf start-sid {
                type uint32;
                description
                 "Starting SID value to be associated
                 with prefix.";
              }
              leaf range {
                type uint32;
                description
                 "Describes how many SIDs could be
                 allocated.";
              }
              description
               "Mapping entries.";
            }
            description
             "IPv6 mapping entries.";
          }
          description
           "Configuration of mapping-server
            local entries.";
        }
        description
         "List of bindings.";
      }
      list srgb {
        key "lower-bound upper-bound";
        ordered-by user;
        leaf lower-bound {
          type uint32;
          description
          "Lower value in the block.";
        }
        leaf upper-bound {
          type uint32;
          description
          "Upper value in the block.";
        }
        description
          "List of global blocks to be
             advertised.";
      }

      container interfaces {
        list interface {
          key "name";
          leaf name {
            type if:interface-ref;

            description
             "Reference to the interface within
              the routing-instance.";
          }
          container adjacency-sid {
            list advertise-adj-group-sid {
              key group-id;

              leaf group-id {
                type uint32;
                description

                 "The value is an internal value to identify
                 a group-ID. Interfaces with the same
                 group-ID will be bundled together.
                 ";
              }
              description
               "Control advertisement of S flag.
                 Enable to advertise a common Adj-SID
                 for parallel links.";
            }
            leaf advertise-protection {
              type enumeration {
                enum "single" {
                  description
                   "A single Adj-SID is associated
                   with the adjacency and reflects
                   the protection configuration.";
                }
                enum "dual" {
                  description
                   "Two Adj-SIDs will be associated
                   with the adjacency if interface
                   is protected. In this case
                   one will be enforced with
                   backup flag set, the other
                   will be enforced to backup flag unset.
                   In case, protection is not configured,
                   a single Adj-SID will be advertised
                   with backup flag unset.";
                }
              }
              description
               "If set, the Adj-SID refers to an
              adjacency being protected.";
            }
            description
             "Defines the adjacency SID properties.";
          }
          container prefix-sid {
            container ipv4 {
              uses prefix-sid-cfg;
              description
               "Parameters associated with IPv4 prefix SID";
            }
            container ipv6 {
              uses prefix-sid-cfg;
              description
               "Parameters associated with IPv6 prefix SID";
            }
            description
             "Prefix SID configuration.";
          }
          description
           "List of interfaces.";
        }
        description
         "Interface configuration.";
      }
      description
      "segment routing global config.";
    }
  }

  augment "/rt:routing/rt:routing-instance/" +
        "rt:routing-protocols/rt:routing-protocol"+
        "/isis:isis/isis:instance" {
    when "rt:type = 'isis:isis'" {
      description
      "This augment ISIS routing protocol when used";
    }
    description
     "This augments ISIS protocol configuration
      with segment routing.";

    uses controlplane-cfg;
  }

  augment "/rt:routing/rt:routing-instance/rt:routing-protocols" +
        "/rt:routing-protocol/ospf:ospf/ospf:instance" {
    when "rt:type = 'ospf:ospfv2' or rt:type = 'ospf:ospfv3'" {
      description
      "This augment ISIS routing protocol when used";
    }
    description
     "This augments ISIS protocol configuration
      with segment routing.";
    uses controlplane-cfg;
  }

  /* Operational states */

  augment "/rt:routing-state/rt:routing-instance" {
    description
     "This augments the operational states
      with segment-routing.";
    container segment-routing {
      list label-blocks {
        leaf lower-bound {
          type uint32;
          description
           "Lower bound of the label block.";
        }
        leaf upper-bound {
          type uint32;
          description
           "Upper bound of the label block.";
        }
        leaf size {
          type uint32;
          description
           "Number of indexes in the block.";
        }
        leaf free {
          type uint32;
          description
           "Number of indexes free in the block.";
        }
        leaf used {
          type uint32;
          description
           "Number of indexes used in the block.";
        }
        description
         "List of labels blocks currently
         in use.";
      }

      container global-sid-list {
        list sid {
          key "target sid source source-protocol binding-type";
          ordered-by system;

          leaf target {
            type string;
            description
             "Defines the target of the binding.
             It can be a prefix or something else.";
          }
          leaf sid {
            type uint32;
            description
             "Index associated with the prefix.";
          }
          leaf algorithm {
            type uint8;
            description
             "Algorithm to be used for the prefix
             SID.";
          }
          leaf source {
            type inet:ip-address;
            description
             "IP address of the router than own
              the binding.";
          }
          leaf used {
            type boolean;
            description
             "Defines if the binding is used
              in forwarding plane.";
          }
          leaf source-protocol {
            type leafref {
              path "/rt:routing-state/rt:routing-instance/" +
              "rt:routing-protocols/rt:routing-protocol/rt:name";
            }
            description
             "Rtg protocol that owns the binding";
          }
          leaf binding-type {
            type enumeration {
              enum prefix-sid {
                description
                 "Binding is learned from
                 a prefix SID.";
              }
              enum binding-tlv {
                description
                 "Binding is learned from
                 a binding TLV.";
              }
            }
            description
             "Type of binding.";
          }
          description
            "Binding.";

        }
        description
         "List of prefix and SID associations.";
      }
      description
       "Segment routing operational states.";
    }
  }

  /* Notifications */

  notification segment-routing-global-sid-collision {
    leaf received-target {
      type string;
      description
      "Target received in the controlplane that
             caused SID collision.";
    }
    leaf original-target {
      type string;
      description
      "Target already available in database that have the same SID
      as the received target.";
    }
    leaf index {
      type uint32;
      description
      "Value of the index used by two different prefixes.";
    }
    leaf routing-protocol {
      type leafref {
        path "/rt:routing-state/rt:routing-instance/" +
        "rt:routing-protocols/rt:routing-protocol/rt:name";
      }
      description
       "Routing protocol reference that received the event.";
    }
    description
      "This notification is sent when a new mapping is learned
      , containing mapping
      where the SID is already used.
      The notification generation must be throttled with at least
       a 5 second gap. ";
  }
  notification segment-routing-index-out-of-range {
    leaf received-target {
      type string;
      description
      "Target received in the controlplane
            that caused SID collision.";
    }
    leaf received-index {
      type uint32;
      description
      "Value of the index received.";
    }
    leaf routing-protocol {
      type leafref {
        path "/rt:routing-state/rt:routing-instance/" +
        "rt:routing-protocols/rt:routing-protocol/rt:name";
      }
      description
       "Routing protocol reference that received the event.";
    }
    description
      "This notification is sent when a binding
      is received, containing a segment index
      which is out of the local configured ranges.
      The notification generation must be throttled with at least
       a 5 second gap. ";
  }

}
