module ietf-igmp-mld-snooping-l2vpn {
  yang-version 1.1;
  namespace "urn:ietf:params:xml:ns:yang:ietf-igmp-mld-snooping-l2vpn";

  prefix ims-l2vpn;

  import ietf-interfaces {
    prefix "if";
    reference
      "RFC 8343: A YANG Data Model for Interface Management";
  }

  import ietf-routing {
    prefix "rt";
    reference
      "RFC 8349: A YANG Data Model for Routing Management (NMDA
       Version)";
  }

  import ietf-network-instance {
    prefix "ni";
    reference
      "RFC 8529: YANG Data Model for Network Instances";
  }

  import ietf-l2vpn {
    prefix "l2vpn";
    reference
      "draft-ietf-bess-l2vpn-yang: YANG Data Model for MPLS-based
L2VPN";
  }

  import ietf-pseudowires {
    prefix "pw";
    reference
      "draft-ietf-bess-l2vpn-yang: YANG Data Model for MPLS-based
L2VPN";
  }

  import ietf-igmp-mld-snooping {
    prefix "ims";
    reference
      "draft-ietf-pim-igmp-mld-snooping-yang: A Yang Data Model for IGMP
and MLD Snooping";
  }

  organization
    "IETF PIM Working Group";

  contact
    "WG Web:   <http://tools.ietf.org/wg/pim/>
     WG List:  <mailto:pim@ietf.org>

     Editors:  Hongji Zhao
               <mailto:hongji.zhao@ericsson.com>

               Xufeng Liu
               <mailto:xufeng.liu.ietf@gmail.com>

               Yisong Liu
               <mailto:liuyisong@chinamobile.com>

               Anish Peter
               <mailto:anish.ietf@gmail.com>

               Mahesh Sivakumar
               <mailto:sivakumar.mahesh@gmail.com>

    ";

  description
    "The module contains a collection of YANG definitions of
     IGMP & MLD Snooping in L2VPN service.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2021-10-25 {
    description
      "Initial revision.";
    reference
      "RFC XXXX: IGMP and MLD Snooping Yang Module Extension in L2VPN
service";
  }

  /* identities */

  identity l2vpn {
    base ims:l2-service-type;
    description
      "This identity represents L2VPN service.";
  }

  /*
   * Groupings
   */

  grouping static-l2vpn-mrouter-interface-ac-pw-igmp-mld-snooping {
    description
      "The static mrouter interface in L2VPN service.";

    leaf-list static-l2vpn-mrouter-interface-ac {
      when 'derived-from-or-self(../l2-service-type,"ims:l2vpn")';
      type if:interface-ref;
      description
        "The static mrouter interface whose type is interface
         in L2VPN service.";
    }

    leaf-list static-l2vpn-mrouter-interface-pw {
      when 'derived-from-or-self(../l2-service-type,"ims:l2vpn")';
      type pw:pseudowire-ref;
      description
        "The static mrouter interface whose type is PW
         in L2VPN service.";
    }
  }
  grouping dynamic-l2vpn-mrouter-interface-ac-pw-igmp-mld-snooping {

    description
      "The dynamic mrouter interface in L2VPN service.";

    leaf-list l2vpn-mrouter-interface-ac {
      when 'derived-from-or-self(../l2-service-type,"ims:l2vpn")';
      type if:interface-ref;
      config false;
      description
        "The mrouter interface whose type is interface in L2VPN
         service. When switch receives IGMP/MLD queries from
         multicast router on an interface, this interface will
         become mrouter interface for IGMP/MLD snooping.";
    }

    leaf-list l2vpn-mrouter-interface-pw {
      when 'derived-from-or-self(../l2-service-type,"ims:l2vpn")';
      type pw:pseudowire-ref;
      config false;
      description
        "The mrouter interface whose type is PW in L2VPN service.
         When switch receives IGMP/MLD queries from multicast router
         on a PW, this PW will become mrouter interface for IGMP/MLD
         snooping.";
    }
  }

  grouping l2vpn-outgoing-ac-pw-igmp-mld-snooping {
    description
      "Outgoing Attachment Circuit (AC) or Pseudo Wire (PW) in L2VPN.";

    leaf-list l2vpn-outgoing-ac {
      when 'derived-from-or-self(../../../l2-service-type,"ims:l2vpn")';
      type if:interface-ref;
      description "Outgoing Attachment Circuit (AC) in L2VPN";
    }

    leaf-list l2vpn-outgoing-pw {
      when 'derived-from-or-self(../../../l2-service-type,"ims:l2vpn")';
      type pw:pseudowire-ref;
      description "Outgoing Pseudo Wire (PW) in L2VPN";
    }
  }

  /*
   * The mrouter interface in L2VPN service.
   */

  augment "/rt:routing/rt:control-plane-protocols"+
        "/rt:control-plane-protocol/ims:igmp-snooping-instance" {
    description
      "The mrouter interface in L2VPN service for IGMP Snooping.";

    uses static-l2vpn-mrouter-interface-ac-pw-igmp-mld-snooping;

    uses dynamic-l2vpn-mrouter-interface-ac-pw-igmp-mld-snooping;

  }

  augment "/rt:routing/rt:control-plane-protocols"+
        "/rt:control-plane-protocol/ims:mld-snooping-instance" {
    description
      "The mrouter interface in L2VPN service for MLD Snooping.";

    uses static-l2vpn-mrouter-interface-ac-pw-igmp-mld-snooping;

    uses dynamic-l2vpn-mrouter-interface-ac-pw-igmp-mld-snooping;

  }

  /*
   * Static Outgoing AC or PW in L2VPN service
   */

  augment "/rt:routing/rt:control-plane-protocols"+
        "/rt:control-plane-protocol"+
        "/ims:igmp-snooping-instance/ims:static-l2-multicast-group" {

    description
      "Static Outgoing AC or PW in L2VPN service for IGMP snooping.";

    uses l2vpn-outgoing-ac-pw-igmp-mld-snooping;

  }

  augment "/rt:routing/rt:control-plane-protocols"+
        "/rt:control-plane-protocol"+
        "/ims:mld-snooping-instance/ims:static-l2-multicast-group" {

    description
      "Static Outgoing AC or PW in L2VPN service for MLD snooping.";

    uses l2vpn-outgoing-ac-pw-igmp-mld-snooping;

  }

  /*
   * Dynamic Outgoing AC or PW in L2VPN service
   */

  augment "/rt:routing/rt:control-plane-protocols"+
        "/rt:control-plane-protocol"+
        "/ims:igmp-snooping-instance/ims:group/ims:source" {

    description
      "Dynamic Outgoing AC or PW in L2VPN service for IGMP snooping.";

    uses l2vpn-outgoing-ac-pw-igmp-mld-snooping;

  }

  augment "/rt:routing/rt:control-plane-protocols"+
        "/rt:control-plane-protocol"+
        "/ims:mld-snooping-instance/ims:group/ims:source" {

    description
      "Dynamic Outgoing AC or PW in L2VPN service for MLD snooping.";

    uses l2vpn-outgoing-ac-pw-igmp-mld-snooping;

  }

  /*
   * Use IGMP & MLD snooping instance in L2VPN
   */

  augment "/ni:network-instances/ni:network-instance"+
    "/ni:ni-type/l2vpn:l2vpn" {

    description
      "Use IGMP & MLD snooping instance in L2VPN.";

    leaf igmp-snooping-instance {
      type ims:igmp-mld-snooping-instance-ref;
      description
        "Configure IGMP snooping instance in L2VPN.";
    }

    leaf mld-snooping-instance {
      type ims:igmp-mld-snooping-instance-ref;
      description
        "Configure MLD snooping instance in L2VPN.";
    }
  }
}
