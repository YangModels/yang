module spf-arp {
    namespace "urn:cisco:params:xml:ns:yang:spf-arp";
    // replace with IANA namespace when assigned
    prefix spf-arp;

    import stateless-pf { prefix spf; }
    import spf-ip { prefix spf-ip; }
    import spf-mac { prefix spf-mac; }

    organization
       "IETF NETMOD (NETCONF Data Modeling Language) Working Group";

    contact
         "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com

        Editor: Alexander Clemm
        alex@cisco.com

        Editor: Andy Bierman
        andy@yumaworks.com";
    description
        "This YANG module augments the 'stateless-pf' module with
        configuration and operational data for ARP stateless
        packet filter.

        An Stateless Packet Filter (SPF), also know as an Access
        Control List (SPF), is an ordered set of rules and
        actions used to filter traffic.
        Each set of rules and actions is represented as a Packet Filter
        Entry (PFE), also know as an Access
        Control Entries (PFE). Each PFE is evaluated sequentially.
        When the rule matches then action for that rule is applied
        to the packet.

        ARP SPFs - The device applies ARP SPFs to IP traffic.

        Terms and Acronyms
         PFE (pfe): Packet Filter Entry

         SPF (spf): Stateless Packet Filter

         ARP (arp): Address Resolution Protocol

         IP (ip): Internet Protocol

         MAC: Media Access Control

         VLAN (vlan): Virtual Local Area Network
       ";

    revision 2013-09-03 {
        description "Initial revision. ";
    }

    /* Identities */

    identity arp-spf {
        base "spf:spf-type";
        description "ARP SPF type";
    }

    /* Data Nodes */

    augment "/spf:spfs/spf:spf" {
        when "spf:spf-type = 'arp-spf'";

        description "ARP Packet FIlter Entry (PFE).";
        container arp-pfes {
            list arp-pfe {
              key "name";
              ordered-by user;

              leaf name {
                  type spf:spf-name-string;
              }

              choice remark-or-arp-pfe {
                leaf remark {
                    type spf:spf-remark;
                    // mandatory true;
                }
                case arp-pfe {
                  container filters {
                     leaf direction {
                        default "bi-direction";
                        type enumeration {
                           enum bi-direction;
                           enum request;
                           enum response;
                        }
                        description "ARP request/response.";
                     }

                     uses spf-ip:IP-SOURCE-NETWORK;
                     uses spf-ip:IP-DESTINATION-NETWORK {
                       when "../direction = 'response'";
                     }

                     uses spf-mac:MAC-SOURCE-NETWORK;
                     uses spf-mac:MAC-DESTINATION-NETWORK {
                       when "../direction = 'response'";
                     }

                     uses spf:FILTER-COMMON;

                  }  // container filters
                  uses spf:PFE-COMMON;

                } // case arp-pfe
              }  // choice remark-or-arp-pfe
            }  // list arp-pfe
        } // container arp-pfes
    } // augment

}
