module ietf-adaptive-subscription {
  yang-version 1.1;
  namespace "urn:ietf:params:xml:ns:yang:ietf-adaptive-subscription";
  prefix as;
  import ietf-subscribed-notifications {
    prefix sn;
  }
  import ietf-yang-push {
    prefix yp;
  }
  import ietf-yang-types {
    prefix yang;
  }

  organization
    "IETF NETCONF (Network Configuration) Working Group";
  contact
    "";
  description
    "NETCONF Protocol Data Types and Protocol Operations.
     Copyright (c) 2020 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC xxxx; see
     the RFC itself for full legal notices.";

  revision 2020-02-14 {
    description
      "Initial revision";
    reference
      "RFCxxx Adaptive subscription to YANG notification.";
  }

  identity adaptive-unsupported {
    base sn:establish-subscription-error;
    description
      "Adaptive-subscription is not supported for any objects
       that are selectable by the filter.";
  }

  identity xpath-evaluation-unsupported {
    base sn:establish-subscription-error;
    description
      "Unable to parse the xpath evaluation criteria defined in
      âxpath-external-evalâ because of a syntax error or some
       XPath 1.0 syntax not supported against the specific object.";
  }

  identity multi-xpath-criteria-conflict {
    base sn:establish-subscription-error;
    base sn:subscription-terminated-reason;
    description
      "Multiple Xpath evaluation criteria represented by
       'xpath-external-eval' is evaluated as conflict, i.e.,
       more than one condition expressions are evaluated to
      'true'.";
}

  grouping adaptive-subscription-modifiable {
    description
      "This grouping describes the datastore-specific adaptive subscription
       conditions that can be changed during the lifetime of the
       subscription.";
    choice adaptive-subscription {
      description
        "Defines necessary conditions for sending an event record to
               the subscriber.";
      container adaptive-subscriptions {
        list adaptive-period {
          key "name";
          description
            "Defines necessary conditions to switch update interval for
            sending an event record to the subscriber. The event record output
            generation will not be influenced these conditions.";
          leaf name {
            type string {
          length "1..64";
           }
        description
          "The name of the condition to be matched.  A device MAY further
           restrict the length of this name; space and special
           characters are not allowed.";
         }
          leaf xpath-external-eval {
            type string;
            description
              "A XPath string, representing a logical expression,
               which can contain comparisons of datastore values
               and logical operations in the XPath format.";
          }
          leaf period {
            type yp:centiseconds;
            mandatory true;
            description
              "Duration of time that should occur between periodic
               push updates, in units of 0.01 seconds.";
          }
          leaf anchor-time {
            type yang:date-and-time;
            description
              "Designates a timestamp before or after which a series
               of periodic push updates are determined.  The next
               update will take place at a point in time that is a
               multiple of a period from the 'anchor-time'.
               For example, for an 'anchor-time' that is set for the
               top of a particular minute and a period interval of a
               minute, updates will be sent at the top of every
               minute that this subscription is active.";
          }
        }
        description
          "Container for adaptive subscription.";
      }
    }
  }

  augment "/sn:subscriptions/sn:subscription/yp:update-trigger" {
    description
      "This augmentation adds additional subscription parameters
       that apply specifically to adaptive subscription.";
    uses adaptive-subscription-modifiable;
  }
  augment "/sn:establish-subscription/sn:input/yp:update-trigger" {
    description
      "This augmentation adds additional subscription parameters
         that apply specifically to datastore updates to RPC input.";
    uses adaptive-subscription-modifiable;
  }

  notification adaptive-period-update {
    sn:subscription-state-notification;
    description
      "This notification contains a push update that in turn contains
       data subscribed to via a subscription.  In the case of a
       periodic subscription, this notification is sent for periodic
       updates.  It can also be used for synchronization updates of
       an on-change subscription.  This notification shall only be
       sent to receivers of a subscription.  It does not constitute
       a general-purpose notification that would be subscribable as
       part of the NETCONF event stream by any receiver.";
    leaf id {
      type sn:subscription-id;
      description
        "This references the subscription that drove the
         notification to be sent.";
    }
    leaf period {
      type yp:centiseconds;
      mandatory true;
      description
        "New duration of time that should occur between periodic
         push updates, in units of 0.01 seconds.";
    }
    leaf anchor-time {
      type yang:date-and-time;
      description
        "Designates a timestamp before or after which a series
         of periodic push updates are determined.  The next
         update will take place at a point in time that is a
         multiple of a period from the 'anchor-time'.
         For example, for an 'anchor-time' that is set for the
         top of a particular minute and a period interval of a
         minute, updates will be sent at the top of every
         minute that this subscription is active.";
    }
    uses yp:datastore-criteria {
      refine "selection-filter/within-subscription" {
        description
          "Specifies the selection filter and where it originated
           from.  If the 'selection-filter-ref' is populated, the
           filter in the subscription came from the 'filters'
           container.  Otherwise, it is populated in-line as part
           of the subscription itself.";
      }
    }
  }
}
