module ietf-lmap-report {

  namespace "urn:ietf:params:xml:ns:yang:ietf-lmap-report";
  prefix "lmapr";

  import ietf-yang-types {
    prefix yang;
  }
  import ietf-lmap-control {
    prefix lmapc;
  }

  organization
    "IETF Large-Scale Measurement Platforms Working Group";
  contact
    "WG Web:   <http://tools.ietf.org/wg/lmap/>
     WG List:  <mailto:lmap@ietf.org>

     Editor:   Juergen Schoenwaelder
               <j.schoenwaelder@jacobs-university.de>

     Editor:   Vaibhav Bajpai
               <v.bajpai@jacobs-university.de>";

  description
    "This module defines a data model for reporting results from
     measurement agents that are part of a Large-Scale Measurement
     Platform (LMAP).";

  revision "2015-04-10" {
    description
     "Initial version";
    reference
     "RFC XXX: A YANG Data Model for LMAP Measurement Agents";
  }

  notification report {
    description
      "The result record produced by a certain task.";

    leaf date {
      type yang:date-and-time;
      mandatory true;
      description
        "The date and time when this report was sent.";
      // XXX It is unclear why this is useful. The receiver can
      // XXX easily timestamp when data was received.
    }

    leaf agent-id {
      type yang:uuid;
      description
        "The agent-id of the agent from which this
         report originates.";
    }

    leaf group-id {
      type string;
      description
        "The group-id of the agent from which this
         report originates.";
    }
    uses lmapc:task-grouping;
    // XXX We would prefer to just send a configuration version
    // XXX number such that the configuration can be identified
    // XXX that was active XXX when the report was generated. It
    // XXX would be nice to have a generic configuration version
    // XXX number that we could reuse. If this works out, we can
    // XXX inline the grouping as well.

    // XXX Note that task-grouping contains stuff that is not
    // XXX relevant here, perhaps using a grouping is not helpful
    // XXX here. It is also missing stuff, such as the options
    // XXX in the schedule entry.

    container header {
      description
        "The header of the result records.";

      leaf-list column {
        type string;
        description
          "A header of a column in the result rows.";
      }
    }

    list row {
      description
        "The rows of the result record.";

      leaf start {
        type yang:date-and-time;
        mandatory true;
        description
          "The date and time when the measurement producing
           this result row started.";
      }

      leaf end {
        type yang:date-and-time;
        description
          "The date and time when the measurement producing
           this result row stopped.";
      }

      leaf-list conflict {
        type string;
        description
          "The name of a task overlapping with the execution
           of the task that has produced this result record.";
      }

      leaf-list value {
        type string;
        description
          "The value of a cell in the result.";
        // XXX We could make this a union / choice in order to a
        // XXX more compact encoding of numbers in certain encodings
        // XXX (e.g. JSON)
      }
    }
  }
}
