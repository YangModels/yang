module ietf-lisp-mapresolver {
  namespace "urn:ietf:params:xml:ns:yang:ietf-lisp-mapresolver";
  prefix lisp-mr;
  import ietf-lisp {
    prefix lisp;
  }
  import ietf-inet-types {
    prefix inet;
  }

  organization
    "IETF LISP (Locator/ID Separation Protocol) Working Group";
  contact
    "lisp@ietf.org";
  description
    "This YANG module defines the generic parameters for a LISP
     Map-Resolver. The module can be extended by vendors to define
     vendor-specific parameters and policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";
  revision 2017-07-01 {
    description
      "Initial revision.";
    reference
      "https://tools.ietf.org/html/rfc6833";
  }
  identity mr {
    base lisp:lisp-role;
    description
      "LISP Map-Resolver.";
  }
  augment "/lisp:lisp/lisp:lisp-router-instances"
  +"/lisp:lisp-router-instance" {
    when "lisp:lisp-role/lisp:lisp-role-type = 'lisp-mr:mr'" {
      description
        "Augment is valid when LISP device type is Map-Resolver.";
    }
    description
      "This augments LISP devices list with Map-Resolver specific
       parameters.";
    container map-resolver {
      presence "LISP Map-Resolver operation enabled";
      description
        "Map-Resolver parameters.";
      leaf mapping-system-type {
        type lisp:mapping-system-ref;
        description
        "A reference to the mapping system";
      }
      leaf ms-address {
        when "../mapping-system-type='lisp-mr:single-node-mapping-system'";
        type inet:ip-address;
        description
          "address to reach the Map Server when "
          + "lisp-mr:single-node-mapping-system is being used.";
      }
    }
  }
}
