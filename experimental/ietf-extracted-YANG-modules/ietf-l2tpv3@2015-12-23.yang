module ietf-l2tpv3 {
        namespace "urn:ietf:params:xml:ns:yang:ietf-l2tpv3";
        prefix "l2tpv3";

    import ietf-interfaces {
        prefix "if";
    }

/*    import ietf-yang-types {
        prefix yang;
    }
*/
    import ietf-inet-types {
        prefix "inet";
    }

        organization "ietf l2tpv3 working group";
        contact "shenhaoxing@huawei.com
                 leo.liubing@huawei.com";
        description "The module for implementing l2tpv3 protocol";
        revision 2015-12-23 {
          description "version-03, lots of grammar revision to pass pyang compiler";
          reference "draft-shen-l2tpext-l2tpv3-yang-model-02";
        }

        typedef hexBinary {
                type string {
                        length "1..127";
                        pattern "0[xX][0-9a-fA-F]+";
                }
                description "This is a hexadecimal variable.";
        }

        typedef password {
                type string {
                   length "1..127";
                }
                description "This is a dedicated password variable.";
        }

        container l2tpv3CtrlInstances {
          description "This is some general configuration of an l2tpv3 tunnel.";

                list l2tpv3CtrlInstance {

                        key "ctrlName";
                        description "There could be multiple control instances, each
                                     of them is mapping to a tunnel instance.";

                        leaf ctrlName {

                          type "string"{
                          length "1..19";
                          }
                          description "The name of the control instance.";

                        }
                        leaf hostName {
                                type "string";
                                mandatory "true";
                                description "The name of the host.";
                        }
                        leaf routerID {

                                type "uint16";
                                mandatory "true";
                                description "Router ID.";
                        }
                        leaf rcvWinSize {

                                type "uint16";
                                description "Receiving window size.";
                        }
                        leaf helloInterval {

                                type "uint16";
                                description "Hello interval time.";
                        }
                        leaf digestType{

                                 type enumeration {
                                   enum "HMAC_MD5" {
                                     description "HMAC_MD5 algorithm.";
                                   }
                                   enum "HMAC_SHA_1" {
                                     description "HMAC_SHA_1 algorithm.";
                                   }
                                 }
                                 description "Digest algorithm selection.";
                        }
                        leaf authenNonce{

                                type password {
                                  length "1..16";
                                }
                                description "The authentication Nonce is in the password format.";
                        }
                }

        }
        container l2tpv3TunnelInstance {
          description "In contrast to the above control instance,
                       this configuration is regarding to the
                       tunnel interface itself.";

                list l2tpv3TunnelInstance {
                  key "tunnelName";
                  description "There could be multiple tunnel instance.";

                        leaf tunnelName {

                                type "string"{
                                        length "1..19";
                                }
                                description "The tunnel name.";
                        }
                        leaf sourceIfName {

                type if:interface-ref;
                description
                "Interface name as defined by ietf-interfaces";

                        }
                        leaf sourceIP {
                                type inet:ip-address;
                                mandatory "true";
                                description "Source IP address.";
                        }
                        leaf destIP {
                                type inet:ip-address;
                                mandatory "true";
                                description "Destination IP address.";
                        }
                        leaf tnlType {
                                      type enumeration {
                                                enum "static" {
                                                  description "Static tunnel.";
                                                }
                                                enum "auto" {
                                                  description "Automatic IP address.";
                                                }
                                        }
                                        mandatory "true";
                                        description "Tunnel type.";
                        }
                    choice tunnelType {
                        mandatory "true";
                        description "Each tunnel can be configured to only one type.";
                        case static{
                                    when "tnlType = 'static'";
                                        leaf localSessionId {

                                                type uint32 {
                                                        range "1..4294967295";
                                                }
                                                default "4294967295";
                                                description "Local session ID of the tunnel.";
                                        }
                                        leaf remoteSessionId {

                                                type uint32 {
                                                        range "1..4294967295";
                                                }
                                                default "4294967295";
                                                description "Remote session ID of the tunnel.";
                                        }
                                        leaf localCookieAutoMode {

                                                type enumeration {
                                                        enum "authNone" {
                                                          description "No authentication.";
                                                        }
                                                        enum "authPlain" {
                                                          description "Plain text authentication.";
                                                        }
                                                        enum "authCipher" {
                                                          description "Ciper authentication.";
                                                        }
                                                }
                                                mandatory "true";
                                                description "Local cookie authentication mode.";
                                        }

                        choice localCookieMode {
                           default authNone;
                           description "Each tunnel can be configured to only one local cookie mode.";

                                                case authNone {
                                                when "localCookieAutoMode = 'authNone'";

                                                }
                                                case authPlain {
                                                when "localCookieAutoMode = 'authPlain'";
                                                        leaf localCookieLength {

                                                                type enumeration {
                                                                        enum "4" {
                                                                         description "4 byte cookie.";
                                                                        }
                                                                        enum "8" {
                                                                         description "8 byte cookie.";
                                                                        }
                                                                }
                                                                default "4";
                                                                description "Local cookie length.";
                                                        }
                                                        leaf localHighCookie {

                                                                type "hexBinary"{
                                                                    length "3..6";
                                                                }
                                                                description "Local high cookie.";
                                                        }
                                                        leaf localLowCookie {

                                                                type "hexBinary"{
                                                                    length "3..6";
                                                                }
                                                                description "Local low cookie.";
                                                        }
                                                }
                                                case authCipher {
                                                when "localCookieAutoMode = 'authCipher'";
                                                        leaf localCookieCipher {

                                                                type password {
                                                                length "1..8";
                                                                }
                                                                description "Local cookie cipher.";
                                                        }
                                                }
                                        }
                                        leaf remoteCookieAutoMode {

                                                type enumeration {
                                                        enum "authNone" {
                                                          description "No authentication.";
                                                        }
                                                        enum "authPlain" {
                                                          description "Plain text authentication.";
                                                        }
                                                        enum "authCipher"        {
                                                          description "Plain text authentication.";
                                                        }
                                                }
                                                mandatory "true";
                                                description "Remote Cookie AutoMode.";
                                        }
                                        choice remoteCookieMode {
                                                default authNone;
                                                description "Choosing one remote cookie mode.";
                                                case authNone {
                        when "remoteCookieAutoMode = 'authNone'";
                                                }
                                                case authPlain {
                                                when "remoteCookieAutoMode = 'authPlain'";
                                                        leaf remoteCookieLength {

                                                                type enumeration {
                                                                        enum "4" {
                                                                          description "Cookie length is 4 byte.";
                                                                        }
                                                                        enum "8" {
                                                                          description "Cookie length is 4 byte.";
                                                                        }
                                                                }
                                                                default "4";
                                                                description "Remote Cookie length.";
                                                        }
                                                        leaf remoteHighCookie {

                                                                type "hexBinary"{
                                                                    length "3..6";
                                                                }
                                                                description "Remote high Cookie.";
                                                        }
                                                        leaf remoteLowCookie {

                                                                type "hexBinary"{
                                                                    length "3..6";
                                                                }
                                                                description "Remote low Cookie.";
                                                        }
                                                }
                                                case authCipher {
                                                when "remoteCookieAutoMode = 'authCipher'";
                                                        leaf remoteCookieCipher {

                                                                type password {
                                                                        length "1..8";
                                                                }
                                                                description "Remote Cookie cipher.";
                                                        }
                                                }
                                        }
                }
                        case auto{
                    when "tnlType = 'auto'";
                                        leaf ctrlName {

                                                type string{
                                                        length "1..19";
                                                }
                                                mandatory "true";
                                                description "Relevant control instance name.";
                                        }
                                        leaf encapType {

                                                type enumeration
                                                {
                                                        enum "HDLC" {
                                                          description "HDLC encapsulation.";
                                                        }
                                                        enum "Ethernet" {
                                                          description "Ethernet encapsulation.";
                                                        }
                                                        enum "VLAN" {
                                                          description "VLAN encapsulation.";
                                                        }
                                                        enum "ATM" {
                                                          description "ATM encapsulation.";
                                                        }
                                                }
                                                mandatory "true";
                                                description "Encapsulation type.";
                                        }

                            }
                    }

                        leaf sendPacket {
                                type "uint64";
                                config "false";
                                description "Sent packet count.";
                        }
                        leaf sendByte {
                                type "uint64";
                                config "false";
                                description "Sent byte count.";
                        }
                        leaf rcvPacket {
                                type "uint64";
                                config "false";
                                description "Received packet count.";
                        }
                        leaf receiveByte {
                                type "uint64";
                                config "false";
                                description "Received byte count.";
                        }
                        leaf recvDropPacket {
                                type "uint64";
                                config "false";
                                description "Drop packet count among the received packets.";
                        }
                        leaf cookieMisDropPacket {
                                type "uint64";
                                config "false";
                                description "Cookie mis-drop packet count.";
                        }
                        leaf state {
                                type enumeration {
                                        enum "down" {
                                                value "0";
                                                description "down:";
                                        }
                                        enum "up" {
                                                value "1";
                                                description "up:";
                                        }
                                }
                                config "false";
                                description "Tunnel running state.";
                        }
                }
        }
}
