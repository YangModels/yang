module iana-bgp-community-types {
  yang-version 1.1;
  namespace
    "urn:ietf:params:xml:ns:yang:iana-bgp-community-types";
  prefix bct;

  import ietf-yang-semver {
    prefix ysv;
    reference
      "I-D.ietf-netmod-yang-semver: YANG Semantic Versioning";
  }

  organization
    "IANA";
  contact
    "Internet Assigned Numbers Authority

     Postal: ICANN
             12025 Waterfront Drive, Suite 300
             Los Angeles, CA 90094-2536
             United States of America
     Tel:    +1 310 301 5800
     <mailto:iana@iana.org>

     Authors: Mahesh Jethanandani (mjethanandani at gmail.com),
              Keyur Patel (keyur at arrcus.com),
              Susan Hares (shares at ndzh.com),
              Jeffrey Haas (jeffrey.haas at hpe.com).";

  description
    "This module contains data definitions for BGP Communities in
     their various forms.  It can be imported by modules that make
     use of BGP attributes.

     This YANG module is maintained by IANA and reflects the
     'BGP Well Known Communities' registry at IANA.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     The initial version of this YANG module is part of RFC XXXX;
     see the RFC itself for full legal notices.

     The most recent version of this YANG module is available at
     <https://www.iana.org/assignments/iana-bgp-community-types>.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-10-31 {
    description
      "Initial Version";
    ysv:version 0.0.9;
    reference
      "RFC XXXX: YANG module for Border Gateway Protocol (BGP-4).";
  }

  /*
   * Identities.
   */

  /* BGP Well-Known Standard (RFC 1997) Community Identities. */

  identity bgp-well-known-std-community {
    description
      "Base identity for reserved communities within the standard
       community space defined by RFC 1997. These communities must
       fall within the range 0xFFFF0000 to 0xFFFFFFFF";
    reference
      "RFC 1997: BGP Communities Attribute.";
  }

  identity no-export {
    base bgp-well-known-std-community;
    description
      "Do not export NLRI received carrying this community outside
       the bounds of this autonomous system, or this confederation
       (if the local autonomous system is a confederation member AS).
        This community has a value of 0xFFFFFF01.";
    reference
      "RFC 1997: BGP Communities Attribute.";
  }

  identity no-advertise {
    base bgp-well-known-std-community;
    description
      "All NLRI received carrying this community must not be
       advertised to other BGP peers. This community has a value of
       0xFFFFFF02.";
    reference
      "RFC 1997: BGP Communities Attribute.";
  }

  identity no-export-subconfed {
    base bgp-well-known-std-community;
    description
      "All NLRI received carrying this community must not be
       advertised to external BGP peers - including over
       confederation sub-AS boundaries. This community has a value of
       0xFFFFFF03.";
    reference
      "RFC 1997: BGP Communities Attribute.";
  }

  identity no-peer {
    base bgp-well-known-std-community;
    description
      "An autonomous system receiving NLRI tagged with this community
       is advised not to re-advertise the NLRI to external bilateral
       peer autonomous systems. An AS may also filter received NLRI
       from bilateral peer sessions when they are tagged with this
       community value. This community has a value of 0xFFFFFF04.";
    reference
      "RFC 3765: NOPEER Community for BGP.";
  }

  /*
   * Typedefs.
   */

  typedef bgp-well-known-community-type {
    type identityref {
      base bgp-well-known-std-community;
    }
    description
      "Type definition for well-known IETF community attribute
       values.";
    reference
      "IANA Border Gateway Protocol (BGP) Well Known Communities";
  }

  typedef bgp-ipv6-ext-community-rt-type {
    type string {
      pattern 'ipv6\-route\-target:'
            + '((:|[0-9a-fA-F]{0,4}):)([0-9a-fA-F]{0,4}:){0,5}'
            + '((([0-9a-fA-F]{0,4}:)?(:|[0-9a-fA-F]{0,4}))|'
            + '(((25[0-5]|2[0-4][0-9]|1[0-9]{2}|[1-9]?[0-9])\.){3}'
            + '(25[0-5]|2[0-4][0-9]|1[0-9]{2}|[1-9]?[0-9])))'
            + ':'
            + '([0-9]|[1-9][0-9]{1,3}|[1-5][0-9]{4}|'
            + '6[0-5][0-9]{3}|66[0-4][0-9]{2}|'
            + '665[0-2][0-9]|6653[0-5])';
      pattern 'ipv6\-route\-target:'
            + '((([^:]+:){6}(([^:]+:[^:]+)|(.*\..*)))|'
            + '((([^:]+:)*[^:]+)?::(([^:]+:)*[^:]+)?))'
            + ':'
            + '([0-9]|[1-9][0-9]{1,3}|[1-5][0-9]{4}|'
            + '6[0-5][0-9]{3}|66[0-4][0-9]{2}|'
            + '665[0-2][0-9]|6653[0-5])';
    }
    description
      "Type 0x00, Sub-Type 0x02: IPv6 Route-Target
       ipv6-route-target:(IPv6 address):(local-admin)
       16 octets global administrator and 2 octets local
       administrator.

       Note: The patterns above are excerpted from RFC 8294.";
    reference
      "RFC 5701: IPv6 Address Specific BGP Extended Community
       Attribute, Section 3.";
  }

  typedef bgp-ipv6-ext-community-ro-type {
    type string {
      pattern 'ipv6\-route\-origin:'
            + '((:|[0-9a-fA-F]{0,4}):)([0-9a-fA-F]{0,4}:){0,5}'
            + '((([0-9a-fA-F]{0,4}:)?(:|[0-9a-fA-F]{0,4}))|'
            + '(((25[0-5]|2[0-4][0-9]|1[0-9]{2}|[1-9]?[0-9])\.){3}'
            + '(25[0-5]|2[0-4][0-9]|1[0-9]{2}|[1-9]?[0-9])))'
            + ':'
            + '([0-9]|[1-9][0-9]{1,3}|[1-5][0-9]{4}|'
            + '6[0-5][0-9]{3}|66[0-4][0-9]{2}|'
            + '665[0-2][0-9]|6653[0-5])';
      pattern 'ipv6-route\-origin:'
            + '((([^:]+:){6}(([^:]+:[^:]+)|(.*\..*)))|'
            + '((([^:]+:)*[^:]+)?::(([^:]+:)*[^:]+)?))'
            + ':'
            + '([0-9]|[1-9][0-9]{1,3}|[1-5][0-9]{4}|'
            + '6[0-5][0-9]{3}|66[0-4][0-9]{2}|'
            + '665[0-2][0-9]|6653[0-5])';
    }
    description
      "Type 0x00, Sub-Type 0x03: IPv6 Route-Origin
       ipv6-route-origin:(IPv6 address):(local-admin)
       16 octets global administrator and 2 octets local
       administrator.

       Note: The patterns above are excerpted from RFC 8294.";
    reference
      "RFC 5701: IPv6 Address Specific BGP Extended Community
       Attribute, Section 3.";
  }

  typedef bgp-ipv6-ext-community-raw-type {
    type string {
      pattern 'ipv6-raw:'
            + '([0-9A-Fa-f][0-9A-Fa-f]:){19}'
            + '[0-9A-Fa-f][0-9A-Fa-f]';
    }
    description
      "Raw IPv6 extended community value encoded as
       ipv6-raw:(hex-octet):(hex-octet):...:(hex-octet)
       with 20 hex-encoded octets.";
  }

  typedef bgp-ipv6-ext-community-type {
    type union {
      type bgp-ipv6-ext-community-rt-type;
      type bgp-ipv6-ext-community-ro-type;
      type bgp-ipv6-ext-community-raw-type;
    }
    description
      "Type definition for IPv6 extended community attributes.
       It includes a way to specify a 'raw' string that
       is followed by 20 bytes of octet string to support
       new and experimental type definitions.";
    reference
      "RFC 5701: IPv6 Address Specific BGP Extended Community
       Attribute, Section 3.";
  }

  typedef bgp-ext-community-rt-asn-type {
    type string {
      pattern 'route\-target:'
            + '([0-9]|[1-9][0-9]{1,3}|[1-5][0-9]{4}|'
            + '6[0-5][0-9]{3}|66[0-4][0-9]{2}|'
            + '665[0-2][0-9]|6653[0-5])'
            + 'L?'
            + ':'
            + '([0-9]|[1-9][0-9]{1,8}|[1-3][0-9]{9}|4[01][0-9]{8}|'
            + '42[0-8][0-9]{7}|429[0-3][0-9]{6}|4294[0-8][0-9]{5}|'
            + '42949[0-5][0-9]{4}|429496[0-6][0-9]{3}|'
            + '4294967[01][0-9]{2}|42949672[0-8][0-9]|'
            + '429496729[0-5])';
    }
    description
      "Type 0x00, Sub-Type 0x02: Route-Target
       route-target:(ASN):(local-admin)
       2 octets global administrator and 4 octets local
       administrator.

       When the 'L' qualifier is used, this community
       represents a Type 0x02, Sub-Type 0x02: Route-Target
       route-target:(ASN):(local-admin) 4 octets global
       administrator with a value < 65536 and 2 octets local
       administrator.";
    reference
      "RFC 4360: BGP Extended Communities Attribute,
       Section 4.
       RFC 5668: 4-Octet AS Specific BGP Extended Community,
       Section 4.";
  }

  typedef bgp-ext-community-rt-ipv4-type {
    type string {
      pattern 'route\-target:'
            + '(([0-9]|[1-9][0-9]|1[0-9][0-9]|2[0-4][0-9]|'
            + '25[0-5])\.){3}([0-9]|[1-9][0-9]|1[0-9][0-9]|'
            + '2[0-4][0-9]|25[0-5])'
            + ':'
            + '([0-9]|[1-9][0-9]{1,3}|[1-5][0-9]{4}|'
            + '6[0-5][0-9]{3}|66[0-4][0-9]{2}|'
            + '665[0-2][0-9]|6653[0-5])';
    }
    description
      "Type 0x01, Sub-Type 0x02: Route-Target
       route-target:(IPv4):(local-admin)
       4 octets IP address global administrator and 2 octets
       local administrator.";
    reference
      "RFC 4360: BGP Extended Communities Attribute,
       Section 4.";
  }

  typedef bgp-ext-community-rt-4octet-asn-type {
    type string {
      pattern 'route\-target:'
            + '([0-9]|[1-9][0-9]{1,8}|[1-3][0-9]{9}|4[01][0-9]{8}|'
            + '42[0-8][0-9]{7}|429[0-3][0-9]{6}|4294[0-8][0-9]{5}|'
            + '42949[0-5][0-9]{4}|429496[0-6][0-9]{3}|'
            + '4294967[01][0-9]{2}|42949672[0-8][0-9]|'
            + '429496729[0-5])'
            + ':'
            + '([0-9]|[1-9][0-9]{1,3}|[1-5][0-9]{4}|'
            + '6[0-5][0-9]{3}|66[0-4][0-9]{2}|'
            + '665[0-2][0-9]|6653[0-5])';
    }
    description
      "Type 0x02, Sub-Type 0x02: Route-Target
       route-target:(ASN):(local-admin)
       4 octets global administrator and 2 octets local
       administrator.";
    reference
      "RFC 5668: 4-Octet AS Specific BGP Extended Community,
       Section 4.";
  }

  typedef bgp-ext-community-ro-asn-type {
    type string {
      pattern 'route\-origin:'
            + '([0-9]|[1-9][0-9]{1,3}|[1-5][0-9]{4}|'
            + '6[0-5][0-9]{3}|66[0-4][0-9]{2}|'
            + '665[0-2][0-9]|6653[0-5])'
            + 'L?'
            + ':'
            + '([0-9]|[1-9][0-9]{1,8}|[1-3][0-9]{9}|4[01][0-9]{8}|'
            + '42[0-8][0-9]{7}|429[0-3][0-9]{6}|4294[0-8][0-9]{5}|'
            + '42949[0-5][0-9]{4}|429496[0-6][0-9]{3}|'
            + '4294967[01][0-9]{2}|42949672[0-8][0-9]|'
            + '429496729[0-5])';
    }
    description
      "Type 0x00, Sub-Type 0x03: Route-Origin
       route-origin:(ASN):(local-admin)
       2 octets global administrator and 4 octets local
       administrator.

       When the 'L' qualifier is used, this community
       represents a Type 0x02, Sub-Type 0x03: Route-Origin
       route-origin:(ASN):(local-admin) 4 octets global
       administrator with a value < 65536 and 2 octets local
       administrator.";
    reference
      "RFC 4360: BGP Extended Communities Attribute,
       Section 5.
       RFC 5668: 4-Octet AS Specific BGP Extended Community,
       Section 4.";
  }

  typedef bgp-ext-community-ro-ipv4-type {
    type string {
      pattern 'route\-origin:'
            + '(([0-9]|[1-9][0-9]|1[0-9][0-9]|2[0-4][0-9]|'
            + '25[0-5])\.){3}([0-9]|[1-9][0-9]|1[0-9][0-9]|'
            + '2[0-4][0-9]|25[0-5])'
            + ':'
            + '([0-9]|[1-9][0-9]{1,3}|[1-5][0-9]{4}|'
            + '6[0-5][0-9]{3}|66[0-4][0-9]{2}|'
            + '665[0-2][0-9]|6653[0-5])';
    }
    description
      "Type 0x01, Sub-Type 0x03: Route-Origin
       route-origin:(IPv4):(local-admin)
       4 octets IP address global administrator and 2 octets
       local administrator.";
    reference
      "RFC 4360: BGP Extended Communities Attribute,
       Section 5.";
  }

  typedef bgp-ext-community-ro-4octet-asn-type {
    type string {
      pattern 'route\-origin:'
            + '([0-9]|[1-9][0-9]{1,8}|[1-3][0-9]{9}|4[01][0-9]{8}|'
            + '42[0-8][0-9]{7}|429[0-3][0-9]{6}|4294[0-8][0-9]{5}|'
            + '42949[0-5][0-9]{4}|429496[0-6][0-9]{3}|'
            + '4294967[01][0-9]{2}|42949672[0-8][0-9]|'
            + '429496729[0-5])'
            + ':'
            + '([0-9]|[1-9][0-9]{1,3}|[1-5][0-9]{4}|'
            + '6[0-5][0-9]{3}|66[0-4][0-9]{2}|'
            + '665[0-2][0-9]|6653[0-5])';
    }
    description
      "Type 0x02, Sub-Type 0x03: Route-Origin
       route-origin:(ASN):(local-admin)
       4 octets global administrator and 2 octets local
       administrator.";
    reference
      "RFC 5668: 4-Octet AS Specific BGP Extended Community,
       Section 4.";
  }

  typedef bgp-ext-community-raw-type {
    type string {
      pattern 'raw:'
            + '([0-9A-Fa-f][0-9A-Fa-f]:){7}'
            + '[0-9A-Fa-f][0-9A-Fa-f]';
    }
    description
      "Raw extended community value encoded as
       raw:(hex-octet):(hex-octet):...:(hex-octet)
       with 8 hex-encoded octets.";
  }

  typedef bgp-ext-community-type {
    type union {
      type bgp-ext-community-rt-asn-type;
      type bgp-ext-community-rt-ipv4-type;
      type bgp-ext-community-rt-4octet-asn-type;
      type bgp-ext-community-ro-asn-type;
      type bgp-ext-community-ro-ipv4-type;
      type bgp-ext-community-ro-4octet-asn-type;
      type bgp-ext-community-raw-type;
    }
    description
      "Type definition for extended community attributes.
       It includes a way to specify a 'raw' string that
       is followed by 8 bytes of octet string to support
       new and experimental type definitions.";
    reference
      "RFC 4360: BGP Extended Communities Attribute.";
  }
}
