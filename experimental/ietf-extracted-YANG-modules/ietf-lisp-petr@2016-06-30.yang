module ietf-lisp-petr {
  namespace "urn:ietf:params:xml:ns:yang:ietf-lisp-petr";
  prefix lisp-petr;
  import ietf-lisp {
    prefix lisp;
  }
  organization
    "IETF LISP (Locator/ID Separation Protocol) Working Group";
  contact
    "lisp@ietf.org";
  description
    "This YANG module defines the generic configuration
     data for a LISP PETR. The module can be extended by vendors to
     define vendor-specific configuration parameters and policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";
  revision 2016-06-30 {
    description
      "Initial revision.";
    reference
      "https://tools.ietf.org/html/rfc6832";
  }
  identity petr {
    base lisp:lisp-role;
    description
      "LISP PETR.";
  }
  augment "/lisp:lisp/lisp:lisp-router-instances"
  + "/lisp:lisp-router-instance/lisp:lisp-role" {
    when "lisp:lisp-role-type = 'lisp-petr:petr'" {
      description
        "Augment is valid when LISP device type is PETR.";
    }
    description
      "This augments LISP devices list with PETR specific
       parameters.";
    container proxy-etr-cfg {
      presence "LISP PETR operation enabled";
      description
        "Proxy ETR configuration parameters.";

      uses lisp:servicing-eids-grouping;
    }//proxy-etr-cfg
  }
}
