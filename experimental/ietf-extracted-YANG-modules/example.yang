module example {

namespace "http://example.com/ns/interfaces";

prefix exam;

typedef itf-status-type {
   description "Interface status";
   type enumeration {
     enum ok;
     enum 'waking up';
     enum 'not feeling so good';
     enum 'better check it out';
     enum 'better call for help';
   }
   default ok;
}

container interfaces {
    description "Example interfaces group";

    list interface {
      description "Example interface entry";
      key name;

      leaf name {
        description
          "The administrative name of the interface.
           This is an identifier which is only unique
           within the scope of this list, and only
           within a specific server.";
        type string {
          length "1 .. max";
        }
      }

      leaf mtu {
        description
          "The maximum transmission unit (MTU) value assigned to
           this interface.";
        type uint32;
        default 1500;
      }

      leaf itf-status {
        description
          "The current status of this interface.";
        type itf-status-type;
        config false;
      }
    }
  }
}
