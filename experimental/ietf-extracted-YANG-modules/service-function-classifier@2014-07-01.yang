module service-function-classifier {
  yang-version 1;

  namespace "urn:cisco:params:xml:ns:yang:sfc-scf";

  prefix sfc-scf;

  import ietf-acl {prefix "ietf-acl";}

  organization "Cisco Systems, Inc.";
  contact "Reinaldo Penno <repenno@cisco.com>";

  description
    "This module contains a collection of YANG definitions for
     managing service classification functions.";

  revision 2014-07-01 {
    description
    "Revised based on Opendaylight Project feedback";
  }

  grouping attachment-point {
    description
      "Reusable group of all possible attachment point types";
    choice attachment-point-type {
      description
        "Provides a choice between access list
         attachment point types";
      case bridge {
        leaf bridge {
          type string;
          description
            "OVS bridge as an attachment point";
        }
      }
      case interface {
        leaf interface {
          type string;
          description
            "interface name as attachment point";
        }
      }
    }
  }

  container service-function-classifiers {
    description
    "Classifier container which represents the ACL being applied,
     attachment point and the chain associated with that ACL.";
    list service-function-classifier {
      description
        "A list that holds all service function classifiers";
      key "name";
      leaf name {
        type string;
         description
         "Classification function name";
      }
      leaf access-list {
        description
          "The ACL name associated with this classifier";
        type string;
      }

      leaf rendered-service-path {
        description
           "The classifier will direct packets to the SFP
          specified here";
        type string;
      }
      list scl-service-function-forwarder {
        description
          "The classifier will be attached to these SFFs";
        key "name";
        leaf name {
          description
          "The classifier will be attached to this SFF";
          type string;
        }
        uses attachment-point {
          description "Classifier attachment point";
        }
      }
    }
  }

  container service-function-classifiers-state {
    description
      "This container hold operational state for all service
       function classifiers";
    config false;
    list service-function-classifier-state {
      description
        "This list holds operational data for all service function
         classifiers in the domain";
      key "name";
      leaf name {
        type string;
        description
          "The name of the service function classifier";
      }
      list scl-rendered-service-path {
        key "name";
        leaf name {
          type string;
          description
            "The name of the Rendered Service Path";
        }
        description
        "A list of all rendered service paths that use this classifier";
      }
    }
  }
}
