module ietf-bgp-rib-entry {
  yang-version 1.1;
  namespace "urn:ietf:params:xml:ns:yang:ietf-bgp-rib-entry";
  prefix bre;

  import ietf-inet-types {
    prefix inet;
    reference
      "RFC 9911: Common YANG Data Types.";
  }
  import ietf-yang-types {
    prefix yang;
    reference
      "RFC 9911: Common YANG Data Types.";
  }
  import ietf-routing {
    prefix rt;
    reference
      "RFC 8022: A YANG Data Model for Routing Management.";
  }
  import iana-bgp-afi-safi-types {
    prefix bast;
    reference
      "RFC XXXX: YANG Model for Border Gateway Protocol (BGP-4).";
  }
  import ietf-bgp-types {
    prefix ibt;
    reference
      "RFC XXXX: YANG Model for Border Gateway Protocol (BGP-4).";
  }

  // TODO: in the future import the single capabilities module if at idr
  // they decide to move from submodules to a modules
  import ietf-bgp {
    prefix bgp;
    reference
      "RFC XXXX: YANG Model for Border Gateway Protocol (BGP-4).";
  }

  organization
    "IETF Draft";
  contact
    "Author:    Thomas Graf
                <mailto:thomas.graf@swisscom.com>
                Paolo Lucente
                <mailto:paolo@ntt.net>
                Leonardo Rodoni
                <mailto:leonardo.rodoni@swisscom.com>
                Maxence Younsi
                <mailto:maxence.younsi4@swisscom.com>";

  description
    "Defines a module for representing a single entry from a BGP
     Routing Information Base (RIB). The submodule supports entries
     from 5 logical RIB types per address family:

     loc-rib: An entry from the main BGP routing table for the local
     routing instance, containing best-path selections for each
     prefix. The key for the loc-rib entry corresponds either to a
     route in the adj-rib-in-post table or a route redistributed
     from another protocol.

     adj-rib-in-pre: An entry from the per-neighbor table containing
     the BGP routes received from the neighbor before any local
     input policy rules have been applied. This can be considered
     the 'raw' routes from a given neighbor.

     adj-rib-in-post: An entry from the per-neighbor table containing
     the routes received from the neighbor that are eligible for
     best-path selection after local input policy rules have been
     applied. The 'best-path' leaf is attached to the route selected
     by the BGP Decision Process (RFC 4271, Section 9.1). Such
     routes may be present in the loc-rib, described above,
     when local configuration determines that the BGP best-path will
     be used for that destination.

     adj-rib-out-pre: An entry from the per-neighbor table containing
     routes eligible for sending (advertising) to the neighbor before
     output policy rules have been applied.

     adj-rib-out-post: An entry from the per-neighbor table containing
     routes eligible for sending (advertising) to the neighbor after
     output policy rules have been applied.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2026 IETF Trust and the persons identified as
     authors of the code. All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC XXXX; see the RFC
     itself for full legal notices.";

  revision 2026-10-30 {
    description
      "Initial Version";
    reference
      "RFC XXXX";
  }

  grouping bgp-common-route-attributes {
    description
      "BGP path attributes and communities.";
    uses bgp-path-attributes;
    uses bgp:bgp-community-attr-state;
    uses bgp:ext-community-attributes;
    uses bgp:ipv6-ext-community-attributes;
    uses bgp:large-community-attributes;
  }

  grouping bgp-path-attributes {
    description
      "BGP path attributes.";
    container attributes {
      description
        "BGP path attribute parameters.";
      leaf origin {
        type ibt:bgp-origin-attr-type;
        mandatory true;
        description
          "BGP attribute defining the origin of the path information.";
        reference
          "RFC 4271: A Border Gateway Protocol 4 (BGP-4), Section 5.1.1.";
      }
      container as-path {
        description
          "Enclosing container for the list of AS path segments.";
        reference
          "RFC 4271: A Border Gateway Protocol 4 (BGP-4), Section 5.1.2.
           RFC 6793: BGP Support for Four-Octet Autonomous System (AS)
           Number Space.
           RFC 5065: Autonomous System Confederations for BGP.";
        list segment {
          uses bgp:bgp-as-path-segment;
          description
            "List of AS PATH segments.";
        }
      }
      leaf next-hop {
        type inet:ip-address;
        description
          "BGP next hop attribute.";
        reference
          "RFC 4271: A Border Gateway Protocol 4 (BGP-4), Section 5.1.3.";
      }
      leaf link-local-next-hop {
        type inet:ipv6-address;
        description
          "Link-local next-hop when using RFC 2545 procedures.";
        reference
          "RFC 2545: Use of BGP-4 Multiprotocol Extensions for IPv6
           Inter-Domain Routing.";
      }
      leaf med {
        type uint32;
        description
          "BGP multi-exit discriminator attribute.";
        reference
          "RFC 4271: A Border Gateway Protocol 4 (BGP-4), Section 5.1.4.";
      }
      leaf local-pref {
        type uint32;
        description
          "BGP local preference attribute.";
        reference
          "RFC 4271: A Border Gateway Protocol 4 (BGP-4), Section 5.1.5.";
      }
      container as4-path {
        description
          "AS4_PATH attribute for 4-octet AS numbers in Adj-RIB-In/Out.
           Not populated in Loc-RIB.";
        reference
          "RFC 6793: BGP Support for Four-octet AS Number Space.";
        list segment {
          uses bgp:bgp-as-path-segment;
          description
            "List of AS PATH segments.";
        }
      }
      container aggregator {
        description
          "BGP AGGREGATOR attribute.";
        reference
          "RFC 4271: A Border Gateway Protocol 4 (BGP-4), Section 5.1.7.
           RFC 6793: BGP Support for Four-octet AS Number Space.";
        leaf as {
          type inet:as-number;
          description
            "AS number of the aggregating router.";
          reference
            "RFC 4271: A Border Gateway Protocol 4 (BGP-4), Section 5.1.7.";
        }
        leaf identifier {
          type yang:dotted-quad;
          description
            "BGP Identifier of the aggregating router.";
          reference
            "RFC 4271: A Border Gateway Protocol 4 (BGP-4), Section 5.1.7.";
        }
      }
      container aggregator4 {
        description
          "AS4_AGGREGATOR attribute. Not populated in Loc-RIB.";
        reference
          "RFC 6793: BGP Support for Four-Octet Autonomous System (AS)
           Number Space.";
        leaf as4 {
          type inet:as-number;
          description
            "4-octet AS number of the aggregating router.";
          reference
            "RFC 6793: BGP Support for Four-Octet Autonomous System (AS)
             Number Space, Section 3.";
        }
        leaf identifier {
          type yang:dotted-quad;
          description
            "BGP Identifier of the aggregating router.";
          reference
            "RFC 6793: BGP Support for Four-Octet Autonomous System (AS)
             Number Space, Section 3.";
        }
      }
      leaf atomic-aggregate {
        type boolean;
        description
          "BGP ATOMIC_AGGREGATE attribute.";
        reference
          "RFC 4271: A Border Gateway Protocol 4 (BGP-4), Section 5.1.6.";
      }
      leaf originator-id {
        type yang:dotted-quad;
        description
          "BGP ORIGINATOR_ID attribute for route reflection.";
        reference
          "RFC 4456: BGP Route Reflection, Section 8.";
      }
      leaf-list cluster-list {
        type yang:dotted-quad;
        description
          "BGP CLUSTER_LIST attribute for route reflection.";
        reference
          "RFC 4456: BGP Route Reflection, Section 8.";
      }
      leaf aigp-metric {
        type uint64;
        description
          "BGP AIGP attribute.";
        reference
          "RFC 7311: The Accumulated IGP Metric Attribute for BGP.";
      }
    }
  }

  grouping rib-entry {
    description
      "Grouping for a BGP RIB entry. The AFI-SAFI and the RIB the
       entry belongs to are given by the afi-safi-type and rib-type
       leaves, placed next to the rib-entry container so that they
       can be read without parsing the entry itself. The route data
       is shared by all RIB types; the NLRI is specific to the
       AFI-SAFI.";

    leaf afi-safi-type {
      type identityref {
        base bast:afi-safi-type;
      }
      mandatory true;
      description
        "AFI,SAFI name.";
    }

    leaf rib-type {
      type enumeration {
        enum loc-rib {
          description
            "Main BGP routing table for the local routing instance,
             containing best-path selections for each prefix.";
        }
        enum adj-rib-in-pre {
          description
            "Routes received from the neighbor before any local
             input policy rules or filters have been applied.";
        }
        enum adj-rib-in-post {
          description
            "Routes received from the neighbor after local input
             policy rules have been applied.";
        }
        enum adj-rib-out-pre {
          description
            "Routes eligible to be sent to the neighbor before
             output policy rules have been applied.";
        }
        enum adj-rib-out-post {
          description
            "Routes eligible to be sent to the neighbor after
             output policy rules have been applied.";
        }
      }
      mandatory true;
      description
        "The RIB the route or End-of-RIB marker belongs to.";
    }

    container rib-entry {
      description
        "Encapsulates the route entry for the AFI-SAFI given by
         afi-safi-type and the RIB given by rib-type.";

      choice entry-type {
        mandatory true;
        description
          "Either a route or an End-of-RIB marker.";

        case route {
          leaf path-id {
            type uint32;
            description
              "Path identifier of the route (RFC 7911). For the
               adj-rib-in RIB types this is the received (Rx)
               path-id, for the adj-rib-out RIB types the sent (Tx)
               path-id. For the loc-rib it is a locally generated
               value. Absent when ADD-PATH is not in use.";
            reference
              "RFC 7911: Advertisement of Multiple Paths in BGP.";
          }

          leaf origin {
            when "../../rib-type = 'loc-rib'";
            type union {
              type inet:ip-address;
              type identityref {
                base rt:routing-protocol;
              }
            }
            description
              "Origin of a Loc-RIB route. If the route is learned
               from a neighbor, this is the neighbor address. If the
               route was injected or redistributed from another
               protocol, this is the source protocol.";
          }

          container nlri {
            description
              "The Network Layer Reachability Information of the
               route, selected by afi-safi-type. Further AFI-SAFIs
               are supported by augmenting the afi-safi choice with
               a container named after the AFI-SAFI identity.";
            choice afi-safi {
              mandatory true;
              description
                "Choice of AFI-SAFI specific NLRI, enforced by the
                 afi-safi-type leaf.";

              container ipv4-unicast {
                when "derived-from-or-self(../../../afi-safi-type, "
                   + "'bast:ipv4-unicast')";
                description
                  "IPv4 unicast NLRI.";
                leaf prefix {
                  type inet:ipv4-prefix;
                  mandatory true;
                  description
                    "The IPv4 prefix.";
                }
              }
              container ipv6-unicast {
                when "derived-from-or-self(../../../afi-safi-type, "
                   + "'bast:ipv6-unicast')";
                description
                  "IPv6 unicast NLRI.";
                leaf prefix {
                  type inet:ipv6-prefix;
                  mandatory true;
                  description
                    "The IPv6 prefix.";
                }
              }
            }
          }

          uses bgp-common-route-attributes;
          uses bgp:bgp-common-route-annotations-state;
          uses bgp:bgp-unknown-attr-top;
          uses bgp:rib-ext-route-annotations;
        }

        case end-of-rib {
          container end-of-rib {
            presence
              "Indicates an End-of-RIB marker.";
            description
              "End-of-RIB marker for the AFI-SAFI given by
               afi-safi-type and the RIB given by rib-type; carries
               no route.";
          }
        }
      }
    }
  }
}
