submodule openconfig-mpls-te {

  yang-version "1";

  belongs-to "openconfig-mpls" {
    prefix "mpls";
  }

  // import some basic types
  import ietf-inet-types { prefix inet; }
  import openconfig-mpls-rsvp { prefix rsvp; }
  import openconfig-mpls-sr { prefix sr; }
  import openconfig-mpls-types {prefix mplst; }
  import openconfig-types { prefix oc-types; }
  import ietf-yang-types { prefix yang; }

  // meta
  organization "OpenConfig working group";

  contact
    "OpenConfig working group
    netopenconfig@googlegroups.com";

  description
    "Configuration related to constrained-path LSPs and traffic
    engineering.  These definitions are not specific to a particular
    signaling protocol or mechanism (see related submodules for
    signaling protocol-specific configuration).";

  revision "2015-10-04" {
    description
      "Work in progress";
    reference "TBD";
  }

  // extension statements

  // feature statements

  // identity statements

  // using identities for path comp method, though enums may also
  // be appropriate if we decided these are the primary computation
  // mechanisms in future.
  identity path-computation-method {
    description
     "base identity for supported path computation
      mechanisms";
  }

  identity locally-computed {
    base path-computation-method;
    description
      "indicates a constrained-path LSP in which the
      path is computed by the local LER";
  }

  identity externally-queried {
    base path-computation-method;
    description
     "constrained-path LSP in which the path is
      obtained by querying an external source, such as a PCE server";
  }

  identity explicitly-defined {
    base path-computation-method;
    description
     "constrained-path LSP in which the path is
      explicitly specified as a collection of strict or/and loose
      hops";
  }

  // typedef statements

  typedef mpls-hop-type {
    type enumeration {
      enum LOOSE {
        description "loose hop in an explicit path";
      }
      enum STRICT {
        description "strict hop in an explicit path";
      }
    }
    description
     "enumerated type for specifying loose or strict
      paths";
  }

  typedef te-metric-type {
    type union {
      type enumeration {
        enum IGP {
          description
           "set the LSP metric to track the underlying
            IGP metric";
        }
      }
      type uint32;
    }
    description
     "union type for setting the LSP TE metric to a
      static value, or to track the IGP metric";
  }
  typedef cspf-tie-breaking {
    type enumeration {
      enum RANDOM {
        description
         "CSPF calculation selects a random path among
          multiple equal-cost paths to the destination";
      }
      enum LEAST_FILL {
        description
         "CSPF calculation selects the path with greatest
          available bandwidth";
      }
      enum MOST_FILL {
        description "CSPF calculation selects the path with the least
          available bandwidth";
      }
    }
    default RANDOM;
    description
     "type to indicate the CSPF selection policy when
      multiple equal cost paths are available";
  }

  // grouping statements

  grouping te-tunnel-reoptimize_config {
    description "Definition for reoptimize timer configuration";
    leaf te-lsp-reoptimize-timer {
      type uint16;
      units seconds;
      description
       "frequency of reoptimization of
        a traffic engineered LSP";
    }
  }

  grouping path-placement-constraints {
    description
      "Top level grouping for path placement constraints";

      container admin-groups {
        description
          "Include/Exclude constraints for link affinities";
        uses te-lsp-exclude-admin-group_config;
        uses te-lsp-include-any-admin-group_config;
        uses te-lsp-include-all-admin-group_config;
      }
  }

  grouping te-tunnel-bandwidth_config {
    description "Bandwidth configuration for TE LSPs";
    choice bandwidth {
      default explicit;
      description
       "select how bandwidth for the LSP will be
        specified and managed";
      case explicit {
        leaf set-bandwidth {
          type uint32;
          description
           "set bandwidth explicitly, e.g., using
            offline calculation";
        }
      }
      case auto {
        uses te-lsp-auto-bandwidth_config;
      }
    }
  }

  grouping te-lsp-auto-bandwidth_config {
    description "Configuration parameters related to autobandwidth";
    container auto-bandwidth {
      description
       "configure auto-bandwidth operation in
        which devices automatically adjust bandwidth to meet
        requirements";

      leaf enabled {
        type boolean;
        default false;
        description
         "enables mpls auto-bandwidth on the
          lsp";
      }

      leaf min-bw {
        type uint32;
        description
         "set the minimum bandwidth in Mbps for an
          auto-bandwidth LSP";
      }

      leaf max-bw {
        type uint32;
        description
         "set the maximum bandwidth in Mbps for an
          auto-bandwidth LSP";
      }

      leaf adjust-interval {
        type uint32;
        description
         "time in seconds between adjustments to
          LSP bandwidth";
      }

      leaf adjust-threshold {
        type oc-types:percentage;
        description
         "percentage difference between the LSP's
          specified bandwidth and its current bandwidth
          allocation -- if the difference is greater than the
          specified percentage, auto-bandwidth adjustment is
          triggered";
      }

      container overflow {
        description
         "configuration of MPLS overflow bandwidth
          adjustement for the LSP";
        uses te-lsp-overflow_config;
      }

      container underflow {
        description
         "configuration of MPLS underflow bandwidth
          adjustement for the LSP";
        uses te-lsp-underflow_config;
      }
    }
  }

  grouping  te-lsp-overflow_config {
    description
     "configuration for mpls lsp bandwidth
      overflow adjustment";

    leaf enabled {
      type boolean;
      default false;
      description
       "enables mpls lsp bandwidth overflow
        adjustment on the lsp";
    }

    leaf overflow-threshold {
      type oc-types:percentage;
      description
       "bandwidth percentage change to trigger
        an overflow event";

    }

    leaf trigger-event-count {
      type uint16;
      description
       "number of consecutive overflow sample
        events needed to trigger an overflow adjustment";
    }
  }

  grouping te-lsp-underflow_config {
    description
      "configuration for mpls lsp bandwidth
      underflow adjustment";

    leaf enabled {
      type boolean;
      default false;
      description
       "enables bandwidth underflow
        adjustment on the lsp";
    }

    leaf underflow-threshold {
      type oc-types:percentage;
      description
       "bandwidth percentage change to trigger
        and underflow event";
    }

    leaf trigger-event-count {
      type uint16;
      description
       "number of consecutive underflow sample
        events needed to trigger an underflow adjustment";
    }
  }

  grouping te-tunnel-metric_config {
    description "Configuration parameters related to LSP metric";
    leaf metric {
      type te-metric-type;
      description "LSP metric, either explicit or IGP";
    }
  }

  grouping te-lsp-exclude-admin-group_config {
    description
     "Configuration parameters related to admin-groups
      to exclude in path calculation";
    list exclude-groups {

      key exclude-admin-group-name;

      description
        "list of admin-groups to exclude in path calculation";

      leaf exclude-admin-group-name {
        type leafref {
          path "/mpls/te-global-attributes/mpls-admin-groups/" +
            "admin-group/admin-group-name";
        }
        description
          "name of the admin group -- references a defined admin
          group";
      }
    }
  }

  grouping te-lsp-include-all-admin-group_config {
    description
     "Configuration parameters related to admin-groups
      which all must be included in the path calculation";
    list include-all-groups {

      key all-admin-group-name;
      description
        "list of admin-groups of which all must be included";

      leaf all-admin-group-name {
        type leafref {
          path "/mpls/te-global-attributes/mpls-admin-groups/" +
            "admin-group/admin-group-name";
        }
        description
          "name of the admin group -- references a defined
          admin group";
      }
    }
  }

  grouping te-lsp-include-any-admin-group_config {
    description
     "Configuration parameters related to admin-groups
      of which one must be included in the path calculation";
    list include-any-groups {

      key any-admin-group-name;
      description
        "list of admin-groups of which one must be included";

      leaf any-admin-group-name {
        type leafref {
          path "/mpls/te-global-attributes/mpls-admin-groups/" +
            "admin-group/admin-group-name";
        }
        description
          "name of the admin group -- references a defined
          admin group";
      }
    }
  }

  grouping te-tunnel-protection_config {
    description
     "Configuration parameters related to LSP
      protection";
    leaf protection-style-requested {
      type identityref {
        base mplst:protection-type;
      }
      default mplst:unprotected;
      description
        "style of mpls frr protection desired: can be
        link, link-node or unprotected.";
    }
  }

  grouping te-lsp-comp-explicit {
    description
     "definitions for LSPs in which hops are explicitly
      specified";

    container explicit-path {
      description "LSP with explicit path specification";
      leaf path-name {
        type leafref {
          path "/mpls/lsps/constrained-path/"
            + "explicit-path/config/named-explicit-paths/name";
          require-instance true;
        }
        description "reference to a defined path";
      }
    }
  }

  grouping te-lsp-comp-queried {
    description "definitons for LSPs computed by querying a remote
      service, e.g., PCE server";

    container queried-path {
      description "LSP with path queried from an external server";

      leaf path-computation-server {
        type inet:ip-address;
        description
         "Address of the external path computation
          server";
      }
    }
  }

  grouping te-lsp-comp-local {
    description "definitons for locally-computed LSPs";

    container locally-computed {
      description "LSP with path computed by local ingress LSR";

      leaf use-cspf {
        type boolean;
        description "Flag to enable CSPF for locally computed LSPs";
      }
      leaf cspf-tiebreaker {
        type cspf-tie-breaking;
        description
          "Determine the tie-breaking method to choose between
          equally desirable paths during CSFP computation";
      }
    }
  }

  grouping explicit-route-subobject {
    description
      "The explicit route subobject grouping";
    choice type {
      description
        "The explicit route subobject type";
      case ipv4-address {
        description
          "IPv4 address explicit route subobject";
        leaf address {
          type inet:ip-address;
          description "router hop for the LSP path";
        }

        leaf hop-type {
          type mpls-hop-type;
          description "strict or loose hop";
        }
      }

      case label {
        leaf value {
          type uint32;
          description "the label value";
        }
        description
          "The Label ERO subobject";
      }
    }
  }

  // Explicit paths config somewhat following the IETF model
  grouping named-explicit-path_config {
    description
      "Global explicit path configuration
      grouping";
    list named-explicit-paths {
      key "name";
      description
        "A list of explicit paths";
      leaf name {
        type string;
        description
          "A string name that uniquely identifies
          an explicit path";
      }
      list explicit-route-objects {
        key "index";
        description
          "List of explicit route objects";
        leaf index {
          type uint8 {
            range "0..255";
          }
          description
            "Index of this explicit route object,
             to express the order of hops in path";
        }
        uses explicit-route-subobject;
      }
    }
  }

  grouping explicit-paths-top {
    description
      "common information for MPLS explicit path definition";
      list explicit-path {
        key name;
        description "Explicit path definition";

        leaf name {
          type leafref {
            path "/mpls/lsps/constrained-path/"
              + "explicit-path/config/named-explicit-paths/name";
            require-instance true;
          }
          description "definition for naming an explicit  path";

        }
        container config {
          description "configuration for an explicit path";
          uses named-explicit-path_config;
        }
        container state {
          config false;
          description "operational state for LSP path name";
          uses named-explicit-path_config;
        }
      }
  }

  grouping mpls-te-srlg_config {
    description
      "Configuration of various attributes associated
      with the SRLG";

    leaf srlg-name {
      type string;
      description "SRLG group identifier";
    }

    leaf srlg-value {
      type uint32;
      description "group ID for the SRLG";
    }

    leaf srlg-cost {
      type uint32;
      description
        "The cost of the SRLG to the computation
        algorithm";
    }
  }

  grouping mpls-te-srlg-members_config {
    description "Configuration of the membership of the SRLG";

    leaf from-address {
      type inet:ip-address;
      description "IP address of the a-side of the SRLG link";
    }

    leaf to-address {
      type inet:ip-address;
      description "IP address of the z-side of the SRLG link";
    }
  }

  grouping mpls-te-srlg-top {
    description
      "Top level grouping for MPLS shared
      risk link groups.";
    container mpls-te-srlg {
      description
        "Shared risk link groups attributes";
      list srlg {
        key srlg-name;
        description "List of shared risk link groups";

        leaf srlg-name {
          type leafref {
            path "../config/srlg-name";
            require-instance true;
          }
          description "The SRLG group identifier";
        }

        container config {
          description "Configuration parameters related to the SRLG";
          uses mpls-te-srlg_config;
        }

        container state {
          config false;
          description "State parameters related to the SRLG";
          uses mpls-te-srlg_config;
        }

        list members-list {
          key from-address;
          description
            "List of SRLG members, which are expressed
            as IP address endpoints of links contained in the SRLG";

          leaf from-address {
            type leafref {
              path "../config/from-address";
              require-instance true;
            }
            description "The from address of the link in the SRLG";
          }

          container config {
            description
              "Configuration parameters relating to the
              SRLG members";
            uses mpls-te-srlg-members_config;
          }

          container state {
            config false;
            description
              "State parameters relating to the SRLG
              members";
            uses mpls-te-srlg-members_config;
          }
        }
      }
    }
  }

  grouping tunnel-path_config {
    description
      "Tunnel path properties grouping";
    container path-computation-method {
      description
        "select and configure the way the LSP path is
        computed";

      leaf path-computation {
        type identityref {
          base path-computation-method;
        }
        description "path computation method to use with the LSP";
      }

      uses te-lsp-comp-explicit;
      uses te-lsp-comp-queried;
      uses te-lsp-comp-local;
    }

    uses path-placement-constraints;

    leaf no-cspf {
      type empty;
      description
        "Indicates no CSPF is to be attempted on this
        path.";
    }

    choice sigaling-specific-path-attributes {
      description "Signaling-protocol specific path attributes.";
      case RSVP {
        uses rsvp:rsvp-p2p-path-attributes_config;
      }
      case SR {
        uses sr:sr-path-attributes_config;
      }
    }
  }

  grouping te-tunnel_config {
    description
      "Configuration parameters relevant to a single
       traffic engineered tunnel.";

    leaf name {
      type string;
      description "The tunnel name";
    }
    leaf type {
      type identityref {
        base mplst:tunnel-type;
      }
      description "Tunnel type, p2p or p2mp";
    }

    leaf local-id {
      type union {
        type uint32;
        type string;
      }
      description
        "locally signficant optional identifier for the
         tunnel; may be a numerical or string value";
    }

    leaf description {
      type string;
      description "optional text description for the tunnel";
    }

    leaf admin-status {
      type identityref {
        base mplst:tunnel-admin-status;
      }
      default mplst:ADMIN_UP;
      description "TE tunnel administrative state.";
    }

    leaf preference {
      type uint8 {
        range "1..255";
      }
      description "Specifies a preference for this tunnel.
        A lower number signifies a better preference";
    }

    uses te-tunnel-metric_config;
    uses te-tunnel-bandwidth_config;
    uses te-tunnel-protection_config;
    uses te-tunnel-reoptimize_config;

    choice signaling-specific-tunnel-attributes {
      description "Signaling-protocol specific path attributes.";
      case RSVP {
        uses rsvp:rsvp-p2p-tunnel-attributes_config;
      }
    }

    choice tunnel-type {
      description
        "Describes tunnel by type type";
      case p2p {
        leaf destination {
          type inet:ip-address;
          description
            "P2P tunnel destination address";
        }
        /* P2P list of path(s) */
        list primary-paths {
          key "name";
          leaf name {
            type string;
            description "Path name";
          }
          description
            "List of primary paths for this
            tunnel.";
          leaf preference {
            type uint8 {
              range "1..255";
            }
            description
              "Specifies a preference for
              this path. The lower the
              number higher the
              preference";
          }
          uses tunnel-path_config;
        }

        list secondary-paths {
          key "name";
          description
            "List of secondary paths for this
              tunnel.";
          leaf name {
            type string;
            description "Path name";
          }
          leaf preference {
            type uint8 {
              range "1..255";
            }
            description
              "Specifies a preference for
                this path. The lower the
                number higher the
                preference";
          }
          uses tunnel-path_config;
        }
      }
      case p2mp {
        // TODO - complete
      }
    }
  }

  grouping te-tunnel_state {
    description
      "Counters and statistical data relevent to a single
       tunnel.";

    leaf oper-status {
      type identityref {
        base mplst:lsp-oper-status;
      }
      description
        "The operational status of the TE tunnel";
    }

    leaf role {
      type identityref {
        base mplst:lsp-role;
      }
      description
        "The lsp role at the current node, whether it is headend,
        transit or tailend.";
    }

    container counters {
      description
        "State data for MPLS label switched paths. This state
        data is specific to a single label switched path.";

      leaf bytes {
        type yang:counter64;
        description
          "Number of bytes that have been forwarded over the
           label switched path.";
      }
      leaf packets {
        type yang:counter64;
        description
          "Number of pacets that have been forwarded over the
           label switched path.";
      }

      leaf path-changes {
        type yang:counter64;
        description
          "Number of path changes for the label switched path";
      }

      leaf state-changes {
        type yang:counter64;
        description
          "Number of state changes for the label switched path";
      }

      leaf online-time {
        type yang:date-and-time;
        description
          "Indication of the time the label switched path
           transitioned to an Oper Up or in-service state";
      }

      leaf current-path-time {
        type yang:date-and-time;
        description
          "Indicates the time the LSP switched onto its
           current path. This is reset upon a LSP path
           change.";
      }

      leaf next-reoptimization-time {
        type yang:date-and-time;
        description
          "Indicates the next scheduled time the LSP
           will be reoptimized.";
      }
    }
  }

  grouping te-tunnels-top {
    description
      "Top level grouping for TE tunnels";

    list tunnel {
      key "name type";
      description "List of TE tunnels";

      leaf name {
        type leafref {
          path "../config/name";
          require-instance true;
        }
        description "The tunnel name";
      }

      leaf type {
        type leafref {
          path "../config/type";
          require-instance true;
        }
        description "The tunnel type, p2p or p2mp.";
      }

      container config {
        description
          "Configuration parameters related to TE tunnels:";
        uses te-tunnel_config;
      }

      container state {
        config false;
        description "State parameters related to TE interfaces";
        uses te-tunnel_config;
        uses te-tunnel_state;
      }
    }
  }

// data definition statements

// augment statements

// rpc statements

// notification statements
}
