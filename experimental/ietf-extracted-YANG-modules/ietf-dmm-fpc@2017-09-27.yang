module ietf-dmm-fpc {
  yang-version 1.1;
    namespace "urn:ietf:params:xml:ns:yang:ietf-dmm-fpc";
    prefix fpc;

    import ietf-inet-types { prefix inet;
        revision-date 2013-07-15; }
    import ietf-restconf { prefix restconf;
        revision-date 2017-01-26; }
    import ietf-dmm-fpc-settingsext { prefix fpcbase;
    revision-date 2017-09-27;
  }

    organization "IETF Distributed Mobility Management (DMM)
      Working Group";

    contact
       "WG Web:   <http://tools.ietf.org/wg/netmod/>
        WG List:  <mailto:netmod@ietf.org>

        WG Chair: Dapeng Liu
                  <mailto:maxpassion@gmail.com>

        WG Chair: Jouni Korhonen
                  <mailto:jouni.nospam@gmail.com>

        Editor:   Satoru Matsushima
                  <mailto:satoru.matsushima@g.softbank.co.jp>

        Editor:   Lyle Bertz
                  <mailto:lylebe551144@gmail.com>";

    description
    "This module contains YANG definition for
     Forwarding Policy Configuration Protocol (FPCP).

     Copyright (c) 2016 IETF Trust and the persons identified as the
     document authors. All rights reserved.

     This document is subject to BCP 78 and the IETF Trust's Legal
     Provisions Relating to IETF Documents
     (http://trustee.ietf.org/license-info) in effect on the date of
     publication of this document. Please review these documents
     carefully, as they describe your rights and restrictions with
     respect to this document. Code Components extracted from this
     document must include Simplified BSD License text as described
     in Section 4.e of the Trust Legal Provisions and are provided
     without warranty as described in the Simplified BSD License.";

    revision 2017-09-27 {
    description "Version 10 updates.";
    reference "draft-ietf-dmm-fpc-cpdp-10";
  }
revision 2017-07-22 {
    description "Version 08 updates.";
    reference "draft-ietf-dmm-fpc-cpdp-08";
}
revision 2017-03-08 {
    description "Version 06 updates.";
    reference "draft-ietf-dmm-fpc-cpdp-06";
}
revision 2016-08-03 {
    description "Initial Revision.";
    reference "draft-ietf-dmm-fpc-cpdp-05";
}
    feature fpc-basename-registry {
      description "Ability to track Base Names already provisioned
        on the Agent";
    }
    feature fpc-bundles {
      description "Ability for Client to send multiple bundles of
        actions to an Agent";
    }
    feature fpc-auto-binding {
      description "Allows a FPC Agent to advertise Topology Objects
        that could be DPNs";
    }
    feature operation-ref-scope {
      description "Provides the scope of refeneces in an operation.
        Used to optmize the Agent processing.";
    }

  //General Structures
    typedef fpc-identity {
        type union {
            type uint32;
            type string;
            type instance-identifier;
        }
        description "FPC Identity";
    }
    grouping target-value {
      leaf target {
          type fpc-identity;
      mandatory true;
      description "Target Identity";
      }
      description "FPC Target Value";
    }
  // Topology
  typedef fpc-interface-id {
        type fpc:fpc-identity;
        description "DPN interface Identifier";
  }
    identity interface-protocols {
        description "Protocol supported by the interface";
    }
    identity features {
        description "Protocol features";
    }
  // Settings
  grouping settings {
    container settings-set {
      uses fpcbase:fpc-settings;
      description "Settings";
    }
    description "Settings container";
  }
  //Topology - Groupings
  grouping interface-settings {
    container interface-settings-set {
      description "Interface settings";
    }
    description "Generic interface settings container";
  }
  grouping access-technology-key {
    leaf access-technology {
      type identityref {
        base "fpcbase:access-technology";
      }
      mandatory true;
      description "Access Technology";
    }
    description "Access Technology key";
  }
  grouping role-key {
    leaf role {
      type identityref {
        base "fpcbase:role";
      }
      mandatory true;
      description "Access Technology Role";
    }
    description "Access Technology Role key";
  }
  grouping interface-id-key {
    leaf interface-id {
      type fpc:fpc-interface-id;
      mandatory true;
      description "interface identifier";
    }
    description "Interface Identifier key";
  }
  grouping dpn-identifier-key {
    leaf dpn-id {
      type fpc:fpc-identity;
      mandatory true;
      description "DPN Identifier Type";
    }
    description "DPN Identifier key";
  }
  grouping dpn-interface-reference {
    uses fpc:access-technology-key;
    uses fpc:role-key;
    uses fpc:interface-id-key;
    description "A reference to a DPN interface";
  }
  // Topology Grouping
  grouping fpc-topology {
    list dpn-set {
      key dpn-id;
      uses fpc:dpn-identifier-key;
      leaf dpn-name {
        type string;
        description "DPN name";
      }
      leaf dpn-resource-mapping-reference {
        type string;
        description "Reference to underlying DPN resource(s)";
      }
      list interface-set {
        key "access-technology role interface-id";
        uses fpc:dpn-interface-reference;
        uses fpc:interface-settings;
        description "DPN interfaces";
      }
      description "Set of DPNs";
    }
    list dpn-type-set {
      key "access-technology role";
      uses fpc:access-technology-key;
      leaf access-technology-name {
        type string;
        description "Access Technology Name";
      }
      uses fpc:role-key;
      leaf role-name {
        type string;
        description "Access Technology Role Name";
      }
      list interface-set {
        key interface-id;
        uses fpc:interface-id-key;
        leaf interface-name {
          type string;
          description "DPN-Type Interface Name";
        }
        leaf-list interface-protocol-set {
          type identityref {
            base "interface-protocols";
          }
          description "Supported protocols";
        }
        leaf-list feature-set {
          type identityref {
            base "interface-protocols";
          }
          description "Supported features";
        }
        uses fpc:interface-settings;
        description "A DPN interface types";
      }
      description "Set of DPN types";
    }
    list dpn-group-set {
      key "dpn-group-id";
      leaf dpn-group-id {
        type fpc:fpc-identity;
        mandatory true;
        description "DPN Group Identifier";
      }
      list referenced-dpns-set {
        key "access-technology role interface-id";
        uses fpc:dpn-interface-reference;
        leaf-list supporting-dpn-id-set {
          type fpc:fpc-identity;
          description "DPNs that suppport this group";
        }
        leaf-list dpn-group-peer-id-set {
          type fpc:fpc-identity;
          description "DPN Peer Groups reference";
        }
        description "A list of DPNs supporting a group
          by DPN Type";
      }
      list dpn-group-peer-set {
        key remote-dpn-group-id;
        leaf remote-dpn-group-id {
          type fpc:fpc-identity;
          mandatory true;
          description "Remote DPN Group identifier";
        }
        uses fpc:interface-settings;
        description "Locally applied settings used for
          the referenced DPN-Group (peer group).";
      }
      leaf domain-id {
        type fpc:fpc-identity;
        description "Domain Identiifer";
      }
      description "List of DPN groups";
    }
    list domain-set {
      key domain-id;
      leaf domain-id {
        type fpc:fpc-identity;
        mandatory true;
        description "Domain Identifier";
      }
      leaf domain-name {
        type string;
        description "Domain displayname";
      }
      leaf domain-reference {
        type string;
        description "Reference to domain resources";
      }
      description "List of Domains";
    }
    description "FPC Topology grouping";
  }
  // Policy Structures
    // Descriptor Structure
    identity fpc-descriptor-type {
        description "A traffic descriptor";
    }
    grouping descriptor-definition {
        leaf descriptor-id {
            type fpc:fpc-identity;
            mandatory true;
            description "Descriptor Id";
        }
        leaf descriptor-type {
            type identityref {
              base "fpc-descriptor-type";
            }
            description "Descriptor Type Value";
        }
    uses fpcbase:fpc-descriptor-value;
        description "FPC Descriptor Definition";
    }
    // Action Structure
    identity fpc-action-type {
        description "Action Type";
    }
    grouping action-definition {
        leaf action-id {
            type fpc:fpc-identity;
            description "Action Identifier";
        }
        leaf action-type {
            type identityref {
              base "fpc-action-type";
            }
            description "Action Type";
        }
        uses fpcbase:fpc-action-value;
        description "FPC Action Definition";
    }
    // Rule Structure
    typedef fpc-direction-type {
       type enumeration {
         enum uplink {
           description "uplink";
         }
         enum downlink {
           description "Downlink";
         }
         enum both {
           description "Both";
        }
       }
       description "FPC Direction";
    }
    grouping fpc-rule-id {
    leaf rule-id {
      type fpc:fpc-identity;
      mandatory true;
      description "Rule Identifier";
    }
    description "FPC Rule-Id key";
    }
    grouping match-type {
        leaf descriptor-match-type {
          type enumeration {
            enum or {
              value 0;
              description "OR logic";
            }
            enum and {
              value 1;
              description "AND logic";
            }
          }
          mandatory true;
          description "Type of Match (OR or AND) applied to the
            descriptor-reference-set.";
      }
        description "Map Type Grouping";
    }
    grouping fpc-action-order {
        leaf action-order {
            type uint32;
            mandatory true;
            description "Action Execution Order";
        }
        description "Action Order Leaf";
    }
    grouping rule-definition {
        uses fpc:fpc-rule-id;
    uses fpc:match-type;
        list descriptor-reference-set {
          key "descriptor-id-reference";
          leaf descriptor-id-reference {
              type fpc:fpc-identity;
              mandatory true;
              description "Descriptor Id Reference";
          }
          leaf direction {
              type fpc:fpc-direction-type;
              description "Direction";
          }
          description "A set of Descriptor references";
        }
        list action-reference-set {
          key "action-order";
      uses fpc:fpc-action-order;
          leaf action-id-reference {
      type fpc:fpc-identity;
      mandatory true;
      description "Action Identifier Reference";
          }
          description "A set of Action references";
        }
        description
          "Rule.Definition";
    }
    // Policy Structures
    grouping fpc-precedence {
    leaf precedence {
      type uint32;
      mandatory true;
      description "Rule Precedence";
    }
    description "FPC Rule Precedence";
    }
    grouping policy {
        leaf policy-id {
            type fpc:fpc-identity;
            description "Policy Identifier";
        }
        list rule-set {
            key "precedence";
            unique "rule-id-reference";
            uses fpc:fpc-precedence;
            leaf rule-id-reference {
                type fpc:fpc-identity;
                mandatory true;
                description "Rule Identifier";
            }
            description "Rule Entry";
        }
        description "FPC Policy";
    }
    // FPC Policy
  grouping fpc-policy {
    list action-definition-set {
      key action-id;
      uses fpc:action-definition;
      description "List of Actions";
    }
    list descriptor-definition-set {
      key descriptor-id;
      uses fpc:descriptor-definition;
      description "List of Descriptors";
    }
    list rule-definition-set {
      key rule-id;
      uses fpc:rule-definition;
      description "List of Rules";
    }
    list policy-definition-set {
      key policy-id;
      uses fpc:policy;
      description "List of Policies";
    }
    description "FPC Policy Structures";
  }
    // Mobility Structures
  grouping configurable-policy-set {
    list installed-policy-list {
      key dpn-id-reference;
      leaf dpn-id-reference {
        type fpc:fpc-identity;
        description "Installed Policy identifier";
      }
      list installed-policy-set {
        key installed-policy-id;
        leaf installed-policy-id {
          type fpc:fpc-identity;
          description "Installed Policy Identifier";
        }
        leaf policy-id-reference {
          type fpc:fpc-identity;
          description "Installed Policy Identifier";
        }
        container policy-settings {
          uses fpcbase:fpc-settings;
          description "Policy Settings";
        }
        description "Policy installed upon a DPN";
      }
      description "Configurable Policy";
      uses fpc:settings;
    }
    description "List of installed DPN policies and settings";
  }
    // Dynamic Policy
    grouping mobility-context {
    leaf mobility-context-id {
      type fpc:fpc-identity;
      mandatory true;
      description "Mobility Context Identifier";
    }
    leaf dpn-group-id-reference {
      type fpc:fpc-identity;
      description "Group ID used when DPN selecitons were
        made";
    }
    leaf parent-mobility-context-id-reference {
      type fpc:fpc-identity;
      description "Parent Mobility Context";
    }
    list dpn-reference-list {
      key "dpn-id-reference direction";
      leaf dpn-id-reference {
        type fpc:fpc-identity;
        mandatory true;
        description "DPN Id reference";
      }
      leaf direction {
        type fpc:fpc-direction-type;
        mandatory true;
        description "Direction of DPN assignment";
      }
      container dpn-settings-complementary {
        uses fpcbase:fpc-settings;
        description "Complentary Settings";
      }
      leaf interface-id-reference {
        type fpc:fpc-interface-id;
        mandatory true;
        description "referenced interface";
      }
      list embedded-rule-set {
        key "precedence";
        unique "rule-id";
        uses fpc:fpc-rule-id;
        uses fpc:match-type;
        uses fpc:fpc-precedence;
        list action-definition-set {
          key "action-order";
          uses fpc:fpc-action-order;
          uses fpc:action-definition;
          description "List of Actions";
        }
        list descriptor-definition-set {
          key descriptor-id;
          uses fpc:descriptor-definition;
          description "List of Descriptors";
        }
        description "List of FPC Embedded Rule Definitions";
      }
      leaf-list assigned-policy-reference-set {
        type fpc:fpc-identity;
        description "List of Policies request to be enforced for
          this Mobility Context";
      }
      description "DPN List";
    }

    leaf-list requested-policy-reference-set {
      type fpc:fpc-identity;
      description "List of Policies request to be enforced for
        this Mobility Context";
    }
    container context-settings-complementary {
      uses fpcbase:fpc-settings;
      description "Context Settings";
    }
    description "Mobility Context";
    }
    // Events, Probes & Notifications
  identity event-type {
    description "Base Event Type";
  }
  typedef event-type-id {
    type uint32;
    description "Event ID Type";
  }
  grouping monitor-id {
    leaf monitor-id {
      type fpc:fpc-identity;
      mandatory true;
      description "Monitor Identifier";
    }
    description "Monitor Id";
  }
    grouping monitor-config {
        uses fpc:monitor-id;
    leaf deterrable {
      type boolean;
      description "Indicates reports related to this
        config can be delayed.";
    }
    container binding-information {
      description "Placeholder for information helpful
        to binding the monitor ot the correct target";
    }
    uses fpc:target-value;
    choice configuration {
      mandatory true;
      case periodic-config {
        leaf period {
          type uint32;
          description "Period";
        }
        description "Periodic Config Case";
      }
      case threshold-config {
        leaf lo-thresh {
          type uint32;
          description "lo threshold";
        }
        leaf hi-thresh {
          type uint32;
          description "hi threshold";
        }
        description "Threshold Config Case";
      }
      case scheduled-config {
        leaf report-time {
          type uint32;
          description "Reporting Time";
        }
        description "Scheduled Config Case";
      }
      case events-config-ident {
        leaf-list event-identities {
          type identityref {
            base "fpc:event-type";
          }
          description "Event Identities";
        }
        description "Events Config Identities Case";
      }
      case events-config {
        leaf-list event-ids {
          type uint32;
            description "Event IDs";
        }
        description "Events Config Case";
      }
      description "Event Config Value";
    }
    description "Monitor Configuration";
  }
    grouping report {
      uses fpc:monitor-config;
      choice report-value {
        leaf trigger {
          type fpc:event-type-id;
          description "Trigger Identifier";
        }
        case simple-empty {
          leaf nothing {
            type empty;
            description "Empty Value";
          }
          description "Empty Case";
        }
        case simple-val32 {
          leaf val32 {
            type uint32;
            description "Unsigned 32 bit value";
          }
          description "Simple Value Case";
        }
        case list-simple-val32 {
            leaf-list  val32-list {
              type uint32;
              description "Unsigned 32 bit value";
            }
            description "Simple Value Case";
          }
        description "Report Value";
      }
      description "Monitor Report";
    }
    typedef agent-identifier {
        type fpc:fpc-identity;
        description "Agent Identifier";
    }
    typedef client-identifier {
        type fpc:fpc-identity;
        description "Client Identifier";
    }
    grouping basename-info {
          leaf basename {
            type fpc:fpc-identity;
            description "Rules Basename";
          }
          leaf base-state {
            type string;
            description "Current State";
          }
          leaf base-checkpoint {
            type string;
            description "Checkpoint";
          }
          description "Basename Information";
    }
    // Top Level Structures
  container tenants {
    list tenant {
      key "tenant-id";
      leaf tenant-id {
          type fpc:fpc-identity;
          description "Tenant ID";
      }
          container mobility {
           container topology {
              uses fpc:fpc-topology;
             uses fpc:basename-info {
               if-feature fpc:fpc-basename-registry;
             }
              description "Topology";
            }
           container policy {
             uses fpc:fpc-policy;
             uses fpc:basename-info {
               if-feature fpc:fpc-basename-registry;
             }
             description "Policy";
           }
            uses fpc:configurable-policy-set;
            list mobility-context-set {
                key "mobility-context-id";
                config false;
                uses fpc:mobility-context;
                description "Mobility Context Set";
            }
            list monitor-set {
              key monitor-id;
              uses fpc:monitor-config;
              description "Monitor Configurations";
            }
            description "Mobility Elements";
          }
      description "Tenant";
    }
    description "Tenant List";
  }
    // RPC
    // RPC Specific Structures
    typedef op-identifier {
        type uint64;
        description "Operation Identifier";
    }
    typedef ref-scope {
      type enumeration {
        enum none {
          value 0;
          description "no references";
        }
        enum op {
          value 1;
          description "All references are intra-operation";
        }
        enum bundle {
          value 2;
          description "All references in exist in bundle";
        }
        enum storage {
          value 3;
          description "One or more references exist in storage.";
        }
        enum unknown {
          value 4;
          description "The location of the references are unknown.";
        }
      }
      description "Search scope for references in the operation.";
    }
    grouping context-operation {
      uses fpc:mobility-context;
      uses fpcbase:instructions;
      description "Context Operation";
    }
    grouping payload {
        uses fpc:configurable-policy-set;
    list mobility-context-set {
        key "mobility-context-id";
        uses fpc:mobility-context;
        description "Mobility Context Set";
    }
    uses fpc:fpc-policy;
    description "Payload";
  }
    grouping op-header {
    leaf client-id {
      type fpc:client-identifier;
      mandatory true;
      description "Client ID";
    }
    leaf delay {
      type uint32;
      description "Operation Delay (ms)";
    }
    leaf op-id {
      type op-identifier;
      mandatory true;
      description "Operation Identifier";
    }
    description "Common Operation header";
    }
  grouping fpc-op-type {
    leaf op-type {
      type enumeration {
        enum create {
          value 0;
          description "create";
        }
        enum update {
          value 1;
          description "update";
        }
        enum query {
          value 2;
          description "query";
        }
        enum delete {
          value 3;
          description "delete";
        }
      }
      mandatory true;
      description "Type";
    }
    description "FPC Operation Type";
  }
  grouping fpc-op-ref-scope {
    leaf op-ref-scope {
      if-feature operation-ref-scope;
      type fpc:ref-scope;
      description "Reference Scope";
    }
    description "FPC OP-REF Scope";
  }
  grouping op-input {
    uses fpc:fpc-op-ref-scope;
    uses fpcbase:instructions;
    choice op_body {
      case create_or_update {
        uses fpc:payload;
        description "Create/Update input";
      }
      case delete_or_query {
        uses fpc:target-value;
        description "Delete/Query input";
      }
      description "Opeartion Input value";
    }
    description "Operation Input";
  }
  typedef result-status {
    type enumeration {
      enum ok {
        value 0;
        description "OK";
      }
      enum err {
        value 1;
        description "Error";
      }
    }
    description "Result Status";
  }
  grouping status-value {
    leaf op-id {
      type op-identifier;
      mandatory true;
      description "Operation Identifier";
    }
    leaf status {
      type result-status;
      mandatory true;
      description "Status";
    }
    description "Status value for all messages";
  }
  grouping result {
    uses fpc:status-value;
    uses fpc:result-body;
    description "General Result grouping";
  }
  grouping result-body {
    leaf notify-follows {
      type boolean;
      description "Indicates that a notification will
        follow regarding this result";
    }
    choice result-type {
      case err {
        uses restconf:errors;
        description "Error Information";
      }
      case create-or-update-success {
        uses fpc:payload;
        description "Create/Update Success";
      }
      case delete_or_query-success {
        uses fpc:target-value;
        description "Delete/Query Success";
      }
      case empty-case {
        description "Empty Case";
      }
      description "Result Value";
    }
    description "Common Result member body";
  }
  // Common RPCs
  rpc configure {
    description "CONF message";
    input {
      uses fpc:op-header;
      uses fpc:fpc-op-type;
      uses fpc:op-input;
    }
    output {
      uses fpc:result;
    }
  }
  rpc configure-bundles {
    if-feature fpc:fpc-bundles;
    description "CONF_BUNDLES message";
    input {
      uses fpc:op-header;
      uses fpc:fpc-op-type;
      uses fpc:fpc-op-ref-scope;
      list bundles {
        key op-id;
        leaf op-id {
          type op-identifier;
          mandatory true;
          description "Operation Identifier";
        }
        uses fpc:op-input;
        description "List of operations";
      }
    }
    output {
      uses fpc:status-value;
      list bundles {
        key op-id;
        uses fpc:result;
        description "Operation Identifier";
      }
    }
  }
  rpc reg_monitor {
    description "Used to register monitoring of parameters/events";
    input {
      uses fpc:op-header;
      uses fpc:monitor-config;
    }
    output {
      uses fpc:status-value;
      uses restconf:errors;
    }
  }
  rpc dereg_monitor {
    description "Used to de-register monitoring of
      parameters/events";
    input {
      uses fpc:op-header;
      leaf-list monitor-set {
        type fpc:fpc-identity;
        min-elements 1;
        description "Monitor Identifier";
      }
      leaf send_data {
        type boolean;
        description "Indicates if NOTIFY with final data
          is desired upon deregistration";
      }
    }
    output {
      uses fpc:status-value;
      uses restconf:errors;
    }
  }
  rpc probe {
    description "Probe the status of a registered monitor";
    input {
      uses fpc:op-header;
      uses fpc:monitor-id;
    }
    output {
      uses fpc:status-value;
      uses restconf:errors;
    }
  }
  // Notification Messages & Structures
  grouping notification-header {
    leaf notification-id {
      type uint32;
      description "Notification Identifier";
    }
    leaf timestamp {
      type uint32;
      description "timestamp";
    }
    description "Notification Header";
  }
  notification config-result-notification {
    uses fpc:notification-header;
    uses fpc:status-value;
    choice value {
      case config-result {
        uses result-body;
        description "CONF Result";
      }
      case config-bundle-result {
        list bundles {
          key op-id;
          uses fpc:result;
          description "Operation Identifier";
        }
        description "CONF_BUNDLES Result";
      }
      description "Config Result value";
    }
    description "CONF/CONF_BUNDLES Async Result";
  }
  identity notification-cause {
    description "Notification Cause";
  }
  identity dpn-availabilty-change {
    base "notification-cause";
    description "DPN Candidate/Exisitng DPN Availablity Change";
  }
  identity monitoring-suspension {
    base "notification-cause";
    description "Indicates monitoring suspension";
  }
  identity monitoring-resumption {
    base "notification-cause";
    description "Indicates that monitoring has resumed";
  }
  identity monitor-notification {
    base "notification-cause";
    description "Indicates 1+ monitor reports";
  }
  notification notify {
    uses fpc:notification-header;
    leaf cause {
      type identityref {
        base "notification-cause";
      }
      description "Notification Cause";
    }
    choice value {
      case dpn-candidate-available {
        if-feature fpc:fpc-auto-binding;
        leaf node-id {
          type inet:uri;
          description "Topology URI";
        }
        list supported-interface-list {
          key "access-technology role";
          uses fpc:access-technology-key;
          uses fpc:role-key;
          description "Support Intefaces";
        }
        description "DPN Candidate Information";
      }
      case dpn-unavailable {
        leaf dpn-id {
          type fpc:fpc-identity;
          description "DPN Identifier";
        }
        description "DPN Unavailable";
      }
      case monitor-notification {
        list reports {
          uses fpc:report;
          description "Reports";
        }
        description "Monitor Notification";
      }
      description "Notify Value";
    }
    description "Notify Message";
  }
}
