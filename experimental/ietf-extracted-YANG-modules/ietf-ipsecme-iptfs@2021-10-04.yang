module ietf-ipsecme-iptfs {
  yang-version 1.1;
  namespace "urn:ietf:params:xml:ns:yang:ietf-ipsecme-iptfs";
  prefix iptfs;

  import ietf-i2nsf-ike {
    prefix nsfike;
  }
  import ietf-i2nsf-ikeless {
    prefix nsfikels;
  }

  organization
    "IETF IPSECME Working Group (IPSECME)";
  contact
    "WG Web:  <https://tools.ietf.org/wg/ipsecme/>
     WG List: <mailto:ipsecme@ietf.org>

     Author: Don Fedyk
             <mailto:dfedyk@labn.net>

     Author: Christian Hopps
             <mailto:chopps@chopps.org>";

  // RFC Ed.: replace XXXX with actual RFC number and
  // remove this note.

  description
    "This module defines the configuration and operational state for
     managing the IP Traffic Flow Security functionality [RFC XXXX].

     Copyright (c) 2020 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://tools.ietf.org/html/rfcXXXX); see the RFC itself for
     full legal notices.";

  revision 2021-10-04 {
    description
      "Initial Revision";
    reference
      "RFC XXXX: IP Traffic Flow Security YANG Module";
  }

  feature ipsec-stats {
    description
      "This feature indicates the device supports
       per SA IPsec statistics";
  }

  feature iptfs-stats {
    description
      "This feature indicates the device supports
       per SA IP Traffic Flow Security statistics";
  }

  /*--------------------*/
  /*   groupings        */
  /*--------------------*/

  grouping ipsec-tx-stat-grouping {
    description
      "IPsec outbound statistics";
    leaf tx-pkts {
      type uint64;
      config false;
      description
        "Outbound Packet count";
    }
    leaf tx-octets {
      type uint64;
      config false;
      description
        "Outbound Packet bytes";
    }
    leaf tx-drop-pkts {
      type uint64;
      config false;
      description
        "Outbound dropped packets count";
    }
  }

  grouping ipsec-rx-stat-grouping {
    description
      "IPsec inbound statistics";
    leaf rx-pkts {
      type uint64;
      config false;
      description
        "Inbound Packet count";
    }
    leaf rx-octets {
      type uint64;
      config false;
      description
        "Inbound Packet bytes";
    }
    leaf rx-drop-pkts {
      type uint64;
      config false;
      description
        "Inbound dropped packets count";
    }
  }

  grouping iptfs-inner-tx-stat-grouping {
    description
      "IP-TFS outbound inner packet statistics";
    leaf tx-pkts {
      type uint64;
      config false;
      description
        "Total number of IP-TFS inner packets sent. This
         count is whole packets only.  A fragmented packet
         counts as one packet";
      reference
        "draft-ietf-ipsecme-iptfs";
    }
    leaf tx-octets {
      type uint64;
      config false;
      description
        "Total number of IP-TFS inner octets sent.  This is
         inner packet octets only.  Does not count padding.";
      reference
        "draft-ietf-ipsecme-iptfs";
    }
  }

  grouping iptfs-outer-tx-stat-grouping {
    description
      "IP-TFS outbound inner packet statistics";
    leaf tx-all-pad-pkts {
      type uint64;
      config false;
      description
        "Total number of transmitted IP-TFS packets that
         were all padding with no inner packet data.";
      reference
        "draft-ietf-ipsecme-iptfs section 2.2.3";
    }
    leaf tx-all-pad-octets {
      type uint64;
      config false;
      description
        "Total number transmitted octets of padding added to
         IP-TFS packets with no inner packet data.";
      reference
        "draft-ietf-ipsecme-iptfs section 2.2.3";
    }
    leaf tx-extra-pad-pkts {
      type uint64;
      config false;
      description
        "Total number of transmitted outer IP-TFS packets
         that included some padding.";
      reference
        "draft-ietf-ipsecme-iptfs section 2.2.3.1";
    }
    leaf tx-extra-pad-octets {
      type uint64;
      config false;
      description
        "Total number of transmitted octets of padding added
         to outer IP-TFS packets with data.";
      reference
        "draft-ietf-ipsecme-iptfs section 2.2.3.1";
    }
  }

  grouping iptfs-inner-rx-stat-grouping {
    description
      "IP-TFS inner packet inbound statistics";
    leaf rx-pkts {
      type uint64;
      config false;
      description
        "Total number of IP-TFS inner packets received.";
      reference
        "draft-ietf-ipsecme-iptfs section 2.2";
    }
    leaf rx-octets {
      type uint64;
      config false;
      description
        "Total number of IP-TFS inner octets received.  Does
         not include padding or overhead";
      reference
        "draft-ietf-ipsecme-iptfs section 2.2";
    }
    leaf rx-incomplete-pkts {
      type uint64;
      config false;
      description
        "Total number of IP-TFS inner packets that were
         incomplete.  Usually this is due to fragments not
         received. Also, this may be due to misordering or
         errors in received outer packets.";
      reference
        "draft-ietf-ipsecme-iptfs";
    }
  }

  grouping iptfs-outer-rx-stat-grouping {
    description
      "IP-TFS outer packet inbound statistics";
    leaf rx-all-pad-pkts {
      type uint64;
      config false;
      description
        "Total number of received IP-TFS packets that were
         all padding with no inner packet data.";
      reference
        "draft-ietf-ipsecme-iptfs section 2.2.3";
    }
    leaf rx-all-pad-octets {
      type uint64;
      config false;
      description
        "Total number received octets of padding added to
         IP-TFS packets with no inner packet data.";
      reference
        "draft-ietf-ipsecme-iptfs section 2.2.3";
    }
    leaf rx-extra-pad-pkts {
      type uint64;
      config false;
      description
        "Total number of received outer IP-TFS packets that
         included some padding.";
      reference
        "draft-ietf-ipsecme-iptfs section 2.2.3.1";
    }
    leaf rx-extra-pad-octets {
      type uint64;
      config false;
      description
        "Total number of received octets of padding added to
         outer IP-TFS packets with data.";
      reference
        "draft-ietf-ipsecme-iptfs section 2.2.3.1";
    }
    leaf rx-errored-pkts {
      type uint64;
      config false;
      description
        "Total number of IP-TFS outer packets dropped due to
         errors.";
      reference
        "draft-ietf-ipsecme-iptfs";
    }
    leaf rx-missed-pkts {
      type uint64;
      config false;
      description
        "Total number of IP-TFS outer packets missing
         indicated by missing sequence number.";
      reference
        "draft-ietf-ipsecme-iptfs";
    }
  }

  grouping iptfs-config {
    description
      "This is the grouping for iptfs configuration";
    container traffic-flow-security {
      // config true; want this so we can refine?
      description
        "Configure the IPSec TFS in Security
         Association Database (SAD)";
      leaf congestion-control {
        type boolean;
        default "true";
        description
          "Congestion Control With the congestion controlled
           mode, IP-TFS adapts to network congestion by
           lowering the packet send rate to accommodate the
           congestion, as well as raising the rate when
           congestion subsides.";
        reference
          "draft-ietf-ipsecme-iptfs section 2.5.2";
      }
      container packet-size {
        description
          "Packet size is either auto-discovered or manually
           configured.";
        leaf use-path-mtu-discovery {
          type boolean;
          default "true";
          description
            "Utilize path mtu discovery to determine maximum IP-TFS
             packet size. If the packet size is explicitly
             configured, then it will only be adjusted downward
             if use-path-mtu-discovery is set.";
          reference
            "draft-ietf-ipsecme-iptfs section 4.2";
        }
        leaf outer-packet-size {
          type uint16;
          description
            "The size of the outer encapsulating tunnel packet (i.e.,
             the IP packet containing the ESP payload).";
          reference
            "draft-ietf-ipsecme-iptfs section 4.2";
        }
      }
      choice tunnel-rate {
        description
          "TFS bit rate may be specified at layer 2 wire
           rate or layer 3 packet rate";
        leaf l2-fixed-rate {
          type uint64;
          description
            "Target bandwidth/bit rate in bps for iptfs tunnel. This
             fixed rate is the nominal timing for the fixed size packet.
             If congestion control is enabled the rate may be adjusted
             down (or up if unset).";
          reference
            "draft-ietf-ipsecme-iptfs section 4.1";
        }
        leaf l3-fixed-rate {
          type uint64;
          description
            "Target bandwidth/bit rate in bps for iptfs tunnel. This
             fixed rate is the nominal timing for the fixed size packet.
             If congestion control is enabled the rate may be adjusted
             down (or up if unset).";
          reference
            "draft-ietf-ipsecme-iptfs section 4.1";
        }
      }
      leaf dont-fragment {
        type boolean;
        default "false";
        description
          "Disable packet fragmentation across consecutive iptfs
           tunnel packets";
        reference
          "draft-ietf-ipsecme-iptfs section 2.2.4 and 6.4.1";
      }
      leaf max-aggregation-time {
        type decimal64 {
          fraction-digits 6;
        }
        units "milliseconds";
        description
          "Maximum Aggregation Time in  Milliseconds
           or fractional milliseconds down to 1 nanosecond";
      }
    }
  }

  /*
   * IP-TFS ike configuration
   */

  augment "/nsfike:ipsec-ike/nsfike:conn-entry/nsfike:spd/"
        + "nsfike:spd-entry/"
        + "nsfike:ipsec-policy-config/"
        + "nsfike:processing-info/"
        + "nsfike:ipsec-sa-cfg" {
    description
      "IP-TFS configuration for this policy.";
    uses iptfs-config;
  }

  augment "/nsfike:ipsec-ike/nsfike:conn-entry/"
        + "nsfike:child-sa-info" {
    description
      "IP-TFS configured on this SA.";
    uses iptfs-config {
      refine "traffic-flow-security" {
        config false;
      }
    }
  }

  /*
   * IP-TFS ikeless configuration
   */

  augment "/nsfikels:ipsec-ikeless/nsfikels:spd/"
        + "nsfikels:spd-entry/"
        + "nsfikels:ipsec-policy-config/"
        + "nsfikels:processing-info/"
        + "nsfikels:ipsec-sa-cfg" {
    description
      "IP-TFS configuration for this policy.";
    uses iptfs-config;
  }

  augment "/nsfikels:ipsec-ikeless/nsfikels:sad/"
        + "nsfikels:sad-entry" {
    description
      "IP-TFS configured on this SA.";
    uses iptfs-config {
      refine "traffic-flow-security" {
        config false;
      }
    }
  }

  /*
   * packet counters
   */

  augment "/nsfike:ipsec-ike/nsfike:conn-entry/"
        + "nsfike:child-sa-info" {
    description
      "Per SA Counters";
    container ipsec-stats {
      if-feature "ipsec-stats";
      config false;
      description
        "IPsec per SA packet counters.";
      uses ipsec-tx-stat-grouping {
        //when "direction = 'outbound'";
      }
      uses ipsec-rx-stat-grouping {
        //when "direction = 'inbound'";
      }
    }
    container iptfs-inner-pkt-stats {
      if-feature "iptfs-stats";
      config false;
      description
        "IPTFS per SA inner packet counters.";
      uses iptfs-inner-tx-stat-grouping {
        //when "direction = 'outbound'";
      }
      uses iptfs-inner-rx-stat-grouping {
        //when "direction = 'inbound'";
      }
    }
    container iptfs-outer-pkt-stats {
      if-feature "iptfs-stats";
      config false;
      description
        "IPTFS per SA outer packets counters.";
      uses iptfs-outer-tx-stat-grouping {
        //when "direction = 'outbound'";
      }
      uses iptfs-outer-rx-stat-grouping {
        //when "direction = 'inbound'";
      }
    }
  }

  /*
   * packet counters
   */

  augment "/nsfikels:ipsec-ikeless/nsfikels:sad/"
        + "nsfikels:sad-entry" {
    description
      "Per SA Counters";
    container ipsec-stats {
      if-feature "ipsec-stats";
      description
        "IPsec per SA packet counters.";
      uses ipsec-tx-stat-grouping {
        //when "direction = 'outbound'";
      }
      uses ipsec-rx-stat-grouping {
        //when "direction = 'inbound'";
      }
    }
    container iptfs-inner-pkt-stats {
      if-feature "iptfs-stats";
      config false;
      description
        "IPTFS per SA inner packet counters.";
      uses iptfs-inner-tx-stat-grouping {
        //when "direction = 'outbound'";
      }
      uses iptfs-inner-rx-stat-grouping {
        //when "direction = 'inbound'";
      }
    }
    container iptfs-outer-pkt-stats {
      if-feature "iptfs-stats";
      config false;
      description
        "IPTFS per SA outer packets counters.";
      uses iptfs-outer-tx-stat-grouping {
        //when "direction = 'outbound'";
      }
      uses iptfs-outer-rx-stat-grouping {
        //when "direction = 'inbound'";
      }
    }

  }
}
