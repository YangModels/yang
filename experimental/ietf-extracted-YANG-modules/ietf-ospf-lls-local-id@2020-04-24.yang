module ietf-ospf-lls-local-id {
  yang-version 1.1;
  namespace "urn:ietf:params:xml:ns:yang:ietf-ospf-lls-local-id";

  prefix ospf-lls-localid;

  import ietf-routing {
    prefix "rt";
  }

  import ietf-ospf {
    prefix "ospf";
  }

  organization
    "IETF LSR - Link State Routing Working Group";

  contact
     "WG Web:   <http://tools.ietf.org/wg/lsr>
      WG List:  <mailto:lsr@ietf.org>

      Author:   Yingzhen Qu
                <mailto:yqu@futurewei.com>
      Author:   Acee Lindem
                <mailto:acee@cisco.com>";

  description
    "This YANG module defines the configuration and operational
    state for OSPF Link-Local Signaling (LLS) Extensions for Local
    Interface ID Advertisement feature as defined in RFC 8510.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";

  reference "RFC XXXX";

  revision 2020-04-24 {
    description
      "Initial version";
    reference
      "RFC XXXX: A YANG Data Model for OSPF.";
  }

  augment "/rt:routing/rt:control-plane-protocols"
        + "/rt:control-plane-protocol/ospf:ospf" {
    when "../rt:type = 'ospf:ospfv2' or "
       + "../rt:type = 'ospf:ospfv3'" {
      description
        "This augments the OSPF routing protocol when used.";
    }
    description
      "This augments the OSPF protocol configuration
       to support LLS extesnions for interfacde ID as
       defined in RFC 8510.";
    container lls-int-id {
      leaf enable {
        type boolean;
        default false;
        description
          "Enable LLS to advertise local interface ID.";
      }
      description
        "OSPF LLS Extensions for interface ID.";
    }
  }
}
