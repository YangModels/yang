module ietf-trans-client-service {
  /* TODO: FIXME */
  //yang-version 1.1;

  namespace "urn:ietf:params:xml:ns:yang:ietf-trans-client-service";
  prefix "clntsvc";

  import ietf-te-types {
    prefix "te-types";
    //reference "RFC XXXX - Traffic Engineering Common YANG Types";
  }

  import ietf-otn-types {
    prefix "otn-types";
    //reference "RFC XXXX - OTN Tunnel YANG Model";
  }
  import ietf-yang-types {
    prefix "yang";
    //reference "RFC 6991 - Common YANG Data Types";
  }

  organization
    "Internet Engineering Task Force (IETF) CCAMP WG";
  contact
    "
      ID-draft editor:
        Haomian Zheng (zhenghaomian@huawei.com);
        Aihua Guo (aihuaguo@huawei.com);
        Italo Busi (italo.busi@huawei.com);
        Anton Snitser (antons@sedonasys.com);
        Francesco Lazzeri (francesco.lazzeri@ericsson.com);
        Yunbin Xu (xuyunbin@ritt.cn);
        Yang Zhao (zhaoyangyjy@chinamobile.com);
        Xufeng Liu (Xufeng_Liu@jabil.com);
        Giuseppe Fioccola (giuseppe.fioccola@huawei.com);
    ";

  description
    "This module defines a YANG data model for describing
     transport client services.

     Copyright (c) 2019 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).";

  revision 2019-03-11 {
    description
      "version -06 as an I-D";
    reference
      "draft-zheng-ccamp-client-signal-yang";
  }

  /*
   * Groupings
   */
  grouping client-svc-access-parameters {
    description
      "Transport client services access parameters";
    leaf access-node-id {
      type te-types:te-node-id;
      description
        "The identifier of the access node in the underlying
         transport topology.";
    }

    leaf access-ltp-id {
      type te-types:te-tp-id;
      description
        "The TE link termination point identifier, used together with
         access-node-id to identify the access LTP.";
    }

    leaf client-signal {
      type identityref {
        base otn-types:client-signal;
      }
      description
        "Identifiies the client signal type associated with this port";
                }
    }

  grouping client-svc-tunnel-parameters {
    description
      "Transport client services tunnel parameters";

    leaf tunnel-name {
      type string;
      description
        "TE service tunnel instance name.";
    }
  }

  grouping  client-svc-instance_config {
    description
      "Configuraiton parameters for client services.";
    leaf client-svc-name {
      type string;
      description
        "Identifier of the p2p transport client service.";
    }

    leaf client-svc-id {
      type string;
      description
        "Name of the p2p transport client service.";
    }
    leaf client-svc-descr {
      type string;
      description
        "Description of the transport client service.";
    }

    leaf client-svc-customer {
      type string;
      description
        "Customer of the transport client service.";
    }

    container resilience {
      description "";
    }

    uses te-types:te-topology-identifier;

    leaf admin-status {
      type identityref {
        base te-types:tunnel-admin-state-type;
      }
      default te-types:tunnel-admin-state-up;
      description "Client service administrative state.";
    }

    container src-access-ports {
      description
        "Source access port of a client service.";
      uses client-svc-access-parameters;
    }

        container dst-access-ports {
          description
                "Destination access port of a client service.";
          uses client-svc-access-parameters;
        }

        list svc-tunnels {
          key tunnel-name;
          description
                "List of the TE Tunnels supporting the client service.";
          uses client-svc-tunnel-parameters;
        }
  }

  grouping  client-svc-instance_state {
        description
          "State parameters for client services.";
        leaf operational-state {
          type identityref {
                base te-types:tunnel-state-type;
          }
          config false;
          description "Client service operational state.";
        }
        leaf provisioning-state {
          type identityref {
                base te-types:lsp-state-type;
          }
          config false;
          description "Client service provisioning state.";
        }
        leaf creation-time {
          type yang:date-and-time;
          config false;
          description "The time of the service be created.";
        }
        leaf last-updated-time {
          type yang:date-and-time;
          config false;
          description "The time of the service's latest update.";
        }
  }

  /*
   * Data nodes
   */

  container client-svc {
    description
      "Transport client services.";

    list client-svc-instances {
      key client-svc-name;
      description
        "The list of p2p transport client service instances";

          uses client-svc-instance_config;
          uses client-svc-instance_state;
    }
  }
}
