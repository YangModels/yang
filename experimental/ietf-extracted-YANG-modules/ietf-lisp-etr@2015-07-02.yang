module ietf-lisp-etr {
  namespace "urn:ietf:params:xml:ns:yang:ietf-lisp-etr";
  prefix lisp-etr;
  import ietf-lisp {
    prefix lisp;
  }
  import ietf-lisp-address-types {
   prefix lcaf;
  }
  import ietf-inet-types {
    prefix inet;
  }
  organization
   "IETF LISP (Locator/ID Separation Protocol) Working Group";
  contact
    "lisp@ietf.org";
  description
    "This YANG module defines the generic configuration
     data for a LISP ETR. The module can be extended by vendors
     to define vendor-specific configuration parameters and
     policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";
  revision 2015-07-02 {
    description
      "Initial revision.";
    reference
      "https://tools.ietf.org/html/rfc6830";
  }
  identity etr {
    base lisp:lisp-device;
    description
      "LISP ETR.";
  }
  augment "/lisp:lisp/lisp:devices/lisp:device" {
    when "lisp:type = lisp-etr:etr" {
      description
        "Augment is valid when LISP device type is ETR.";
    }
    description
      "This augments LISP devices list with ETR specific
       parameters.";
    container etr-cfg {
      presence "LISP ETR operation enabled";
      description
        "ETR configuration parameters.";
      container local-eids {
        description
          "EIDs served by the ETR.";
        list local-eid {
          key "id";
          min-elements 1;
          description
            "List of local EIDs.";
          leaf id {
            type lisp:eid-id;
            description
              "Unique id of local EID.";
          }
          container eid-address {
            uses lcaf:lisp-address;
            description
              "EID address in generic LISP address format.";
          }
          container map-servers {
            description
              "Map-Servers configured for the ETR.";
            list map-server {
              key "address";
              description
                "List of Map-Servers configured for the ETR.";
              leaf address {
                type inet:ip-address;
                description
                  "Map-Server address.";
              }
              leaf auth-key {
                type string;
                description
                  "Map-Server authentication key.";
              }
              leaf auth-key-type {
                type lisp:auth-key-type;
                description
                  "Map-Server authentication type.";
              }
            }
          }
          container rlocs {
            uses lisp:locators;
            description
              "Locators mapped to local EID.";
          }
          leaf record-ttl {
            type uint32;
            description
              "Validity period of the EID to RLOCs mapping provided
               in Map-Replies.";
          }
          leaf want-map-notify {
            type boolean;
            description
              "Flag which if set in a Map-Register requests that a
               Map-Notify be sent in response.";
          }
          leaf proxy-reply {
            type boolean;
            description
              "Flag which if set in a Map-Register requests that the
               Map-Server proxy Map-Replies for the ETR.";
          }
          leaf registration-interval {
            type uint16;
            units "seconds";
            default "60";
            description
              "Interval between consecutive Map-Register messages.";
          }
        }
      }
    }
  }
}
