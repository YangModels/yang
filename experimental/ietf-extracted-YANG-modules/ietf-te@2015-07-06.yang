module ietf-te {

  namespace "urn:ietf:params:xml:ns:yang:ietf-te";

  /* Replace with IANA when assigned */
  prefix "te";

  /* Import TE generic types */
  import ietf-te-types {
    prefix ietf-te-types;
  }

  /* Import TE packet specific types */
  import ietf-te-psc-types {
    prefix ietf-te-psc-types;
  }

  import ietf-interfaces {
    prefix if;
  }

  import ietf-inet-types {
    prefix inet;
  }

  organization
    "IETF TEAS Working Group";

  contact
    "Fill me";

  description
    "YANG data module for TE configuration,
    state, RPC and notifications.";
  revision 2015-07-06 {
    description "Latest update to TE generic YANG module.";
    reference "TBD";
  }

  /**
   * TE interface generic groupings
   */
  grouping te-admin-groups_config {
    description
      "TE interface affinities grouping";
    choice admin-group-type {
      description
        "TE interface administrative groups
        representation type";
      case value-admin-groups {
        choice value-admin-group-type {
          description "choice of admin-groups";
          case value-admin-groups {
            description
              "Administrative group/Resource
              class/Color.";
            leaf admin-group {
              type ietf-te-types:admin-group;
              description
                "TE interface administrative group";
            }
          }
          case value-extended-admin-groups {
            if-feature ietf-te-types:extended-admin-groups;
            description
              "Extended administrative group/Resource
              class/Color.";
            leaf extended-admin-group {
              type ietf-te-types:extended-admin-group;
              description
                "TE interface extended administrativei
                group";
            }
          }
        }
      }
      case named-admin-groups {
        list named-admin-groups {
          if-feature ietf-te-types:extended-admin-groups;
          if-feature ietf-te-types:named-extended-admin-groups;
          key named-admin-group;
          description
            "A list of named admin-group entries";
          leaf named-admin-group {
            type leafref {
              path "/te/globals/" +
                "named-admin-groups/config/"+
                "named-admin-groups/name";
            }
            description
              "A named admin-group entry";
          }
        }
      }
    }
  }

  grouping te-admin-groups {
    description "TE admin-group configuration grouping";
    container te-admin-groups {
      description
        "Configuration parameters for interface
        administrative groups";
      container config {
        description
          "Configuration parameters for interface
          administrative groups";
        uses te-admin-groups_config;
      }
      container state {
        config false;
        description
          "Configuration parameters for interface
          administrative groups";
        uses te-admin-groups_config;
      }
    }
  }

  /* TE interface SRLGs */
  grouping te-srlgs_config {
    description "TE interface SRLG grouping";
    choice srlg-type {
      description "Choice of SRLG configuration";
      case value-srlgs {
        list values {
          key "value";
          description "List of SRLG values that
            this link is part of.";
          leaf value {
            type uint32 {
              range "0..4294967295";
            }
            description
              "Value of the SRLG";
          }
        }
      }
      case named-srlgs {
        list named-srlgs {
          if-feature ietf-te-types:named-srlg-groups;
          key named-srlg;
          description
            "A list of named SRLG entries";
          leaf named-srlg {
            type leafref {
              path "/te:te/te:globals/" +
                "te:named-srlgs/te:config/te:named-srlgs/te:name";
            }
            description
              "A named SRLG entry";
          }
        }
      }
    }
  }

  grouping te-srlgs {
    description "TE SRLG configuration grouping";
    container te-srlgs {
      description "TBD";
      container config {
        description
          "Configuration parameters for interface SRLG
          groups";
        uses te-srlgs_config;
      }
      container state {
        config false;
        description
          "State parameters for interface SRLG groups";
        uses te-srlgs_config;
      }
    }
  }

  grouping te-metric_config {
    description "Interface TE metric grouping";
    leaf te-metric {
      type ietf-te-types:te-metric;
      description "Interface TE metric.";
    }
  }

  grouping te-attributes {
    description "TE attributes configuration grouping";
    container config {
      description
        "Configuration parameters for interface TE
         attributes";
      uses te-metric_config;
    }
    container state {
      config false;
      description
        "State parameters for interface TE metric";
      uses te-metric_config;
      uses interface-advertisements_state;
    }
  }

  /* TE interface switching capabilities */
  grouping te-switching-cap_config {
    description
      "TE interface switching capabilities";
    list switching-capabilities {
      key "switching-capability";
      description
        "List of interface capabilities for this interface";
      leaf switching-capability {
        type identityref {
          base ietf-te-types:switching-capabilities;
        }
        description
          "Switching Capability for this interface";
      }
      leaf encoding {
        type identityref {
          base ietf-te-types:lsp-encoding-types;
        }
        description
          "Encoding supported by this interface";
      }
    }
  }

  grouping te-switching-cap {
    description "TE interface switching capability grouping";
    container te-switching-cap {
      description
        "Interface switching capabilities container";
      container config {
        description
          "Configuration parameters for interface
          switching capabilities";
        uses te-switching-cap_config;
      }
      container state {
        config false;
        description
          "State parameters for interface switching
          capabilities";
        uses te-switching-cap_config;
      }
    }
  }

  grouping interface-advertisements_state {
    description
      "TE interface advertisements state grouping";
    container interface-advertisements_state {
      description
        "TE interface advertisements state container";
      leaf flood-interval {
        type uint32;
        description
          "The periodic flooding interval";
      }
      leaf last-flooded-time {
        type uint32;
        units seconds;
        description
          "Time elapsed since last flooding in seconds";
      }
      leaf next-flooded-time {
        type uint32;
        units seconds;
        description
          "Time remained for next flooding in seconds";
      }
      leaf last-flooded-trigger {
        type enumeration {
          enum link-up {
            description "Link-up flooding trigger";
          }
          enum link-down {
            description "Link-up flooding trigger";
          }
          enum threshold-up {
            description
              "Bandwidth reservation up threshold";
          }
          enum threshold-down {
            description
              "Bandwidth reservation down threshold";
          }
          enum bandwidth-change {
            description "Banwidth capacity change";
          }
          enum user-initiated {
            description "Initiated by user";
          }
          enum srlg-change {
            description "SRLG property change";
          }
          enum periodic-timer {
            description "Periodic timer expired";
          }
        }
        description "Trigger for the last flood";
      }
      list advertized-level-areas {
        key level-area;
        description
          "List of areas the TE interface is advertised
          in";
        leaf level-area {
          type uint32;
          description
            "The IGP area or level where the TE
            interface state is advertised in";
        }
      }
    }
  }
  /*** End of TE interface groupings ***/

  /**
   * TE tunnel generic groupings
   */

  /* TE tunnel path properties */
  grouping tunnel-path-params {
    description
      "Tunnel path properties grouping";
    container tunnel-path-params {
      description
        "Defines a TE tunnel path properties";
      leaf path-named-constraint {
        if-feature ietf-te-types:named-path-constraints;
        type leafref {
          path "/te/globals/named-path-constraints/config/"+
            "named-path-constraints/name";
        }
        description
          "Reference to a globally defined named path
          constraint set";
      }
      uses ietf-te-types:tunnel-path-selection;
      choice type {
        description
          "Describes the path type";
        case dynamic {
          leaf dynamic {
            type empty;
            description
              "A CSPF dynamically computed path";
          }
        }
        case explicit {
          leaf explicit-path-name {
            type leafref {
              path "/te/globals/named-explicit-paths/config/"+
                "named-explicit-paths/name";
            }
            description
              "Reference to a globally defined
              explicit-path";
          }
        }
      }
      leaf no-cspf {
        type empty;
        description
          "Indicates no CSPF is to be attempted on this
          path.";
      }
      leaf lockdown {
        type empty;
        description
          "Indicates no reoptimization to be attempted for
          this path.";
      }
    }
  }

  grouping tunnel-properties_config {
    description
      "Configuration parameters relating to TE tunnel";
    leaf description {
      type string;
      description
        "TE tunnel description.";
    }
    leaf admin-status {
      type identityref {
        base ietf-te-types:state-type;
      }
      default ietf-te-types:state-up;
      description "TE tunnel administrative state.";
    }
    uses ietf-te-psc-types:tunnel-routing-properties;
    uses ietf-te-psc-types:tunnel-forwarding-properties;
    uses ietf-te-types:tunnel-bidir-assoc-properties;
    choice path-type {
      description
        "Describes the path type";
      case p2p {
        leaf destination {
          type inet:ip-address;
          description
            "P2P tunnel destination address";
        }
        /* P2P list of path(s) */
        list primary-paths {
          key "preference";
          description
            "List of primary paths for this
            tunnel.";
          leaf preference {
            type uint8 {
              range "1..255";
            }
            description
              "Specifies a preference for
              this path. The lower the
              number higher the
              preference";
          }
          uses tunnel-path-params;
          list seondary-paths {
            key "preference";
            description
              "List of secondary paths for this
              tunnel.";
            leaf preference {
              type uint8 {
                range "1..255";
              }
              description
                "Specifies a preference for
                this path. The lower the
                number higher the
                preference";
            }
            uses tunnel-path-params;
          }
        }
      }
      case p2mp {
        if-feature ietf-te-types:p2mp-te;
        list p2mp-paths {
          key "destination";
          description
            "List of destinations and their
            paths.";
          leaf destination {
            type inet:ip-address;
            description
              "P2MP destination leaf address";
          }
          list primary-paths {
            key "preference";
            description
              "List of primary paths";
            leaf preference {
              type uint8 {
                range "1..255";
              }
              description
                "Specifies a preference for
                this path. The lower the
                number higher the
                preference";
            }
            uses tunnel-path-params;
            list seondary-paths {
              key "preference";
              description
                "List of secondary paths";
              leaf preference {
                type uint8 {
                  range "1..255";
                }
                description
                  "Specifies a preference
                  for this path. The lower
                    the number higher
                      the preference";
              }
              uses tunnel-path-params;
            }
          }
        }
      }
    }
  }

  grouping tunnel-properties {
    description
      "Top level grouping for tunnel properties.";
    container config {
      description
        "Configuration parameters relating to
        tunnel properties";
      uses tunnel-properties_config;
    }
    container state {
      config false;
      description
        "State information associated with tunnel
        properties";
      uses tunnel-properties_config;
      uses tunnel-properties_state;
    }
  }

  grouping tunnel-properties_state {
    description
      "State parameters relating to TE tunnel";
    leaf oper-status {
      type identityref {
        base ietf-te-types:state-type;
      }
      description "TE tunnel operational state.";
    }
    list lsp {
      key "source destination tunnel-id lsp-id";
      description "List of LSPs associated with the tunnel.";

      leaf source {
        type leafref {
          path "/te/lsps-state/lsp/source";
        }
        description
          "Tunnel sender address extracted from
          SENDER_TEMPLATE  object";
        reference "RFC3209";
      }
      leaf destination {
        type leafref {
          path "/te/lsps-state/lsp/destination";
        }
        description
          "Tunnel endpoint address extracted from
          SESSION object";
        reference "RFC3209";
      }
      leaf tunnel-id {
        type leafref {
          path "/te/lsps-state/lsp/tunnel-id";
        }
        description
          "Tunnel identifier used in the SESSION
          that remains constant over the life
          of the tunnel.";
        reference "RFC3209";
      }
      leaf lsp-id {
        type leafref {
          path "/te/lsps-state/lsp/lsp-id";
        }
        description
          "Identifier used in the SENDER_TEMPLATE
          and the FILTER_SPEC that can be changed
          to allow a sender to share resources with
          itself.";
        reference "RFC3209";
      }
      leaf extended-tunnel-id {
        type leafref {
          path "/te/lsps-state/lsp/extended-tunnel-id";
        }
        description
          "Extended Tunnel ID of the LSP.";
        reference "RFC3209";
      }
      leaf type {
        type leafref {
          path "/te/lsps-state/lsp/type";
        }
        description "LSP type P2P or P2MP";
      }
    }
  }
  /*** End of TE tunnel groupings ***/

  /**
   * LSP related generic groupings
   */

  grouping lsp-properties_state {
    description
      "State parameters relating to LSP";
    leaf oper-status {
      type identityref {
        base ietf-te-types:state-type;
      }
      description "LSP operational state.";
    }

    leaf origin-type {
      type enumeration {
        enum ingress {
          description
            "Origin ingress";
        }
        enum egress {
          description
            "Origin egress";
        }
        enum transit {
          description
            "transit";
        }
      }
      description
        "Origin type of LSP relative to the location
        of the local switch in the path.";
    }
    leaf lsp-resource-status {
      type enumeration {
        enum primary {
          description
            "A primary LSP is a fully established LSP for
             which the resource allocation has been committed
             at the data plane";
        }
        enum secondary {
          description
            "A secondary LSP is an LSP that has been provisioned
             in the control plane only; e.g. resource allocation
             has not been committed at the data plane";
        }
      }
      description "LSP resource allocation type";
      reference "rfc4872, section 4.2.1";
    }

    leaf lsp-protection-status {
      type enumeration {
        enum working {
          description
            "A working LSP must be a primary LSP whilst a protecting
             LSP can be either a primary or a secondary LSP. Also,
             known as protected LSPs when working LSPs are associated
             with protecting LSPs.";
        }
        enum protecting {
          description
            "A secondary LSP is an LSP that has been provisioned
             in the control plane only; e.g. resource allocation
             has not been committed at the data plane";
        }
      }
      description "LSP role type";
      reference "rfc4872, section 4.2.1";
    }

    leaf lsp-operational-status {
      type empty;
      description
        "This bit is set when a protecting LSP is carrying the normal
         traffic after protection switching";
    }

    container lsp-timers {
      when "../origin-type = 'ingress'" {
        description "Applicable to ingress LSPs only";
      }
      description "Ingress LSP timers";
      leaf life-time {
        type uint32;
        units seconds;
        description
          "lsp life time";
      }

      leaf time-to-install {
        type uint32;
        units seconds;
        description
          "lsp installation delay time";
      }

      leaf time-to-die {
        type uint32;
        units seconds;
        description
          "lsp expire delay time";
      }
    }

    container downstream-info {
      description
        "downstream information";

      leaf nhop {
        type inet:ip-address;
        description
          "downstream nexthop.";
      }

      leaf outgoing-interface {
        type if:interface-ref;
        description
          "downstream interface.";
      }

      leaf neighbor {
        type inet:ip-address;
        description
          "downstream neighbor.";
      }

      leaf label {
        type uint32;
        description
          "downstream label.";
      }
    }

    container upstream-info {
      description
        "upstream information";

      leaf nhop { // phop?
        type inet:ip-address;
        description
          "upstream nexthop.";
      }

      leaf incoming-interface {
        type if:interface-ref;
        description
          "upstream interface.";
      }

      leaf neighbor {
        type inet:ip-address;
        description
          "upstream neighbor.";
      }

      leaf label {
        type uint32;
        description
          "upstream label.";
      }
    }
  }
  /*** End of TE LSP groupings ***/

  /**
   * TE global generic groupings
   */

  grouping global-attributes_config {
    description
      "Top level grouping for global config data.";
  }

  grouping global-attributes_state {
    description
      "Top level grouping for global state data.";
    leaf tunnels-counter {
      type uint32;
      description "Tunnels count";
    }
    leaf lsps-counter {
      type uint32;
      description "Tunnels count";
    }
  }

  grouping global-attributes {
    description "TE Global attributes grouping";
    container config {
      description
        "Global configuration parameters";
      uses global-attributes_config;
    }
    container state {
      config false;
      description
        "Global configuration parameters";
      uses global-attributes_config;
      uses global-attributes_state;
    }
  }

  grouping named-admin-groups_config {
    description
      "Global named administrative groups configuration
      grouping";
    list named-admin-groups {
      if-feature ietf-te-types:extended-admin-groups;
      if-feature ietf-te-types:named-extended-admin-groups;
      key "name";
      description
        "List of named TE admin-groups";
      leaf name {
        type string;
        description
          "A string name that uniquely identifies a TE
          interface named admin-group";
      }
      leaf group {
        type ietf-te-types:admin-groups;
        description
          "An SRLG value";
      }
    }
  }

  grouping named-admin-groups {
    description
      "Named admin groups grouping";
    container named-admin-groups {
      description
        "Named admin groups container";
      container config {
        description
          "Configuration parameters for named admin
          groups";
        uses named-admin-groups_config;
      }
      container state {
        config false;
        description
          "State parameters for named admin groups";
        uses named-admin-groups_config;
      }
    }
  }

  grouping named-srlgs_config {
    description
      "Global named SRLGs configuration
      grouping";
    list named-srlgs {
      if-feature ietf-te-types:named-srlg-groups;
      key "name";
      description
        "A list of named SRLG groups";
      leaf name {
        type string;
        description
          "A string name that uniquely identifies a TE
          interface named srlg";
      }
      leaf group {
        type ietf-te-types:srlg;
        description "An SRLG value";
      }
    }
  }

  grouping named-srlgs {
    description
      "Global named SRLGs grouping";
    container named-srlgs {
      description
        "Named SRLGs container";
      container config {
        description
          "Configuration parameters for named SRLG groups";
        uses named-srlgs_config;
      }
      container state {
        config false;
        description
          "State parameters for named SRLG groups";
        uses named-srlgs_config;
      }
    }
  }

  grouping named-explicit-paths_config {
    description
      "Global explicit path configuration
      grouping";
    list named-explicit-paths {
      key "name";
      description
        "A list of explicit paths";
      leaf name {
        type string;
        description
          "A string name that uniquely identifies an
          explicit path";
      }
      list explicit-route-objects {
        key "index";
        description
          "List of explicit route objects";
        leaf index {
          type uint8 {
            range "0..255";
          }
          description
            "Index of this explicit route object";
        }
        uses ietf-te-types:explicit-route-subobject;
        leaf explicit-route-usage {
          type identityref {
            base ietf-te-types:route-usage-type;
          }
          description
            "An IP hop action.";
        }
      }
    }
  }

  grouping named-explicit-paths {
    description
      "Global named explicit path grouping";
    container named-explicit-paths {
      description
        "Nmaed explicit paths container";
      container config {
        description
          "Configuration parameters for named explicit
          paths";
        uses named-explicit-paths_config;
      }
      container state {
        config false;
        description
          "State parameters for named explicit paths";
        uses named-explicit-paths_config;
      }
    }
  }

  grouping named-path-constraints_config {
    description
      "Global named path constraints configuration
      grouping";
    list named-path-constraints {
      if-feature ietf-te-types:named-path-constraints;
      key "name";
      description
        "A list of named path constraints";
      leaf name {
        type string;
        description
          "A string name that uniquely identifies a
          path constraint set";
      }
      uses ietf-te-types:tunnel-path-selection;
    }
  }

  grouping named-path-constraints {
    description
      "Global named path constraints grouping";
    container named-path-constraints {
      description
        "Nmaed explicit paths container";
      container config {
        description
          "Configuration parameters for named explicit
          paths";
        uses named-path-constraints_config;
      }
      container state {
        config false;
        description
          "State parameters for named explicit paths";
        uses named-path-constraints_config;
      }
    }
  }
  /*** End of TE global groupings ***/

  /**
   * TE configurations container
   */
  container te {
    presence "Enable TE feature.";
    description
      "TE global container.";

    /* TE Global Configuration Data */
    container globals {
      description
        "Configuration data for Global System-wide
        Traffic Engineering.";
      uses global-attributes;
      uses named-admin-groups;
      uses named-srlgs;
      uses named-explicit-paths;
      uses named-path-constraints;
    }

    /* TE Interface Configuration Data */
    container interfaces {
      description
        "Configuration data model for TE interfaces.";
      list interface {
        key "interface";
        description "TE interfaces.";
        leaf interface {
          type if:interface-ref;
          description
            "TE interface name.";
        }
        /* TE interface parameters */
        uses te-attributes;
        uses te-admin-groups;
        uses te-srlgs;
        uses te-switching-cap;
        /* TE interface flooding parameters */
        uses ietf-te-types:interface-te-flooding-parameters;
      }
    }

    /* TE Tunnel Configuration Data */
    container tunnels {
      description
        "Configuration, operational, notification and RPC
        data model for TE tunnels.";

      list tunnel {
        key "name type";
        unique "identifier";
        description "TE tunnel.";
        leaf name {
          type string;
          description "TE tunnel name.";
        }
        leaf type {
          type identityref {
            base ietf-te-types:tunnel-type;
          }
          description "TE tunnel type.";
        }
        leaf identifier {
          type uint16;
          description
            "TE tunnel Identifier.";
        }
        uses tunnel-properties;
      }
    }

    /* TE Tunnel Ephemeral State Data (TBD) */
    container tunnels-state {
      config "false";
      description
        "Derived state corresponding to ephemeral tunnels";

      list tunnel {
        key "name type";
        unique "identifier";
        description "TE tunnel.";
        leaf name {
          type string;
          description "TE tunnel name.";
        }
        leaf type {
          type identityref {
            base ietf-te-types:tunnel-type;
          }
          description "TE tunnel type.";
        }
        leaf identifier {
          type uint16;
          description
            "TE tunnel Identifier.";
        }

      }
    }

    /* TE LSPs State Data */
    container lsps-state {
      config "false";
      description "MPLS-TE LSP operational state data.";

      list lsp {
        key
          "source destination tunnel-id lsp-id "+
          "extended-tunnel-id type";
        description
          "List of LSPs associated with the tunnel.";
        leaf source {
          type inet:ip-address;
          description
            "Tunnel sender address extracted from
            SENDER_TEMPLATE  object";
          reference "RFC3209";
        }
        leaf destination {
          type inet:ip-address;
          description
            "Tunnel endpoint address extracted from
            SESSION object";
          reference "RFC3209";
        }
        leaf tunnel-id {
          type uint16;
          description
            "Tunnel identifier used in the SESSION
            that remains constant over the life
            of the tunnel.";
          reference "RFC3209";
        }
        leaf lsp-id {
          type uint16;
          description
            "Identifier used in the SENDER_TEMPLATE
            and the FILTER_SPEC that can be changed
            to allow a sender to share resources with
            itself.";
          reference "RFC3209";
        }
        leaf extended-tunnel-id {
          type inet:ip-address;
          description
            "Extended Tunnel ID of the LSP.";
          reference "RFC3209";
        }
        leaf type {
          type identityref {
            base ietf-te-types:tunnel-type;
          }
          description "The LSP type P2P or P2MP";
        }
        uses lsp-properties_state;
      }
    }
  }

  /* TE Global RPCs/execution Data */
  rpc globals-rpc {
    description
      "Execution data for TE global.";
  }

  /* TE interfaces RPCs/execution Data */
  rpc interfaces-rpc {
    description
      "Execution data for TE interfaces.";
  }

  /* TE Tunnel RPCs/execution Data */
  rpc tunnels-rpc {
    description
      "TE tunnels RPC nodes";
  }

  /* TE Global Notification Data */
  notification globals-notif {
    description
      "Notification messages for Global TE.";
  }

  /* TE Interfaces Notification Data */
  notification interfaces-notif {
    description
      "Notification messages for TE interfaces.";
  }

  /* TE Tunnel Notification Data */
  notification tunnels-notif {
    description
      "Notification messages for TE tunnels.";
  }
}
