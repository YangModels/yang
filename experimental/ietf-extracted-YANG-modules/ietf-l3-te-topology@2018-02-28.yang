module ietf-l3-te-topology {
  yang-version 1.1;
  namespace "urn:ietf:params:xml:ns:yang:ietf-l3-te-topology";
  prefix "l3tet";
  import ietf-network {
    prefix "nw";
  }
  import ietf-network-topology {
    prefix "nt";
  }
  import ietf-l3-unicast-topology {
    prefix "l3t";
  }
  import ietf-te-topology {
    prefix "tet";
  }

  organization "TBD";
  contact "TBD";
  description "L3 TE Topology model";

  revision 2018-02-28 {

    description "Initial revision";
    reference "TBD";
  }

  grouping l3-te-topology-type {
    description
      "Identifies the L3 TE topology type.";
    container l3-te {
      presence "indiates L3 TE Topology";
      description
        "Its presence identifies the L3 TE topology type.";
    }
  }

  augment "/nw:networks/nw:network/nw:network-types/"
    + "l3t:l3-unicast-topology" {
    description
      "Defines the L3 TE topology type.";
    uses l3-te-topology-type;
  }

  augment "/nw:networks/nw:network/l3t:l3-topology-attributes" {
    when "../nw:network-types/l3t:l3-unicast-topology/l3tet:l3-te" {
      description "Augment only for L3 TE topology";
    }
    description "Augment topology configuration";
    uses l3-te-topology-attributes;
  }

  augment "/nw:networks/nw:network/nw:node/l3t:l3-node-attributes" {
    when "../../nw:network-types/l3t:l3-unicast-topology/"
      + "l3tet:l3-te" {
      description "Augment only for L3 TE topology";
    }
    description "Augment node configuration";
    uses l3-te-node-attributes;
  }

  augment "/nw:networks/nw:network/nw:node/nt:termination-point/"
    + "l3t:l3-termination-point-attributes" {
    when "../../../nw:network-types/l3t:l3-unicast-topology/"
      + "l3tet:l3-te" {
      description "Augment only for L3 TE topology";
    }
    description "Augment termination point configuration";
    uses l3-te-tp-attributes;
  }

  augment "/nw:networks/nw:network/nt:link/l3t:l3-link-attributes" {
    when "../../nw:network-types/l3t:l3-unicast-topology/"
      + "l3tet:l3-te" {
      description "Augment only for L3 TE topology";
    }
    description "Augment link configuration";
    uses l3-te-link-attributes;
  }

  grouping l3-te-topology-attributes {
    description "L3 TE topology scope attributes";
    container l3-te-topology-attributes {
      must "/nw:networks/nw:network"
        + "[nw:network-id = current()/network-ref]/nw:network-types/"
        + "tet:te-topology" {
        error-message
          "The referenced network must be a TE topology.";
        description
          "The referenced network must be a TE topology.";
      }
      description "Containing TE topology references";
      uses nw:network-ref;
    } // l3-te-topology-attributes
  } // l3-te-topology-attributes

  grouping l3-te-node-attributes {
    description "L3 TE node scope attributes";
    container l3-te-node-attributes {
      must "/nw:networks/nw:network"
        + "[nw:network-id = current()/network-ref]/nw:network-types/"
        + "tet:te-topology" {
        error-message
          "The referenced network must be a TE topology.";
        description
          "The referenced network must be a TE topology.";
      }
      description "Containing TE node references";
      uses nw:node-ref;
    } // l3-te
  } // l3-te-node-attributes

  grouping l3-te-tp-attributes {
    description "L3 TE termination point scope attributes";
    container l3-te-tp-attributes {
      must "/nw:networks/nw:network"
        + "[nw:network-id = current()/network-ref]/nw:network-types/"
        + "tet:te-topology" {
        error-message
          "The referenced network must be a TE topology.";
        description
          "The referenced network must be a TE topology.";
      }
      description "Containing TE termination point references";
      uses nt:tp-ref;
    } // l3-te
  } // l3-te-tp-attributes

  grouping l3-te-link-attributes {
    description "L3 TE link scope attributes";
    container l3-te-link-attributes {
      must "/nw:networks/nw:network"
        + "[nw:network-id = current()/network-ref]/nw:network-types/"
        + "tet:te-topology" {
        error-message
          "The referenced network must be a TE topology.";
        description
          "The referenced network must be a TE topology.";
      }
      description "Containing TE link references";
      uses nt:link-ref;
    }
  } // l3-te-link-attributes
}
